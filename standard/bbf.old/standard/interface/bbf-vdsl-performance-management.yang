submodule bbf-vdsl-performance-management {
  yang-version 1.1;

  belongs-to bbf-vdsl {
    prefix bbf-vdsl;
  }

  import ietf-interfaces {
    prefix if;
  }

  import bbf-fastdsl {
    prefix bbf-fastdsl;
  }

  include bbf-vdsl-xtu-line-performance-body;

  include bbf-vdsl-xtu-channel-performance-body;

  include bbf-vdsl-line;

  include bbf-vdsl-base-body;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for
     managing performance statistics for VDSL interfaces.

     Copyright (c) 2016, 2017 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  feature performance-24hr {
    description
      "Indicates that collection of 24 hour performance intervals
       is supported";
  }

  // 7 Object model for xDSL Performance Management

  // 7.1 xTU Line Performance

  augment '/if:interfaces-state/if:interface/bbf-fastdsl:line/bbf-'
        + 'vdsl:line' {
    description
      "7.1 xDSL Transmission Unit (xTU) Line Performance config.";

    container performance {
      config false;
      description
        "Performance parameters";

      container intervals-15min {
        description
          "15 minute interval line performance counters.";

        container current {
          description
            "Contains the counts that are currently accumulating.";

          container xtu-c {
            description
              "xDSL Transmission Unit - Central office";

            uses xtu-c-line-performance;
          }

          container xtu-r {
            description
              "xDSL Transmission Unit - Remote side";

            uses xtu-r-line-performance;
          }
        }

        uses performance-history-15min-parameters;

        list history {
          key "interval-number";
          max-elements 96;
          ordered-by system;
          description
            "A history of 15 minute intervals.";

          leaf interval-number {
            type performance-15min-history-interval;
            description
              "The number of the interval relative to the current
               interval.";
          }

          container xtu-c {
            description
              "xDSL Transmission Unit - Central office";

            uses line-time-stamp;
            uses xtu-c-line-performance;
          }

          container xtu-r {
            description
              "xDSL Transmission Unit - Remote side";

            uses line-time-stamp;
            uses xtu-r-line-performance;
          }
        }
      }

      container intervals-24hr {
        if-feature "performance-24hr";
        description
          "24 hour interval line performance counters.";

        container current {
          description
            "Contains the counts that are currently accumulating.";

          container xtu-c {
            description
              "xDSL Transmission Unit - Central office";

            uses xtu-c-line-performance;
          }

          container xtu-r {
            description
              "xDSL Transmission Unit - Remote side";

            uses xtu-r-line-performance;
          }
        }

        uses performance-history-24hr-parameters;

        list history {
          key "interval-number";
          max-elements 96;
          ordered-by system;
          description
            "A history of 24 hour intervals.";

          leaf interval-number {
            type performance-24hr-history-interval;
            description
              "The number of the interval relative to the current
               interval.";
          }

          container xtu-c {
            description
              "xDSL Transmission Unit - Central office";

            uses line-time-stamp;
            uses xtu-c-line-performance;
          }

          container xtu-r {
            description
              "xDSL Transmission Unit - Remote side";

            uses line-time-stamp;
            uses xtu-r-line-performance;
          }
        }
      }
    }
  }

  // 7.2 xTU Channel Performance

  augment '/if:interfaces-state/if:interface/bbf-fastdsl:line/bbf-'
        + 'vdsl:line/bbf-vdsl:channel' {
    description
      "7.2 xDSL Transmission Unit Channel Performance config.";

    container performance {
      config false;
      description
        "Performance parameters";

      container intervals-15min {
        description
          "15 minute interval performance history";

        container current {
          description
            "Contains the counts that are currently accumulating.";

          container xtu-c {
            description
              "xDSL Transmission Unit - Central office";
            uses xtu-channel-performance-c;
          }

          container xtu-r {
            description
              "xDSL Transmission Unit - Remote side";
            uses xtu-channel-performance-cfe;
          }
        }

        uses performance-history-15min-parameters;

        list history {
          key "interval-number";
          max-elements 96;
          ordered-by system;
          description
            "A history of 15 minute intervals.";

          leaf interval-number {
            type performance-15min-history-interval;
            description
              "The number of the interval relative to the current
               interval.";
          }

          container xtu-c {
            description
              "xDSL Transmission Unit - Central office";
            uses xtu-channel-time-stamp;
            uses xtu-channel-performance-c;
          }

          container xtu-r {
            description
              "xDSL Transmission Unit - Remote side";
            uses xtu-channel-time-stamp;
            uses xtu-channel-performance-cfe;
          }
        }
      }

      container intervals-24hr {
        if-feature "performance-24hr";
        description
          "24 hour interval performance history";

        container current {
          description
            "Contains the counts that are currently accumulating.";

          container xtu-c {
            description
              "xDSL Transmission Unit - Central office";
            uses xtu-channel-performance-c;
          }

          container xtu-r {
            description
              "xDSL Transmission Unit - Remote side";
            uses xtu-channel-performance-cfe;
          }
        }

        uses performance-history-24hr-parameters;

        list history {
          key "interval-number";
          max-elements 96;
          ordered-by system;
          description
            "A history of 24 hour intervals.";

          leaf interval-number {
            type performance-24hr-history-interval;
            description
              "The number of the interval relative to the current
               interval.";
          }

          container xtu-c {
            description
              "xDSL Transmission Unit - Central office";
            uses xtu-channel-time-stamp;
            uses xtu-channel-performance-c;
          }

          container xtu-r {
            description
              "xDSL Transmission Unit - Remote side";
            uses xtu-channel-time-stamp;
            uses xtu-channel-performance-cfe;
          }
        }
      }
    }
  }
}
