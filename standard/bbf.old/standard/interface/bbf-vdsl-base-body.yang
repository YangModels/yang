submodule bbf-vdsl-base-body {
  yang-version 1.1;

  belongs-to bbf-vdsl {
    prefix bbf-vdsl;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for 
     managing common aspects of VDSL used among other submodules.

     Copyright (c) 2016, 2017 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef sub-carrier-index {
    type uint16 {
      range "0..8191";
    }
    description
      "Identifies a sub-carrier.";
  }

  typedef vce-port-index {
    type union {
      type enumeration {
        enum "undefined" {
          description
            "The value of the VCE port index is undefined.";
        }
      }
      type uint16 {
        range "1..65535";
      }
    }
    description
      "For the line in a vectored group, the VCE port index is the 
       physical index that uniquely identifies the VCE port to which 
       the line is connected. It is an integer from 1 to the maximum 
       number of lines supported by the VCE.";
  }


  typedef line-identifier {
    type string {
      length "1..64";
    }
    description
      "identifies a line";
  }

  // used for identifiers that aren't formally called out in TR-252
  typedef profile-identifier {
    type string {
      length "1..64";
    }
    description
      "used for identifing profiles";
  }

  typedef performance-15min-history-interval {
    type uint8 {
      range "1..96";
    }
    description
      "Defines the range of 15 minutes intervals and defines
       the position of the interval relative to the current interval
       where 1 is the most recent interval.";
  }

  typedef performance-24hr-history-interval {
    type uint8 {
      range "1..28";
    }
    description
      "Defines the range of 24 hour intervals and defines
       the position of the interval relative to the current interval
       where 1 is the most recent interval.";
  }

  typedef performance-15min-interval {
    type uint8 {
      range "0..96";
    }
    description
      "Defines the range of 15 minute intervals.";
  }

  typedef performance-24hr-interval {
    type uint8 {
      range "0..28";
    }
    description
      "Defines the range of 24 hour intervals.";
  }

  typedef xts-descriptor {
    type enumeration {
      enum "xts1" {
        description
          "Regional standards. It is recommended that
           bit1 be used for ATIS-0600413";
      }
      enum "xts2" {
        description
          "Regional standards. It is recommended that
           bit2 be used for Annex C of ETSI TS 101 388";
      }
      enum "xts3" {
        description
          "G.992.1 operation over POTS non-overlapped spectrum
           (Annex A of [ITU-T G.992.1])";
      }
      enum "xts4" {
        description
          "G.992.1 operation over POTS overlapped spectrum
           (Annex A of [ITU-T G.992.1])";
      }
      enum "xts5" {
        description
          "G.992.1 operation over ISDN non-overlapped spectrum
           (Annex B of [ITU-T G.992.1])";
      }
      enum "xts6" {
        description
          "G.992.1 operation over ISDN overlapped spectrum
           (Annex B of [ITU-T G.992.1])";
      }
      enum "xts7" {
        description
          "G.992.1 operation in conjunction with TCM ISDN
           non-overlapped spectrum (Annex C of [ITU T G.992.1])";
      }
      enum "xts8" {
        description
          "G.992.1 operation in conjunction with TCM ISDN
           overlapped spectrum (Annex C of [ITU T G.992.1])";
      }
      enum "xts9" {
        description
          "G.992.2 operation over POTS non-overlapped spectrum
           (Annex A of [ITU-T G.992.2])";
      }
      enum "xts10" {
        description
          "G.992.2 operation over POTS overlapped spectrum
           (Annex B of [ITU-T G.992.2])";
      }
      enum "xts11" {
        description
          "G.992.2 operation in conjunction with TCM ISDN
           non-overlapped spectrum (Annex C of [ITU T G.992.2])";
      }
      enum "xts12" {
        description
          "G.992.2 operation in conjunction with TCM ISDN
           overlapped spectrum (Annex C of [ITU T G.992.2])";
      }
      // enum xts13; // Reserved
      // enum xts14; // Reserved
      // enum xts15; // Reserved
      // enum xts16; // Reserved
      // enum xts17; // Reserved
      // enum xts18; // Reserved
      enum "xts19" {
        description
          "G.992.3 operation over POTS non-overlapped spectrum
           (Annex A of [ITU-T G.992.3]).";
      }
      enum "xts20" {
        description
          "G.992.3 operation over POTS overlapped spectrum
           (Annex A of [ITU-T G.992.3])";
      }
      enum "xts21" {
        description
          "G.992.3 operation over ISDN non-overlapped spectrum
           (Annex B of [ITU-T G.992.3])";
      }
      enum "xts22" {
        description
          "G.992.3 operation over ISDN overlapped spectrum
           (Annex B of [ITU-T G.992.3])";
      }
      enum "xts23" {
        description
          "G.992.3 operation in conjunction with TCM ISDN
           non-overlapped spectrum (Annex C of [ITU T G.992.3])";
      }
      enum "xts24" {
        description
          "G.992.3 operation in conjunction with TCM ISDN
           overlapped spectrum (Annex C of [ITU T G.992.3])";
      }
      enum "xts25" {
        description
          "G.992.4 operation over POTS non-overlapped spectrum
           (Annex A of [ITU-T G.992.4])";
      }
      enum "xts26" {
        description
          "G.992.4 operation over POTS overlapped spectrum
           (Annex A of [ITU-T G.992.4])";
      }
      // enum xts27; // Reserved
      // enum xts28; // Reserved
      enum "xts29" {
        description
          "G.992.3 all digital mode operation with non-overlapped
           spectrum (Annex I of [ITU T G.992.3])";
      }
      enum "xts30" {
        description
          "G.992.3 all digital mode operation with overlapped
           spectrum (Annex I of [ITU T G.992.3])";
      }
      enum "xts31" {
        description
          "G.992.3 all digital mode operation with non-overlapped
           spectrum (Annex J of [ITU T G.992.3])";
      }
      enum "xts32" {
        description
          "G.992.3 all digital mode operation with overlapped
           spectrum (Annex J of [ITU T G.992.3])";
      }
      enum "xts33" {
        description
          "G.992.4 all digital mode operation with non-overlapped
           spectrum (Annex I of [ITU T G.992.4])";
      }
      enum "xts34" {
        description
          "G.992.4 all digital mode operation with overlapped
           spectrum (Annex I of [ITU T G.992.4])";
      }
      enum "xts35" {
        description
          "G.992.3 reach extended operation over POTS, Mode 1
           (non-overlapped, wide upstream)
           (Annex L of [ITU-T G.992.3])";
      }
      enum "xts36" {
        description
          "G.992.3 reach extended operation over POTS, Mode 2
           (non-overlapped, narrow upstream)
           (Annex L of [ITU-T G.992.3])";
      }
      enum "xts37" {
        description
          "G.992.3 reach extended operation over POTS, Mode 3
           (overlapped, wide upstream)
           (Annex L of [ITU-T G.992.3])";
      }
      enum "xts38" {
        description
          "G.992.3 reach extended operation over POTS, Mode 4
           (overlapped, narrow upstream)
           (Annex L of [ITU-T G.992.3])";
      }
      enum "xts39" {
        description
          "G.992.3 extended upstream operation over POTS
           non-overlapped spectrum (Annex M of [ITU-T G.992.3])";
      }
      enum "xts40" {
        description
          "G.992.3 extended upstream operation over POTS
           overlapped spectrum (Annex M of [ITU T G.992.3])";
      }
      enum "xts41" {
        description
          "G.992.5 operation over POTS non-overlapped spectrum
           (Annex A of [ITU-T G.992.5])";
      }
      enum "xts42" {
        description
          "G.992.5 operation over POTS overlapped spectrum
           (Annex A of [ITU-T G.992.5])";
      }
      enum "xts43" {
        description
          "G.992.5 operation over ISDN non-overlapped spectrum
           (Annex B of [ITU-T G.992.5])";
      }
      enum "xts44" {
        description
          "G.992.5 operation over ISDN overlapped spectrum
           (Annex B of [ITU-T G.992.5])";
      }
      enum "xts45" {
        description
          "G.992.5 operation in conjunction with TCM ISDN
           non-overlapped spectrum (Annex C of [ITU T G.992.5])";
      }
      enum "xts46" {
        description
          "G.992.5 operation in conjunction with TCM ISDN
           overlapped spectrum (Annex C of [ITU T G.992.5])";
      }
      enum "xts47" {
        description
          "G.992.5 all digital mode operation with non-overlapped
           spectrum (Annex I of [ITU T G.992.5])";
      }
      enum "xts48" {
        description
          "G.992.5 all digital mode operation with overlapped
           spectrum (Annex I of [ITU T G.992.5])";
      }
      enum "xts49" {
        description
          "G.992.5 all digital mode operation with non-overlapped
           spectrum (Annex J of [ITU T G.992.5])";
      }
      enum "xts50" {
        description
          "G.992.5 all digital mode operation with overlapped
           spectrum (Annex J of [ITU T G.992.5])";
      }
      enum "xts51" {
        description
          "G.992.5 extended upstream operation over POTS
           non-overlapped spectrum (Annex M of [ITU-T G.992.5])";
      }
      enum "xts52" {
        description
          "G.992.5 extended upstream operation over POTS
           overlapped spectrum (Annex M of [ITU T G.992.5])";
      }
      // enum xts53; // Reserved
      // enum xts54; // Reserved
      // enum xts55; // Reserved
      // enum xts56; // Reserved
      enum "xts57" {
        description
          "G.993.2 Region A (North America)
           (Annex A of [ITU-T G.993.2])";
      }
      enum "xts58" {
        description
          "G.993.2 Region B (Europe)
           (Annex B of [ITU-T G.993.2])";
      }
      enum "xts59" {
        description
          "G.993.2 Region C (Japan)
           (Annex C of [ITU-T G.993.2])";
      }
      // enum xts60; // Reserved
      // enum xts61; // Reserved
      // enum xts62; // Reserved
      // enum xts63; // Reserved
      // enum xts64; // Reserved
    }

    description
      "This is used in *-body submodules to define transmission
       system capabilities (XTS).
       This defines the transmission system types to be
       allowed by the near-end xTU on this line.";
    reference
      "ITU-T G.997.1 clause 7.3.1.1.1 xTU transmission system
       enabling (XTSE)";
  } // end typedef xts-descriptor


  typedef us0mask-descriptor {
    type union {
      type enumeration {
        enum "all" {
          description
            "Select all US0 masks.";
        }
      }
      type bits {
        bit o1b1 {
          position 0;
          description
            "Octet 1 bit 1, EU-32";
        }
        bit o1b2 {
          position 1;
          description
            "Octet 1 bit 2, EU-36";
        }
        bit o1b3 {
          position 2;
          description
            "Octet 1 bit 3, EU-40";
        }
        bit o1b4 {
          position 3;
          description
            "Octet 1 bit 4, EU-44";
        }
        bit o1b5 {
          position 4;
          description
            "Octet 1 bit 5, EU-48";
        }
        bit o1b6 {
          position 5;
          description
            "Octet 1 bit 6, EU-52";
        }
        bit o1b7 {
          position 6;
          description
            "Octet 1 bit 7, EU-56";
        }
        bit o1b8 {
          position 7;
          description
            "Octet 1 bit 8, EU-60";
        }
        bit o2b1 {
          position 8;
          description
            "Octet 2 bit 1, EU-64";
        }
        bit o2b2 {
          position 9;
          description
            "Octet 2 bit 2, EU-128";
        }
        bit o3b1 {
          position 16;
          description
            "Octet 3 bit 1, ADLU-32";
        }
        bit o3b2 {
          position 17;
          description
            "Octet 3 bit 2, ADLU-36";
        }
        bit o3b3 {
          position 18;
          description
            "Octet 3 bit 3, ADLU-40";
        }
        bit o3b4 {
          position 19;
          description
            "Octet 3 bit 4, ADLU-44";
        }
        bit o3b5 {
          position 20;
          description
            "Octet 3 bit 5, ADLU-48";
        }
        bit o3b6 {
          position 21;
          description
            "Octet 3 bit 6, ADLU-52";
        }
        bit o3b7 {
          position 22;
          description
            "Octet 3 bit 7, ADLU-56";
        }
        bit o3b8 {
          position 23;
          description
            "Octet 3 bit 8, ADLU-60";
        }
        bit o4b1 {
          position 24;
          description
            "Octet 4 bit 1, ADLU-64";
        }
        bit o4b2 {
          position 25;
          description
            "Octet 4 bit 2, ADLU-128";
        }
      }
    }
    description
      "Defines us0mask so it can be used for both configuration in
       line-spectrum-profile and status in line-xtu-status.
       This contains the US0 PSD masks for
       the near-end xTU on the line. This parameter is only
       defined for Annex A of [ITU-T G.993.2]. It is
       represented as a bitmap (0 or false if not allowed, and
       1 or true if allowed) with the definitions of Table 7-8
       of [ITU-T G.997.1]. The default is all 1s, corresponding to
       all US0 PSD masks allowed.";
    reference
      "ITU-T G.997.1 clause 7.3.1.2.18 VDSL2 US0 PSD masks
       (US0MASK)";
  } // end typedef us0mask-descriptor

  typedef limitmask-descriptor {

    type bits {
      bit o1b1 {
        position 0;
        description
          "Octet 1, bit 1; Profile class 8.";
      }
      bit o1b2 {
        position 1;
        description
          "Octet 1, bit 2; Profile class 8.";
      }
      bit o1b3 {
        position 2;
        description
          "Octet 1, bit 3; Profile class 8.";
      }
      bit o1b4 {
        position 3;
        description
          "Octet 1, bit 4; Profile class 8.";
      }
      bit o2b1 {
        position 8;
        description
          "Octet 2, bit 1; Profile class 8.";
      }
      bit o2b2 {
        position 9;
        description
          "Octet 2, bit 2; Profile class 8.";
      }
      bit o3b1 {
        position 16;
        description
          "Octet 3, bit 1; Profile class 12.";
      }
      bit o3b2 {
        position 17;
        description
          "Octet 3, bit 2; Profile class 12.";
      }
      bit o3b3 {
        position 18;
        description
          "Octet 3, bit 3; Profile class 12.";
      }
      bit o3b4 {
        position 19;
        description
          "Octet 3, bit 4; Profile class 12.";
      }
      bit o4b1 {
        position 24;
        description
          "Octet 4, bit 1; Profile class 12.";
      }
      bit o4b2 {
        position 25;
        description
          "Octet 4, bit 2; Profile class 12.";
      }
      bit o5b1 {
        position 32;
        description
          "Octet 3, bit 1; Profile class 17.";
      }
      bit o5b2 {
        position 33;
        description
          "Octet 3, bit 2; Profile class 17.";
      }
      bit o5b3 {
        position 34;
        description
          "Octet 3, bit 3; Profile class 17.";
      }
      bit o5b4 {
        position 35;
        description
          "Octet 3, bit 4; Profile class 17.";
      }
      bit o6b1 {
        position 40;
        description
          "Octet 4, bit 1; Profile class 17.";
      }
      bit o6b2 {
        position 41;
        description
          "Octet 4, bit 2; Profile class 17.";
      }
      bit o7b1 {
        position 48;
        description
          "Octet 7, bit 1; Profile class 30.";
      }
      bit o7b2 {
        position 49;
        description
          "Octet 7, bit 2; Profile class 30.";
      }
      bit o7b3 {
        position 50;
        description
          "Octet 7, bit 3; Profile class 30.";
      }
      bit o8b1 {
        position 56;
        description
          "Octet 8, bit 1; Profile class 30.";
      }
      bit o8b2 {
        position 57;
        description
          "Octet 8, bit 2; Profile class 30.";
      }
      bit o9b1 {
        position 64;
        description
          "Octet 9, bit 1; Profile class 35.";
      }
      bit o9b2 {
        position 65;
        description
          "Octet 9, bit 2; Profile class 35.";
      }
      bit o9b3 {
        position 66;
        description
          "Octet 9, bit 3; Profile class 35.";
      }
    }
    description
      "This contains the G.993.2 limit PSD masks of the selected
       PSD mask class, enabled by the near-end xTU on this line for 
       each class of profiles.

       See Table 7-7 of ITU-T G.997.1 for the definition of each 
       bit.";
    reference
      "ITU-T G.997.1 clause 7.3.1.2.16 VDSL2 limit PSD masks
       and band plans enabling (LIMITMASK)";
  }

  typedef classmask-descriptor {
    type enumeration {
      enum "none" {
        description
          "No class mask selected.";
      }
      enum "class1" {
        description
          "Classmask 1 of Table 7-7 of ITU-T G.997.1.";
      }
      enum "class2" {
        description
          "Classmask 2 of Table 7-7 of ITU-T G.997.1.";
      }
      enum "class3" {
        description
          "Classmask 3 of Table 7-7 of ITU-T G.997.1.";
      }
      enum "class5" {
        description
          "Classmask 5 of Table 7-7 of ITU-T G.997.1.";
      }
      enum "class6" {
        description
          "Classmask 6 of Table 7-7 of ITU-T G.997.1.";
      }
      enum "class8" {
        description
          "Classmask 8 of Table 7-7 of ITU-T G.997.1.";
      }
      enum "class9" {
        description
          "Classmask 9 of Table 7-7 of ITU-T G.997.1.";
      }
    }
    description
      "One CLASSMASK parameter is defined per the G.993.2 Annex
       enabled in the XTSE. It selects a single PSD mask class
       per the G.993.2 Annex that is activated at the VTU-O.
       The coding is as indicated in Table 7-6 of [ITU-T G.997.1].";
    reference
      "ITU-T G.997.1 clause 7.3.1.2.15 VDSL2 PSD mask class
       selection (CLASSMASK)";
  }

  typedef profiles {
    type bits {
      bit profile-8a {
        position 1;
        description
          "G.993.2 profile 8a.";
      }
      bit profile-8b {
        position 2;
        description
          "G.993.2 profile 8b.";
      }
      bit profile-8c {
        position 3;
        description
          "G.993.2 profile 8c.";
      }
      bit profile-8d {
        position 4;
        description
          "G.993.2 profile 8d.";
      }
      bit profile-12a {
        position 5;
        description
          "G.993.2 profile 12a.";
      }
      bit profile-12b {
        position 6;
        description
          "G.993.2 profile 12b.";
      }
      bit profile-17a {
        position 7;
        description
          "G.993.2 profile 17a.";
      }
      bit profile-30a {
        position 8;
        description
          "G.993.2 profile 30a.";
      }
      bit profile-35b {
        position 9;
        description
          "G.993.2 profile 35b.";
      }
    }
    description
      "Delineates the VDSL2 profiles.";
    reference
      "ITU-T G.993.2.";
  }

  grouping psdmask-descriptor {
    list psdmask {
      must "count(../psdmask) != 1" {
        description
          "The PSD mask list must either be empty or have at least
           2 elements.";
      }
      key "sub-carrier";

      leaf sub-carrier {
        type sub-carrier-index;
        description
          "The sub-carrier index";
      }

      leaf psd-level {
        type uint8 {
          range "0..190";
        }
        units "-0.5 dBm/Hz";
        mandatory true;
        description
          "PSD level. Valid values: 0..190 (0 to -95 dBm/Hz)";
      }
      description
        "This list defines a PSD level per sub-carrier. The default is
         an empty list indicating no PSD mask.";
    }
    description
      "This grouping is used in other *-body submodules to define
       a power spectral density (PSD) or PSD mask";
  }

  typedef band {
    type enumeration {
      enum "upstream" {
        description
          "Transmission from the xTU-R to the xTU-C (refers to the 
           single upstream band for ADSL/ADSL2/ADSL2plus or to the 
           whole upstream traffic for VDSL2).";
      }
      enum "downstream" {
        description
          "Transmission from the xTU-C to the xTU-R (refers to the 
           single downstream band for ADSL/ADSL2/ADSL2plus or to the
           whole downstream traffic for VDSL2).";
      }
      enum "us0" {
        description
          "Upstream band 0";
      }
      enum "us1" {
        description
          "Upstream band 1";
      }
      enum "us2" {
        description
          "Upstream band 2";
      }
      enum "us3" {
        description
          "Upstream band 3";
      }
      enum "us4" {
        description
          "Upstream band 4";
      }
      enum "ds1" {
        description
          "Downstream band 1";
      }
      enum "ds2" {
        description
          "Downstream band 2";
      }
      enum "ds3" {
        description
          "Downstream band 3";
      }
      enum "ds4" {
        description
          "Downstream band 4";
      }
    }
    description
      "Represents the available upstream and downstream bands";
  }

  feature virtual-noise {
    description
      "Indicates support for virtual noise.";
    reference
      "Broadband Forum TR-252i3 - 5.7 DSL Quality Management 
       related profiles; Virtual Noise Profile.";
  }

  feature sos {
    description
      "Indicates support for SOS.";
    reference
      "Broadband Forum TR-252i3 - 5.7 DSL Quality Management 
       related profiles; SOS Profile.";
  }

  feature impulse-noise-monitoring {
    description
      "Indicates support for impulse noise monitoring.";
    reference
      "Broadband Forum TR-252i3 - 5.7 DSL Quality Management 
       related profiles; Impulse Noise Monitoring Profile.";
  }

  feature re-initialization-policy {
    description
      "Indicates support for re-initialization policy.";
    reference
      "Broadband Forum TR-252i3 - 5.7 DSL Quality Management 
       related profiles; Re-initialization Policy Profile.";
  }

  feature vectoring {
    description
      "Indicates support for vectoring.";
    reference
      "Broadband Forum TR-252i3 - 5.7 DSL Quality Management 
       related profiles; Vectoring Profile.";
  }

  feature data-gathering {
    description
      "Indicates support for data gathering.";
    reference
      "Broadband Forum TR-252i3 - 5.7 DSL Quality Management 
       related profiles; Data Gathering Profile.";
  }
}
