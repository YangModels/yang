submodule bbf-fast-noise-margin-profile-body {
  yang-version 1.1;
  belongs-to bbf-fast {
    prefix bbf-fast;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for
     managing noise margin profiles.

     Copyright (c) 2016, 2017 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping noise-margin-parameters {
    description
      "Noise margin configuration parameters applicable to both
       upstream and downstream.";
    reference
      "ITU-T G.997.2 clause 7.1.3.";

    leaf target-noise-margin {
      type uint16 {
        range "0..310" {
          description
            "Defines a range equivalent to 0 to 31 dB.";
        }
      }
      units "0.1 dB";
      must
        ". <= ../../seamless-rate-adaptation/
                                  upshift-noise-margin" {
        description
          "The target noise margin must be less than or equal to
           the upshift noise margin";
      }
      default "60";
      description
        "Defines the target noise margin for the Channel
         Initialization Policy.";
      reference
        "ITU-T G.997.2 clause 7.1.3.1 (TARSNRMds) and clause 7.1.3.2
         (TARSNRMus); ITU-T G.9701 clause 12.3.7.";
    }

    leaf minimum-noise-margin {
      type uint16 {
        range "0..310" {
          description
            "Defines a range equivalent to 0 to 31 dB.";
        }
      }
      units "0.1 dB";
      must
        ". <= ../../seamless-rate-adaptation/
                                  downshift-noise-margin" {
        description
          "The minimum noise margin must be less than or equal to
           the downshift noise margin";
      }
      default "0";
      description
        "Defines the minimum noise margin the FTU receiver shall
         tolerate. If the noise margin (SNRM) falls below this
         level, the FTU receiver requests the FTU transmitter to
         increase the FTU transmit power. If an increase to FTU
         transmit power is not possible, a loss-of-margin(lom) defect
         occurs. Upon persistency of the lom defect, the FTU receiver
         triggers a re-initialization (see clause 12.1.4.2/G.9701).";
      reference
        "ITU-T G.997.2 clause 7.1.3.4 (MINSNRMds) and clause 7.1.3.5
         (MINSNRMus); ITU-T G.9701 clause 12.3.4.2.1.";
    }
  }

  grouping noise-margin-upstream-parameters {
    description
      "Noise margin configuration parameters applicable in the
       upstream direction.";
    reference
      "ITU-T G.997.2 clause 7.1.3.";

    leaf maximum-noise-margin {
      type uint16 {
        range "0..310 | 511" {
          description
            "Defines a range equivalent to 0 to 31 dB.
             Special value 511: No maximum bound.";
        }
      }
      units "0.1 dB";
      must
        ". >= ../../seamless-rate-adaptation/
                                  upshift-noise-margin" {
        description
          "The maximum noise margin must be greater than or equal to
           the upshift noise margin";
      }
      default "511";
      description
        "Defines the maximum noise margin used in the Channel
         Initialization Policy.
         A special value, 511, indicates there is no maximum bound
         for the noise margin (i.e., the maximum noise margin is
         infinite).";
      reference
        "ITU-T G.997.2 clause 7.1.3.3 MAXSNRMus); ITU-T G.9701
         clause 12.3.7.";
    }
  }

  grouping seamless-rate-adaptation-parameters {
    description
      "Seamless Rate Adaptation (SRA) configuration parameters
       applicable to both upstream and downstream.";
    reference
      "ITU-T G.997.2 clause 7.1.4.";

    leaf upshift-noise-margin {
      type uint16 {
        range "0..310" {
          description
            "Defines a range equivalent to 0 to 31 dB.";
        }
      }
      units "0.1 dB";
      default "70";
      description
        "If the noise margin (SNRM) is above the upshift noise
         margin and stays above that for more than the time specified
         by the minimum upshift rate adaptation interval (SRA-UTIME),
         the transmitting FTU autonomously attempts to increase the
         net data rate (NDR).";
      reference
        "ITU-T G.997.2 clause 7.1.4.1 (SRA-USNRMds) and clause
         7.1.4.2 (SRA-USNRMus); ITU-T G.9701 clause 12.3.4.2.1.";
    }

    leaf upshift-noise-margin-in-l2.1 {
      type uint16 {
        range "0..310" {
          description
            "Defines a range equivalent to 0 to 31 dB.";
        }
      }
      units "0.1 dB";
      default "70";
      description
        "If the noise margin in the L2.1N and L2.1B link states 
         (L2.1-SNRM) is above the upshift noise margin and stays 
         above that for more than the time specified by the minimum 
         upshift rate adaptation interval (SRA-UTIME), the FTU-R 
         autonomously attempts to increase the net data rate in the 
         L2.1 link state.";
      reference
        "ITU-T G.997.2 clause 7.1.10.4 (L2.1-SRA-USNRMds) and clause
         7.1.10.5 (L2.1-SRA-USNRMus); ITU-T G.9701 clause 
         13.4.1.4.7.";
    }

    leaf minimum-time-interval-upshift-sra {
      type uint16 {
        range "0..16383";
      }
      units "1 second";
      default "8";
      description
        "Defines the interval of time the noise margin (SNRM) should
         stay above the upshift noise margin (SRA-USNRM) before the
         transmitting FTU autonomously attempts to increase the net
         data rate (NDR).";
      reference
        "ITU-T G.997.2 clause 7.1.4.3 (SRA-UTIMEds) and clause
         7.1.4.4 (SRA-UTIMEus); ITU-T G.9701 clause 12.3.4.2.1.";
    }

    leaf downshift-noise-margin {
      type uint16 {
        range "0..310" {
          description
            "Defines a range equivalent to 0 to 31 dB.";
        }
      }
      units "0.1 dB";
      must ". <= ../../noise-margin/target-noise-margin" {
        description
          "The downshift noise margin must be less than or equal to
           the target noise margin";
      }
      default "50";
      description
        "If the noise margin (SNRM) is below the downshift noise
         margin and stays below that for more than the time specified
         by the minimum downshift rate adaptation interval
         (SRA-DTIME), the transmitting FTU autonomously attempts to
         decrease the net data rate (NDR).";
      reference
        "ITU-T G.997.2 clause 7.1.4.5 (SRA-DSNRMds) and clause
         7.1.4.6 (SRA-DSNRMus); ITU-T G.9701 clause 12.3.4.2.1.";
    }

    leaf downshift-noise-margin-in-l2.1 {
      type uint16 {
        range "0..310" {
          description
            "Defines a range equivalent to 0 to 31 dB.";
        }
      }
      units "0.1 dB";
      default "50";
      description
        "If the noise margin in the L2.1N and L2.1B link states 
         (L2.1-SNRM) is below the downshift noise margin and stays 
         below that for more than the time specified by the minimum 
         downshift rate adaptation interval (SRA-DTIME), the FTU-R 
         autonomously attempts to decrease the net data rate in the 
         L2.1 link state.";
      reference
        "ITU-T G.997.2 clause 7.1.10.6 (L2.1-SRA-DSNRMds) and clause
         7.1.10.7 (L2.1-SRA-DSNRMus); ITU-T G.9701 clause 
         13.4.1.4.7.";
    }

    leaf minimum-time-interval-downshift-sra {
      type uint16 {
        range "0..16383";
      }
      units "1 second";
      default "2";
      description
        "Defines the interval of time the noise margin (SNRM) should
         stay below the downshift noise margin (SRA-DSNRM) before the
         transmitting FTU autonomously attempts to decrease the net
         data rate (NDR).";
      reference
        "ITU-T G.997.2 clause 7.1.4.7 (SRA-DTIMEds) and clause
         7.1.4.8 (SRA-DTIMEus); ITU-T G.9701 clause 12.3.4.2.1.";
    }
  }


  grouping robust-management-channel-parameters {
    description
      "Robust Management Channel (RMC) configuration parameters
       applicable to both upstream and downstream.";
    reference
      "ITU-T G.997.2 clause 7.1.6.";

    leaf target-noise-margin {
      type uint16 {
        range "0..310" {
          description
            "Defines a range equivalent to 0 to 31 dB.";
        }
      }
      units "0.1 dB";
      default "60";
      description
        "Defines the RMC noise margin (SNRMRMC) that the FTU
         receiver shall achieve, relative to the BER requirement, or
         better, to successfully complete initialization.";
      reference
        "ITU-T G.997.2 clause 7.1.6.1 (TARSNRM-RMCds) and clause
         7.1.6.2 (TARSNRM-RMCus); ITU-T G.9701 clause 12.3.3.2.1.";
    }

    leaf minimum-noise-margin {
      type uint16 {
        range "0..310" {
          description
            "Defines a range equivalent to 0 to 31 dB.";
        }
      }
      units "0.1 dB";
      must ". <= ../target-noise-margin" {
        description
          "The minimum noise margin must be less than or equal to
           the target noise margin";
      }
      default "0";
      description
        "Defines the minimum noise margin the FTU receiver tolerates
         for the RMC. If the RMC noise margin (SNRM-RMC) falls below
         this level, the FTU receiver initiates the RPA procedure.";
      reference
        "ITU-T G.997.2 clause 7.1.6.3 (MINSNRM-RMCds) and clause
         7.1.6.4 (MINSNRM-RMCus); ITU-T G.9701 clause 13.2.1.3.";
    }

    leaf maximum-bit-loading {
      type uint8 {
        range "2..6" {
          description
            "Defines a range equivalent to 2 to 6 bits.";
        }
      }
      default "6";
      description
        "Defines the maximum allowed bit-loading for the RMC
         sub-carriers.";
      reference
        "ITU-T G.997.2 clause 7.1.6.5 (MAXBL-RMCds) and clause
         7.1.6.6 (MAXBL-RMCus); ITU-T G.9701 clause 12.3.3.2.1.";
    }
  }

  grouping noise-margin-low-power-parameters {
    description
      "Noise margin parameters that are specific to low power modes";

    leaf target-noise-margin-in-l2 {
      type uint16 {
        range "0..310" {
          description
            "Defines a range equivalent to 0 to 31 dB.";
        }
      }
      units "0.1 dB";
      must ". >= ../minimum-noise-margin" {
        description
          "The target low power noise margin must be greater than 
           or equal to the minimum noise margin.";
      }
      default "60";
      description
        "Defines the target noise margin used during the L2.1 and
         L2.2 link state for both the upstream and downstream
         direction.";
      reference
        "ITU-T G.997.2 clause 7.1.10.1 (L2-TARSNRM); ITU-T G.9701 
         clause 13.4.1.4 and 13.4.2.4.";
    }

    leaf maximum-noise-margin-in-l2.1 {
      type uint16 {
        range "0..310 | 511" {
          description
            "Defines a range equivalent to 0 to 31 dB.";
        }
      }
      units "0.1 dB";
      must ". >= ../target-noise-margin-in-l2" {
        description
          "The maximum low power noise margin must be greater than 
           or equal to the target low power noise margin.";
      }
      default "511";
      description
        "Defines the maximum noise margin allowed during the L2.1 
         and L2.2 link state for both the upstream and downstream 
         direction. The special value, 511, indicates there is no 
         maximum bound for the noise margin (i.e., the maximum noise 
         margin is infinite).";
      reference
        "ITU-T G.997.2 clause 7.1.10.2 (L2-MAXSNRM); ITU-T G.9701 
         clause 13.4.1.4 and 13.4.2.4.";
    }
  }

  grouping noise-margin-profile {
    description
      "Defines the contents of a Noise Margin Profile.";

    container downstream {
      description
        "Downstream noise margin profile";

      container noise-margin {
        description
          "Noise margin parameters";

        uses noise-margin-parameters;
        uses noise-margin-low-power-parameters;
      }

      container seamless-rate-adaptation {
        description
          "Seamless Rate Adaptation(SRA) parameters";

        uses seamless-rate-adaptation-parameters;
      }

      container robust-management-channel {
        description
          "Robust Management Channel(RMC) parameters";

        uses robust-management-channel-parameters;
      }
    }

    container upstream {
      description
        "Upstream noise margin profile";

      container noise-margin {
        description
          "Noise margin parameters";

        uses noise-margin-parameters;
        uses noise-margin-upstream-parameters;
        uses noise-margin-low-power-parameters;
      }

      container seamless-rate-adaptation {
        description
          "Seamless Rate Adaptation(SRA) parameters";

        uses seamless-rate-adaptation-parameters;
      }

      container robust-management-channel {
        description
          "Robust Management Channel(RMC) parameters";

        uses robust-management-channel-parameters;
      }
    }
  }
}
