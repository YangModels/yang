submodule bbf-fast-line-threshold-profile-body {
  yang-version 1.1;
  belongs-to bbf-fast {
    prefix bbf-fast;
  }

  include bbf-fast-perf-types;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for
     managing line threshold profiles.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping line-thresholds {
    description
      "Performance parameters that have corresponding thresholds
       used to issue reports";

    leaf errored-seconds-threshold {
      type uint32;
      units "1 second";
      default "0";
      description
        "Threshold for the count of errored seconds (ES). A special 
         value (0) indicates the threshold is disabled. An errored
         second (ES) is defined in clause 11.4.4.2/G.9701.";
      reference
        "ITU-T G.997.2 clause 7.7.8 (CURR/PREV_NE/FE_15/24_ES);
         ITU-T G.997.2 clause 8.2 (THRESHOLD_NE/FE_15/24_ES)";
    }

    leaf severely-errored-seconds-threshold {
      type uint32;
      units "1 second";
      default "0";
      description
        "Threshold for the count of severely errored seconds (SES).
         A special value (0) indicates the threshold is disabled. 
         A severely errored second (SES) is defined in clause
         11.4.4.3/G.9701.";
      reference
        "ITU-T G.997.2 clause 7.7.9 (CURR/PREV_NE/FE_15/24_SES);
         ITU-T G.997.2 clause 8.2 (THRESHOLD_NE/FE_15/24_SES)";
    }

    leaf loss-of-signal-seconds-threshold {
      type uint32;
      units "1 second";
      description
        "Threshold for the count of los seconds (LOSS). A special 
         value (0) indicates the threshold is disabled. A los second 
         (LOSS) is defined in clause 11.4.4.4/G.9701. Support for this
         threshold is optional.";
      reference
        "ITU-T G.997.2 clause 7.7.10 (CURR/PREV_NE/FE_15/24_LOSS);
         ITU-T G.997.2 clause 8.2 (THRESHOLD_NE/FE_15/24_LOSS)";
    }

    leaf loss-of-rmc-seconds-threshold {
      type uint32;
      units "1 second";
      description
        "Threshold for the count of lor seconds (LOSS). A special 
         value (0) indicates the threshold is disabled. A lor second
         (LORS) is defined in clause 11.4.4.5/G.9701. Support for this
         threshold is optional.";
      reference
        "ITU-T G.997.2 clause 7.7.11 (CURR/PREV_NE/FE_15/24_LORS);
         ITU-T G.997.2 clause 8.2 (THRESHOLD_NE/FE_15/24_LORS)";
    }

    leaf unavailable-seconds-threshold {
      type uint32;
      units "1 second";
      default "0";
      description
        "Threshold for the count of unavailable seconds (UAS). A 
         special value (0) indicates the threshold is disabled. An
         unavailable second (UAS) is defined in clause
         11.4.4.6/G.9701.";
      reference
        "ITU-T G.997.2 clause 7.7.12 (CURR/PREV_NE/FE_15/24_UAS);
         ITU-T G.997.2 clause 8.2 (THRESHOLD_NE/FE_15/24_UAS)";
    }

    leaf full-initializations-threshold {
      type uint32;
      description
        "Threshold for a count of the full initialization primitives
         (full_init). A special value (0) indicates the threshold is 
         disabled. The full initialization primitive (full_init)
         is defined in clause 11.3.1.5/G.9701. Support for this 
         threshold is optional.";
      reference
        "ITU-T G.997.2 clause 7.7.13 (CURR/PREV_15/24_FULL_INITS);
         ITU-T G.997.2 clause 8.2 (THRESHOLD_15/24_FULL_INITS)";
    }

    leaf failed-initializations-threshold {
      type uint32;
      description
        "Threshold for a count of the failed full initialization
         primitives (failedfull_init). A special value (0) indicates 
         the threshold is disabled. The failed full initialization
         primitive (failedfull_init) is defined in clause
         11.3.1.5/G.9701. Support for this threshold is optional.";
      reference
        "ITU-T G.997.2 clause 7.7.14
         (CURR/PREV_15/24_FAILEDFULL_INITS);
         ITU-T G.997.2 clause 8.2 
         (THRESHOLD_15/24_FAILEDFULL_INITS)";
    }

    leaf fast-initializations-threshold {
      type uint32;
      description
        "Threshold for a count of the fast initialization primitives
         (fast_init). A special value (0) indicates the threshold is 
         disabled. The fast initialization primitive (fast_init)
         is defined in clause 11.3.1.5/G.9701. Support for this 
         threshold is optional.";
      reference
        "ITU-T G.997.2 clause 7.7.15 (CURR/PREV_15/24_FAST_INITS);
         ITU-T G.997.2 clause 8.2 (THRESHOLD_15/24_FAST_INITS)";
    }

    leaf failed-fast-initializations-threshold {
      type uint32;
      description
        "Threshold for a count of the failed fast initialization
         primitives (failedfast_init). A special value (0) indicates 
         the threshold is disabled. The failed fast initialization
         primitive (failedfast_init) is defined in clause
         11.3.1.5/G.9701. Support for this threshold is optional.";
      reference
        "ITU-T G.997.2 clause 7.7.16
         (CURR/PREV_15/24_FAILEDFAST_INITS);
         ITU-T G.997.2 clause 8.2 
         (THRESHOLD_15/24_FAILEDFAST_INITS)";
    }

    leaf spontaneous-interruptions-threshold {
      type uint32;
      description
        "Threshold for a count of the spontaneous interruption 
         anomalies (spont_intrpt). A special value (0) indicates the 
         threshold is disabled. The spontaneous interruption anomaly
         (spont_intrpt) is defined in clause 11.3.1.1/G.9701. Support 
         for this threshold is optional.";
      reference
        "ITU-T G.997.2 clause 7.7.19 (CURR/PREV_24_SPONT_INTRPT);
         ITU-T G.997.2 clause 8.2 (THRESHOLD_24_SPONT_INTRPT)";
    }
  }
}
