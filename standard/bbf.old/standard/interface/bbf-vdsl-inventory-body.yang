submodule bbf-vdsl-inventory-body {
  yang-version 1.1;
  belongs-to bbf-vdsl {
    prefix bbf-vdsl;
  }

  include bbf-vdsl-base-body;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 5.3 xDSL Termination
     Unit (xTU).

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping inventory {

    description
      "An xDSL Termination Unit (xTU) object represents an xDSL
       transceiver at either end of the xDSL Line. This has two
       instantiations: an xTU-C/xTU-O (central office or
       cabinet-located transceiver), and an xTU-R (Remote-located
       transceiver).";

    leaf g.994.1-vendor-id {
      type binary {
        length "8"; // octets
      }
      description
        "The xTU-C G.994.1 vendor ID is the vendor ID as inserted
         by the xTU-C in the G.994.1 CL message. It consists of 8
         binary octets, including a country code followed by a
         (regionally allocated) provider code, as defined in
         [ITU-T T.35]:
         T.35 country code (2 octets)
         T.35 provider code (vendor identification) (4 octets)
         T.35 provider oriented code (vendor revision number) (2
         octets)
         The G.994.1 vendor ID should typically identify the
         vendor of the xTU-C G.994.1 functionality, whether
         implemented in hardware or software. It is not intended
         to indicate the system integrator. Further details are
         defined in [ITU-T G.994.1].";
      reference
        "ITU-T G.997.1 clause 7.4.1 xTU-C G.994.1 vendor ID, and
         clause 7.4.2 xTU-R G.994.1 vendor ID";
    }

    leaf system-vendor-id {
      type binary {
        length "8"; // octets
      }
      description
        "The xTU system vendor ID is the vendor ID as inserted by
         the xTU-C in the overhead messages or by the by the
         xTU-R in the embedded operations channel. It consists of
         8 binary octets, with same format as the xTU-C G.994.1
         vendor ID (xtu-g.994.1-vendor-id).";
      reference
        "ITU-T G.997.1 clause 7.4.3 xTU-C system vendor ID, and
         clause 7.4.4 xTU-R system vendor ID";
    }

    leaf version-number {
      type binary {
        length "16"; // octets
      }
      description
        "The xTU version number is the version number as inserted
         by the xTU-C in the overhead messages, or by the xTU-R
         in the embedded operations channel. It is for version
         control and is vendor specific information.
         For the XTU-C, this consists of up to 16 binary octets.
         For the XTU-R, this consists of up to 16 ASCII
         characters. It contains the xTU-R firmware version and
         the xTU-R model. Both are encoded in this order and
         separated by a space character, i.e., <xTU-R firmware
         version> <xTU-R model>.";
      reference
        "ITU-T G.997.1 clause 7.4.5 xTU-C version number, and
         clause 7.4.6 xTU-R version number";
    }

    leaf serial-number {
      type binary {
        length "32"; // octets
      }
      description
        "The xTU serial number is the serial number as inserted
         by the xTU-C in the overhead messages, or by the xTU-R
         in the embedded operations channel. It is vendor
         specific information.
         For the XTU-C, this consists of up to 32 ASCII
         characters.
         For this XTU-R, this contains the equipment serial
         number, the equipment model and the equipment firmware
         version. All are encoded in this order and separated by
         space characters, i.e., <equipment serial number>
         <equipment model> <equipment firmware version>.";
      reference
        "ITU-T G.997.1 clause 7.4.7 xTU-C serial number, and
         clause 7.4.8 xTU-R serial number";
    }

    leaf self-test-result {
      type uint32;
      description
        "This parameter defines the xTU self-test result. It is
         coded as a 32-bit integer. The most significant octet of
         the self-test result is 00hex if the self-test passed
         and 01hex if the self-test failed. The interpretation of
         the other octets is vendor discretionary and can be
         interpreted in combination with G.994.1 and system
         vendor IDs.";
      reference
        "ITU-T G.997.1 clause 7.4.9 xTU-C self-test result, and
         clause 7.4.8 xTU-R serial number";
    }

    leaf-list transmission-system-capabilities {
      type xts-descriptor;
      // xts-descriptor is defined in bbf-vdsl-base-body.yang
      description
        "This parameter defines the xTU capability list of the
         different transmission system types. It is coded in a
         bit-map representation with the bits defined in the
         reference. This parameter may be derived from the
         handshaking procedures defined in [ITU-T G.994.1].";
      reference
        "ITU-T G.997.1 clause 7.3.1.1.1, clause 7.4.11 xTU-C
         transmission system capabilities, and clause 7.4.12
         xTU-R transmission system capabilitie";
    }
  } // end grouping inventory

  grouping vce {
    description
      "Parameters for Vectoring Control Entity (VCE) identity.";

    leaf vce-id {
      type union {
        type uint8 {
          range "1..255";
        }
        type enumeration {
          enum "not-in-vectored-group" {
            description
              "Indicates that the line is not in a vectored group.";
          }
        }
      }
      description
        "For the line in a vectored group, the VCE ID uniquely
         identifies the VCE that manages and controls the
         vectored group to which the line belongs. It consists of
         one octet and valid ranges are from 1 to 255. A special
         value (enum not-in-vectored-group) means the line is not
         in a vectored group.";
      reference
        "ITU-T G.997.1 clause 7.4.13.1 VCE ID (VCE_ID)";
    }

    leaf vce-port-index {
      type uint16;
      description
        "For the line in a vectored group, the VCE port index is
         the physical index that uniquely identifies the VCE port
         to which the line is connected. It is an integer from 1
         to the maximum number of lines supported by the VCE.";
      reference
        "ITU-T G.997.1 clause 7.4.13.2 VCE port index
         (VCE_port_index)";
    }
  } // end grouping vce
} // end submodule inventory-body
