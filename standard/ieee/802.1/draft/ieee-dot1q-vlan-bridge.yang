module ieee-dot1q-vlan-bridge {
	
	namespace "urn:ieee:params:xml:ns:yang:ieee-dot1q-vlan-bridge";
    prefix "dot1q-vlan-bridge";

	import ieee-dot1q-bridge {
		prefix "dot1q"; 
	}
	import ietf-system { 
		prefix "system"; 
	}
	
	organization
		"Institute of Electrical and Electronics Engineers";

	contact
	    "Web URL: http://www.ieee802.org/1/
    	
        Working Group Chair: 
    	   Glenn Parsons
    	   glenn.parsons@ericsson.com
     
        Working Group Vice-chair: 
    	   John Messenger
    	   J.L.Messenger@ieee.org
     	
        Chair, Time Sensitive Networking Task Group:
    	   Michael Johas Teener
    	   mikejt@broadcom.com
    	
		Vice-Chair, Time Sensitive Networking Task Group:
	       Janos Farkas
		   janos.farkas@ericsson.com
     	
        Editor: 
    	   Marc Holness
     	   mholness@ciena.com";
		   
	description
	   "This YANG module describes the bridge configuration model
		for Customer VLAN Bridges.";   

	revision "2015-09-10" {
	    description
	        "Initial Version.";
	    reference
	        "IEEE 802.1Q-2014, Media Access Control (MAC) Bridges and 
	    	  Virtual Bridged Local Area Networks.";
	}
	
	augment "/system:system/dot1q:bridge" {
		when "/dot1q:components = '1' and
		      /dot1q:bridge-type = 'customer-vlan-bridge' " {
			description
				"Applies when there is a single Bridge component
				of bridge type Customer VLAN Bridge.";
		}
		description
			"Augment the dot1q Bridge model with Customer VLAN Bridge
			nodal information.";
		container vlan-bridge {
		      presence
		    	  "Customer VLAN Bridge";
		      description
		    	  "Customer VLAN bridge configuration data.";
		} // vlan-bridge
	} // Augment dot1q:bridge
} // ieee-dot1q-VLANBridge
