module ieee-dot1q-bridge {
	
    namespace "urn:ieee:params:xml:ns:yang:ieee-dot1q-bridge";
    prefix "dot1q";
	
    import ieee-types { 
    	prefix "ieee"; 
    }
	import ietf-yang-types { 
		prefix "yang"; 
	}
	import ietf-interfaces { 
		prefix "if";
	}
	import iana-if-type { 
		prefix "ianaif"; 
	}
	import ieee-dot1q-types { 
		prefix "dot1qtypes"; 
	}
	import ietf-system { 
		prefix "system"; 
	}

    organization
      "Institute of Electrical and Electronics Engineers";

    contact
      "Web URL: http://www.ieee802.org/1/
    	
        Working Group Chair: 
    	   Glenn Parsons
    	   glenn.parsons@ericsson.com
     
        Working Group Vice-chair: 
    	   John Messenger
    	   J.L.Messenger@ieee.org
     	
        Chair, Time Sensitive Networking Task Group:
    	   Michael Johas Teener
    	   mikejt@broadcom.com
    	
    	Vice-Chair, Time Sensitive Networking Task Group:
    	   Janos Farkas
		   janos.farkas@ericsson.com
     	
        Editor: 
    	   Marc Holness
     	   mholness@ciena.com";
	   
	description
        "This YANG module describes the bridge configuration model
		for the following IEEE 802.1Q Bridges:
		    1. Two Port MAC Relay Bridges
		    2. Customer VLAN Bridges
		    3. Provider Bridges.";   

    revision "2015-09-10" {
      description
        "Initial Version.";
      reference
        "IEEE 802.1Q-2014, Media Access Control (MAC) Bridges and
    	  Virtual Bridged Local Area Networks.";
    }
	
    /*
     * IEEE 802.1Q Bridge Type identities.
     */
	identity type-of-bridge {
		description
			"Represents the configured Bridge type.";
	}	
	identity customer-vlan-bridge {
		base type-of-bridge;
		description
			"Base identity for a Customer VLAN Bridge.";
	}
	identity provider-bridge {
		base type-of-bridge;
		description
			"Base identity for a Provider Bridge (PB).";
	}
	identity provider-edge-bridge {
		base type-of-bridge;
		description
			"Base identity fro a Provider Edge Bridge (PEB).";
	}
	identity backbone-edge-bridge {
		base type-of-bridge;
		description
			"Base identity for a Backbone Edge Bridge (BEB).";
	}
	identity backbone-core-bridge {
		base type-of-bridge;
		description
			"Base identity for a Backbone Core Bridge (BCB).";
	}
	identity two-port-mac-relay-bridge {
		base type-of-bridge;
		description
			"Base identity for a Tow Port MAC Relay (TPMR) Bridge.";
	}
	
	/*
     * IEEE 802.1Q Bridge Component identities.
     */	
	identity type-of-component {
		description
			"Represents the type of Component.";
	}
	identity i-component {
		base type-of-component;
		description
			"Base identity for an I-component.";
	}
	identity b-component {
		base type-of-component;
		description
			"Base identity for a B-component.";
	}
	identity c-vlan-component {
		base type-of-component;
		description
			"Base identity for a C-VLAN component.";
	}
	identity s-vlan-component {
		base type-of-component;
		description
			"Base identity for a S-VLAN component.";
	}
	identity d-bride-component {
		base type-of-component;
		description
			"Base identity for a VLAN unaware component.";
	}
	identity edge-relay-component {
		base type-of-component;
		description
			"Base identity for an EVB station ER component.";
	}
	
	/*
     * IEEE 802.1Q Bridge Port Type identities.
     */
	identity type-of-port {
		description
			"Represents the type of Bridge port.";
	}
	identity cvlan-bridge-port {
		base type-of-port;
		description
			"Indicates the port can be a C-TAG aware port of an
			enterprise VLAN aware Bridge.";
	}
	identity provider-network-port {
		base type-of-port;
		description
			"Indicates the port can be an S-TAG aware port of a
			Provider Bridge or Backbone Edge Bridge used for 
			connections within a PBN or PBBN.";
	}
	identity customer-network-port {
		base type-of-port;
		description
			"Indicates the port can be an S-TAG aware port of a
			Provider Bridge or Backbone Edge Bridge used for 
			connections to the exterior of a PBN or PBBN.";
	}
	identity customer-edge-port {
		base type-of-port;
		description
			"Indicates the port can be a C-TAG aware port of a 
			Provider Bridge used for connections to the exterior of 
			a PBN or PBBN.";
	}
	identity customer-backbone-port {
		base type-of-port;
		description
			"Indicates the port can be a I-TAG aware port of a 
			Backbone Edge Bridges B-component.";
	}
	identity virtual-instance-port {
		base type-of-port;
		description
			"Indicates the port can be a virtual S-TAG aware port
			within a Backbone Edge Bridges I-component which is 
			responsible for handling S-tagged traffic for a
			specific backbone service instance.";
	}
	identity d-bridge-port {
		base type-of-port;
		description
			"Indicates the port can be a VLAN-unaware member of an
			802.1Q Bridge.";
	}
	identity remote-customer-access-port {
		base type-of-port;
		description
			"Indicates the port can be an S-TAG aware port of a
			Provider Bridge capable of providing Remote Customer
			Service Interfaces.";
	}
	identity station-facing-bridge-port {
		base type-of-port;
		description
			"Indicates the station-facing Bridge Port in a 
			EVB Bridge.";
	}
	identity uplink-access-port {
		base type-of-port;
		description
			"Indicates the uplink access port in an EVB Bridge or 
			EVB station.";
	}
	identity uplink-relay-port {
		base type-of-port;
		description
			"Indicates the uplink relay port in an EVB station.";
	}
	
    /*
     * IEEE 802.1Q Bridge features.
     */
	
	feature ingress-filtering {
     description 
    	 "Each Port may support an Enable Ingress Filtering 
    	 parameter. A frame received on a Port that is not in the
    	 member set (8.8.10) associated with the frames VID shall
    	 be discarded if this parameter is set. The default value 
    	 for this parameter is reset, i.e., Disable Ingress 
    	 Filtering, for all Ports. Any Port that supports setting 
    	 this parameter shall also support resetting it. The 
    	 parameter may be configured by the management operations 
    	 defined in Clause 12.";
     reference
    	 "IEEE 802.1Q-2014 Clause 8.6.2";
	}
	feature extended-filtering-services {
		description 
			"Extended Filtering Services support the filtering 
			behavior required for regions of a network in which 
			potential recipients of multicast frames exist, and 
			where both the potential recipients of frames and the 
			Bridges are able to support dynamic configuration of 
			filtering information for group MAC addresses. In order
			to integrate this extended filtering behavior with the 
			needs of regions of the network that support only Basic
			Filtering Services, Bridges that support Extended
			Filtering Services can be statically and dynamically 
			configured to modify their filtering behavior on a 
			per-group MAC address basis, and also on the basis of the
			overall filtering service provided by each outbound 
			Port with regard to multicast frames. The latter
			capability permits configuration of the Ports default 
			forwarding or filtering behavior with regard to group 
			MAC addresses for which no specific static or 
			dynamic filtering information has been configured.";
		reference
			"IEEE 802.1Q-2014 Clause 8.8.4, Clause 10";
	}
	feature port-and-protocol-based-vlan {
		description 
			"A VLAN-aware bridge component implementation in 
			conformance to the provisions of this standard for 
			Port-and-Protocol-based VLAN classification (5.4.1) 
			shall 
			1) Support one or more of the following Protocol 
			   Classifications and Protocol Template formats: 
			   Ethernet, RFC_1042, SNAP_8021H, SNAP_Other,
			   or LLC_Other (6.12);	and may
			2) Support configuration of the contents of the Protocol
			   Group Database.";
		reference
			"IEEE 802.1Q-2014 Clause 5.4.1.2";
	}
	feature flow-filtering {
		description 
			"Flow filtering support enables Bridges to distinguish 
			frames belonging to different client flows and to use 
			this information in the forwarding process. Information 
			related to client flows may be used at the boundary
			of an SPT Domain to generate a flow hash value. The flow
			hash, carried in an F-TAG, serves to distinguish frames
			belonging to different flows and can be used in the 
			forwarding process to distribute frames over equal cost 
			paths. This provides for finer granularity load spreading
			while maintaining frame order for each client flow.";
		reference
			"IEEE 802.1Q-2014 Clause 44.2";
	}
	
	/* --------------------------------------------------------
	 * NOTE: For now, the bridge is defined as an augmentation
	 *       of the system root node. However, the general
	 *       root hierarchy/structure has not been solidified
	 *       yet. That is, perhaps a IEEE-Bridge root node
	 *       needs to be defined. If so, then the Bridge node
	 *       here would augment the IEE-Bridge node instead.
	 * -----------------------------------------------------------
	 */
	
	augment "/system:system" {
		description
			"Augment the system model with the Bridge(s)
			configuration information.";
		list bridge {
			key name;
			unique "address";
			description 
				"Provides configuration data in support of the Bridge
				Configuration resources. There is a single bridge 
				data node per Bridge.";			
			leaf name {
				type dot1qtypes:name-type;
				description 
					"A text string associated with the Bridge, of
					locally determined significance.";
				reference
					"IEEE 802.1Q-2014 Clause 12.4";
			}
			leaf address {
				type ieee:mac-address;
				mandatory true;
				description 
					"The MAC address for the Bridge from which the
					Bridge Identifiers used by the STP, RSTP, and 
					MSTP are derived.";
				reference
					"IEEE 802.1Q-2014 Clause 12.4";
			}
			leaf bridge-type {
				type identityref {
					base type-of-bridge;
				}
				description 
					"The type of Bridge.";
			}
			list component {
				key "name";
				description 
					"The set of components associated with a given 
					Bridge. For example,
					   - A TPMR Bridge is associated with a single
					     VLAN unaware component.
					   - A Customer VLAN Bridge is associated with a 
					     single VLAN aware component.
					   - A Provider Bridge is associated with a
					     single S-VLAN component and zero or more
					     C-VLAN components.";
				reference
					"IEEE 802.1Q-2014 Clause 12.3";
				leaf name {
					type string;
					description
						"The name of the Component.";
				}
				leaf id {
					type uint32;
					description 
						"Unique identifier for a particular Bridge 
						component within the system.";
					reference
						"IEEE 802.1Q-2014 Clause 12.3 l)";
				}
				leaf type {
					type identityref {
						base type-of-component;
					}
					description 
						"The type of component used to classify a 
						particular Bridge component within a Bridge
						system comprising multiple components.";
					reference
						"IEEE 802.1Q-2014 Clause 12.3 m)";
				}
				leaf address {
					type ieee:mac-address;
					description 
						"Unique EUI-48 Universally Administered MAC 
						address assigned to a Bridge component.";
					reference
						"IEEE 802.1Q-2014 Clause 8.13.8, 13.24";
				}
				leaf traffic-class-enabled {
					type boolean;
					default "true";
					description 
						"Indication of Traffic Classes enablement 
						associated with the Bridge Component. A 
						value of True indicates that Traffic Classes
						are enabled on this Bridge Component. A 
						value of False indicates that the Bridge 
						Component operates with a single priority
						level for all traffic.";
					reference
						"IEEE 802.1Q-2014 Clause 12.4.1.5.1";
				}
				leaf mmrp-enabled-status {
					type boolean;
					default "true";
					description 
						"The administrative status of MMRP. The value 
						True indicates that MMRP should be enabled on 
						this device, in all VLANs, on all ports for
						which it has not been specifically disabled.
						A value of False indicates that MMRP is 
						disabled, in all VLANs and on all ports, and
						all MMRP packets will be forwarded 
						transpartently. This object affects both 
						Applicant and Registrar state machines. A 
						transition from False to True will cause a
						reset of all MMRP state machines on all 
						ports.";
					reference
						"IEEE 802.1Q-2014 Clause 12.4.1.5.1";
				}

				container filtering-database {
					when "dot1q:bridge-type != 'TPMR-bridge'" {
						description
							"Applies to non TPMR Bridges.";
					}
					description 
						"Contains filtering information used by the 
						Forwarding Process in deciding through which 
						Ports of the Bridge frames shoudl be 
						forwarded.";
					reference
						"IEEE 802.1Q-2014 Clause 12.7";
					leaf aging-time {
						type uint32 {range "10..10000000";}
						units seconds;
						default 300;
						description 
							"The timeout period in seconds for aging
							out dynamically-learned forwarding 
							information. The value of this object 
							MUST be retained across reinitializations
							of the managment system.";
						reference
							"IEEE 802.1Q-2014 Clause 12.7, 8.8.3";
					}

					list filtering-entries {
						key "database-id vid address";
						description
							"Information for the entries associated
							with the Permanent Database.";
						leaf database-id {
							type uint16;
							description 
								"The identity of this Filtering 
								Database.";
							reference
								"IEEE 802.1Q-2014 Clause 12.7.7";
						}
						leaf address {
							type ieee:mac-address;
							description 
								"A MAC address (unicast, multicast, 
								broadcast) for which the device has 
								forwarding and/or filtering 
								information.";
							reference
								"IEEE 802.1Q-2014 Clause 12.7.7";
						}
						leaf vid {
							type ieee:vlanid;
							description 
								"The VLAN identifier to which this
								entry applies.";
							reference
								"IEEE 802.1Q-2014 Clause 12.7.7";
						}
						leaf entry-type {
							type enumeration {
								enum static {
									description
										"Static entry type";
								}
								enum dynamic {
									description
										"Dynamic/learnt entry type";
								}
							}
							description 
								"The type of filtering entry. Whether 
								static or dynamic.";
							reference
								"IEEE 802.1Q-2014 Clause 12.7.7";							
						}
						uses dot1qtypes:port-map;					
					} // filtering-entries
					
					list vlan-registration-entries {
						key "database-id vid";
						description
							"The VLAN Registration Entries models the
							operations that can be performed on a
							single VLAN Registration Entry in the
							FDB. The set of VLAN Registration 
							Entries within the FDB changes under 
							management control and also as a result
							of MVRP exchanges";
						reference
							"IEEE 802.1Q-2014 Clause 12.7.5";
						leaf database-id {
							type uint32;
							description 
								"The identity of this Filtering 
								Database.";
							reference
								"IEEE 802.1Q-2014 Clause 12.7.7";
						}
						leaf vid {
							type ieee:vlanid;
							description 
								"The VLAN identifier to which this
								entry applies.";
							reference
								"IEEE 802.1Q-2014 Clause 12.7.7";
						}
						leaf entry-type {
							type enumeration {
								enum static {
									description
										"Static entry type";
								}
								enum dynamic {
									description
										"Dynamic/learnt entry type";
								}
							}
							description 
								"The type of filtering entry. Whether 
								static or dynamic.";
							reference
								"IEEE 802.1Q-2014 Clause 12.7.7";						
						}
						uses dot1qtypes:port-map;
					} // vlan-registration-entries
				} // filtering-database
				
				container permanent-database {
					description
						"The Permanent Database container models the 
						operations that can be performed on, or
						affect, the Permanent Database. There is a 
						single Permanent Database per FDB.";
					list filtering-entries {
						key "database-id vid address";
						description
							"Information for the entries associated
							with the Permanent Database.";
						leaf database-id {
							type uint16;
							description 
								"The identity of this Filtering 
								Database.";
							reference
								"IEEE 802.1Q-2014 Clause 12.7.7";
						}
						leaf address {
							type ieee:mac-address;
							description 
								"A MAC address (unicast, multicast, 
								broadcast) for which the device has 
								forwarding and/or filtering 
								information.";
							reference
								"IEEE 802.1Q-2014 Clause 12.7.7";
						}
						leaf vid {
							type ieee:vlanid;
							description 
								"The VLAN identifier to which this
								entry applies.";
							reference
								"IEEE 802.1Q-2014 Clause 12.7.7";
						}
						uses dot1qtypes:port-map;					
					} // filtering-entries
				} // permanent-database
			
				container bridge-vlan {
					when "dot1q:bridge-type != 'TPMR-bridge'" {
						description
							"Applies to non TPMR Bridges.";
					}
					description
						"The Bridge VLAN container models 
						configuration information that modify, or 
						inquire about, the overall configuration of
						the Bridges VLAN resources. There is a single
						Bridge VLAN Configuration managed object per
						Bridge.";
					reference
						"IEEE 802.1Q-2014 Clause 12.10";
					list vlan-id {
						key "vid";
						description
							"List of VLAN related configuration nodes
							associated with the Bridge.";
						reference
							"IEEE 802.1Q-2014 Clause 12.10.2";
						leaf vid {
							type ieee:vlanid;
							description 
								"The VLAN identifier to which this
								entry applies.";
							reference
								"IEEE 802.1Q-2014 Clause 12.10.2";
						}
						leaf name {
							type dot1qtypes:name-type;
							description 
								"A text string of up to 32 characters
								of locally determined significance.";
							reference
								"IEEE 802.1Q-2014 Clause 12.10.2";
						}
					} // vlan-id
					
					container protocol-group-database {
						if-feature port-and-protocol-based-vlan;
						description 
							"A table that contains mappings from
							Protocol Templates to Protocol Group
							Identifiers used for 
							Port-and-Protocol-based VLAN 
							Classification. Entries in this table
							must be persistent over power up 
							restart/reboot";
						reference
							"IEEE 802.1Q-2014 Clause 12.10.1.7";
						leaf frame-format-type {
							type dot1qtypes:protocol-template-format;
							description 
								"The data-link encapsulation format
								or the detagged_frame_type in a 
								Protocol Template";
							reference
								"IEEE 802.1Q-2014 Clause 12.10.1.7";
						}
						choice frame-format {
							description 
								"The identification of the protocol 
								above the data-link layer in a 
								Protocol Template. Depending on the
								frame type, the octet string will
								have one of the following values:						
								  - For ethernet, rfc1042 and 
								    snap8021H, this is the 16-bit
								    (2-octet) IEEE 802.3 Type Field.						
								  - For snapOther, this is the 40-bit 
								    (5-octet) PID.						
								  - For llcOther, this is the 2-octet 
								    IEEE 802.2 Link Service Access
								    Point (LSAP) pair: first octet
								    for Destination Service Access
								    Point (DSAP) and second octet for
								    Source Service Access Point
								    (SSAP).";
							reference
								"IEEE 802.1Q-2014 Clause 12.10.1.7";
							case ethernet-rfc1042-snap8021H {
								description
									"Identifier used if Ethenet, 
									RFC1042, or SNAP 8021H.";
								leaf ether-type {
									type string {
										length "2";
									}
									description
										"Format containing the 16-bit
										IEEE 802.3 EtherType field.";
									reference
										"IEEE 802.1Q-2014 Clause 
										12.10.1.7.1";
								}						
							}
							case snap-other {
								description
									"Identifier used if SNAP other.";
								leaf protocol-id {
									type string {
										length "5";
									}
									description
										"Format containing the 40-bit
										protocol identifier (PID).";
									reference
										"IEEE 802.1Q-2014 Clause 
										12.10.1.7.1";
								}						
							}
							case llc-other {
								description
									"Identifier used if LLC other.";
								container dsap-ssap-pairs {
									description
										"A pair of ISO/IEC 8802-2
										DSAP and SSAP address field
										values, for matching frame
										formats of LLC_Other.";
									leaf llc-address {
										type string {
											length "2";
										}
										description
											"A pair of ISO/IEC 8802-2 
											DSAP and SSAP address 
											field values, for 
											matching frame formats
											of LLC_Other.";
										reference
											"IEEE 802.1Q-2014 Clause 
											12.10.1.7.1";
									}
								}						
							}					
						}
						leaf protocol-group-id {
							type uint32;
							description 
								"Designates a group of protocols in
								the Protocol Group Database.";
							reference
								"IEEE 802.1Q-2014 Clause 6.12.2";
						}
					} // protocol-group-database
					
					list vid-to-fid-allocation {
						key "vids";
						description 
							"The VID to FID allocations managed 
							object models operations that modify, or
							inquire about VID to FID allocations
							(8.8.8) that apply to the operation of
							the Learning Process and the FDB.";
						leaf vids {
							type dot1qtypes:vid-range;
							description
								"Range of VLAN identifiers.";
							reference
								"IEEE 802.1Q-2014 Clause 12.10.3";
						}
						leaf fid {
							type uint16;
							description 
								"The Filtering Database used by this
								VLAN. This value is allocated 
								automatically by the device whenever
								the VLAN is created: either
								dynamically by MVRP, or by 
								management. Allocation of this value
								follows the learning constraints
								defined for this VLAN.";
							reference
								"IEEE 802.1Q-2014 Clause 12.10.3";
						}
					} // vid-to-fid-allocation
				} // bridge-vlan				
			} // component
		} // bridge		
	} // Augment system
	
	augment "/system:system-state" {
		description
			"Augment the system-state model with the Bridge(s)
			operational information.";
		list bridge {
			key name;
			description 
				"Provides configuration data in support of the Bridge
				Configuration resources. There is a single bridge 
				data node per Bridge.";			
			leaf name {
				type dot1qtypes:name-type;
				description 
					"A text string associated with the Bridge, of
					locally determined significance.";
				reference
					"IEEE 802.1Q-2014 Clause 12.4";
			}
			leaf ports {
				type dot1qtypes:port-number-type;
				description 
					"The number of Bridge Ports (MAC Entities)";
				reference
					"IEEE 802.1Q-2014 Clause 12.4";
			}
			leaf up-time {
				type yang:counter32;
				units seconds;
				description 
					"The count in seconds of the time elapsed since
					the Bridge was last reset or initialized.";
				reference
					"IEEE 802.1Q-2014 Clause 12.4";
			}
			leaf components {
				type uint32;
				description
					"The number of components assocaited with the
					Bridge.";
			}			
			list component {
				key "name";
				description 
					"The set of components associated with a given 
					Bridge. For example,
					   - A TPMR Bridge is associated with a single
					     VLAN unaware component.
					   - A Customer VLAN Bridge is associated with a 
					     single VLAN aware component.
					   - A Provider Bridge is associated with a
					     single S-VLAN component and zero or more
					     C-VLAN components.";
				reference
					"IEEE 802.1Q-2014 Clause 12.3";
				leaf name {
					type string;
					description
						"The name of the Component.";
				}
				leaf ports {
					type dot1qtypes:port-number-type;
					description 
						"The number of Bridge Ports associated with
						the Bridge Component.";
					reference
						"IEEE 802.1Q-2014 Clause 12.4.1.1.3 c)";
				}
				leaf-list bridge-port {
					type if:interface-ref;
					description 
						"List of bridge-port references.";
				}
				container capabilities {
					description 
						"Array of Boolean values of the feature 
						capabilities associated with a given Bridge 
						Component.";
					reference
						"IEEE 802.1Q-2014 Clause 12.4.1.5.2, 
						12.10.1.1.3 b)";
					leaf extended-filtering {
						type boolean;
						description 
							"Can perform filtering on individual 
							multicast addresses controlled by MMRP.";
						reference
							"IEEE 802.1Q-2014 Clause 12.4.1.5.2";
					}
					leaf traffic-classes {
						type boolean;
						description 
							"Can map priority to multiple traffic 
							classes.";
						reference
							"IEEE 802.1Q-2014 Clause 12.4.1.5.2";
					}
					leaf static-entry-individual-port {
						type boolean;
						description
							"Static entries per port.";
						reference
							"IEEE 802.1Q-2014 Clause 12.4.1.5.2";
					}
					leaf ivl-capable {
						type boolean;
						description
							"Independent VLAN Learning (IVL).";
						reference
							"IEEE 802.1Q-2014 Clause 12.4.1.5.2";
					}
					leaf svl-capable {
						type boolean;
						description
							"Shared VLAN Learning (SVL).";
						reference
							"IEEE 802.1Q-2014 Clause 12.4.1.5.2";
					}
					leaf hybrid-capable {
						type boolean;
						description 
							"Both IVL and SVL simultaneously.";
						reference
							"IEEE 802.1Q-2014 Clause 12.4.1.5.2";
					}
					leaf configurable-pvid-tagging {
						type boolean;
						description
							"Whether the implementation supports the 
							ability to override the defautl PVID
							setting and its egress status 
							(VLAN-tagged or Untagged) on each port.";
						reference
							"IEEE 802.1Q-2014 Clause 12.4.1.5.2";
					}
					leaf local-vlan-capable {
						type boolean;
						description
							"Can support multiple local Bridges, 
							outside the scope of 802.1Q defined 
							VLANs.";
						reference
							"IEEE 802.1Q-2014 Clause 12.4.1.5.2";
					}
				} // capabilities

				container filtering-database {
					when "dot1q:bridge-type != 'TPMR-bridge'" {
						description
							"Applies to non TPMR Bridges.";
					}
					description 
						"Contains filtering information used by the 
						Forwarding Process in deciding through which 
						Ports of the Bridge frames shoudl be 
						forwarded.";
					reference
						"IEEE 802.1Q-2014 Clause 12.7";
					leaf size {
						type uint16;
						description 
							"The maximum number of entries that can
							be held in the FDB.";
						reference
							"IEEE 802.1Q-2014 Clause 12.7";
					}
					leaf static-entries {
						type uint16;
						description 
							"The number of Static Filtering entries 
							currently in the FDB.";
						reference
							"IEEE 802.1Q-2014 Clause 12.7, 8.8.1";
					}
					leaf dynamic-entries {
						type yang:gauge32;
						description 
							"The number of Dynamic Filtering entries 
							currently in the FDB.";
						reference
							"IEEE 802.1Q-2014 Clause 12.7, 8.8.3";
					}
					leaf static-vlan-registration-entries {
						type uint16;
						description 
							"The number of Static VLAN Registration 
							entries currently in the FDB.";
						reference
							"IEEE 802.1Q-2014 Clause 12.7, 8.8.2";
					}
					leaf dynamic-vlan-registration-entries {
						type yang:gauge32;
						description 
							"The number of Dynamic VLAN Registration 
							entries currently in the FDB.";
						reference
							"IEEE 802.1Q-2014 Clause 12.7, 8.8.5";
					}
					leaf mac-address-registration-entries {
						if-feature extended-filtering-services;
						type yang:gauge32;
						description 
							"The number of MAC Address Registration
							entries currently in the FDB.";
						reference
							"IEEE 802.1Q-2014 Clause 12.7, 8.8.4";
					}

					list filtering-entries {
						key "database-id vid address";
						description 
							"A table containing filtering information
							for Unicast/Multicast/Broadcast MAC 
							addresses for each VLAN, configured into
							the device by (local or network) 
							management specifying the set of Ports
							to which frame received from specific
							Ports and containing specific 
							Unicast/Multicast/Broadcast destination
							MAC addresses are allowed to be 
							forwarded.
							
							A value of zero (as the Port number
							from which frames with a specific 
							destiantion MAC address are received) is
							used to specify all ports for which there
							is no specific entry in this table for
							that particular MAC address.
							
							Two modes of operation are supported.
							When the receive Port index is non-zero,
							then an 802.1D filtering database is
							supported. If the received Port is zero,
							then this table is operating as specified
							in IEEE 802.1Q.";

						leaf database-id {
							type uint32;
							description 
								"The identity of this Filtering 
								Database.";
							reference
								"IEEE 802.1Q-2014 Clause 12.7.7";
						}
						leaf address {
							type ieee:mac-address;
							description 
								"For dynamic entries, the destination
								MAC address in a frame to which this
								entries filtering information 
								applies. For static entries, a MAC 
								address (unicast/multicast/broadcast)
								for which the device has forwarding
								and/or filtering information.";
							reference
								"IEEE 802.1Q-2014 Clause 12.7.7";
						}
						leaf vid {
							type ieee:vlanid;
							description 
								"The VLAN identifier to which this
								entry applies.";
							reference
								"IEEE 802.1Q-2014 Clause 12.7.7";
						}
						leaf status {
							type enumeration {
								enum other {
									description
										"None of the following. This
										may include the case where
										some other object is being
										used to determine if and how
										frames MAC addressed to the
										value of are being 
										forwarded.";
								}
								enum invalid {
									description
										"This entry is no longer 
										valid (e.g., it was learned
										but has since aged out), but
										has not yet been flushed
										from the table.";
								}
								enum learned {
									description
										"The value of the
										corresponding instance of the
										port node was learned and is
										being used.";
								}
								enum self {
									description
										"The value of the
										corresponding instance of the
										address node representing
										one of the devices address.";
								}
								enum mgmt {
									description
										"The value of the 
										corresponding instance of
										address node that is also the
										value of an existing 
										instance.";
								}
							}
							description 
								"The status of this entry.";
						}
					} // filtering-entries
				} // filtering-database
				
				container permanent-database {
					description
						"The Permanent Database container models the 
						operations that can be performed on, or
						affect, the Permanent Database. There is a 
						single Permanent Database per FDB.";
					leaf size {
						type yang:gauge32;
						description 
							"The maximum number of entries that can
							be held in the FDB.";
						reference
							"IEEE 802.1Q-2014 Clause 12.7.6";
					}
					leaf static-entries {
						type yang:gauge32;
						description 
							"The number of Static Filtering entries 
							currently in the FDB.";
						reference
							"IEEE 802.1Q-2014 Clause 12.7.6";
					}
					leaf static-vlan-registration-entries {
						type yang:gauge32;
						description 
							"The number of Static VLAN Registration 
							entries currently in the FDB.";
						reference
							"IEEE 802.1Q-2014 Clause 12.7.6";
					}
				} // permanent-database
			
				container bridge-vlan {
					when "dot1q:bridge-type != 'TPMR-bridge'" {
						description
							"Applies to non TPMR Bridges.";
					}
					description
						"The Bridge VLAN container models 
						configuration information that modify, or 
						inquire about, the overall configuration of
						the Bridges VLAN resources. There is a single
						Bridge VLAN Configuration managed object per
						Bridge.";
					reference
						"IEEE 802.1Q-2014 Clause 12.10";
					leaf version {
						type uint16;
						description
							"The version number supported.";
						reference
							"IEEE 802.1Q-2014, Clause 12.10.1.3";						
					}
					leaf max-vids {
						type uint16;
						description
							"The maximum number of VIDs supported.";
						reference
							"IEEE 802.1Q-2014, Clause 12.10.1.3";
					}
					leaf override-default-pvid {
						type boolean;
						description
							"Indicates if the default PVID can be
							overridden, and its egress status
							(VLAN-tagged or untagged) on each port.";
						reference
							"IEEE 802.1Q-2014, Clause 12.10.1.3";						
					}
					leaf protocol-template {
						if-feature port-and-protocol-based-vlan;
						type dot1qtypes:protocol-template-format;
						description 
							"The data-link encapsulation format
							or the detagged_frame_type in a 
							Protocol Template";
						reference
							"IEEE 802.1Q-2014 Clause 12.10.1.7";						
					}
					leaf max-msti {
						type uint16;
						description
							"The maximum number of MSTIs supported
							within an MST region (i.e., the number
							of spanning tree instances that can be
							supported in addition to the CIST), for
							MST Bridges. Fos SST Bridges, this
							parameter may be either omitted or 
							reported as 0.";
						reference
							"IEEE 802.1Q-2014 Clause 12.10.1.7";
					}
					list vlan-id {
						key "vid";
						description
							"List of VLAN related configuration nodes
							associated with the Bridge.";
						reference
							"IEEE 802.1Q-2014 Clause 12.10.2";
						leaf vid {
							type ieee:vlanid;
							description 
								"The VLAN identifier to which this
								entry applies.";
							reference
								"IEEE 802.1Q-2014 Clause 12.10.2";
						}
						leaf-list untagged-ports {
							type if:interface-ref;
							description
								"The set of ports in the untagged set
								for this VID.";
							reference
								"IEEE 802.1Q-2014 Clause 8.8.2 and
								Clause 12.10.2.1.3";							
						}
						leaf-list egress-ports {
							type if:interface-ref;
							description
								"The set of egress ports in the 
								member set for this VID.";
							reference
								"IEEE 802.1Q-2014 Clause 8.8.10 and
								Clause 12.10.2.1.3";							
						}
					} // vlan-id
										
					container vid-to-fid-allocation {
						description 
							"The VID to FID allocations managed 
							object models operations that modify, or
							inquire about VID to FID allocations
							(8.8.8) that apply to the operation of
							the Learning Process and the FDB.";
						leaf allocation-type {
							type enumeration {
								enum undefined {
									description
										"No allocation defined.";
								}
								enum fixed {
									description
										"A fixed allocation to FID
										is defined.";
								}
								enum dynamic {
									description
										"A dynamic allocation to FID
										is defined.";
								}
							}
							description
								"The type of allocation used";
							reference
								"IEEE 802.1Q-2014 Clause 12.10.3";							
						}
					} // vid-to-fid-allocation
				} // bridge-vlan
			} // component
		} // bridge		
	} // system-state
	
	augment "/if:interfaces/if:interface" {
		when "/if:type = 'ianaif:ethernetCsmacd' or
			  /if:type = 'ianaif:ieee8023adLag'" {
				description
					"Applies when an Ethernet port or LAG interface";
			}
		description
			"Augment the interface model with the Bridge Port";
		container bridge-port {
			description 
				"Bridge Port is an extension of the IETF Interfaces
				model (RFC7223).";
			leaf component-name {
				type dot1qtypes:component-ref;
				description
					"Used to reference configured Component
					nodes.";
			}
			leaf pvid {
				when "dot1q:bridge-type != 'TPMR-bridge'" {
					description
						"Applies to non TPMR Bridges";
				}
				type ieee:vlanid;
				default "1";
				description "The primary (default) VID assigned to a
					specific Bridge Port.";
				reference
					"IEEE 802.1Q-2014 Clause 5.4 m), 12.10.1";
			}
			leaf default-priority {
				type dot1qtypes:priority-type;
				default "0";
				description 
					"The default priority assigned to a specific 
					Bridge Port.";
				reference
					"IEEE 802.1Q-2014 Clause 12.6.2";
			}
			container priority-regeneration {
				description 
					"The Priority Regeneration Table parameters 
					associted with a specific Bridge Port. A list of
					Regenerated User Priorities for each received
					priority on each port of a Bridge. The 
					regenerated priority value may be used to index
					the Traffic Class Table for each input port. This
					only has effect on media that support native 
					priority. The default values for Regenerated User
					Priorities are the same as the User Priorities";
				reference
					"IEEE 802.1Q-2014 Clause 12.6.2, 6.9.4";
				uses dot1qtypes:priority-regeneration-table;
			}
			leaf pcp-selection {
				type dot1qtypes:pcp-selection-type;
				default "8P0D";
				description 
					"The Priority Code Point selection assigned to a
					specific Bridge Port. This object identifies the
					rows in the PCP encoding and decoding tables that
					are used to remark frames on this port if this
					remarking is enabled";
				reference
					"IEEE 802.1Q-2014 Clause 12.6.2, 6.9.3";
			}
			container pcp-decoding-table {
				description 
					"The Priority Code Point Decoding Table 
					parameters associated with a specific Bridge
					Port.";
				leaf selection-type {
					type dot1qtypes:pcp-selection-type;
					default "8P0D";
					description
						"Priority Code Point selection type";
					reference
						"IEEE 802.1Q-2014 Clause 12.6.2, 6.9.3";
				}
				container decoding-table {
					description
						"Priority Code Point decoding table";
					reference
						"IEEE 802.1Q-2014 Clause 12.6.2";
					uses dot1qtypes:pcpDecodingTable;
				}
			} // pcp-decoding-table
			container pcp-encoding-table {
				description 
					"The Priority Code Point Encoding Table 
					parameters associated with a specific Bridge 
					Port.";
				leaf selection-type {
					type dot1qtypes:pcp-selection-type;
					default "8P0D";
					description
						"Priority Code Point selection type";
					reference
						"IEEE 802.1Q-2014 Clause 12.6.2";
				}
				container encoding-table {
					description
						"Priority Code Point encoding table";
					reference
						"IEEE 802.1Q-2014 Clause 12.6.2";
					uses dot1qtypes:pcp-encoding-table;
				}
			}
			leaf use-dei {
				type boolean;
				default "false";
				description 
					"The Drop Eligible Indicator. If it is set to 
					True, then the drop_eligible parameter is encoded
					in the DEI of transmitted frames, and the
					drop_eligible parameter shall be true(1) for a
					received frame if the DEI is set in the VLAN tag
					or the Priority Code Point Decoding Table 
					indicates drop_eligible True for the received PCP
					value. If this parameter is False, the DEI shall
					be transmitted as zero and ignored on receipt.";
				reference
					"IEEE 802.1Q-2014 Clause 12.6.2, 6.9.3";
			}
			leaf drop-encoding {
				type boolean;
				default "false";
				description 
					"The Drop Encoding parameter. If a Bridge 
					supports encoding or decoding of drop_eligible
					from the PCP field of a VLAN tag (6.7.3) on any
					of its Ports, then it shall implement a Boolean 
					parameter Require Drop Encoding on each of its
					Ports with default value False. If Require Drop 
					Encoding is True and the Bridge Port cannot
					encode particular priorities with drop_eligible,
					then frames queued with those priorities and 
					drop_eligible True shall be discarded and not 
					transmitted.";
				reference
					"IEEE 802.1Q-2014 Clause 12.6.2, 8.6.6";
			}
			leaf service-access-priority-selection {
				type enumeration {
					enum enabled {
						description
							"Enable service access priority 
							selection.";
					}
					enum disabled {
						description
							"Disable service access priority 
							selection.";
					}
				}
				description 
					"The Service Access Priority selection. 
					Indication of whether the Service Access Priority
					Selection function is supported on the Customer 
					Bridge Port to request priority handling of the
					frame from a Port-based service interface.";
				reference
					"IEEE 802.1Q-2014 Clause 12.6.2, 6.13";
			}
			container service-access-priority {
				description 
					"The Service Access Priority table parameters. A
					table that contains information about the Service
					Access Priority Selection function for a Provider
					Bridge. The use of this table enables a mechanism
					for a Customer Bridge attached to a Provider 
					Bridged Network to request priority handling of 
					frames. All writable objects in this table MUST
					be persistent over power up restart/reboot";
				reference
					"IEEE 802.1Q-2014 Clause 12.6.2, 6.13.1";
				uses dot1qtypes:service-access-priority-table;
			}
			container traffic-class {
				description 
					"The Traffic Class table parameters. A table 
					mapping evaluated priority to Traffic Class, for
					forwarding by the Bridge";
				reference
					"IEEE 802.1Q-2014 Clause 12.6.3, 8.6.6";
				uses dot1qtypes:traffic-class-table;
			}
			leaf acceptable-frame {
				when "dot1q:bridge-type != 'TPMR-bridge'" {
					description
						"Applies to non TPMR Bridges";
				}
				type enumeration {
					enum admit-only-VLAN-tagged-frames {
						description
							"Admit only VLAN-tagged frames.";
					}
					enum admit-only-untagged-and-priority-tagged {
						description
							"Admit only untagged and priority-tagged
							frames.";
					}
					enum admit-all-frames {
						description
							"Admit all frames.";
					}
				}
				default "admit-all-frames";
				description 
					"To configure the Acceptable Frame Types 
					parameter associated with one or more Ports";
				reference
					"IEEE 802.1Q-2014 Clause 12.10.1.3, 6.9";
			}
			leaf enable-ingress-filtering {
				when "dot1q:bridge-type != 'TPMR-bridge'" {
					description
						"Applies to non TPMR Bridges";
				}
				type boolean;
				default "false";
				description 
					"To configure the Enabled Ingress Filtering 
					parameter(s) associated with one or more Ports.";
				reference
					"IEEE 802.1Q-2014 Clause 12.10.1.4, 8.6.2";
			}
			leaf restricted-vlan-registration {
				when "dot1q:bridge-type != 'TPMR-bridge'" {
					description
						"Applies to non TPMR Bridges";
				}
				type boolean;
				default "false";
				description
					"To configure the Restricted_VLAN_Registration 
					parameter associated with one or more Ports.";
				reference
					"IEEE 802.1Q-2014 Clause 12.10.1.6, 11.2.3.2.3";
			}
			leaf vid-translation-table {
				when "dot1q:bridge-type != 'TPMR-bridge'" {
					description
						"Applies to non TPMR Bridges";
				}
				type boolean;
				default "false";
				description 
					"The VD Translation table associated with a 
					Bridge Port. This is not applicable to Bridge 
					Ports that do no support a VID Translation 
					Table.";
				reference
					"IEEE 802.1Q-2014 Clause 12.10.1.8, 6.9";
			}
			leaf egress-vid-translation-table {
				when "dot1q:bridge-type != 'TPMR-bridge'" {
					description
						"Applies to non TPMR Bridges";
				}
				type boolean;
				default "false";
				description 
					"The Egress VID Translation table associated with
					a Bridge Port. This is not applicable to Ports 
					that do not support an Egress VID Translation
					table.";
				reference
					"IEEE 802.1Q-2014 Clause 12.10.1.9, 6.9";
			}
			leaf protocol-group-id {
				when "dot1q:bridge-type != 'TPMR-bridge'" {
					description
						"Applies to non TPMR Bridge";
				}
				if-feature port-and-protocol-based-vlan;
				type uint16;
				description 
					"Designates a group of protocols in the Protocol
					Group Database";
				reference
					"IEEE 802.1Q-2014 Clause 6.12.2";
			}
			container protocol-group-database-contents {
				when "dot1q:bridge-type != 'TPMR-bridge'" {
					description
						"Applies to non TPMR Bridges";
				}
				if-feature port-and-protocol-based-vlan;
				description 
					"A table that contains mappings from Protocol 
					Templates to Protocol Group Identifiers used for
					Port-and-Protocol-based VLAN Classification. 
					Entries in this table must be persistent over
					power up restart/reboot.";
				leaf template {
					type dot1qtypes:protocol-template-format;
					description
						"The protocol template format type";
					reference
						"IEEE 802.1Q-2014 Clause 12.10.1.7";
				}
				leaf group-id {
					type uint16;
					description
						"The protocol group identifier";
					reference
						"IEEE 802.1Q-2014 Clause 12.10.1.7";
				}
			} // protocol-group-database-contents
			leaf admin-point-to-point {
				type uint16;
				description 
					"For a port running spanning tree, this object 
					represents the administrative point-to-point 
					status of the LAN segment attached to this port,
					using the enumeration values of IEEE Std 802.1AC. 
					A value of forceTrue(1) indicates that this port
					should always be treated as if it is connected to
					a point-to-point link. A value of forceFalse(2)
					indicates that this port should be treated as 
					having a shared media connection. A value of 
					auto(3) indicates that this port is considered to
					have a point-to-point link if it is an Aggregator
					and all of its members are aggregatable, or if 
					the MAC entity is configured for full duplex 
					operation, either through auto-negotiation or by
					management means. Manipulating this object 
					changes the underlying adminPointToPointMAC.
						
					The value of this object MUST be retained across
					reinitializations of the management system.";
				reference
					"IEEE 802.1Q-2014 Clause 6.8.2, 12.4.2";
			}	
			list vid-translations {
				// Need to re-assess and confirm these definitions.
				when "dot1q:bridge-type != 'TPMR-bridge'" {
					description
						"Applies to non TPMR Bridges";
				}
				key "local-vid";
				description 
					"To configure the VID Translation Table (6.9) 
					associated with a Port. This object is not 
					applicable to Ports that do not support a VID
					Translation Table. The default configuration of
					the table has the value of the Relay VID equal to
					the value of the Local VID for all Local VID
					values. If the port supports an Egress VID 
					translation table, the VID Translation 
					Configuration object configures the Local VID to
					Relay VID mapping on ingress only. If an Egress
					VID translation is not supported, the VID 
					Translation Configuration object defines a 
					single bidirectional mapping.";
				leaf local-vid {
					type ieee:vlanid;
					description 
						"The Local VID after translation received at
						the ISS or EISS.";
					reference
						"IEEE 802.1Q-2014 Clause 12.10.1.8, 6.9";
				}
				leaf relay-vid {
					type ieee:vlanid;
					description 
						"The Relay VID received before translation
						received at ISS or EISS.";
					reference
						"IEEE 802.1Q-2014 Clause 12.10.1.8, 6.9";
				}					
			} // vid-translations
			list egress-vid-translations {
				// Need to re-assess and confirm these definitions.
				when "dot1q:bridge-type != 'TPMR-bridge'" {
					description
						"Applies to non TPMR Bridges";
				}
				key "relay-vid";
				description 
					"To configure the Egress VID Translation Table
					(6.9) associated with a Port. This object is not
					applicable to Ports that do not support an Egress
					VID Translation Table. The default configuration
					of the table has the value of the Local VID 
					equal to the value of the Relay VID for all 
					Relay VID values.";
				leaf relay-vid {
					type ieee:vlanid;
					description 
						"The Relay VID received before translation
						received at ISS or EISS.";
					reference
						"IEEE 802.1Q-2014 Clause 12.10.1.9, 6.9";
				}
				leaf local-vid {
					type ieee:vlanid;
					description 
						"The Local VID after translation received at
						the ISS or EISS.";
					reference
						"IEEE 802.1Q-2014 Clause 12.10.1.9, 6.9";
				}					
			} // egress-vid-translations
		} // bridge-port
	} // augment interfaces
	
	augment "/if:interfaces-state/if:interface" {
		when "/if:type = 'ianaif:ethernetCsmacd' or
			  /if:type = 'ianaif:ieee8023adLag'" {
			description
				"Applies when interface is Ethernet port or LAG.";
		}
		description
			"Augment the interface-state model with the Bridge Port";
		container bridge-port-state {
			description 
				"Bridge Port nodes are extensions of the IETF 
				Interfaces model (RFC7223).";		
			leaf protocol-based-vlan-classification {
				when "dot1q:bridge-type != 'TPMR-bridge'" {
					description
						"Applies to non TPMR Bridges";
				}
				if-feature port-and-protocol-based-vlan;
				type boolean;
				description 
					"A boolean indication indicating if 
					Port-and-Prorotocl-based VLAN classification is
					supported on a given Port.";
				reference
					"IEEE 802.1Q-2014 Clause 5.4.1.2";
			}
			leaf max-vid-set-entries {
				when "dot1q:bridge-type != 'TPMR-bridge'" {
					description
						"Applies to non TPMR Bridges";
				}
				if-feature port-and-protocol-based-vlan;
				type uint16;
				description 
					"The maximum number of entries suppored in the 
					VID set on a given Port.";
				reference
					"IEEE 802.1Q-2014 Clause 12.10.1.1.3";
			}
			leaf port-number {
				type dot1qtypes:port-number-type;
				description 
					"The number of the Bridge Port.";
				reference
					"IEEE 802.1Q-2014 Clause 13.25, 12.4.2";
			}
			leaf port-type {
				type identityref {
					base type-of-port;
				}
				description 
					"The port type. Indicates the capabilities of 
					this port.";
				reference
					"IEEE 802.1Q-2014 Clause 12.4.2.1";
				
			}
			leaf address {
				type ieee:mac-address;
				description 
					"The specific MAC address of the individual MAC
					Entity associated with the Port.";
				reference
					"IEEE 802.1Q-2014 Clause 12.4.2, 12.4.2.1.1.3 a)";
			}
			leaf capabilities {
				type uint16;
				description
					"The feature capabilities associated with port";
				reference
					"IEEE 802.1Q-2014 Clause 12.4.2, 12.10.1.1.3 c)";
			}
			leaf type-capabilties {
				type uint16;
				description
					"The type of feature capabilities supported with
					port.";
				reference
					"IEEE 802.1Q-2014 Clause 12.4.2";
			}
			leaf external {
				type boolean;
				description 
					"A boolean indicating whether the port is 
					external. A value of True means the port is
					external. A value of False means the port is 
					internal.";
				reference
					"IEEE 802.1Q-2014 Clause 12.4.2";
			}
			leaf oper-point-to-point {
				type boolean;
				description 
					"For a port running spanning tree, this object 
					represents the operational point-to-point status
					of the LAN segment attached to this port. It 
					indicates whether a port is considered to have a
					point-to-point connection.
					
					If adminPointToPointMAC is set to auto(2), then
					the value of operPointToPointMAC is determined in
					accordance with the specific procedures defined
					for the MAC entity concerned, as defined in IEEE
					Std 802.1AC. The value is determined dynamically;
					that is, it is re-evaluated whenever the value of
					adminPointToPointMAC changes, and whenever the 
					specific procedures defined for the MAC entity 
					evaluate a change in its point-to-point status.";
				reference
					"IEEE 802.1Q-2014 Clause 12.4.2, IEEE 802.1AC";
			}
			container bridge-port-statistics {
				description
					"Container of operational state node information
					associated with the bridge port.";
				leaf delay-exceeded-discards {
					type yang:counter64;
					description 
						"The number of frames discarded by this port
						due to excessive transit delay through the 
						Bridge. It is incremented by both transparent
						and source route Bridges.";
					reference
						"IEEE 802.1Q-2014 Clause 12.6.1.1.3, 8.6.6";
				}
				leaf mtu-exceeded-discards {
					type yang:counter64;
					description 
						"The number of frames discarded by this port
						due to an excessive size. It is incremented 
						by both transparent and source route Bridges.";
					reference
						"IEEE 802.1Q-2014 Clause 12.6.1.1.3 g)";
				}
				leaf frame-rx {
					type yang:counter64;
					description 
						"The number of frames that have been received
						by this port from its segment. Note that a 
						frame received on the interface corresponding
						to this port is only counted by this object
						if and only if it is for a protocol being
						processed by the local bridging function, 
						including Bridge management frames.";
					reference
						"IEEE 802.1Q-2014 Clause 12.6.1.1.3";
				}
				leaf octets-rx {
					type yang:counter64;
					description 
						"The total number of octets in all valid 
						frames received (including BPDUs, frames 
						addressed to the Bridge as an end station, 
						and frames that were submitted to the 
						Forwarding Process).";
					reference
						"IEEE 802.1Q-2014 Clause 12.6.1.1.3";
				}
				leaf frame-tx {
					type yang:counter64;
					description 
						"The number of frames that have been 
						transmitted by this port to its segment. Note
						that a frame transmitted on the interface 
						corresponding to this port is only counted
						by this object if and only if it is for a 
						protocol being processed by the local 
						bridging function, including Bridge
						management frames.";
				}
				leaf octets-tx {
					type yang:counter64;
					description
						"The total number of octets that have been
						transmitted by this port to its segment.";
				}
				leaf discard-inbound {
					type yang:counter64;
					description 
						"Count of received valid frames that were 
						discarded (i.e., filtered) by the Forwarding
						Process.";
					reference
						"IEEE 802.1Q-2014 Clause 12.6.1.1.3";
				}
				leaf forward-outbound {
					type yang:counter64;
					description 
						"The number of frames forwarded to the 
						associated MAC Entity (8.5).";
					reference
						"IEEE 802.1Q-2014 Clause 12.6.1.1.3";
				}
				leaf discard-lack-of-buffers {
					type yang:counter64;
					description 
						"The count of frames that were to be 
						transmitted through the associated Port but 
						were discarded due to lack of buffers.";
					reference
						"IEEE 802.1Q-2014 Clause 12.6.1.1.3";
				}
				leaf discard-transit-delay-exceeded {
					type yang:counter64;
					description 
						"The number of frames discarded by this port
						due to excessive transit delay through the 
						Bridge. It is incremented by both transparent
						and source route Bridges.";
					reference
						"IEEE 802.1Q-2014 Clause 12.6.1.1.3";
				}
				leaf discard-on-error {
					type yang:counter64;
					description 
						"The number of frames that were to be 
						forwarded on the associated MAC but could not
						be transmitted (e.g., frame would be too
						large, 6.5.8).";
					reference
						"IEEE 802.1Q-2014 Clause 12.6.1.1.3";
				}
				leaf discard-on-ingress-filtering {
					when "dot1q:bridge-type != 'TPMR-bridge'" {
						description
							"Applies to non TPMR Bridges";
					}
					if-feature ingress-filtering;
					type yang:counter64;
					description 
						"The number of frames that were discarded as
						a result of Ingress Filtering being enabled.";
					reference
						"IEEE 802.1Q-2014 Clause 12.6.1.1.3";
				}
				leaf discard-ttl-expired {
					when "dot1q:bridge-type != 'TPMR-bridge'" {
						description
							"Applies to non TPMR Bridges";
					}
					if-feature flow-filtering;
					type yang:counter64;
					description 
						"The number of frames discarded because they
						were received with the TTL field expired";
					reference
						"IEEE 802.1Q-2014 Clause 12.6.1.1.3";
				}
			} // bridge-port-statistics
			
			list vlan-statistics {
				when "dot1q:bridge-type != 'TPMR-bridge'" {
					description
						"Applies to non TPMR Bridges";
				}
				key "vid";
				description
					"Per VLAN, per bridge port statistics";
				leaf vid {
					type ieee:vlanid;
					description "The VLAN identifier to which this 
						entry applies.";
				}
				leaf frame-rx {
					type yang:counter64;
					description 
						"The number of frames that have been received
						by this port from its segment. Note that a 
						frame received on the interface corresponding
						to this port is only counted by this object
						if and only if it is for a protocol being
						processed by the local bridging function, 
						including Bridge management frames.";
					reference
						"IEEE 802.1Q-2014 Clause 12.6.1.1.3";
				}
				leaf octets-rx {
					type yang:counter64;
					description 
						"The total number of octets in all valid 
						frames received (including BPDUs, frames 
						addressed to the Bridge as an end station, 
						and frames that were submitted to the 
						Forwarding Process).";
					reference
						"IEEE 802.1Q-2014 Clause 12.6.1.1.3";
				}
				leaf discard-inbound {
					type yang:counter64;
					description 
						"Count of received valid frames that were 
						discarded (i.e., filtered) by the Forwarding
						Process.";
					reference
						"IEEE 802.1Q-2014 Clause 12.6.1.1.3";
				}
				leaf forward-outbound {
					type yang:counter64;
					description 
						"The number of frames forwarded to the 
						associated MAC Entity (8.5).";
					reference
						"IEEE 802.1Q-2014 Clause 12.6.1.1.3";
				}
				leaf discard-lack-of-buffers {
					type yang:counter64;
					description 
						"The count of frames that were to be 
						transmitted through the associated Port but
						were discarded due to lack of buffers.";
					reference
						"IEEE 802.1Q-2014 Clause 12.6.1.1.3";
				}
				leaf discard-transit-delay-exceeded {
					type yang:counter64;
					description 
						"The number of frames discarded by this port
						due to excessive transit delay through the 
						Bridge. It is incremented by both transparent
						and source route Bridges.";
					reference
						"IEEE 802.1Q-2014 Clause 12.6.1.1.3";
				}
				leaf discard-on-error {
					type yang:counter64;
					description 
						"The number of frames that were to be 
						forwarded on the associated MAC but could not
						be transmitted (e.g., frame would be too 
						large, 6.5.8).";
					reference
						"IEEE 802.1Q-2014 Clause 12.6.1.1.3";
				}
				leaf discard-on-ingress-filtering {
					if-feature ingress-filtering;
					type yang:counter64;
					description 
						"The number of frames that were discarded as
						a result of Ingress Filtering being 
						enabled.";
					reference
						"IEEE 802.1Q-2014 Clause 12.6.1.1.3";
				}
				leaf discard-ttl-expired {
					if-feature flow-filtering;
					type yang:counter64;
					description 
						"The number of frames discarded because they
						were received with the TTL field expired";
					reference
						"IEEE 802.1Q-2014 Clause 12.6.1.1.3";
				}	            	
			} // vlan-statistics
		} // bridge-port-state
	} // augment interfaces-state

} // ieee-dot1q-bridge
