module ieee-dot1q-pb {
	
	namespace "urn:ieee:params:xml:ns:yang:ieee-dot1q-pb";
    prefix "dot1q-pb";

	import ieee-dot1q-bridge {
		prefix dot1q; 
	}
	import ieee-dot1q-types { 
		prefix "dot1qtypes"; 
	}
    import ieee-types { 
    	prefix "ieee"; 
    }
    import ietf-interfaces { 
    	prefix "if"; 
    }
    import ietf-system { 
		prefix "system"; 
	}
    
    organization
		"Institute of Electrical and Electronics Engineers";

	contact
	    "Web URL: http://www.ieee802.org/1/
    	
        Working Group Chair: 
    	   Glenn Parsons
    	   glenn.parsons@ericsson.com
     
        Working Group Vice-chair: 
    	   John Messenger
    	   J.L.Messenger@ieee.org
     	
        Chair, Time Sensitive Networking Task Group:
    	   Michael Johas Teener
    	   mikejt@broadcom.com
    	
		Vice-Chair, Time Sensitive Networking Task Group:
	       Janos Farkas
		   janos.farkas@ericsson.com
     	
        Editor: 
    	   Marc Holness
     	   mholness@ciena.com";
		   
	description
	   "This YANG module describes the bridge configuration model
		for Provider Bridges.";   

	revision "2015-09-10" {
	    description
	        "Initial Version.";
	    reference
	        "IEEE 802.1Q-2014, Media Access Control (MAC) Bridges and 
	    	  Virtual Bridged Local Area Networks.";
	}
    
    augment "/if:interfaces/if:interface/dot1q:bridge-port" {
    	description
    		"Augment the interfac model with 802.1Q Bridge Port
    		configuration specific nodes.";
    	list cvid-registration-table {
    		when "/dot1q:bridges/dot1q:bridge/dot1q:component"
    			+ "/dot1q:component-type = 'cVlanComponent' and
      	          /dot1q:bridges/dot1q:bridge/dot1q:component"
    			+ "/dot1q:bridge-port/"
    			+ "dot1q:port-type = 'customer-edge-port'" {
    			description
    				"Applies when the component associated with this
    				interface is a CVLAN component and the port-type
    				is a customer edge port.";
    		}
    		key "cvid";
    		description 
    			"The C-VID Registration Table, provides a mapping 
    			between a C-VID and the service instance represented 
    			by an S-VID selected for that C-VLAN. This table 
    			provides the equivalent functionality of
    			1) Configuring the PVID of the internal CNP on the 
    			   S-VLAN component
    			2) Adding the corresponding PEP on the C-VLAN 
    			   component to the member set of the C-VLAN
    			3) Adding the PEP and/or CEP to the untagged set of 
    			   the C-VLAN (if it is desired that frames forwarded
    			   to that port are transmitted untagged for this 
    			   C-VLAN).";
    		leaf cvid {
    			type ieee:vlanid;
    			description 
        			"Customer VLAN identifiers associated
            		with this bridge port.";
    			reference
    				"IEEE 802.1Q-2014 Clause 12.13.2.1";	
        	}
        	leaf svid {
        		type ieee:vlanid;
        		description 
        			"Service VLAN identifier.";
        		reference
					"IEEE 802.1Q-2014 Clause 12.13.2.1";
        	}
        	leaf untagged-pep {
        		type boolean;
        		description 
        			"A boolean indicating frames for this C-VLAN 
        			should be forwarded untagged through the Provider
        			Edge Port";
        		reference
					"IEEE 802.1Q-2014 Clause 12.13.2.1";
        	}
        	leaf untagged-cep {
        		type boolean;
        		description 
        			"A boolean indicating frames for this C-VLAN 
        			should be forwarded untagged through the Customer
        			Edge Port";
        		reference
					"IEEE 802.1Q-2014 Clause 12.13.2.1";
        	}    		
    	} // cvid-registration-table
    	
    	list service-priority-regeneration-table {
    		when "/system:system/dot1q:bridge/dot1q:component"
    			+ "/dot1q:component-type = 'cVlanComponent' and
      	          /dot1q:bridges/dot1q:bridge/dot1q:component"
    			+ "/dot1q:bridge-port"
    			+ "/dot1q:port-type = 'customer-edge-port'" {
    			description
    				"Applies when the bridge component assocaited with
    				this interface is a CVLAN component and the
    				bridge port type is a customer edge port.";
    		}
    		key "svid";
    		description 
    			"The Service Priority Regeneration Table, which 
    			provides the Priority Regeneration Table (12.6.2) for
    			each internal CNP connected to the C-VLAN component 
    			associated with the CEP.";
    		leaf svid {
        		type ieee:vlanid;
        		description 
        			"Service VLAN identifier.";
        		reference
        			"IEEE 802.1Q-2014 Clause 12.13.2.6";
        	}
    		container priority-regeneration {
    			description
    				"Contains Service Priority Regeneration table
    				nodal information.";
    			reference
    				"IEEE 802.1Q-2014 Clause 12.13.2.6";
				uses dot1qtypes:priority-regeneration-table;
			}
    	} // service-priority-regeneration-table
    	
    	list rcap-internal-interface-table {
    		when "/system:system/dot1q:bridge/dot1q:component"
    			+ "/dot1q:component-type = 'sVlanComponent' and
    	          /dot1q:bridges/dot1q:bridge/dot1q:component"
    			+ "/dot1q:bridge-port"
    			+ "/dot1q:port-type = 'remote-customer-access-port'" {
    			description
    				"Applies when the Bridge component type associated
    				with this interface is an SVLAN component and the
    				bridge port type is a remote customer access port.";
    		}
    		key "external-svid";
    		description 
    			"Designating an external port as a RCAP automatically
    			creates a Port-mapping S-VLAN component associated 
    			with that port. This Port-mapping S-VLAN component 
    			includes one internal PNP.";
    		leaf external-svid {
    			type ieee:vlanid;
    			description 
    				"External Service VLAN identifier.";
    			reference
    				"IEEE 802.1Q-2014 Clause 12.13.3.2";
    		}
    		leaf internal-port-number {
    			type dot1qtypes:port-number-type;
    			description 
    				"The number of the RCAP.";
    			reference
    				"IEEE 802.1Q-2014 Clause 12.13.3.2";
    		}
    		leaf internal-svid {
    			type ieee:vlanid;
    			description 
    				"Internal Service VLAN Identifier (not applicable
    				for a C-tagged RCSI).";
    			reference
    				"IEEE 802.1Q-2014 Clause 12.13.3.2";
    		}
    		leaf internal-interface-type {
    			type enumeration {
					enum port-based-rsci {
						description
							"Port-based RCSI";
					}
					enum c-tagged-rsci {
						description
							"C-tagged RCSI";
					}
					enum pnp {
						description
							"Provider Network Port";
					}
					enum discard {
						description
							"Discard (external S-VID is not associated
							with an internal port).";
					}
				}
    			description 
    				"A value indicating the type of internal 
    				interface associated with the external S-VID.";
    			reference
    				"IEEE 802.1Q-2014 Clause 12.13.3.2";
    		}
    	} // rcap-internal-interface-table
    } // Augment interfaces
} // ieee-dot1q-pb
