module ieee802-dot1q-cfm-mip {
  yang-version 1.1;
  
  namespace "urn:ieee:std:802.1Q:yang:ieee802-dot1q-cfm-mip";
  prefix "cfm-mip";
  
  import ieee802-dot1q-cfm { prefix "dot1q-cfm"; }
  import ieee802-dot1q-cfm-types { prefix "cfm-types"; }

  organization
    "IEEE 802.1 Working Group";

  contact
    "WG-URL: http://www.ieee802.org/1/
    WG-EMail: stds-802-1-L@ieee.org

    Contact: IEEE 802.1 Working Group Chair
    Postal: C/O IEEE 802.1 Working Group
            IEEE Standards Association
            445 Hoes Lane
            P.O. Box 1331
            Piscataway
            NJ 08855-1331
            USA
  
    E-mail: STDS-802-1-L@IEEE.ORG";

  description
    "TBD.";
  
  revision 2018-06-25 {
    description
      "Creation for Task Group review.";
    reference
      "IEEE Std 802.1Q-2018, Bridges and Bridged Networks.";
  }
  
  
  augment "/dot1q-cfm:cfm" {
    description
      "Augment the CFM (base/common) YANG module (ieee802-dot1q-cfm)
      with explicit MIP configuration specific attributes.";
    
    container mips {
      description
        "Maintenance Domain Intermediate Points";
      list mip {
        key "mip-id";
        description
          "A list of MIPs associated with device interface.";
        leaf mip-id {
          type cfm-types:name-key-type;
          description
            "The index into the MIP list which identifies the MIP.";
        }
        leaf md-level {
          type cfm-types:md-level-type;
          default 0;
          description
            "A value indicating the MD Level at which MHFs are to be
            created, and Sender ID TLV transmission by those MHFs is to
            be controlled, for the VLAN to which this entry's objects
            apply.";
          reference
            "12.14.3.1.3c, 12.14.3.2.2b of IEEE Std 802.1Q-2018";
        }
        leaf mhf-creation {
          type cfm-types:mhf-creation-type;
          default "mhf-default";
          description
            "A value indicating if the Management entity can create MHFs
            (MIP Half Function) for this VID at this MD Level. If this
            object has the value mhf-defer, MHF creation for this VLAN
            is controlled by md-mhf-creation. The value of this variable
            is meaningless if the values of md-status is false.";
          reference
            "12.14.3.1.3d of IEEE Std 802.1Q-2018";
          
        }
        leaf id-permission {
          type cfm-types:sender-id-permission-type;
          default "send-id-none";
          description
            "Enumerated value indicating what, if anything, is to be
            included in the Sender ID TLV transmitted by MHFs
            created by the Default Maintenance Domain. If this object
            has the value send-if-defer, Sender ID TLV transmission 
            for this VLAN is controlled by md-id-permission-type.";
          reference
            "12.14.3.1.3e, 12.14.3.2.2a of IEEE Std 802.1Q-2018";
        }
      } // mip
    } // mips
  }
} // ieee802-cfm-mip
