module ieee-dot1q-types {
	
	namespace "urn:ieee:params:xml:ns:yang:ieee-dot1q-types";
    prefix "dot1q-types";
    
    import ietf-interfaces { 
		prefix "if"; 
	}
    
    organization
        "Institute of Electrical and Electronics Engineers";

    contact
    	"Web URL: http://www.ieee802.org/1/
    	
        Working Group Chair: 
    	   Glenn Parsons
    	   glenn.parsons@ericsson.com
     
        Working Group Vice-chair: 
    	   John Messenger
    	   J.L.Messenger@ieee.org
     	
        Chair, Time Sensitive Networking Task Group:
    	   Michael Johas Teener
    	   mikejt@broadcom.com
    	
    	Vice-Chair, Time Sensitive Networking Task Group:
    	   Janos Farkas
		   janos.farkas@ericsson.com
     	
        Editor: 
    	   Marc Holness
     	   mholness@ciena.com";

    description 
    	"Common types used within dot1Q-bridge modules.";

    revision "2015-09-10" {
        description 
        	"Initial revision.";
        reference
            "IEEE 802.1Q-2014, Media Access Control (MAC) Bridges 
        	and Virtual Bridged Local Area Networks.";
    }
	
	/*
     * IEEE 802.1Q Type Definitions.
     */	
    
    typedef component-ref {
    	type string;
    	description 
			"Unique identifier for a particular Bridge component
    		within the system.";
    }
	
	typedef name-type {
		type string { 
			length "0..32";
		}
		description 
			"A text string of up to 32 characters, of locally 
			determined significance.";
	}	
	
	typedef port-number-type {		
		type uint16 { 
			range "1..4095"; 
		}
		description 
			"An Unsigned value assigned to a Port as part of
			a Port Identifier. Valid Port Numbers are in the range 1 
			through 4095.";
	}	
	
	typedef priority-type {
		type uint8 { 
			range "0..7"; 
		}
		description 
			"A range of priorities from 0 to 7 (inclusive).";
	}	
	
	typedef vid-range {
		/*
		 * Defines the type used to represent ranges of VLAN Ids.
		 *
		 * Ideally we would model that as a list of VLAN Ids in YANG,
		 * but the model is easier to use if this is just represented
		 * as a string.
		 *
		 * This type is used to match an ordered list of VLAN Ids, or
		 * contiguous ranges of VLAN Ids. Valid VLAN Ids must be in 
		 * the range 1 to 4094, and included in the list in non 
		 * overlapping ascending order.
		 *
		 * For example, "1, 10-100, 50, 500-1000"
		 *
		 */		
		type string {
			pattern "([0-9]{1,4}(-[0-9]{1,4})?(,[0-9]{1,4}" +
		            "(-[0-9]{1,4})?)*)";
		}
		description 
			"A list of VLAN Ids, or non overlapping VLAN ranges,
            in ascending order, between 1 and 4094";
	}	
	
	typedef pcp-selection-type {
		type enumeration {
			enum 8P0D {
				description
					"8 priorities, 0 discard";
			}
			enum 7P1D {
				description
					"7 priorities, 1 discard";
			}
			enum 6P2D {
				description
					"6 priorities, 2 discards";
			}
			enum 5P3D {
				description
					"5 priorities, 3 discards";
			}
		}
		description 
			"Priority Code Point selection types.";
		reference
			"IEEE 802.1Q-2014 Clause 12.6.2.5.3, 6.9.3";
	}	
	
	typedef protocol-template-format {
		type enumeration {
			enum Ethernet {
				description
					"Ethernet frame format";
			}
			enum rfc1042 {
				description
					"RFC 1042 frame format";
			}
			enum snap8021H {
				description
					"SNAP 802.1H frame format";
			}
			enum snapOther {
				description
					"Other SNAP frame format";
			}
			enum llcOther {
				description
					"Other LLC frame format";
			}
		}
		description 
			"A value representing the frame format to be matched.";
		reference
			"IEEE 802.1Q-2014 Clause 12.10.1.7.1";
	}	
	
	typedef etherType {
		type uint16;
		description 
			"The Ethernet Type (or Length) value.";
		reference
			"IEEE 802.3-2012 Clause 3.2.6";
	}
	
	/*
     * IEEE 802.1Q Bridge Group definitions.
     */	
	
	grouping priority-regeneration-table {
		description 
			"The priority regeneration table.";
		reference
			"IEEE 802.1Q-2014 Clause 6.9.4";
		leaf priority0 {
			type priority-type;
			description
				"Priority 0";
			reference
				"IEEE 802.1Q-2014 Clause 6.9.4, 12.6.2.3";
		}
		leaf priority1 {
			type priority-type;
			description
				"Priority 1";
			reference
				"IEEE 802.1Q-2014 Clause 6.9.4, 12.6.2.3";
		}
		leaf priority2 {
			type priority-type;
			description
				"Priority 2";
			reference
				"IEEE 802.1Q-2014 Clause 6.9.4, 12.6.2.3";
		}
		leaf priority3 {
			type priority-type;
			description
				"Priority 3";
			reference
				"IEEE 802.1Q-2014 Clause 6.9.4, 12.6.2.3";
		}
		leaf priority4 {
			type priority-type;
			description
				"Priority 4";
			reference
				"IEEE 802.1Q-2014 Clause 6.9.4, 12.6.2.3";
		}
		leaf priority5 {
			type priority-type;
			description
				"Priority 5";
			reference
				"IEEE 802.1Q-2014 Clause 6.9.4, 12.6.2.3";
		}
		leaf priority6 {
			type priority-type;
			description
				"Priority 6";
			reference
				"IEEE 802.1Q-2014 Clause 6.9.4, 12.6.2.3";
		}
		leaf priority7 {
			type priority-type;
			description
				"Priority 7";
			reference
				"IEEE 802.1Q-2014 Clause 6.9.4, 12.6.2.3";
		}
	} // priority-regeneration-table
	
	grouping pcpDecodingTable {
		description 
			"The Priority Code Point decoding table.";
		reference
			"IEEE 802.1Q-2014 Clause 6.9.3";
		container pcp0 {
			description
				"Priority code point 0 value";
			leaf priority {
				type priority-type;
				description
					"Priority associated with pcp";
				reference
					"IEEE 802.1Q-2014 Clause 12.6.2.7, 6.9.3";
			}
			leaf drop-eligible {
				type boolean;
				description
					"Drop eligible value for pcp0";
				reference
					"IEEE 802.1Q-2014 Clause 12.6.2.7, 6.9.3";
			}
		}
		container pcp1 {
			description
				"Priority code point 1 value";
			leaf priority {
				type priority-type;
				description
					"Priority associated with pcp";
				reference
					"IEEE 802.1Q-2014 Clause 12.6.2.7, 6.9.3";
			}
			leaf drop-eligible {
				type boolean;
				description
					"Drop eligible value for pcp1";
				reference
					"IEEE 802.1Q-2014 Clause 12.6.2.7, 6.9.3";
			}
		}
		container pcp2 {
			description
				"Priority code point 2 value";
			leaf priority {
				type priority-type;
				description
					"Priority associated with pcp";
				reference
					"IEEE 802.1Q-2014 Clause 12.6.2.7, 6.9.3";
			}
			leaf drop-eligible {
				type boolean;
				description
					"Drop eligible value for pcp2";
				reference
					"IEEE 802.1Q-2014 Clause 12.6.2.7, 6.9.3";
			}
		}
		container pcp3 {
			description
				"Priority code point 3 value";
			leaf priority {
				type priority-type;
				description
					"Priority associated with pcp";
				reference
					"IEEE 802.1Q-2014 Clause 12.6.2.7, 6.9.3";
			}
			leaf drop-eligible {
				type boolean;
				description
					"Drop eligible value for pcp3";
				reference
					"IEEE 802.1Q-2014 Clause 12.6.2.7, 6.9.3";
			}
		}
		container pcp4 {
			description
				"Priority code point 4 value";
			leaf priority {
				type priority-type;
				description
					"Priority associated with pcp";
				reference
					"IEEE 802.1Q-2014 Clause 12.6.2.7, 6.9.3";
			}
			leaf drop-eligible {
				type boolean;
				description
					"Drop eligible value for pcp4";
				reference
					"IEEE 802.1Q-2014 Clause 12.6.2.7, 6.9.3";
			}
		}
		container pcp5 {
			description
				"Priority code point 5 value";
			leaf priority {
				type priority-type;
				description
					"Priority associated with pcp";
				reference
					"IEEE 802.1Q-2014 Clause 12.6.2.7, 6.9.3";
			}
			leaf drop-eligible {
				type boolean;
				description
					"Drop eligible value for pcp5";
				reference
					"IEEE 802.1Q-2014 Clause 12.6.2.7, 6.9.3";
			}
		}
		container pcp6 {
			description
				"Priority code point 6 value";
			leaf priority {
				type priority-type;
				description
					"Priority associated with pcp";
				reference
					"IEEE 802.1Q-2014 Clause 12.6.2.7, 6.9.3";
			}
			leaf drop-eligible {
				type boolean;
				description
					"Drop eligible value for pcp6";
				reference
					"IEEE 802.1Q-2014 Clause 12.6.2.7, 6.9.3";
			}
		}
		container pcp7 {
			description
				"Priority code point 7 value";
			leaf priority {
				type priority-type;
				description
					"Priority associated with pcp";
				reference
					"IEEE 802.1Q-2014 Clause 12.6.2.7, 6.9.3";
			}
			leaf drop-eligible {
				type boolean;
				description
					"Drop eligible value for pcp7";
				reference
					"IEEE 802.1Q-2014 Clause 12.6.2.7, 6.9.3";
			}
		}
	} // pcpDecodingTable
	
	grouping pcp-encoding-table {
		description 
			"The Priority Code Point encoding table.";
		reference
			"IEEE 802.1Q-2014 Clause 12.6.2.9, 6.9.3";
		container priority0 {
			description
				"Priority 0 PCP encoding table entry";
			leaf pcp-dei-false {
				type priority-type;
				description
					"PCP value for priority 0 when DEI false";
				reference
					"IEEE 802.1Q-2014 Clause 12.6.2.9, 6.9.3";
			}
			leaf pcp-dei-true {
				type priority-type;
				description
					"PCP value for priority 0 when DEI true";
				reference
					"IEEE 802.1Q-2014 Clause 12.6.2.9, 6.9.3";
			}
		}
		container priority1 {
			description
				"Priority 1 PCP encoding table entry";
			leaf pcp-dei-false {
				type priority-type;
				description
					"PCP value for priority 1 when DEI false";
				reference
					"IEEE 802.1Q-2014 Clause 12.6.2.9, 6.9.3";
			}
			leaf pcp-dei-true {
				type priority-type;
				description
					"PCP value for priority 1 when DEI true";
				reference
					"IEEE 802.1Q-2014 Clause 12.6.2.9, 6.9.3";
			}
		}
		container priority2 {
			description
				"Priority 2 PCP encoding table entry";
			leaf pcp-dei-false {
				type priority-type;
				description
					"PCP value for priority 2 when DEI false";
				reference
					"IEEE 802.1Q-2014 Clause 12.6.2.9, 6.9.3";
			}
			leaf pcp-dei-true {
				type priority-type;
				description
					"PCP value for priority 2 when DEI true";
				reference
					"IEEE 802.1Q-2014 Clause 12.6.2.9, 6.9.3";
			}
		}
		container priority3 {
			description
				"Priority 3 PCP encoding table entry";
			leaf pcp-dei-false {
				type priority-type;
				description
					"PCP value for priority 3 when DEI false";
				reference
					"IEEE 802.1Q-2014 Clause 12.6.2.9, 6.9.3";
			}
			leaf pcp-dei-true {
				type priority-type;
				description
					"PCP value for priority 3 when DEI true";
				reference
					"IEEE 802.1Q-2014 Clause 12.6.2.9, 6.9.3";
			}
		}
		container priority4 {
			description
				"Priority 4 PCP encoding table entry";
			leaf pcp-dei-false {
				type priority-type;
				description
					"PCP value for priority 4 when DEI false";
				reference
					"IEEE 802.1Q-2014 Clause 12.6.2.9, 6.9.3";
			}
			leaf pcp-dei-true {
				type priority-type;
				description
					"PCP value for priority 4 when DEI true";
				reference
					"IEEE 802.1Q-2014 Clause 12.6.2.9, 6.9.3";
			}
		}
		container priority5 {
			description
				"Priority 5 PCP encoding table entry";
			leaf pcp-dei-false {
				type priority-type;
				description
					"PCP value for priority 5 when DEI false";
				reference
					"IEEE 802.1Q-2014 Clause 12.6.2.9, 6.9.3";
			}
			leaf pcp-dei-true {
				type priority-type;
				description
					"PCP value for priority 5 when DEI true";
				reference
					"IEEE 802.1Q-2014 Clause 12.6.2.9, 6.9.3";
			}
		}
		container priority6 {
			description
				"Priority 6 PCP encoding table entry";
			leaf pcp-dei-false {
				type priority-type;
				description
					"PCP value for priority 6 when DEI false";
				reference
					"IEEE 802.1Q-2014 Clause 12.6.2.9, 6.9.3";
			}
			leaf pcp-dei-true {
				type priority-type;
				description
					"PCP value for priority 6 when DEI true";
				reference
					"IEEE 802.1Q-2014 Clause 12.6.2.9, 6.9.3";
			}
		}
		container priority7 {
			description
				"Priority 7 PCP encoding table entry";
			leaf pcp-dei-false {
				type priority-type;
				description
					"PCP value for priority 7 when DEI false";
				reference
					"IEEE 802.1Q-2014 Clause 12.6.2.9, 6.9.3";
			}
			leaf pcp-dei-true {
				type priority-type;
				description
					"PCP value for priority 7 when DEI true";
				reference
					"IEEE 802.1Q-2014 Clause 12.6.2.9, 6.9.3";
			}
		}
	} // pcp-encoding-table	
	
	grouping service-access-priority-table {
		description 
			"The Service Access Priority Table.";
		reference
			"IEEE 802.1Q-2014 Clause 6.13.1, 12.6.2.17";
		leaf priority0 {
			type priority-type;
			description
				"Service access priority value for priority 0";
			reference
				"IEEE 802.1Q-2014 Clause 6.13.1, 12.6.2.17";
		}
		leaf priority1 {
			type priority-type;
			description
				"Service access priority value for priority 1";
			reference
				"IEEE 802.1Q-2014 Clause 6.13.1, 12.6.2.17";
		}
		leaf priority2 {
			type priority-type;
			description
				"Service access priority value for priority 2";
			reference
				"IEEE 802.1Q-2014 Clause 6.13.1, 12.6.2.17";
		}
		leaf priority3 {
			type priority-type;
			description
				"Service access priority value for priority 3";
			reference
				"IEEE 802.1Q-2014 Clause 6.13.1, 12.6.2.17";
		}
		leaf priority4 {
			type priority-type;
			description
				"Service access priority value for priority 4";
			reference
				"IEEE 802.1Q-2014 Clause 6.13.1, 12.6.2.17";
		}
		leaf priority5 {
			type priority-type;
			description
				"Service access priority value for priority 5";
			reference
				"IEEE 802.1Q-2014 Clause 6.13.1, 12.6.2.17";
		}
		leaf priority6 {
			type priority-type;
			description
				"Service access priority value for priority 6";
			reference
				"IEEE 802.1Q-2014 Clause 6.13.1, 12.6.2.17";
		}
		leaf priority7 {
			type priority-type;
			description
				"Service access priority value for priority 7";
			reference
				"IEEE 802.1Q-2014 Clause 6.13.1, 12.6.2.17";
		}
	} // service-access-priority-table
	
	grouping traffic-class-table {
		description
			"The Traffic Class Table models the operations that can
			be performed on, or inquire about, the current contents
			of the Traffic Class Table (8.6.6) for a given Port.";
		reference
			"IEEE 802.1Q-2014 Clause 12.6.3, 8.6.6";		
		// To be confirmed
		list tc-entries {
			key "priority";
			description
				"The priority index into the traffic class table.";
			leaf priority {
				type priority-type;
				description
					"The priority of the traffic class entry.";
				reference
					"IEEE 802.1Q-2014 Clause 8.6.6";
			}
			list available-TC {
				key "traffic-class";
				description
					"The traffic class index associated with a given
					priority within the traffic class table.";
				reference
					"IEEE 802.1Q-2014 Clause 8.6.6";
				leaf traffic-class {
					type uint8 {
						range "1..8";
					}
					description
						"The traffic class index associated with a
						given traffic class entry.";
					reference
						"IEEE 802.1Q-2014 Clause 8.6.6";
				}
				leaf num-tc {
					type priority-type;
					description
						"The available number of traffic classes.";
					reference
						"IEEE 802.1Q-2014 Clause 8.6.6";					
				}
			}
		}
	} // traffic-class-table
	
	grouping port-map {
		description 
			"A set of control indicators, one for each Port.";
		reference
			"IEEE 802.1Q-2014 Clause 8.8.1, 8.8.2";
		list port-map {
			key "port-number";
			description
				"The list of entries composing the port map.";
			leaf port-number {
				//type port-number-type;
				type if:interface-ref;
				description
					"The interface port reference associated with 
					this map.";
				reference
					"IEEE 802.1Q-2014 Clause 8.8.1";
			}
			leaf map {
				// Need to confirm this
				type enumeration {
					enum forward {
						description
							"Forwarded, independently of any dynamic
							filtering information held by the FDB.";
					}
					enum filter {
						description
							"Filtered, independently of any dynamic
							filtering information.";
					}
					enum forward-filter {
						description
							"Forwarded or filtered on the basis of 
							dynamic filtering information, or on the 
							basis of the default Group filtering 
							behavior for the outbound Port (8.8.6)
							if no dynamic filtering information is 
							present specifically for the MAC address.";
					}
				}
				description
					"containing a control element for each outbound
					Port, specifying that a frame with a destination 
					MAC address, and in the case of VLAN Bridge 
					components, VID that meets this specification.";
				reference
					"IEEE 802.1Q-2014 Clause 8.8.1";
			}
		}
	} // port-map
}
