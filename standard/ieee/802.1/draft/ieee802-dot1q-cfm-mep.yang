module ieee802-dot1q-cfm-mep {
  yang-version 1.1;
  
  namespace "urn:ieee:std:802.1Q:yang:ieee802-cfm-mep";
  prefix "cfm-mep";
  
  import ieee802-dot1q-cfm { prefix "dot1q-cfm"; }
  import ieee802-dot1q-types { prefix "dot1q-types"; }
  import ieee802-types { prefix "ieee"; }
  import ietf-yang-types { prefix "yang"; }
  import ieee802-dot1q-cfm-types { prefix "cfm-types"; }

  organization
    "IEEE 802.1 Working Group";

  contact
    "WG-URL: http://www.ieee802.org/1/
    WG-EMail: stds-802-1-L@ieee.org

    Contact: IEEE 802.1 Working Group Chair
    Postal: C/O IEEE 802.1 Working Group
            IEEE Standards Association
            445 Hoes Lane
            P.O. Box 1331
            Piscataway
            NJ 08855-1331
            USA
  
    E-mail: STDS-802-1-L@IEEE.ORG";

  description
    "TBD.";
  
  revision 2018-04-10 {
    description
      "Initial creation for Task Group review.";
    reference
      "IEEE Std 802.1Q-2018, Bridges and Bridged Networks.";
  }
  
  grouping meps {
    description
      "Grouping of MEPs and MEP attributes.";
    list mep {
      key "mep-id";
      description 
        "A list of local Maintenance association End Points (MEPs).
        A MEP is an actively managed CFM entity, associated with
        a specific DoSAP of a service instance, which can
        generate and receive CFM PDUs and track any responses.
        It is an end point of a single Maintenance Association
        (MA) and is an end point of a separate Maintenance
        Entity for each of the other MEPs in the same MA.";
      leaf mep-id {
        type leafref {
          path '/dot1q-cfm:cfm/dot1q-cfm:maintenance-domains'
            + '/dot1q-cfm:maintenance-domain'
            + '[md-id = current()/../../md-name]'
            + '/dot1q-cfm:maintenance-association'
            + '[ma-id = current()/../../ma-name]'
            + '/dot1q-cfm:maintenance-association-mep-list'
            + '/dot1q-cfm:mep-id';
        }
        description
          "Integer that is unique among all the MEPs in the
          same Maintenance Association.";
        reference
          "3.114, 12.14.7, 19.2 of IEEE Std 802.1Q-2018";
      }
      leaf direction {
        type cfm-types:mp-direction-type;
        description
          "The direction in which the MEP faces on the Bridge
          Port. Example, up or down.";
        reference
          "12.14.7.1.3c, 19.2 of IEEE Std 802.1Q-2018";
      }
      leaf primary-vid {
        type uint32 {
          range "0..16777215";
        }
        default 0;
        description
          "An integer indicating the Primary VID of the MEP. It
          is always one of the VIDs assigned to the MEPs MA. A
          value of 0 indicates that either the Primary VID is
          that of the MEPs MA, or that the MEPs MA is 
          associated with no VID.";
        reference
          "12.14.7.1.3d of IEEE Std 802.1Q-2018"; 
      }
      leaf admin-state {
        type boolean;
        default "false";
        description
          "The administrative state of the MEP. TRUE indicates
          that the MEP is to functional normally, and FALSE
          indicates that it is to cease functioning.";
        reference
          "12.14.7.1.3e, 20.9.1 of IEEE Std 802.1Q-2018";
      }
      leaf fng-state {
        type cfm-types:fng-state-type;
        default "fng-reset";
        config false;
        description
          "The current state of the MEP Fault Notification 
          Generator state machine.";
        reference
          "12.14.7.1.3f, 20.35 of IEEE Std 802.1Q-2018";
      }
      leaf ccm-ltm-priority {
        type dot1q-types:priority-type;
        description
          "The priority value for CCMs and LTMs transmitted by
          the MEP. The default value is the highest priority 
          allowed to pass through the Bridge Port for any of
          the MEPs VID(s).";
        reference
          "12.14.7.1.3h of IEEE Std 802.1Q-2018";
      }
      leaf mac-address {
        type ieee:mac-address;
        config false;
        description
          "The MAC address of the MEP.";
        reference
          "12.14.7.1.3i, 19.4 of IEEE Std 802.1Q-2018";
      }
      leaf fault-alarm-address {
        type cfm-types:fault-alarm-address-type;
        default "not-specified";
        description
          "A value indicating whether Fault Alarms are to be 
          transmitted or not. The default is not specified, 
          which implies that the disposition of the fault-alarm
          used by the MD should be used.";
        reference
          "3.122, 12.14.7.1.3j of IEEE Std 802.1Q-2018";
      }
      leaf lowest-priority-defect {
        type cfm-types:lowest-alarm-priority-type;
        default "mac-remote-error-xcon";
        description
          "The lowest priority defect that is allowed to
          generate fault alarms.";
        reference
          "12.14.7.1.3k, 20.9.5 of IEEE Std 802.1Q-2018";
      }
      leaf fng-alarm-time {
        type yang:zero-based-counter32 {
          range "250..1000";
        }
        units deciseconds;
        default 250;
        description
          "The time that defect must be present before a Fault
          Alarm is issued.";
        reference
          "12.14.7.1.3l, 20.35.3 of IEEE Std 802.1Q-2018";
      }
      leaf fng-reset-time {
        type yang:zero-based-counter32 {
          range "250..1000";
        }
        units deciseconds;
        default 1000;
        description
          "The time that defects must be absent before 
          resetting a Fault Alarm.";
        reference
          "12.14.7.1.3m, 20.35.4 of IEEE Std 802.1Q-2018";
      }
      leaf highest-priority-defect {
        type cfm-types:highest-defect-priority-type;
        config false;
        description
          "The highest priority defect that has been present
          sicne the MEPs Fault Notification Generator state
          machine was last in the FNG_RESET state.";
        reference
          "12.14.7.1.3n, 20.35.9 of IEEE Std 802.1Q-2018";
      }
      leaf defects {
        type cfm-types:mep-defects-type;
        config false;
        description
          "Vector of boolean error conditions";
        reference
          "12.14.7.1.3o-s, 20.21.3,
          20.23.3, 20.35.5, 20.35.6, 20.35.7 of IEEE Std 802.1Q-2018";
      }
      leaf error-ccm-last-failure {
        type string {
          length "1..2000";
        }
        config false;
        description
          "The last received CCM that triggered a def-error-ccm
          fault.";
        reference
          "12.14.7.1.3t, 20.21.2 of IEEE Std 802.1Q-2018";
      }
      leaf xcon-ccm-last-failure {
        type string {
          length "1..2000";
        }
        config false;
        description
          "The last received CCM that triggered a def-xcon-ccm
          fault.";
        reference
          "12.14.7.1.3u, 20.23.2 of IEEE Std 802.1Q-2018";
      }
      
      list mep-db {
        key rmep-id;
        description
          "The MEP CCM Database. A database, maintained by every 
          MEP, that maintains received information about other MEPs
          in the Maintenance Domain.";
        leaf rmep-id {
          type leafref {
            path '/dot1q-cfm:cfm/dot1q-cfm:maintenance-domains'
              + '/dot1q-cfm:maintenance-domain'
              + '[md-id = current()/../../md-name]'
              + '/dot1q-cfm:maintenance-association'
              + '[ma-id = current()/../../ma-name]'
              + '/dot1q-cfm:maintenance-association-mep-list'
              + '/dot1q-cfm:mep-id';
          }
          description
            "Maintenance association Endpoint Identifier of a
            remote MEP whose information from the MEP Database
            is to be returned.";
          reference
            "12.14.7.6.2b of IEEE Std 802.1Q-2018";
        }
        leaf rmep-state {
          type cfm-types:remote-mep-state-type;
          config false;
          description 
            "The operational state of the remote MEP  state
            machine";
          reference
            "12.14.7.6.3b, 20.20 of IEEE Std 802.1Q-2018";
        }
        leaf rmep-failed-ok-time {
          type yang:zero-based-counter32;
          units seconds;
          config false;
          description
            "The time (SysUpTime) at which the Remote MEP state
            machine last entered either the RMEP_FAILED or
            RMEP_OK state";
          reference
            "12.14.7.6.3c of IEEE Std 802.1Q-2018";
        }
        leaf mac-address {
          type ieee:mac-address;
          config false;
          description
            "The MAC address of the remote MEP.";
          reference
            "12.14.7.6.3d, 20.19.7 of IEEE Std 802.1Q-2018";
        }
        leaf rdi {
          type boolean;
          config false;
          description
            "State of the RDI bit in the last received CCM
            (true for RDI=1), or false if none has been 
            received.";
          reference
            "12.14.7.6.3e, 20.19.2 of IEEE Std 802.1Q-2018";
        }
        leaf port-status-tlv {
          type cfm-types:port-status-tlv-value;
          default "no-port-state-tlv";
          config false;
          description
            "An enumerated value of the Port status TLV 
            received in the last CCM from the remote MEP or 
            the default value no-port-state-tlv indicating
            either no CCM has been received, or that no port
            status TLV was received in the last CCM.";
          reference
            "12.14.7.6.3f, 20.19.3 of IEEE Std 802.1Q-2018";
        }
        leaf interface-status-tlv {
          type cfm-types:interface-status-tlv-value;
          default "is-no-interface-status-tlv";
          config false;
          description
            "An enumerated value of the Interface status TLV
            received in the last CCM from the remote MEP or the
            default value is-no-interface-status-tlv indicating
            either no CCM has been received, or that no 
            interface status TLV was received in the last 
            CCM.";
          reference
            "12.14.7.6.3g, 20.19.4 of IEEE Std 802.1Q-2018";
        }
        leaf chassis-id-subtype {
          type cfm-types:lldp-chassis-id-subtype;
          config false;
          description
            "This object specifies the format of the Chassis ID
            received in the last CCM.";
          reference
            "12.14.7.6.3h, 21.5.3.2 of IEEE Std 802.1Q-2018";
        }
        leaf chassis-id {
          type cfm-types:lldp-chassis-id;
          config false;
          description
            "The Chassis ID. The format of this object is
            determined by the value of the 
            ltr-chassis-id-subtype object.";
          reference
            "12.14.7.6.3h, 21.5.3.3 of IEEE Std 802.1Q-2018";
        }
        leaf man-address-domain {
          type cfm-types:transport-service-domain;
          config false;
          description
            "The transport-service-domain that identifies the
            type and format of the related mep-db-man-address
            object, used to access the YANG agent of the system
            transmitting the CCM. Received in the CCM Sender ID
            TLV from that system.
            
            The value zeroDotZero (from RFC2578) indicates no
            management address was present in the LTR, in which
            case the related mep-db-man-address object MUST
            have a zero-length OCTET STRING as a value.";
          reference
            "12.14.7.6.3h, 21.5.3.5,
            21.6.7 of IEEE Std 802.1Q-2018";
        }
        leaf man-address {
          type cfm-types:transport-service-address;
          config false;
          description
            "The transport-service-address that can be used to 
            access the YANG agent of the system transmitting
            the CCM, received in the CCM Sender ID TLV from
            that system. If the related 
            mep-db-man-address-domain object contains the 
            value zeroDotZero, this object mep-db-man-address
            MUST have a zero-length OCTET STRING as a value.";
          reference
            "12.14.7.6.3h, 21.5.3.7,
            21.6.7 of IEEE Std 802.1Q-2018";
        }
        leaf rmep-is-active {
          type boolean;
          description
            "A Boolean value statign if the remote MEP is 
            active.";
          reference
            "12.14.7.1.3ae";
        }
      } // mep-db
      
      container continuity-check {
        description
          "Continuity check protocol";
        leaf ccm-enabled {
          type boolean;
          default "false";
          description
            "Indicates whether the MEP can generate CCMs. If 
            TRUE, the MEP will generate CCM PDUs.";
          reference
            "12.14.7.1.3g, 20.10.1 of IEEE Std 802.1Q-2018";
        }
        leaf priority {
          type dot1q-types:priority-type;
          description
            "The priority value for CCMs and LTMs transmitted by
            the MEP. The default value is the highest priority 
            allowed to pass through the Bridge Port for any of
            the MEPs VID(s).";
          reference
            "12.14.7.1.3h of IEEE Std 802.1Q-2018";
        }
        leaf ccm-interval {
          type cfm-types:cfm-interval-type;
          description
            "The interval between CCM transmissions to be used by all
            MEPs in the Maintenance Association.";
          reference
            "12.14.6.1.3e of IEEE Std 802.1Q-2018";
        }
      } // continuity-check
      
      container loopback {
        description
          "Loopback protocol";
        leaf status {
          type boolean;
          default "false";
          description
            "A Boolean flag set to TRUE by the MEP Loopback
            Initiator state machine or YANG network configuration
            manager to indicate that another LBM is being 
            transmitted. Reset to FALSE by the MEP Loopback
            initiator state machine.";
          reference
            "20.32, Figure 20-11 of IEEE Std 802.1Q-2018";
        }
        leaf interval {
          type cfm-types:cfm-interval-type;
          default 1sec;
          description
            "The interval between LBM transmissions to be used by all
            MEPs in the Maintenance Association.";
        }
        leaf dest-mac-address {
          type ieee:mac-address;
          description
            "The target MAC Address field to be transmitted.
            A unicast destination MAC address. This address
            is used if node mep-transmit-lbm-dest-is-mep-id
            is FALSE.";
          reference
            "12.14.7.3.2b of IEEE Std 802.1Q-2018";
        }
        leaf dest-mep-id {
          type cfm-types:mep-id-or-zero-type;
          description
            "The identifier of a remote MEP in the same MA to
            which the LBM is to be sent. This address
            is used if node mep-transmit-lbm-dest-is-mep-id
            is TRUE.";
          reference
            "12.14.7.3.2b of IEEE Std 802.1Q-2018";
        }
        leaf dest-is-mep-id {
          type boolean;
          default "false";
          description
            "TRUE indicates that MEP ID of the target MEP is used
            for Loopback transmissions. FALSE indicates that
            unicast destination MAC address of the target MEP is
            used for Loopback transmissions.";
          reference
            "12.14.7.3.2b of IEEE Std 802.1Q-2018";
        }
        leaf message-count {
          type uint32 {
            range "1..1024";
          }
          default 1;
          description
            "The number of Loopback messages to be transmitted.";
          reference
            "12.14.7.3.2c of IEEE Std 802.1Q-2018";
        }
        leaf data-tlv {
          type cfm-types:lbm-data-tlv-type;
          description
            "An arbitrary amount of data to be included in the
            Data TLV, if the Data TLV is selected to be sent. The
            intent is to be able to fill the frame carrying the
            CFM PDU to its maximum length.";
          reference
            "12.14.7.3.2d of IEEE Std 802.1Q-2018";
        }
        leaf priority {
          type dot1q-types:priority-type;
          description
            "Priority. 3 bit value to be used in the VLAN tag, if
            present in the transmitted frame. The default value
            should be the CCM priority.";
          reference
            "12.14.7.3.2e of IEEE Std 802.1Q-2018";
        }
        leaf vlan-drop-eligible {
          type boolean;
          default "false";
          description
            "Drop eligible bit value to be used in the VLAN tag,
            if present in the transmitted frame";
          reference
            "12.14.7.3.2e of IEEE Std 802.1Q-2018";
        }
        leaf result-ok {
          type boolean;
          default "true";
          config false;
          description
            "Indicates the result of the operation:
               TRUE - The LBM will be (or has been) sent.
               FALSE - The LBM will not be sent.";
          reference
            "12.14.7.3.3a of IEEE Std 802.1Q-2018";
        }
        leaf seq-number {
          type cfm-types:seq-number-type;
          config false;
          description
            "The Loopback transaction identifier
            (mep-next-lbm-trans-id) of the first LBM (to be) 
            sent. The value returned is undefined if 
            mep-transmit-lbm-result-ok is FALSE.";
          reference
            "12.14.7.3.3b of IEEE Std 802.1Q-2018";
        }
        leaf next-lbm-trans-id {
          type cfm-types:seq-number-type;
          config false;
          description
            "Next sequence number identifier to be sent in a
            Loopback message. This sequence number can be zero
            since it can wrap around.";
          reference
            "12.14.7.1.3x, 20.28.2 of IEEE Std 802.1Q-2018";
        }
      } // loopback
      
      container linktrace {
        description
          "Linktrace protocol";
        leaf status {
          type boolean;
          default "false";
          description
            "A Boolean flag set to TRUE by the Bridge Port to 
            indicate that another LTM may be transmitted. Reset
            to FALSE by the MEP Linktrace initiator state 
            machine.";
          reference
            "20.49, Figure 20-17 of IEEE Std 802.1Q-2018";
        }
        leaf interval {
          type cfm-types:cfm-interval-type;
          default 1sec;
          description
            "The interval between LTM transmissions to be used by all
            MEPs in the Maintenance Association.";
        }
        leaf priority {
          type dot1q-types:priority-type;
          description
            "The priority value for CCMs and LTMs transmitted by
            the MEP. The default value is the highest priority 
            allowed to pass through the Bridge Port for any of
            the MEPs VID(s).";
          reference
            "12.14.7.1.3h of IEEE Std 802.1Q-2018";
        }
        leaf flags {
          type cfm-types:mep-tx-ltm-flags-type;
          default use-fdb-only;
          description
            "The flags field for the LTMs transmitted by the 
            MEP.";
          reference
            "12.14.7.4.2b, 20.42.1 of IEEE Std 802.1Q-2018";
          
        }
        leaf target-mac-address {
          type ieee:mac-address;
          description
            "The target MAC address field to be transmitted. A
            unicast MAC address. This address will be used if the
            value of mep-transmit-ltm-target-is-mep-id is FALSE.";
          reference
            "12.14.7.4.2c of IEEE Std 802.1Q-2018";
        }
        leaf target-mep-id {
          type cfm-types:mep-id-or-zero-type;
          description
            "The target MAC address field to be transmitted. The
            MEP identifier of another MEP in the same MA. This
            address will be used if the value of 
            mep-transmit-ltm-target-is-mep-id is TRUE.";
          reference
            "12.14.7.4.2c of IEEE Std 802.1Q-2018";
        }
        leaf target-is-mep-id {
          type boolean;
          default "false";
          description
            "TRUE indicates that MEP id of the target MEP is used
            for Linktrace transmission. FALSE indicates that
            unicast destination MAC address of the target MEP is
            used for LinkTrace transmission.";
          reference
            "12.14.7.4.2c of IEEE Std 802.1Q-2018";
        }
        leaf ttl {
          type uint32 {
            range "0..255";
          }
          default 64;
          description
            "The LTM TTL field. Indicates the number of hops 
            remaining to the LTM. Decremented by 1 by each
            Linktrace Responder that handles the LTM. The value
            returned in the LTR is one less than that received in
            the LTM. If the LTM TTL is 0 or 1, the LTM is not
            forwarded to the next hop, and if 0, no LTR is 
            generated.";
          reference
            "12.14.7.4.2d, 21.8.4 of IEEE Std 802.1Q-2018";
        }
        leaf result {
          type boolean;
          default "true";
          config false;
          description
            "Indicates the result of the operation:
               TRUE - The Linktrace message will be (or has been) 
                      sent.
               FALSE - The Linktrace message will not be sent.";
          reference
            "12.14.7.4.3a of IEEE Std 802.1Q-2018";
        }
        leaf seq-number {
          type cfm-types:seq-number-type;
          config false;
          description
            "The LTM transaction identifier 
            (mep-ltm-next-seq-number) of the LTM sent. The value
            returned is undefined if mep-transmit-ltm-result is 
            FALSE.";
          reference
            "12.14.7.4.3b of IEEE Std 802.1Q-2018";
        }
        leaf egress-identifier {
          type string {
            length "8";
          }
          config false;
          description
            "Identifies the MEP Linktrace Initiator that is 
            originating, or the Linktrace Responder that is
            forwarding, this LTM.
            
            The low-order six octets contain a 48-bit IEEE MAC
            address unique to the system in which the MEP 
            Linktrace Initiator or Linktrace Responder resides.
            The high-order two octets contain a value sufficient
            to uniquely identify the MEP Linktrace Initiator or 
            Linktrace Responder within that system.
            
            For most Bridges, the address of any MAC attached to
            the Bridge will suffice for the low-order six octets,
            and 0 for the high-order octets. In some situations,
            e.g., if multiple virtual Bridges utilizing emulated
            LANs are implemented in a single physical system, the
            high-order two octets can be used to differentiate
            among the transmitting entities.
            
            The value returned is undefined if 
            mep-transmit-ltm-result is FALSE.";
          reference
            "12.14.7.4.3c of IEEE Std 802.1Q-2018";
        }
        leaf next-seq-number {
          type cfm-types:seq-number-type;
          config false;
          description
            "Next transaction identifier to be sent in a 
            LinkTrace message.This sequence number can be zero
            since it can wrap around.";
          reference
            "12.14.7.1.3ab, 20.41.1 of IEEE Std 802.1Q-2018";
        }
      } // linktrace
      
      container stats {
        config false;
        description
          "Contains the counters associated with the MEP.";
        leaf mep-ccm-sequence-errors {
          type yang:counter64;
          description
            "The total number of out-of-sequence CCMs received
            from all remote MEPs.";
          reference
            "12.14.7.1.3v, 20.16.12 of IEEE Std 802.1Q-2018";
        }
        leaf mep-ccms-sent {
          type yang:counter64;
          description
            "Total number of CCMs transmitted";
          reference
            "12.14.7.1.3w, 20.10.2 of IEEE Std 802.1Q-2018";
        }
        leaf mep-lbr-in {
          type yang:counter64;
          description
            "Total number of valid, in-order Loopback Replies
            received.";
          reference
            "12.14.7.1.3y, 20.31.1 of IEEE Std 802.1Q-2018";
        }
        leaf mep-lbr-in-out-of-order {
          type yang:counter64;
          description
            "The total number of valid, out-of-order
            Loopback Replies received";
          reference
            "12.14.7.1.3z, 20.31.1 of IEEE Std 802.1Q-2018";
        }
        leaf mep-lbr-bad-msdu {
          type yang:counter64;
          description
            "The total number of LBRs received whose
            mac_service_data_unit did not match (except for the
            OpCode) that of the corresponding LBM.";
          reference
            "12.14.7.1.3aa, 20.2.3 of IEEE Std 802.1Q-2018";
        }
        leaf mep-unexpected-ltr-in {
          type yang:counter64;
          description
            "The total number of unexpected LTRs received.";
          reference
            "12.14.7.1.3ac, 20.44.1 of IEEE Std 802.1Q-2018";
        }
        leaf mep-lbr-out {
          type yang:counter64;
          description
            "Total number of Loopback Replies transmitted.";
          reference
            "12.14.7.1.3ad, 20.28.2 of IEEE Std 802.1Q-2018";
        }
      } // stats
      
      notification mep-fault-alarm {
        description
          "To alert the Manager to the existence of a fault in a
          monitored MA by issuing a Fault Alarm.";
        leaf mep-priority-defect {
          type leafref {
            path "../../highest-priority-defect";
          }
          description
            "The highest priority defect that has been present
            since the MEPs Fault Notification Generator state
            machine was last in the FNG_RESET state.";
        }
      } // mep-fault-alarm
    } // mep
  } // meps
  
  grouping cfm-operations {
    description
      "Grouping of CFM commands.";
    list cfm-operation {
      key "maintenance-group mep-id";
      description 
        "A list of CFM commands that can be performed.";
      leaf maintenance-group {
        type leafref {
          path '/cfm/maintenance-group-list/maintenance-group';
        }
        description
          "A reference to the maintenance group.";
      }
      leaf mep-id {
        type leafref {
          path '/cfm'
            + '/maintenance-group-list'
            + '[maintenance-group = current()/../maintenance-group]'
            + '/mep/mep-id';
        }
        description
          "A reference to a MEP associated with the maintenance
          group.";
      }
      
      action transmit-loopback {
        description
          "To signal to the MEP to transmit some number of LBMs.";
        input {
          leaf lbm-dest-is-mep-id {
            type boolean;
            default "false";
            description
              "TRUE indicates that MEP ID of the target MEP is used
              for Loopback transmissions. FALSE indicates that
              unicast destination MAC address of the target MEP is
              used for Loopback transmissions.";
            reference
              "12.14.7.3.2b of IEEE Std 802.1Q-2018";
          }
          leaf lbm-dest-mac-address {
            type ieee:mac-address;
            description
              "The target MAC Address field to be transmitted.
              A unicast destination MAC address. This address
              is used if node lbm-dest-is-mep-id is FALSE.";
            reference
              "12.14.7.3.2b of IEEE Std 802.1Q-2018";
          }
          leaf lbm-dest-mep-id {
            type cfm-types:mep-id-or-zero-type;
            default 0;
            description
              "The identifier of a remote MEP in the same MA to
              which the LBM is to be sent. This address
              is used if node mep-transmit-lbm-dest-is-mep-id
              is TRUE.";
            reference
              "12.14.7.3.2b of IEEE Std 802.1Q-2018";
          }
          leaf interval {
            type cfm-types:cfm-interval-type;
            default 1sec;
            description
              "The interval between LBM transmissions to be used by all
              MEPs in the Maintenance Association.";
          }
          leaf lbm-messages {
            type uint32 {
              range "1..1024";
            }
            default 1;
            description
              "The number of Loopback messages to be transmitted.";
            reference
              "12.14.7.3.2c of IEEE Std 802.1Q-2018";
          }
          leaf lbm-priority {
            type dot1q-types:priority-type;
            description
              "Priority. 3 bit value to be used in the VLAN tag, if
              present in the transmitted frame. The default value
              should be the CCM priority.";
            reference
              "12.14.7.3.2e of IEEE Std 802.1Q-2018";
          }
          leaf lbm-drop-eligible {
            type boolean;
            default "false";
            description
              "Drop eligible bit value to be used in the VLAN tag, if
              present in the transmitted frame";
            reference
              "12.14.7.3.2e of IEEE Std 802.1Q-2018";
          }
          leaf lbm-data-tlv {
            type cfm-types:lbm-data-tlv-type;
            description
              "An arbitrary amount of data to be included in the
              Data TLV, if the Data TLV is selected to be sent. The
              intent is to be able to fill the frame carrying the
              CFM PDU to its maximum length.";
            reference
              "12.14.7.3.2d of IEEE Std 802.1Q-2018";
          }
        } // input
        output {
          leaf lbm-result-ok {
            type boolean;
            default "true";
            description
              "Indicates the result of the operation:
                 TRUE - The LBM will be (or has been) sent.
                 FALSE - The LBM will not be sent.";
            reference
              "12.14.7.3.3a of IEEE Std 802.1Q-2018";
          }
          leaf lbm-seq-number {
            type cfm-types:seq-number-type;
            description
              "The Loopback transaction identifier
              (mep-next-lbm-trans-id) of the first LBM (to be) sent.
              The value returned is undefined if 
              mep-transmit-lbm-result-ok is FALSE.";
            reference
              "12.14.7.3.3b of IEEE Std 802.1Q-2018";
          }     
        } // output        
      } // transmit-loopback
      
      action transmit-linktrace {
        description
          "To signal to the MEP to transmit an LTM and to create an LTM
          entry in the MEPs Linktrace Database.";
        input {
          leaf interval {
            type cfm-types:cfm-interval-type;
            default 1sec;
            description
              "The interval between LTM transmissions to be used by all
              MEPs in the Maintenance Association.";
          }
          leaf ltm-target-is-mep-id {
            type boolean;
            default "false";
            description
              "TRUE indicates that MEP id of the target MEP is used
              for Linktrace transmission. FALSE indicates that
              unicast destination MAC address of the target MEP is
              used for LinkTrace transmission.";
            reference
              "12.14.7.4.2c of IEEE Std 802.1Q-2018";
          }
          leaf ltm-target-mac-address {
            type ieee:mac-address;
            description
              "The target MAC address field to be transmitted. A
              unicast MAC address. This address will be used if the
              value of mep-transmit-ltm-target-is-mep-id is FALSE.";
            reference
              "12.14.7.4.2c of IEEE Std 802.1Q-2018";
          }
          leaf ltm-target-mep-id {
            type cfm-types:mep-id-or-zero-type;
            default 0;
            description
              "The target MAC address field to be transmitted. The
              MEP identifier of another MEP in the same MA. This
              address will be used if the value of 
              mep-transmit-ltm-target-is-mep-id is TRUE.";
            reference
              "12.14.7.4.2c of IEEE Std 802.1Q-2018";
          }
          leaf ltm-priority {
            type dot1q-types:priority-type;
            description
              "Priority. 3 bit value to be used in the VLAN tag, if
              present in the transmitted frame. The default value
              should be the CCM priority.";
          }
          leaf ltm-drop-eligible {
            type boolean;
            default "false";
            description
              "Drop eligible bit value to be used in the VLAN tag, if
              present in the transmitted frame";
          }
          leaf ltm-ttl {
            type uint32 {
              range "0..255";
            }
            default 64;
            description
              "The LTM TTL field. Indicates the number of hops 
              remaining to the LTM. Decremented by 1 by each
              Linktrace Responder that handles the LTM. The value
              returned in the LTR is one less than that received in
              the LTM. If the LTM TTL is 0 or 1, the LTM is not
              forwarded to the next hop, and if 0, no LTR is 
              generated.";
            reference
              "12.14.7.4.2d, 21.8.4 of IEEE Std 802.1Q-2018";
          }
          leaf ltm-flags {
            type cfm-types:mep-tx-ltm-flags-type;
            default use-fdb-only;
            description
              "The flags field for the LTMs transmitted by the MEP.";
            reference
              "12.14.7.4.2b, 20.42.1 of IEEE Std 802.1Q-2018";
            
          }
        } // input
        output {
          leaf ltm-result-ok {
            type boolean;
            default "true";
            description
              "Indicates the result of the operation:
                 TRUE - The Linktrace message will be (or has been) 
                        sent.
                 FALS - The Linktrace message will not be sent.";
            reference
              "12.14.7.4.3a of IEEE Std 802.1Q-2018";
          }
          leaf ltm-seq-number {
            type cfm-types:seq-number-type;
            description
              "The LTM transaction identifier 
              (mep-ltm-next-seq-number) of the LTM sent. The value
              returned is undefined if mep-transmit-ltm-result is 
              FALSE.";
            reference
              "12.14.7.4.3b of IEEE Std 802.1Q-2018";
          }
          leaf ltm-egress-identifier {
            type string {
              length "8";
            }
            description
              "Identifies the MEP Linktrace Initiator that is 
              originating, or the Linktrace Responder that is
              forwarding, this LTM.
              
              The low-order six octets contain a 48-bit IEEE MAC
              address unique to the system in which the MEP Linktrace
              Initiator or Linktrace Responder resides. The 
              high-order two octets contain a value sufficient to 
              uniquely identify the MEP Linktrace Initiator or 
              Linktrace Responder within that system.
              
              For most Bridges, the address of any MAC attached to
              the Bridge will suffice for the low-order six octets,
              and 0 for the high-order octets. In some situations,
              e.g., if multiple virtual Bridges utilizing emulated
              LANs are implemented in a single physical system, the
              high-order two octets can be used to differentiate
              among the transmitting entities.
              
              The value returned is undefined if 
              mep-transmit-ltm-result is FALSE.";
            reference
              "12.14.7.4.3c of IEEE Std 802.1Q-2018";
          }
        } // output
      } // transmit-linktrace
      
      list loopback-reply {
        key "lbr-seq-number lbr-receive-order";
        description 
          "This table extends the MEP table and contains a list
          of Loopback replies received by a specific MEP in
          response to a loopback message.";
        leaf lbr-seq-number {
          type cfm-types:seq-number-type;
          description
            "The Loopback transaction identifier
            (mep-next-lbm-trans-id) of the first LBM (to be) 
            sent. The value returned is undefined if 
            mep-transmit-lbm-result-ok is FALSE.";
          reference
            "12.14.7.3.3b of IEEE Std 802.1Q-2018";
        }
        leaf lbr-receive-order {
          type uint32 {
            range "1..4294967295";
          }
          description
            "An index to distinguish among multiple LBRs with
            the same LBR Transaction Identifier field value. 
            Assigned sequentially from 1, in the order that the 
            Loopback Initiator received the LBRs.";
        }
        leaf result-ok {
          type boolean;
          default "true";
          config false;
          description
            "Indicates the result of the operation:
               TRUE - The LBM will be (or has been) sent.
               FALSE - The LBM will not be sent.";
          reference
            "12.14.7.3.3a of IEEE Std 802.1Q-2018";
        }
      } // loopback-reply
      
      list linktrace-reply {
        key "ltr-seq-number ltr-receive-order";
        description
          "This table extends the MEP table and contains a list
          of Linktrace replies received by a specific MEP in
          response to a linktrace message.";
        leaf ltr-seq-number {
          type cfm-types:seq-number-type;
          description
            "Transaction identifier returned by a previous
            transmit linktrace message command, indicating
            which LTMs response is going to be returned.";
          reference
            "12.14.7.5.2b of IEEE Std 802.1Q-2018";
        }
        leaf ltr-receive-order {
          type uint32 {
            range "1..4294967295";
          }
          description
            "An index to distinguish among multiple LTRs with
            the same LTR Transaction Identifier field value. 
            Assigned sequentially from 1, in the order that the 
            Linktrace Initiator received the LTRs.";
        }
        leaf ltr-ttl {
          type uint32 {
            range "0..255";
          }
          config false;
          description
            "TTL field value for a returned LTR.";
          reference
            "12.14.7.5, 20.41.2.2 of IEEE Std 802.1Q-2018";
        }
        leaf ltr-forwarded {
          type boolean;
          config false;
          description
            "Indicates if a LTM was forwarded by the responding
            MP, as returned in the FwdYes flag of the flags 
            field.";
          reference
            "12.14.7.5.3c, 20.41.2.1 of IEEE Std 802.1Q-2018";
        }           
        leaf ltr-terminal-mep {
          type boolean;
          config false;
          description
            "A Boolean value stating whether the forwarded LTM
            reached a MEP enclosing its MA, as returned in the
            Terminal MEP flag of the Flags field";
          reference
            "12.14.7.5.3d, 20.41.2.1 of IEEE Std 802.1Q-2018";
        }
        leaf ltr-last-egress-identifier {
          type string {
            length "8";
          }
          config false;
          description
            "An octet field holding the Last Egress Identifier
            returned in the LTR Egress Identifier TLV of the
            LTR. The Last Egress Identifier identifies the MEP
            Linktrace Initiator that originated, or the 
            Linktrace Responder that forwarded, the LTM to
            which this LTR is the response. This is the same
            value as the Egress Identifier TLV of that LTM.";
          reference
            "12.14.7.5.3e, 20.41.2.3 of IEEE Std 802.1Q-2018";
        }
        leaf ltr-next-egress-identifier {
          type string {
            length "8";
          }
          config false;
          description
            "An octet field holding the Next Egress Identifier
            returned in the LTR Egress Identifier TLV of the 
            LTR. The Next Egress Identifier Identifies the
            Linktrace Responder that transmitted this LTR, and
            can forward the LTM to the next hop. This is the
            same value as the Egress Identifier TLV of the
            forwarded LTM, if any. If the FwdYes bit of the
            Flags field is false, the contents of this field
            are undefined, i.e., any value can be transmitted,
            and the field is ignored by the receiver.";
          reference
            "12.14.7.5.3f, 20.41.2.4 of IEEE Std 802.1Q-2018";
        }
        leaf ltr-relay {
          type cfm-types:relay-action-field-value;
          config false;
          description
            "Value returned in the Relay Action field.";
          reference
            "12.14.7.5.3g, 20.41.2.5 of IEEE Std 802.1Q-2018";
        }           
        leaf ltr-chassis-id-subtype {
          type cfm-types:lldp-chassis-id-subtype;
          config false;
          description
            "Specifies the format of the Chassis ID returned
            in the Sender ID TLV of the LTR, if any. This value
            is meaningless if the ltr-chassis-id has a length
            of 0.";
          reference
            "12.14.7.5.3h, 21.5.3.2 of IEEE Std 802.1Q-2018";
        }           
        leaf ltr-chassis-id {
          type cfm-types:lldp-chassis-id;
          config false;
          description
            "The Chassis ID returned in the Sender ID TLV of 
            the LTR, if any. The format of this object is
            determined by the value of the 
            ltr-chassis-id-subtype object.";
          reference
            "12.14.7.5.3i, 21.5.3.2 of IEEE Std 802.1Q-2018";
        }           
        leaf ltr-man-address-domain {
          type cfm-types:transport-service-domain;
          config false;
          description
            "The transport-service-domain that identifies the
            type and format of the related mep-db-man-address
            object, used to access the YANG agent of the system
            transmitting the LTR. Received in the LTR Sender ID
            TLV from that system.";
          reference
            "12.14.7.5.3j, 21.5.3.5,
            21.9.6 of IEEE Std 802.1Q-2018";
        }           
        leaf ltr-man-address {
          type cfm-types:transport-service-address;
          config false;
          description
            "The transport-service-address that can be used to
            access the YANG agent of the system transmitting
            the CCM, received in the CCM Sender ID TLV from
            that system.
            
            If the related object ltr-man-address-domain
            contains the value zeroDotZero, this object
            ltr-man-address MUST have a zero-length OCTET 
            STRING as a value.";
          reference
            "12.14.7.5.3j, 21.5.3.7,
            21.9.6 of IEEE Std 802.1Q-2018";
        }           
        leaf ltr-ingress {
          type cfm-types:ingress-action-field-value;
          config false;
          description
            "The value returned in the Ingress Action Field of
            the LTM. The value ingress-no-tlv indicates that no
            Reply Ingress TLV was returned in the LTM.";
          reference
            "12.14.7.5.3k, 20.41.2.6 of IEEE Std 802.1Q-2018";
        }           
        leaf ltr-ingress-mac {
          type ieee:mac-address;
          config false;
          description
            "MAC address returned in the ingress MAC address
            field. If the ltr-ingress object contains the value 
            ingress-no-tlv, then the contents of this object
            are meaningless.";
          reference
            "12.14.7.5.3l, 20.41.2.7 of IEEE Std 802.1Q-2018";
        }           
        leaf ltr-ingress-port-id-subtype {
          type cfm-types:lldp-port-id-subtype;
          config false;
          description
            "Ingress Port ID. The format of this object is 
            determined by the value of the 
            ltr-ingress-port-id-subtype object. If the
            ltr-ingress object contains the value 
            ingress-no-tlv, then the contents of this object
            are meaningless.";
          reference
            "12.14.7.5.3n, 20.41.2.9 of IEEE Std 802.1Q-2018";
        }           
        leaf ltr-egress {
          type cfm-types:egress-action-field-value;
          config false;
          description
            "The value returned in the Egress Action Field of
            the LTM. The value egress-no-tlv indicates that 
            no Reply Egress TLV was returned in the LTM.";
          reference
            "12.14.7.5.3o, 20.41.2.10 of IEEE Std 802.1Q-2018";
        }           
        leaf ltr-egress-mac {
          type ieee:mac-address;
          config false;
          description
            "MAC address returned in the egress MAC address
            field. If the ltr-egress object contains the value
            egress-no-tlv, then the contents of this object are
            meaningless.";
          reference
            "12.14.7.5.3p, 20.41.2.11 of IEEE Std 802.1Q-2018";
        }           
        leaf ltr-egress-port-id-subtype {
          type cfm-types:lldp-port-id-subtype;
          config false;
          description
            "Format of the egress Port ID. If the ltr-egress
            object contains the value egress-no-tlv, then the
            contents of this object are meaningless.";
          reference
            "12.14.7.5.3q, 20.41.2.12 of IEEE Std 802.1Q-2018";
        }           
        leaf ltr-egress-port-id {
          type cfm-types:lldp-port-id;
          config false;
          description
            "Egress Port ID. The format of this object is
            determined by the value of the
            ltr-egress-port-id-subtype object. If the 
            ltr-egress object contains the value egress-no-tlv,
            then the contents of this object are meaningless.";
          reference
            "12.14.7.5.3r, 20.41.2.13 of IEEE Std 802.1Q-2018";
        }           
        leaf ltr-organization-specific-tlv {
          type string {
            length "0 | 4..1500";
          }
          config false;
          description
            "All Organization specific TLVs returned in the 
            LTR, if any. Includes all octets including and
            following the TLV Length field of each TLV, 
            concatenated together.";
          reference
            "12.14.7.5.3s, 21.5.2 of IEEE Std 802.1Q-2018";
        }
      } // linktrace-reply
    } // cfm-operation
  } // cfm-operations
  
} // ieee802-cfm-mep
