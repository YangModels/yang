module ieee802-dot1q-preemption {
  namespace urn:ieee:std:802.1Q:yang:ieee802-dot1q-preemption;
  prefix preempt;
  import ieee802-dot1q-types {
    prefix dot1q-types;
  }
  import ietf-interfaces {
    prefix if;
  }
  organization
    "IEEE 802.1 Working Group";
  contact
    "WG-URL: http://www.ieee802.org/1/
    WG-EMail: stds-802-1-L@ieee.org
    
    Contact: IEEE 802.1 Working Group Chair
    Postal: C/O IEEE 802.1 Working Group
    IEEE Standards Association
    445 Hoes Lane
    P.O. Box 1331
    Piscataway
    NJ 08855-1331
    USA
    
    E-mail: STDS-802-1-L@IEEE.ORG";
  description
    "This module provides for management of IEEE Std 802.1Q Bridges
    that support Frame Preemption.";
  revision 2018-07-10 {
    description
      "Module for IEEE Std 802.1Qbu-2016, Frame Preemption";
    reference
      "IEEE Std 802.1Qbu-2016";
  }
  feature frame-preemption {
    description
      "Each / A Port supports Frame Preemption.";
    reference
      "IEEE Std 802.1Qbu-2016";
  }
  augment "/if:interfaces/if:interface" {
    if-feature "frame-preemption";
    description
      "Augment interface management with Frame Preemption
      configuration.";
    container frame-preemption-parameters {
      description
        "A table containing a set of frame preemption parameters, one
        for each Port. All writeable objects in this table must be
        persistent over power up restart/reboot.";
      reference
        "12.30.1 of IEEE Std 802.1Qbu-2016
        6.7.2 of IEEE Std 802.1Qbu-2016";
      list frame-preemption-status-table {
        key "traffic-class";
        description
          "The framePreemptionStatusTable (6.7.2) consists of 8
          framePreemptionAdminStatus values (12.30.1.1.1), one per
          priority";
        reference
          "12.30.1.1 of IEEE Std 802.1Qbu-2016
          6.7.2 of IEEE Std 802.1Qbu-2016";
        leaf traffic-class {
          type dot1q-types:traffic-class-type;
          description
            "Traffic class";
        }
        leaf frame-preemption-status {
          type enumeration {
            enum express {
              value 1;
              description
                "Frames queued for the priority are to be transmitted
                using the express service for the Port.";
            }
            enum preemptable {
              value 2;
              description
                "Frames queued for the priority are to be transmitted
                using the preemptable service for the Port and
                preemption is enabled for the Port.";
            }
          }
          description
            "The value of the framePreemptionAdminStatus parameter for
            the traffic class. The default value of the
            framePreemptionAdminStatus parameter is express (1). The
            value of this object MUST be retained across
            reinitializations of the management system.";
          reference
            "12.30.1.1.1 of IEEE Std 802.1Qbu-2016
            6.7.2 of IEEE Std 802.1Qbu-2016";
        }
      }
      leaf hold-advance {
        type uint32;
        description
          "The value of the holdAdvance parameter for the Port in
          nanoseconds. There is no default value; the holdAdvance is a
          property of the underlying MAC.";
        reference
          "12.30.1.2 of IEEE Std 802.1Qbu-2016
          6.7.2 of IEEE Std 802.1Qbu-2016";
      }
      leaf release-advance {
        type uint32;
        description
          "The value of the releaseAdvance parameter for the Port in
          nanoseconds. There is no default value; the holdAdvance is a
          property of the underlying MAC.";
        reference
          "12.30.1.3 of IEEE Std 802.1Qbu-2016
          6.7.2 of IEEE Std 802.1Qbu-2016";
      }
      leaf preemption-active {
        type boolean;
        description
          "TRUE if preemption is both supported by the MAC and
          currently active.";
        reference
          "12.30.1.4 of IEEE Std 802.1Qbu-2016
          6.7.2 of IEEE Std 802.1Qbu-2016";
      }
      leaf hold-request {
        type enumeration {
          enum hold {
            value 1;
            description
              "Sequence of gate operations for the Port has executed a
              Set-And-Hold-MAC operation.";
          }
          enum release {
            value 2;
            description
              "Sequence of gate operations for the Port has executed a
              Set-And-Release-MAC operation.";
          }
        }
        description
          "The value is hold (1) when the sequence of gate operations
          for the Port has executed a Set-And-Hold-MAC operation, and
          release (2) when the sequence of gate operations has
          executed a Set-And-Release-MAC operation. The value of this
          object is release (2) on system initialization.";
        reference
          "12.30.1.5 of IEEE Std 802.1Qbu-2016
          6.7.2 of IEEE Std 802.1Qbu-2016";
      }
    }
  }
}
