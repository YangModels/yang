module ieee802-dot1q-vlan-bridge {

  namespace "urn:ieee:std:802.1Q:yang:ieee802-dot1q-vlan-bridge";
  prefix "dot1q-vlan-bridge";

  organization
    "Institute of Electrical and Electronics Engineers";

  contact
  	"WG-URL: http://grouper.ieee.org/groups/802/1/
    WG-EMail: stds-802-1@ieee.org

    Contact: IEEE 802.1 Working Group Chair
    Postal: C/O IEEE 802.1 Working Group
            IEEE Standards Association
            445 Hoes Lane
            P.O. Box 1331
            Piscataway
            NJ 08855-1331
            USA
 	
    E-mail: STDS-802-1-L@LISTSERV.IEEE.ORG";

  description
    "This YANG module describes the bridge configuration model for
    Customer VLAN Bridges.";
  
  revision 2017-09-07 {
    description
      "Updates based upon comment resolution on draft
      D1.2 of P802.1Qcp.";
    reference
      "IEEE 802.1Q-2017, Media Access Control (MAC) Bridges and
      Virtual Bridged Local Area Networks.";
  }

}
