module ieee-dot1q-tpmr {
	
	namespace "urn:ieee:params:xml:ns:yang:ieee-dot1q-tpmr";
    prefix "dot1q-tpmr";

	import ieee-dot1q-bridge {
		prefix "dot1q"; 
	}
	import ietf-yang-types { 
		prefix "yang"; 
	}
	import ietf-interfaces { 
		prefix "if"; 
	}
	import ietf-system { 
		prefix "system"; 
	}
	
	organization
		"Institute of Electrical and Electronics Engineers";

	contact
		"Web URL: http://www.ieee802.org/1/
    	
        Working Group Chair: 
    	   Glenn Parsons
    	   glenn.parsons@ericsson.com
     
        Working Group Vice-chair: 
    	   John Messenger
    	   J.L.Messenger@ieee.org
     	
        Chair, Time Sensitive Networking Task Group:
    	   Michael Johas Teener
    	   mikejt@broadcom.com
    	
		Vice-Chair, Time Sensitive Networking Task Group:
 	       Janos Farkas
		   janos.farkas@ericsson.com
     	
        Editor: 
    	   Marc Holness
     	   mholness@ciena.com";
		   
	description
	   "This YANG module describes the bridge configuration model
		for the Two Port MAC Relay Bridges.";   

	revision "2015-09-10" {
	    description
	        "Initial Version.";
	    reference
	        "IEEE 802.1Q-2014, Media Access Control (MAC) Bridges and
	    	Virtual Bridged Local Area Networks.";
	}
	
	augment "/system:system/dot1q:bridge" {
		when "/dot1q:components = '1' and
		      /dot1q:bridge-type = 'two-port-mac-relay-bridge' " {
			description
				"Applies when there is a single Bridge component
				of bridge type TPMR.";
		}
		description
			"Augment the dot1q Bridge model with TPMR bridge
			nodal information.";
		container tpmr {
		      presence
		    	  "Two Port MAC Relay Bridge";
		      description
		    	  "TPMR bridge configuration data.";
		} // tpmr
	} // Augment /system:system/dot1q:bridge
    
    augment "/if:interfaces/if:interface/dot1q:bridge-port" {
    	when "/dot1q:bridges/dot1q:bridge/dot1q:num-ports = '2'" {
    		description
    			"Applies when the number of bridge ports is 2";
    	}
    	description
    		"Augment Interface model with TPMR bridge port
    		configuration specific nodes.";
    	leaf managed-address {
    		type boolean;
    		default "true";
    		description 
    			"A Boolean value, which is TRUE if the MAC address is 
    			the management address for the TPMR, and is otherwise
    			FALSE.";
    	}
    	container mac-status-propagation {
    		description
    			"MAC status propagation configuration node
    			parameters.";
    		leaf link-notify {
        		type boolean;
        		default "false";
        		description 
    				"The current value (Boolean) of LinkNotify 
    				(23.5.1) being used by the MSP state machines.";
        		reference
        			"IEEE 802.1Q-2014 Clause 12.19.4.1.1.3,
        			12.19.4.1.2.2";
        	}
        	leaf link-notify-wait {
        		type yang:timeticks;
        		description 
        			"The current value, in centiseconds, of 
        			LinkNotifyWait (23.5.2) being used by the MSP
        			state machines.";
        		reference
        			"IEEE 802.1Q-2014 Clause 12.19.4.1.1.3,
        			12.19.4.1.2.2";
        	}
        	leaf link-notify-retry {
        		type yang:timeticks;
        		description 
        			"The current value, in centiseconds, of 
        			LinkNotifyRetry (23.5.3) being used by the MSP 
        			state machines.";
        		reference
        			"IEEE 802.1Q-2014 Clause 12.19.4.1.1.3,
        			12.19.4.1.2.2";
        	}
        	leaf mac-notify {
        		type boolean;
        		default "false";
        		description 
        			"The current value (Boolean) of MACNotify (23.5.4) 
        			being used by the MSP state machines.";
        		reference
        			"IEEE 802.1Q-2014 Clause 12.19.4.1.1.3,
        			12.19.4.1.2.2";
        	}
        	leaf mac-notify-time {
        		type yang:timeticks;
        		description 
        			"The current value, in centiseconds, of 
        			MACNotifyTime (23.5.5) being used by the MSP 
        			state machines.";
        		reference
        			"IEEE 802.1Q-2014 Clause 12.19.4.1.1.3,
        			12.19.4.1.2.2";
        	}
        	leaf mac-recover-time {
        		type yang:timeticks;
        		description 
        			"The current value, in centiseconds, of 
        			MACRecoverTime (23.5.6) being used by the MSP 
        			state machines.";
        		reference
        			"IEEE 802.1Q-2014 Clause 12.19.4.1.1.3,
        			12.19.4.1.2.2";
        	}    		
    	} // mac-status-propagation
    } // Augment interfaces
    
    augment "/if:interfaces-state/if:interface"
    	+ "/dot1q:bridge-port-state/dot1q:bridge-port-statistics" {
    	when "/dot1q:bridges/dot1q:bridge/dot1q:num-ports = '2'" {
    		description
    			"Applies when there are 2 Bridge ports.";
    	}
    	description
    		"Augment Interface-state model with TPMR bridge port
    		operational state specific nodes.";
    	leaf acks-tx {
    		type yang:counter64;
    		description 
    			"The number of acks transmitted (23.6.15) by the 
    			Ports Transmit Process as a consequence of txAck 
    			being set.";
    		reference
    			"IEEE 802.1Q-2014 Clause 12.19.4.1.3.3";
    	}
    	leaf add-notificatons-tx {
    		type yang:counter64;
    		description 
    			"The number of adds transmitted (23.6.16) by the 
    			Ports Transmit Process as a consequence of txAdd 
    			being set.";
    		reference
    			"IEEE 802.1Q-2014 Clause 12.19.4.1.3.3";
    	}
    	leaf loss-notification-tx {
    		type yang:counter64;
    		description 
    			"The number of losses transmitted (23.6.18) by the 
    			Ports Transmit Process as a consequence of txLoss 
    			being set.";
    		reference
    			"IEEE 802.1Q-2014 Clause 12.19.4.1.3.3";
    	}
    	leaf loss-confirmation-tx {
    		type yang:counter64;
    		description 
    			"The number of loss confirms transmitted (23.6.19) by
    			the Ports Transmit Process as a consequence of 
    			txLossConfirm being set.";
    		reference
    			"IEEE 802.1Q-2014 Clause 12.19.4.1.3.3";
    	}
    	leaf acks-rx {
    		type yang:counter64;
    		description 
    			"The number of acks received (23.6.10) by the Ports
    			Transmit Process.";
    		reference
    			"IEEE 802.1Q-2014 Clause 12.19.4.1.3.3";
    	}
    	leaf add-notificatons-rx {
    		type yang:counter64;
    		description 
    			"The number of adds received (23.6.11) by the Ports
    			Receive Process.";
    		reference
    			"IEEE 802.1Q-2014 Clause 12.19.4.1.3.3";
    	}
    	leaf loss-notification-rx {
    		type yang:counter64;
    		description 
    			"The number of losses received (23.6.13) by the Ports
    			Receive Process.";
    		reference
    			"IEEE 802.1Q-2014 Clause 12.19.4.1.3.3";
    	}
    	leaf loss-confirmation-rx {
    		type yang:counter64;
    		description 
    			"The number of loss confirms received (23.6.14) by 
    			the Ports Receive Process.";
    		reference
    			"IEEE 802.1Q-2014 Clause 12.19.4.1.3.3";
    	}
    	leaf add-events {
    		type yang:counter64;
    		description 
    			"The number of transitions to STM:ADD directly from 
    			STM:DOWN or STM:LOSS (23.8).";
    		reference
    			"IEEE 802.1Q-2014 Clause 12.19.4.1.3.3";
    	}
    	leaf loss-events {
    		type yang:counter64;
    		description 
    			"The number of transitions to STM:LOSS directly from
    			STM:UP or STM:ADD (23.8).";
    		reference
    			"IEEE 802.1Q-2014 Clause 12.19.4.1.3.3";
    	}
    	leaf mac-status-notifications {
    		type yang:counter64;
    		description 
    			"The number of transitions to SNM:MAC_NOTIFICATION
    			(23.9).";
    		reference
    			"IEEE 802.1Q-2014 Clause 12.19.4.1.3.3";
    	}
    } // Augment interfaces-state
} // ieee-dot1q-tpmr
