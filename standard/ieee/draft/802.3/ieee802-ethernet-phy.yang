module ieee802-ethernet-phy {
  yang-version 1.1;
  namespace "urn:ieee:std:802.3:yang:ieee802-ethernet-phy";
  prefix ieee802-eth-phy;

  import ietf-yang-types {
    prefix yang;
    reference
      "IETF RFC 6991 YANG Types";
  }
  import iana-if-type {
    prefix ianaift;
    reference
      "IANA Interface Types";
  }
  import ietf-interfaces {
    prefix if;
    reference
      "IETF RFC 8343";
  }
  import ieee802-ethernet-phy-type {
    prefix ieee802-phy;
    reference
      "IEEE Std 802.3-2022";
  }

  organization
    "IEEE Std 802.3 Ethernet Working Group";
  contact
    "Web URL: http://www.ieee802.org/3/";
  description
    "This module contains YANG definitions for  802.3 PHYs and PMDs.";

  revision 2024-12-23 {
    description
      "Initial revision derived from IEEE8023-MAU-MIB
       using smidump.";
    reference
      "IEEE Std 802.3-2022, unless dated explicitly";
  }

  feature fec-support {
    description
      "This object indicates support for one or more FEC modes.";
  }

  feature baset-snr-support {
    description
      "This object indicates support for SNR measurement for
       BASE-T interfaces.";
  }

  feature time-sync-support {
    description
      "This object indicates support for time syncronisation.";
  }

  feature pcs-lane-statistics-support {
    description
      "This object indicates support for PCS Lane statistics.";
  }

  feature auto-negotiation-support {
    description
      "This object indicates support for Auto-Negotiation.";
  }

  typedef snr-value {
    type int32 {
      range "-127..127";
    }
    units "0.1dB";
    description
      "SNR units of 0.1 dB to an accuracy of 0.5 dB within
       the range of -12.7 dB to 12.7 dB.";
  }

  typedef counter-1000-second {
    type yang:counter64;
    description
      "This counter increments no more than 1000 times per second.";
  }

  typedef counter-5000-second {
    type yang:counter64;
    description
      "This counter increments no more than 5000 times per second.";
  }

  typedef counter-pcs-lane {
    type yang:counter64;
    description
      "This counter has a maximum per second increment rate of:
       1.2 million for 1000 Mb/s
       5 million for 10 Gb/s and 40 Gb/s
       2.5 million for 100 Gb/s";
  }

  typedef enabled-state {
    type enumeration {
      enum unknown {
        description
          "Initializing.";
      }
      enum disabled {
        description
          "Disabled";
      }
      enum enabled {
        description
          "Enabled";
      }
    }
    description
      "Enabled, disabled or unknown.";
  }

  augment "/if:interfaces/if:interface" {
    when "derived-from-or-self(if:type,'ianaift:ethernetCsmacd')" {
      description
        "Applies to all Ethernet interfaces.";
    }
    description
      "Augment interface model with Ethernet interface
       information";
    container phy-table {
      description
        "Table of descriptive and status information
         about the Ethernet interface physical layer.";
      container control {
        description
          "Control information for the Ethernet interface
           physical layer.";
        leaf phy-reset {
          type boolean;
          description
            "Setting this to 'True' resets the interface in the
             same manner as would a power-off, power-on cycle of
             at least 0.5 s duration.";
          reference
            "IEEE Std 802.3, 30.5.1.2.1 acResetMAU";
        }
        leaf phy-admin-control {
          type enumeration {
            enum operational {
              description
                "Operational";
            }
            enum standby {
              description
                "Standby";
            }
            enum shutdown {
              description
                "Shutdown";
            }
          }
          description
            "The configured state of the interface. This object
             MAY be implemented as a read-only object by devices
             that do not implement software control of the interface
             state. Some devices may not support setting the value
             tof this object to some of the enumerated values.

             This can be set to “standby”, “operational”, and
             “shutdown” state, except that a “standby” action
             to a multidrop interface will cause the interface
             to enter the “shutdown” management state.";
          reference
            "IEEE Std 802.3, 30.5.1.2.2 acMAUAdminControl";
        }
        container fec-control {
          if-feature "fec-support";
          presence "The port supports one or more FEC modes.";
          description
            "FEC Control.";
          leaf fec-mode-control {
            type enumeration {
              enum disabled {
                description
                  "FEC disabled";
              }
              enum enabled {
                description
                  "FEC enabled";
              }
              enum BASE-R-enabled {
                description
                  "BASE-R FEC enabled";
              }
              enum RS-FEC-enabled {
                description
                  "RS-FEC enabled";
              }
              enum RS-FEC-Int-enabled {
                description
                  "RS-FEC-Int enabled";
              }
            }
            description
              "The FEC mode across the MDI of the port.
               BASE-R-enabled, RS-FEC-enabled and
               RS-FEC-Int-enabled are only used for PHYs which
               support more than one type of FEC operation.
               When Clause 73 Auto-Negotiation is enabled, this
               leaf becomes read-only.";
            reference
              "IEEE Std 802.3, 30.5.1.1.16";
          }
          leaf rs-fec-bypass-control {
            type enabled-state;
            description
              "Is RS-FEC bypass enabled?";
            reference
              "IEEE Std 802.3, 30.5.1.1.31";
          }
        }
      }
      container status {
        config false;
        description
          "Status for the port.";
        leaf phy-type {
          type identityref {
            base ieee802-phy:phy-type;
          }
          description
            "This object identifies the PHY type.";
          reference
            "IEEE Std 802.3, 30.5.1.1.2, aPHYType.";
        }
        leaf pmd-type {
          type identityref {
            base ieee802-phy:pmd-type;
          }
          description
            "This object identifies the PMD type.";
          reference
            "IEEE Std 802.3, 30.5.1.1.2, aMAUType.";
        }
        leaf pmd-type-list {
          type ieee802-phy:pmd-type-list;
          description
            "PMD types this interface supports.";
        }
        leaf phy-status {
          type enumeration {
            enum unknown {
              description
                "Initializing, true state
                 not yet known";
            }
            enum operational {
              description
                "Powered and connected";
            }
            enum standby {
              description
                "Inactive but on";
            }
            enum shutdown {
              description
                "Inactive and powered down";
            }
          }
          description
            "The current state of the interface.";
          reference
            "IEEE Std 802.3, 30.5.1.1.7, aMAUAdminState";
        }
        leaf phy-media-available {
          type ieee802-phy:media-available-type;
          description
            "This object reports if the media is availeable.";
          reference
            "IEEE Std 802.3, 30.5.1.1.4, aMediaAvailable.";
        }
        /* Jabber */
        leaf jabber-state {
          type enumeration {
            enum other {
              description
                "undefined";
            }
            enum unknown {
              description
                "initializing, true state
                 not yet known";
            }
            enum normal {
              description
                "state is true or normal";
            }
            enum fault {
              description
                "state is false, fault, or
                 abnormal";
            }
          }
          description
            "The JABBER state of the multidrop interface.";
          reference
            "IEEE Std 802.3, 30.5.1.1.6, aJabber.jabberFlag.";
        }
        leaf jabbering-state-enters {
          type yang:counter64;
          description
            "The number of times  this interface detected JABBER.";
          reference
            "IEEE Std 802.3,
             30.5.1.1.6, aJabber.jabberCounter.";
        }
        /* FEC */
        container fec-status {
          if-feature "fec-support";
          presence "The port supports one or more FEC modes.";
          description
            "FEC Status.";
          leaf fec-ability {
            type bits {
              bit other {
                description
                  "Other";
              }
              bit base-r {
                description
                  "BASE-R FEC supported";
              }
              bit rs-fec {
                description
                  "RS-FEC supported";
              }
              bit rs-fec-bypass {
                description
                  "RS-FEC bypass supported";
              }
              bit rs-fec-bypass-indication {
                description
                  "RS-FEC error indication bypass supported";
              }
              bit pcs-fec-bypass {
                description
                  "PCS FEC error bypass supported";
              }
              bit pcs-fec-bypass-indication {
                description
                  "PCS FEC error indication bypass supported";
              }
            }
            description
              "The FEC modes this port supports.";
            reference
              "IEEE Std 802.3, 30.5.1.1.15, 30.5.1.1.16
               30.5.1.1.29, 30.5.1.1.30, 30.5.1.1.33,
               30.5.1.1.34";
          }
          leaf fec-mode-status {
            type enumeration {
              enum unknown {
                description
                  "Initializing, true state not yet known.";
              }
              enum disabled {
                description
                  "FEC disabled";
              }
              enum enabled {
                description
                  "FEC enabled";
              }
              enum BASE-R-enabled {
                description
                  "BASE-R FEC enabled";
              }
              enum RS-FEC-enabled {
                description
                  "RS-FEC enabled";
              }
              enum RS-FEC-Int-enabled {
                description
                  "RS-FEC-Int enabled";
              }
            }
            description
              "The FEC mode of the PHY.
               BASE-R-enabled, RS-FEC-enabled and
               RS-FEC-Int-enabled are only used by PHYs which
               support more than one type of FEC operation.";
            reference
              "IEEE Std 802.3, 30.5.1.1.16";
          }
          leaf rs-fec-bypass-enabled-status {
            type enabled-state;
            description
              "Is RS-FEC bypass indication enabled?";
            reference
              "IEEE Std 802.3, 30.5.1.1.32";
          }
        }
        /* MultiGBASE-T SNR */
        container baset-snr {
          if-feature "baset-snr-support";
          presence "The port supports BASE-T SNR measurements.";
          description
            "BASE-T SNR Status.";
          leaf snr-op-margin-chnl-a {
            type snr-value;
            description
              "The current SNR operating margin on channel A
               on this port for MultiGBASE-T PMAs.";
            reference
              "IEEE Std 802.3, 30.5.1.1.19";
          }
          leaf snr-op-margin-chnl-b {
            type snr-value;
            description
              "The current SNR operating margin on channel B
               on this port for MultiGBASE-T PMAs.";
            reference
              "IEEE Std 802.3, 30.5.1.1.20";
          }
          leaf snr-op-margin-chnl-c {
            type snr-value;
            description
              "The current SNR operating margin on channel C
               on this port for MultiGBASE-T PMAs.";
            reference
              "IEEE Std 802.3, 30.5.1.1.21";
          }
          leaf snr-op-margin-chnl-d {
            type snr-value;
            description
              "The current SNR operating margin on channel CD
               on this port for MultiGBASE-T PMAs.";
            reference
              "IEEE Std 802.3, 30.5.1.1.22";
          }
        }
        /* TimeSync */
        container time-sync {
          if-feature "time-sync-support";
          presence "The port supports Time Sync.";
          description
            "Time Sync Status.";
          leaf time-sync-ability {
            type bits {
              bit transmit {
                description
                  "Transmit";
              }
              bit receive {
                description
                  "Receive";
              }
            }
            description
              "The TimeSync capabities of this port.";
            reference
              "IEEE Std 802.3, 30.13.1.1, 30.13.1.2";
          }
          leaf time-sync-delay-tx-max {
            type uint32;
            units "nano-seconds";
            description
              "The maximum transmit data delay between
               the xMII input to the MDI output.";
            reference
              "IEEE Std 802.3, 30.13.1.3";
          }
          leaf time-sync-delay-tx-min {
            type uint32;
            units "nano-seconds";
            description
              "The minimum transmit data delay between
               the xMII input to the MDI output.";
            reference
              "IEEE Std 802.3, 30.13.1.4";
          }
          leaf time-sync-delay-rx-max {
            type int32;
            units "nano-seconds";
            description
              "The maximum receive data delay between
               the MDI input to the xMII output.";
            reference
              "IEEE Std 802.3, 30.13.5";
          }
          leaf time-sync-delay-rx-min {
            type int32;
            units "nano-seconds";
            description
              "The minimum receive data delay between
               the MDI input to the xMII output.";
            reference
              "IEEE Std 802.3, 30.13.5";
          }
        }
      }
      container statistics {
        config false;
        description
          "Counters for the port.";
        leaf phy-media-losts {
          type yang:counter64;
          description
            "The number of times phy-media-available changed
             from 'available'.";
          reference
            "IEEE Std 802.3, 30.5.1.1.5 aLoseMediaCounter.";
        }
        leaf jabbering-state-enters {
          type yang:counter64;
          description
            "The number of times this interface detected JABBER.";
          reference
            "IEEE Std 802.3, 30.5.1.1.6, aJabber.jabberCounter.";
        }
        leaf false-carriers {
          type yang:counter64;
          description
            "The number of false carrier
             events during IDLE in 100BASE-X and
             1000BASE-X links.

             For all other interface types, this counter
             will always indicate zero.

             It can increment at a maximum rate of once
             per 100 ms for 100BASE-X and once per 10us
             for 1000BASE-X.";
          reference
            "IEEE Std 802.3, 30.5.1.1.10, aFalseCarriers.";
        }
        leaf pcs-coding-violations {
          type yang:counter64;
          description
            "The number of PCS coding violations for 100Mb/s and
             1000Mb/s ports.

             This counter increments at a maximum rate of 25 thousand
             per second for 100 Mb/s implementations and
             125 thousand per second for 1000 Mb/s
             implementations.

             The contents of this
             attribute is undefined when FEC is operating.";
          reference
            "IEEE Std 802.3, 30.5.1.1.14";
        }
        leaf fast-retrain-count-local {
          type counter-1000-second;
          description
            "The number of fast retrains initiated
             by the local device.";
          reference
            "IEEE Std 802.3, 30.5.1.1.24";
        }
        leaf fast-retrain-count-peer {
          type counter-1000-second;
          description
            "The number of fast retrains initiated
             by the link partner.";
          reference
            "IEEE Std 802.3, 30.5.1.1.25";
        }
      }
      container pcs-lane-statistics {
        if-feature "pcs-lane-statistics-support";
        config false;
        description
          "Per PCS lane counters for the port.
           These counters apply to the following:
           1000BASE-PX,
           10/25/40/50/100/200/400GBASE-R
           100GBASE-P
           10GBASE-PR
           10/1GBASE-PRX";
        list pcs-lane {
          key "pcs-lane-index";
          description
            "Per PCS lane counters for the port.";
          leaf pcs-lane-index {
            type uint32 {
              range "0..255";
            }
            description
              "PCS lane index.";
          }
          leaf fec-corrected-blocks {
            type counter-pcs-lane;
            description
              "The number blocks that FEC corrected.";
            reference
              "IEEE Std 802.3, 30.5.1.1.17";
          }
          leaf fec-uncorrected-blocks {
            type counter-pcs-lane;
            description
              "The number blocks that FEC could not correct.";
            reference
              "IEEE Std 802.3, 30.5.1.1.18";
          }
        }
      }
    }
    container auto-neg-table {
      if-feature "auto-negotiation-support";
      description
        "Configuration and status objects for Auto-Negotiation
         on Ethernet interfaces.";
      container control {
        description
          "Auto-Negotiation control.";
        leaf auto-neg-control {
          type boolean;
          default "true";
          description
            "Enable/disable Auto-Negotiation for this interface.";
          reference
            "IEEE Std 802.3, 30.6.1.1.2, acAutoNegAdminControl.";
        }
        leaf auto-neg-restart {
          type boolean;
          description
            "Setting this to true restarts Auto-Negotiation if enabled.";
          reference
            "IEEE Std 802.3,
             30.6.1.2.1, acAutoNegRestartAutoConfig.";
        }
      }
      container status {
        config false;
        description
          "Auto-Negotiation status.";
        leaf auto-neg-enabled {
          type boolean;
          description
            "Is Auto-Negotiation enabled for this interface.";
          reference
            "IEEE Std 802.3,
             30.6.1.1.2 aAutoNegAdminState.";
        }
        leaf auto-neg-remote-signaling {
          type boolean;
          description
            "Is the link partner using Auto-Negotiation?";
          reference
            "IEEE Std 802.3, 30.6.1.1.3, aAutoNegRemoteSignaling.";
        }
        leaf auto-neg-status {
          type enumeration {
            enum other {
              description
                "Unknown state.";
            }
            enum configuring {
              description
                "Auto-Negotiation is active.";
            }
            enum complete {
              description
                "Auto-Negotiation is complete.";
            }
            enum disabled {
              description
                "Auto-Negotiation s disabled.";
            }
            enum parallelDetectFail {
              description
                "Auto-Negotiation failed because the
                 link partner does not suport, or has
                 disabled, Auto-Negotiation.";
            }
          }
          description
            "The current status of Auto-Negotiation.";
          reference
            "IEEE Std 802.3, 30.6.1.1.4, aAutoNegAutoConfig.";
        }
        leaf auto-neg-capability-bits {
          type ieee802-phy:auto-neg-ability-bits;
          description
            "The capabilities of the local Auto-Negotiation entity.";
          reference
            "IEEE Std 802.3, 30.6.1.1.5,
             aAutoNegLocalTechnologyAbility.";
        }
        leaf auto-neg-cap-advertised-bits {
          type ieee802-phy:auto-neg-ability-bits;
          description
            "The capabilities advertised by the local
             Auto-Negotiation entity.";
          reference
            "IEEE Std 802.3, 30.6.1.1.6,
             aAutoNegadvertisedTechnologyAbility.";
        }
        leaf auto-neg-cap-received-bits {
          type ieee802-phy:auto-neg-ability-bits;
          description
            "Auto-Negotiation capabilities received from
             the link partner.";
          reference
            "IEEE Std 802.3, 30.6.1.1.7,
             aAutoNegreceivedTechnologyAbility.";
        }
      }
    }
  }
}
