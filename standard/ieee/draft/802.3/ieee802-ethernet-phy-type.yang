module ieee802-ethernet-phy-type {
  yang-version 1.1;
  namespace "urn:ieee:std:802.3:yang:ieee802-ethernet-phy-type";
  prefix ieee802-eth-phy-type;

  organization
    "IEEE Std 802.3 Ethernet Working Group
     Web URL: http://www.ieee802.org/3/";
  contact
    "Web URL: http://www.ieee802.org/3/";
  description
    "This module contains YANG definitions for Physical Layer device
        (PHY) and Physical Medium Dependent(PMD) indentities and related
        types.";

  revision 2025-04-17 {
    description
      "Initial revision derived from IANA-MAU-MIB REVISION
       202309070000Z using smidump.";
    reference
      "IEEE Std 802.3-2022, unless dated explicitly";
  }

  /* PHY type identities */

  identity phy-type {
    description
      "Base type for PHY types.";
    reference
      "IEEE Std 802.3, Clause 30.3.2.1.2 aPhyType";
  }

  identity phy-type-other {
    base phy-type;
    description
      "Undefined";
  }

  identity phy-type-unknown {
    base phy-type;
    description
      "Initializing, true state or type not yet known";
  }

  identity phy-type-none {
    base phy-type;
    description
      "MII present and nothing connected";
  }

  identity phy-type-10BASE-T {
    base phy-type;
    description
      "Clause 14 10 Mb/s PAM3";
  }

  identity phy-type-10BASE-T1L {
    base phy-type;
    description
      "Clause 146 10 Mb/s PAM3";
  }

  identity phy-type-10BASE-T1S {
    base phy-type;
    description
      "Clause 147 10 Mb/s DME";
  }

  identity phy-type-100BASE-T1 {
    base phy-type;
    description
      "Clause 96 100 Mb/s PAM3";
  }

  identity phy-type-100BASE-X {
    base phy-type;
    description
      "Clause 24 or subclause 66.1 100 Mb/s 4B/5B";
  }

  identity phy-type-1000BASE-H {
    base phy-type;
    description
      "Clause 115 1000 Mb/s PAM16-THP";
  }

  identity phy-type-1000BASE-T {
    base phy-type;
    description
      "Clause 40 1000 Mb/s 4D-PAM5";
  }

  identity phy-type-1000BASE-T1 {
    base phy-type;
    description
      "Clause 97 1000 Mb/s PAM3";
  }

  identity phy-type-1000BASE-X {
    base phy-type;
    description
      "Clause 36 or subclause 66.2 1000 Mb/s 8B/10B";
  }

  identity phy-type-2.5GBASE-T {
    base phy-type;
    description
      "Clause 126 2.5 Gb/s PAM16";
  }

  identity phy-type-2.5GBASE-T1 {
    base phy-type;
    description
      "Clause 149 2.5 Gb/s PAM4";
  }

  identity phy-type-2.5GBASE-X {
    base phy-type;
    description
      "Clause 127 2.5 Gb/s 8B/10B";
  }

  identity phy-type-5GBASE-R {
    base phy-type;
    description
      "Clause 129 5 Gb/s 64/66B";
  }

  identity phy-type-5GBASE-T {
    base phy-type;
    description
      "Clause 126 5 Gb/s PAM16";
  }

  identity phy-type-5GBASE-T1 {
    base phy-type;
    description
      "Clause 149 5 Gb/s PAM4";
  }

  identity phy-type-10G-1GBASE-PRX {
    base phy-type;
    description
      "Clause 76 10/1G-EPON 10 Gb/s 64B/66B downstream and
       1 Gb/s 8B/10B upstream";
  }

  identity phy-type-10GBASE-PR {
    base phy-type;
    description
      "Clause 76 10/10G-EPON 10 Gb/s 64B/66B";
  }

  identity phy-type-10GBASE-R {
    base phy-type;
    description
      "Clause 49 10 Gb/s 64B/66B";
  }

  identity phy-type-10GBASE-T {
    base phy-type;
    description
      "Clause 55 10 Gb/s DSQ128";
  }

  identity phy-type-10GBASE-T1 {
    base phy-type;
    description
      "Clause 149 10 Gb/s PAM4";
  }

  identity phy-type-10GBASE-X {
    base phy-type;
    description
      "Clause 48 10 Gb/s 4 lane 8B/10B";
  }

  identity phy-type-10GPASS-XR {
    base phy-type;
    description
      "Clause 101 PCS up to 10 Gb/s 64B/66B OFDM downstream
       and up to 1.6 Gb/s 64B/66B OFDMA upstream";
  }

  identity phy-type-10G-2p5GGBASE-SP {
    base phy-type;
    description
      "Clause 164.3 10 Gb/s downstream and 2.5 Gb/s upstream
       256B/257B";
  }

  identity phy-type-10GBASE-SP {
    base phy-type;
    description
      "Clause 164.3 10 Gb/s 256B/257B";
  }

  identity phy-type-25G-10GBASE-PQ {
    base phy-type;
    description
      "Clause 142 25/10G-EPON 256B/257B";
  }

  identity phy-type-25GBASE-PQ {
    base phy-type;
    description
      "Clause 142 25/25G-EPON 256B/257B";
  }

  identity phy-type-25GBASE-R {
    base phy-type;
    description
      "Clause 107 25 Gb/s 64B/66B";
  }

  identity phy-type-25GBASE-T {
    base phy-type;
    description
      "Clause 113 25 Gb/s DSQ128";
  }

  identity phy-type-40GBASE-R {
    base phy-type;
    description
      "Clause 82 40 Gb/s multi-PCS lane 64B/66B";
  }

  identity phy-type-40GBASE-T {
    base phy-type;
    description
      "Clause 113 40 Gb/s DSQ128";
  }

  identity phy-type-50G-10GBASE-PQ {
    base phy-type;
    description
      "Clause 142 50/10G-EPON 256B/257B";
  }

  identity phy-type-50G-25GBASE-PQ {
    base phy-type;
    description
      "Clause 142 50/25G-EPON 256B/257B";
  }

  identity phy-type-50GBASE-PQ {
    base phy-type;
    description
      "Clause 142 50/50G-EPON 256B/257B";
  }

  identity phy-type-50GBASE-R {
    base phy-type;
    description
      "Clause 133 50 Gb/s multi-PCS lane 64B/66B";
  }

  identity phy-type-100GBASE-P {
    base phy-type;
    description
      "Clause 82 100 Gb/s multi-PCS lane using >2-level PAM";
  }

  identity phy-type-100GBASE-R {
    base phy-type;
    description
      "Clause 82 100 Gb/s multi-PCS lane using 2-level PAM";
  }

  identity phy-type-200GBASE-R {
    base phy-type;
    description
      "Clause 119 200 Gb/s multi-PCS lane 64B/66B";
  }

  identity phy-type-400GBASE-R {
    base phy-type;
    description
      "Clause 119 400 Gb/s multi-PCS lane 64B/66B";
  }

  identity phy-type-800GBASE-R {
    base phy-type;
    description
      "Clause 172 800 Gb/s multi-PCS lane 64B/66B";
  }

  /* PMD  identities */

  identity pmd-type {
    description
      "Base type for Physical Medium Dependent(PMD)sublayer types.";
    reference
      "IEEE Std 802.3, Clause 30.5.1.1.2 aMAUType";
  }

  identity pmd-type-global {
    base pmd-type;
    description
      "Undefined";
  }

  identity pmd-type-other {
    base pmd-type;
    description
      "Nonconformant PMD.";
  }

  identity pmd-type-unknown {
    base pmd-type;
    description
      "Initializing, true state or type not yet known.";
  }

  identity pmd-type-10BASE-T {
    base pmd-type;
    description
      "Twisted-pair cabling MAU as specified in Clause 14";
  }

  identity pmd-type-10BASE-T1L {
    base pmd-type;
    description
      "Single balanced pair PHY as specified in Clause 146";
  }

  identity pmd-type-10BASE-T1S {
    base pmd-type;
    description
      "Single balanced pair PHY as specified in Clause 147, full
       duplex mode";
  }

  identity pmd-type-10BASE-T1SMD {
    base pmd-type;
    description
      "Single balanced pair PHY as specified in Clause 147,
       multidrop mode";
  }

  identity pmd-type-100BASE-BX10D {
    base pmd-type;
    description
      "One single-mode fiber OLT PHY as specified in Clause 58";
  }

  identity pmd-type-100BASE-BX10U {
    base pmd-type;
    description
      "One single-mode fiber ONU PHY as specified in Clause 58";
  }

  identity pmd-type-100BASE-FX {
    base pmd-type;
    description
      "100BASE-FX PMD as specified in Clause 26";
  }

  identity pmd-type-100BASE-LX10 {
    base pmd-type;
    description
      "Two fiber PHY as specified in Clause 58";
  }

  identity pmd-type-100BASE-T1 {
    base pmd-type;
    description
      "Single balanced twisted-pair copper cabling PHY as specified
       in Clause 96";
  }

  identity pmd-type-100BASE-TX {
    base pmd-type;
    description
      "Two-pair Category 5 twisted-pair cabling as specified in
       Clause 25";
  }

  identity pmd-type-1000BASE-BX10D {
    base pmd-type;
    description
      "One single-mode fiber OLT PHY as specified in Clause 59";
  }

  identity pmd-type-1000BASE-BX10U {
    base pmd-type;
    description
      "One single-mode fiber ONU PHY as specified in Clause 59";
  }

  identity pmd-type-1000BASE-KX {
    base pmd-type;
    description
      "1000BASE-KX PCS/PMA over an electrical backplane PMD as
       specified in Clause 70";
  }

  identity pmd-type-1000BASE-LX {
    base pmd-type;
    description
      "1000BASE-LX fiber over long-wavelength laser PMD as specified
       in Clause 38";
  }

  identity pmd-type-1000BASE-LX10 {
    base pmd-type;
    description
      "Two fiber 10 km PHY as specified in Clause 59";
  }

  identity pmd-type-1000BASE-PX10-D {
    base pmd-type;
    description
      "One single-mode fiber OMP OLT PHY, as specified in Clause 60,
       supporting a distance of at least 10 km, and a split of at
       least 1:16";
  }

  identity pmd-type-1000BASE-PX10-U {
    base pmd-type;
    description
      "One single-mode fiber OMP ONU PHY, as specified in Clause 60,
       supporting a distance of at least 10 km, and a split of at
       least 1:16";
  }

  identity pmd-type-1000BASE-PX20-D {
    base pmd-type;
    description
      "One single-mode fiber OMP OLT PHY, as specified in Clause 60,
       supporting a distance of at least 20 km, and a split of at
       least 1:16";
  }

  identity pmd-type-1000BASE-PX20-U {
    base pmd-type;
    description
      "One single-mode fiber OMP ONU PHY, as specified in Clause 60,
       supporting a distance of at least 20 km, and a split of at
       least 1:16";
  }

  identity pmd-type-1000BASE-PX30-D {
    base pmd-type;
    description
      "One single-mode fiber OMP OLT PHY, as specified in Clause 60,
       supporting a distance of at least 20 km, and a split of at
       least 1:32";
  }

  identity pmd-type-1000BASE-PX30-U {
    base pmd-type;
    description
      "One single-mode fiber OMP ONU PHY, as specified in Clause 60,
       supporting a distance of at least 20 km, and a split of at
       least 1:32";
  }

  identity pmd-type-1000BASE-PX40-D {
    base pmd-type;
    description
      "One single-mode fiber OMP OLT PHY as specified in Clause 60,
       supporting a distance of at least 20 km, and a split of at
       least 1:64";
  }

  identity pmd-type-1000BASE-PX40-U {
    base pmd-type;
    description
      "One single-mode fiber OMP ONU PHY as specified in Clause 60,
       supporting a distance of at least 20 km, and a split of at
       least 1:64";
  }

  identity pmd-type-1000BASE-RHA {
    base pmd-type;
    description
      "Plastic optical fiber PHY as specified in Clause 115.";
  }

  identity pmd-type-1000BASE-RHB {
    base pmd-type;
    description
      "Plastic optical fiber PHY as specified in Clause 115.";
  }

  identity pmd-type-1000BASE-RHC {
    base pmd-type;
    description
      "Plastic optical fiber PHY as specified in Clause 115.";
  }

  identity pmd-type-1000BASE-SX {
    base pmd-type;
    description
      "1000BASE-SX fiber over short-wavelength laser PMD as
       specified in Clause 38";
  }

  identity pmd-type-1000BASE-T {
    base pmd-type;
    description
      "Four-pair Category 5 twisted-pair cabling PHY as specified in
       Clause 40";
  }

  identity pmd-type-1000BASE-T1 {
    base pmd-type;
    description
      "Single twisted-pair copper cable PHY as specified in Clause
       97";
  }

  identity pmd-type-1000BASE-X {
    base pmd-type;
    description
      "1000BASE-X PCS/PMA as specified in Clause 36 over undefined
       PMD";
  }

  identity pmd-type-2.5GBASE-KX {
    base pmd-type;
    description
      "2.5GBASE-X PMD as specified in Clause 128 over an electrical
       backplane as specified in Clause 128";
  }

  identity pmd-type-2.5GBASE-T {
    base pmd-type;
    description
      "Four-pair twisted-pair balanced copper cabling PHY as
       specified in Clause 126";
  }

  identity pmd-type-2.5GBASE-T1 {
    base pmd-type;
    description
      "Single balanced pair of conductors PHY as specified in Clause
       149";
  }

  identity pmd-type-2.5GBASE-X {
    base pmd-type;
    description
      "2.5GBASE-X PCS/PMA as specified in Clause 127 over undefined
       PMD";
  }

  identity pmd-type-5GBASE-KR {
    base pmd-type;
    description
      "5GBASE-KR PMD as specified in Clause 130 over an electrical
       backplane as specified in Clause 130";
  }

  identity pmd-type-5GBASE-R {
    base pmd-type;
    description
      "5GBASE-R PCS/PMA as specified in Clause 129 over undefined
       PMD";
  }

  identity pmd-type-5GBASE-T {
    base pmd-type;
    description
      "Four-pair twisted-pair balanced copper cabling PHY as
       specified in Clause 126";
  }

  identity pmd-type-5GBASE-T1 {
    base pmd-type;
    description
      "Single balanced pair of conductors PHY as specified in Clause
       149";
  }

  identity pmd-type-10G-1GBASE-PRX-D1 {
    base pmd-type;
    description
      "One single-mode fiber 10.3125 GBd continuous downstream /
       1.25 GBd burst mode upstream OLT PHY as specified in Clause 75";
  }

  identity pmd-type-10G-1GBASE-PRX-D2 {
    base pmd-type;
    description
      "One single-mode fiber 10.3125 GBd continuous downstream /
       1.25 GBd burst mode upstream OLT PHY as specified in Clause 75";
  }

  identity pmd-type-10G-1GBASE-PRX-D3 {
    base pmd-type;
    description
      "One single-mode fiber 10.3125 GBd continuous downstream /
       1.25 GBd burst mode upstream OLT PHY as specified in Clause 75";
  }

  identity pmd-type-10G-1GBASE-PRX-D4 {
    base pmd-type;
    description
      "One single-mode fiber 10.3125 GBd continuous downstream /
       1.25 GBd burst mode upstream OLT PHY as specified in Clause 75";
  }

  identity pmd-type-10G-1GBASE-PRX-U1 {
    base pmd-type;
    description
      "One single-mode fiber 10.3125 GBd continuous downstream /
       1.25 GBd burst mode upstream ONU PHY as specified in Clause 75";
  }

  identity pmd-type-10G-1GBASE-PRX-U2 {
    base pmd-type;
    description
      "One single-mode fiber 10.3125 GBd continuous downstream /
       1.25 GBd burst mode upstream ONU PHY as specified in Clause 75";
  }

  identity pmd-type-10G-1GBASE-PRX-U3 {
    base pmd-type;
    description
      "One single-mode fiber 10.3125 GBd continuous downstream /
       1.25 GBd burst mode upstream ONU PHY as specified in Clause 75";
  }

  identity pmd-type-10G-1GBASE-PRX-U4 {
    base pmd-type;
    description
      "One single-mode fiber 10.3125 GBd continuous downstream /
       1.25 GBd burst mode upstream ONU PHY as specified in Clause 75";
  }

  identity pmd-type-10GBASE-BR10-D {
    base pmd-type;
    description
      "One single-mode fiber OLT PHY supporting a distance of at
       least 10 km as specified in Clause 158";
  }

  identity pmd-type-10GBASE-BR10-U {
    base pmd-type;
    description
      "One single-mode fiber ONU PHY supporting a distance of at
       least 10 km as specified in Clause 158";
  }

  identity pmd-type-10GBASE-BR20-D {
    base pmd-type;
    description
      "One single-mode fiber OLT PHY supporting a distance of at
       least 20 km as specified in Clause 158";
  }

  identity pmd-type-10GBASE-BR20-U {
    base pmd-type;
    description
      "One single-mode fiber ONU PHY supporting a distance of at
       least 20 km as specified in Clause 158";
  }

  identity pmd-type-10GBASE-BR40-D {
    base pmd-type;
    description
      "One single-mode fiber OLT PHY upporting a distance of at
       least 40 km as specified in Clause 158";
  }

  identity pmd-type-10GBASE-BR40-U {
    base pmd-type;
    description
      "One single-mode fiber ONU PHY supporting a distance of at
       least 40 km as specified in Clause 158";
  }

  identity pmd-type-10GBASE-CX4 {
    base pmd-type;
    description
      "10GBASE-CX4 copper over 8 pair 100-Ohm balanced cable as
       specified in Clause 54";
  }

  identity pmd-type-10GBASE-ER {
    base pmd-type;
    description
      "10GBASE-ER fiber over 1550nm optics as specified in Clause 52";
  }

  identity pmd-type-10GBASE-EW {
    base pmd-type;
    description
      "10GBASE-EW fiber over 1550nm optics as specified in Clause 52";
  }

  identity pmd-type-10GBASE-KR {
    base pmd-type;
    description
      "10GBASE-KR PCS/PMA over an electrical backplane PMD as
       specified in Clause 72";
  }

  identity pmd-type-10GBASE-KX4 {
    base pmd-type;
    description
      "10GBASE-KX4 PCS/PMA over an electrical backplane PMD as
       specified in Clause 71";
  }

  identity pmd-type-10GBASE-LR {
    base pmd-type;
    description
      "10GBASE-LR fiber over 1310nm optics as specified in Clause 52";
  }

  identity pmd-type-10GBASE-LRM {
    base pmd-type;
    description
      "10GBASE-LRM fiber over 1310 nm optics as specified in Clause
       68";
  }

  identity pmd-type-10GBASE-LW {
    base pmd-type;
    description
      "10GBASE-LW fiber over 1310nm optics as specified in Clause 52";
  }

  identity pmd-type-10GBASE-LX4 {
    base pmd-type;
    description
      "10GBASE-LX4 fiber over 4 lane 1310nm optics as specified in
       Clause 53";
  }

  identity pmd-type-10GBASE-PR-D1 {
    base pmd-type;
    description
      "One single-mode fiber 10.3125 GBd continuous downstream /
       1.25 GBd burst mode upstream OLT PHY as specified in Clause 75";
  }

  identity pmd-type-10GBASE-PR-D2 {
    base pmd-type;
    description
      "One single-mode fiber 10.3125 GBd continuous downstream /
       1.25 GBd burst mode upstream OLT PHY as specified in Clause 75";
  }

  identity pmd-type-10GBASE-PR-D3 {
    base pmd-type;
    description
      "One single-mode fiber 10.3125 GBd continuous downstream /
       1.25 GBd burst mode upstream OLT PHY as specified in Clause 75";
  }

  identity pmd-type-10GBASE-PR-D4 {
    base pmd-type;
    description
      "One single-mode fiber 10.3125 GBd continuous downstream /
       1.25 GBd burst mode upstream OLT PHY as specified in Clause 75";
  }

  identity pmd-type-10GBASE-PR-U1 {
    base pmd-type;
    description
      "One single-mode fiber 10.3125 GBd continuous downstream /
       1.25 GBd burst mode upstream ONU PHY as specified in Clause 75";
  }

  identity pmd-type-10GBASE-PR-U3 {
    base pmd-type;
    description
      "One single-mode fiber 10.3125 GBd continuous downstream /
       1.25 GBd burst mode upstream ONU PHY as specified in Clause 75";
  }

  identity pmd-type-10GBASE-PR-U4 {
    base pmd-type;
    description
      "One single-mode fiber 10.3125 GBd continuous downstream /
       1.25 GBd burst mode upstream ONU PHY as specified in Clause 75";
  }

  identity pmd-type-10GBASE-R {
    base pmd-type;
    description
      "10GBASE-R PCS/PMA as specified in Clause 49 over undefined
       PMD";
  }

  identity pmd-type-10GBASE-SR {
    base pmd-type;
    description
      "10GBASE-SR fiber over 850nm optics as specified in Clause 52";
  }

  identity pmd-type-10GBASE-SW {
    base pmd-type;
    description
      "10GBASE-SW fiber over 850nm optics as specified in Clause 52";
  }

  identity pmd-type-10GBASE-T {
    base pmd-type;
    description
      "Four-pair twisted-pair balanced copper cabling PHY as
       specified in Clause 55";
  }

  identity pmd-type-10GBASE-T1 {
    base pmd-type;
    description
      "Single balanced pair of conductors PHY as specified in Clause
       149";
  }

  identity pmd-type-10GBASE-X {
    base pmd-type;
    description
      "10GBASE-X PCS/PMA as specified in Clause 48 over undefined
       PMD";
  }

  identity pmd-type-10GPASS-XR {
    base pmd-type;
    description
      "Coax cable distribution network PHY continuous
       downstream/burst mode upstream PHY as specified in Clause 100
       and Clause 101";
  }

  identity pmd-type-10G-2p5GGBASE-SP1-Dx {
    base pmd-type;
    description
      "One single-mode fiber 10.3125 GBd continuous downstream /
       2.578125 GBd burst mode upstream OLT PHY supporting
       channel x of FSR set 1, as specified in 164.2,";
  }

  identity pmd-type-10G-2p5GGBASE-SP1-Uxy {
    base pmd-type;
    description
      "One single-mode fiber 10.3125 GBd continuous downstream /
       2.578125 GBd burst mode upstream ONU PHY supporting
       channels x to y of FSR set 1, as specified in 164.2";
  }

  identity pmd-type-10GBASE-SP {
    base pmd-type;
    description
      "Clause 164.3 10 Gb/s 256B/257B";
  }

  identity pmd-type-25G-10GBASE-PQG-D2 {
    base pmd-type;
    description
      "One single mode fiber, 1 × 25.78125 GBd continuous
       transmission / 1 × 10.3125 GBd burst mode reception, medium
       power class, as specified in Clause 141";
  }

  identity pmd-type-25G-10GBASE-PQG-D3 {
    base pmd-type;
    description
      "One single mode fiber, 1 × 25.78125 GBd continuous
       transmission / 1 × 10.3125 GBd burst mode reception, high
       power class, as specified in Clause 141";
  }

  identity pmd-type-25G-10GBASE-PQG-U2 {
    base pmd-type;
    description
      "One single mode fiber, 1 × 25.78125 GBd continuous reception
       / 1 × 10.3125 GBd burst mode transmission, medium power class,
       as specified in Clause 141";
  }

  identity pmd-type-25G-10GBASE-PQG-U3 {
    base pmd-type;
    description
      "One single mode fiber, 1 × 25.78125 GBd continuous reception
       / 1 × 10.3125 GBd burst mode transmission, high power class,
       as specified in Clause 141";
  }

  identity pmd-type-25G-10GBASE-PQX-D2 {
    base pmd-type;
    description
      "One single mode fiber, 1 × 25.78125 GBd continuous
       transmission / 1 × 10.3125 GBd burst mode reception, medium
       power class, as specified in Clause 141";
  }

  identity pmd-type-25G-10GBASE-PQX-D3 {
    base pmd-type;
    description
      "One single mode fiber, 1 × 25.78125 GBd continuous
       transmission / 1 × 10.3125 GBd burst mode reception, high
       power class, as specified in Clause 141";
  }

  identity pmd-type-25G-10GBASE-PQX-U2 {
    base pmd-type;
    description
      "One single mode fiber, 1 × 25.78125 GBd continuous reception
       / 1 × 10.3125 GBd burst mode transmission, medium power class,
       as specified in Clause 141";
  }

  identity pmd-type-25G-10GBASE-PQX-U3 {
    base pmd-type;
    description
      "One single mode fiber, 1 × 25.78125 GBd continuous reception
       / 1 × 10.3125 GBd burst mode transmission, high power class,
       as specified in Clause 141";
  }

  identity pmd-type-25GBASE-BR10-D {
    base pmd-type;
    description
      "One single-mode fiber OLT PHY supporting a distance of at
       least 10 km as specified in Clause 159";
  }

  identity pmd-type-25GBASE-BR10-U {
    base pmd-type;
    description
      "One single-mode fiber ONU PHY supporting a distance of at
       least 10 km as specified in Clause 159";
  }

  identity pmd-type-25GBASE-BR20-D {
    base pmd-type;
    description
      "One single-mode fiber OLT PHY supporting a distance of at
       least 20 km as specified in Clause 159";
  }

  identity pmd-type-25GBASE-BR20-U {
    base pmd-type;
    description
      "One single-mode fiber ONU PHY supporting a distance of at
       least 20 km as specified in Clause 159";
  }

  identity pmd-type-25GBASE-BR40-D {
    base pmd-type;
    description
      "One single-mode fiber OLT PHY supporting a distance of at
       least 40 km as specified in Clause 159";
  }

  identity pmd-type-25GBASE-BR40-U {
    base pmd-type;
    description
      "One single-mode fiber ONU PHY supporting a distance of at
       least 40 km as specified in Clause 159";
  }

  identity pmd-type-25GBASE-CR {
    base pmd-type;
    description
      "25GBASE-R PCS/PMA over shielded balanced copper cable PMD as
       specified in Clause 110";
  }

  identity pmd-type-25GBASE-CR-S {
    base pmd-type;
    description
      "25GBASE-R PCS/PMA over shielded balanced copper cable PMD as
       specified in Clause 110 without support for RS-FEC ";
  }

  identity pmd-type-25GBASE-ER {
    base pmd-type;
    description
      "25GBASE-R PCS/PMA over single-mode fiber PMD, with extended
       reach, as specified in Clause 114";
  }

  identity pmd-type-25GBASE-KR {
    base pmd-type;
    description
      "25GBASE-R PCS/PMA over an electrical backplane PMD as
       specified in Clause 111";
  }

  identity pmd-type-25GBASE-KR-S {
    base pmd-type;
    description
      "25GBASE-R PCS/PMA over an electrical backplane PMD as
       specified in Clause 111 without support for RS-FEC";
  }

  identity pmd-type-25GBASE-LR {
    base pmd-type;
    description
      "25GBASE-R PCS/PMA over single-mode fiber PMD, with long
       reach, as specified in Clause 114";
  }

  identity pmd-type-25GBASE-PQG-D2 {
    base pmd-type;
    description
      "One single mode fiber, 1 × 25.78125 GBd continuous
       transmission / 1 × 25.78125 GBd burst mode reception, medium
       power class,  as specified in Clause 141";
  }

  identity pmd-type-25GBASE-PQG-D3 {
    base pmd-type;
    description
      "One single mode fiber, 1 × 25.78125 GBd continuous
       transmission / 1 × 25.78125 GBd burst mode reception, high
       power class, as specified in Clause 141";
  }

  identity pmd-type-25GBASE-PQG-U2 {
    base pmd-type;
    description
      "One single mode fiber, 1 × 25.78125 GBd continuous reception
       / 1 × 25.78125 GBd burst mode transmission, medium power
       class, as specified in Clause 141";
  }

  identity pmd-type-25GBASE-PQG-U3 {
    base pmd-type;
    description
      "One single mode fiber, 1 × 25.78125 GBd continuous reception
       / 1 × 25.78125 GBd burst mode transmission, high power class,
       as specified in Clause 141";
  }

  identity pmd-type-25GBASE-PQX-D2 {
    base pmd-type;
    description
      "One single mode fiber, 1 × 25.78125 GBd continuous
       transmission / 1 × 25.78125 GBd burst mode reception, medium
       power class, as specified in Clause 141";
  }

  identity pmd-type-25GBASE-PQX-D3 {
    base pmd-type;
    description
      "One single mode fiber, 1 × 25.78125 GBd continuous
       transmission / 1 × 25.78125 GBd burst mode reception, high
       power class, as specified in Clause 141";
  }

  identity pmd-type-25GBASE-PQX-U2 {
    base pmd-type;
    description
      "One single mode fiber, 1 × 25.78125 GBd continuous reception
       / 1 × 25.78125 GBd burst mode transmission, medium power
       class, as specified in Clause 141";
  }

  identity pmd-type-25GBASE-PQX-U3 {
    base pmd-type;
    description
      "One single mode fiber, 1 × 25.78125 GBd continuous reception
       / 1 × 25.78125 GBd burst mode transmission, high power class,
       as specified in Clause 141";
  }

  identity pmd-type-25GBASE-R {
    base pmd-type;
    description
      "PCS as specified in Clause 107 with PMA as specified in
       Clause 109 over undefined PMD";
  }

  identity pmd-type-25GBASE-SR {
    base pmd-type;
    description
      "25GBASE-R PCS/PMA over multimode fiber PMD as specified in
       Clause 112";
  }

  identity pmd-type-25GBASE-T {
    base pmd-type;
    description
      "Four-pair twisted-pair balanced copper cabling PHY as
       specified in Clause 113";
  }

  identity pmd-type-40GBASE-CR4 {
    base pmd-type;
    description
      "40GBASE-R PCS/PMA over 4 lane shielded copper balanced cable
       PMD as specified in Clause 85";
  }

  identity pmd-type-40GBASE-ER4 {
    base pmd-type;
    description
      "40GBASE-R PCS/PMA over 4 WDM lane single mode fiber PMD, with
       extended reach, as specified in Clause 87";
  }

  identity pmd-type-40GBASE-FR {
    base pmd-type;
    description
      "40GBASE-R PCS/PMA over single mode fiber PMD as specified in
       Clause 89";
  }

  identity pmd-type-40GBASE-KR4 {
    base pmd-type;
    description
      "40GBASE-R PCS/PMA over an electrical backplane PMD as
       specified in Clause 84";
  }

  identity pmd-type-40GBASE-LR4 {
    base pmd-type;
    description
      "40GBASE-R PCS/PMA over 4 WDM lane single mode fiber PMD, with
       long reach, as specified in Clause 87";
  }

  identity pmd-type-40GBASE-R {
    base pmd-type;
    description
      "Multi-lane PCS as specified in Clause 82 over undefined
       PMA/PMD";
  }

  identity pmd-type-40GBASE-SR4 {
    base pmd-type;
    description
      "40GBASE-R PCS/PMA over 4 lane multimode fiber PMD as
       specified in Clause 86";
  }

  identity pmd-type-40GBASE-T {
    base pmd-type;
    description
      "Four-pair twisted-pair balanced copper cabling PHY as
       specified in Clause 113";
  }

  identity pmd-type-50G-10GBASE-PQG-D2 {
    base pmd-type;
    description
      "One single mode fiber, 2 × 25.78125 GBd continuous
       transmission / 1 × 10.3125 GBd burst mode reception, medium
       power class, as specified in Clause 141";
  }

  identity pmd-type-50G-10GBASE-PQG-D3 {
    base pmd-type;
    description
      "One single mode fiber, 2 × 25.78125 GBd continuous
       transmission / 1 × 10.3125 GBd burst mode reception, high
       power class, as specified in Clause 141";
  }

  identity pmd-type-50G-10GBASE-PQG-U2 {
    base pmd-type;
    description
      "One single mode fiber, 2 × 25.78125 GBd continuous reception
       / 1 × 10.3125 GBd burst mode transmission, medium power class,
       as specified in Clause 141";
  }

  identity pmd-type-50G-10GBASE-PQG-U3 {
    base pmd-type;
    description
      "One single mode fiber, 2 × 25.78125 GBd continuous reception
       / 1 × 10.3125 GBd burst mode transmission, high power class,
       as specified in Clause 141";
  }

  identity pmd-type-50G-10GBASE-PQX-D2 {
    base pmd-type;
    description
      "One single mode fiber, 2 × 25.78125 GBd continuous
       transmission / 1 × 10.3125 GBd burst mode reception, medium
       power class, as specified in Clause 141";
  }

  identity pmd-type-50G-10GBASE-PQX-D3 {
    base pmd-type;
    description
      "One single mode fiber, 2 × 25.78125 GBd continuous
       transmission / 1 × 10.3125 GBd burst mode reception, high
       power class, as specified in Clause 141";
  }

  identity pmd-type-50G-10GBASE-PQX-U2 {
    base pmd-type;
    description
      "One single mode fiber, 2 × 25.78125 GBd continuous reception
       / 1 × 10.3125 GBd burst mode transmission, medium power class,
       as specified in Clause 141";
  }

  identity pmd-type-50G-10GBASE-PQX-U3 {
    base pmd-type;
    description
      "One single mode fiber, 2 × 25.78125 GBd continuous reception
       / 1 × 10.3125 GBd burst mode transmission, high power class,
       as specified in Clause 141";
  }

  identity pmd-type-50G-25GBASE-PQG-D2 {
    base pmd-type;
    description
      "One single mode fiber, 2 × 25.78125 GBd continuous
       transmission / 1 × 25.78125 GBd burst mode reception, medium
       power class, as specified in Clause 141";
  }

  identity pmd-type-50G-25GBASE-PQG-D3 {
    base pmd-type;
    description
      "One single mode fiber, 2 × 25.78125 GBd continuous
       transmission / 1 × 25.78125 GBd burst mode reception, high
       power class, as specified in Clause 141";
  }

  identity pmd-type-50G-25GBASE-PQG-U2 {
    base pmd-type;
    description
      "One single mode fiber, 2 × 25.78125 GBd continuous reception
       / 1 × 25.78125 GBd burst mode transmission, medium power
       class, as specified in Clause 141";
  }

  identity pmd-type-50G-25GBASE-PQG-U3 {
    base pmd-type;
    description
      "One single mode fiber, 2 × 25.78125 GBd continuous reception
       / 1 × 25.78125 GBd burst mode transmission, high power class,
       as specified in Clause 141";
  }

  identity pmd-type-50G-25GBASE-PQX-D2 {
    base pmd-type;
    description
      "One single mode fiber, 2 × 25.78125 GBd continuous
       transmission / 1 × 25.78125 GBd burst mode reception, medium
       power class, as specified in Clause 141";
  }

  identity pmd-type-50G-25GBASE-PQX-D3 {
    base pmd-type;
    description
      "One single mode fiber, 2 × 25.78125 GBd continuous
       transmission / 1 × 25.78125 GBd burst mode reception, high
       power class, as specified in Clause 141";
  }

  identity pmd-type-50G-25GBASE-PQX-U2 {
    base pmd-type;
    description
      "One single mode fiber, 2 × 25.78125 GBd continuous reception
       / 1 × 25.78125 GBd burst mode transmission, medium power
       class, as specified in Clause 141";
  }

  identity pmd-type-50G-25GBASE-PQX-U3 {
    base pmd-type;
    description
      "One single mode fiber, 2 × 25.78125 GBd continuous reception
       / 1 × 25.78125 GBd burst mode transmission, high power class,
       as specified in Clause 141";
  }

  identity pmd-type-50GBASE-BR10-D {
    base pmd-type;
    description
      "One single-mode fiber OLT PHY supporting a distance of at
       least 10 km as specified in Clause 160";
  }

  identity pmd-type-50GBASE-BR10-U {
    base pmd-type;
    description
      "One single-mode fiber ONU PHY supporting a distance of at
       least 10 km as specified in Clause 160";
  }

  identity pmd-type-50GBASE-BR20-D {
    base pmd-type;
    description
      "One single-mode fiber OLT PHY supporting a distance of at
       least 20 km as specified in Clause 160";
  }

  identity pmd-type-50GBASE-BR20-U {
    base pmd-type;
    description
      "One single-mode fiber ONU PHY supporting a distance of at
       least 20 km as specified in Clause 160";
  }

  identity pmd-type-50GBASE-BR40-D {
    base pmd-type;
    description
      "One single-mode fiber OLT PHY supporting a distance of at
       least 40 km as specified in Clause 160";
  }

  identity pmd-type-50GBASE-BR40-U {
    base pmd-type;
    description
      "One single-mode fiber ONU PHY supporting a distance of at
       least 40 km as specified in Clause 160";
  }

  identity pmd-type-50GBASE-CR {
    base pmd-type;
    description
      "50GBASE-R PCS/PMA over shielded copper balanced cable PMD as
       specified in Clause 136 ";
  }

  identity pmd-type-50GBASE-ER {
    base pmd-type;
    description
      "50GBASE-R PCS/PMA over single-mode fiber PMD with reach up to
       at least 40 km as specified in Clause 139";
  }

  identity pmd-type-50GBASE-FR {
    base pmd-type;
    description
      "50GBASE-R PCS/PMA over single mode fiber PMD as specified in
       Clause 139";
  }

  identity pmd-type-50GBASE-KR {
    base pmd-type;
    description
      "50GBASE-R PCS/PMA over an electrical backplane PMD as
       specified in Clause 137";
  }

  identity pmd-type-50GBASE-LR {
    base pmd-type;
    description
      "50GBASE-R PCS/PMA over single mode fiber PMD as specified in
       Clause 139";
  }

  identity pmd-type-50GBASE-PQG-D2 {
    base pmd-type;
    description
      "One single mode fiber, 2 × 25.78125 GBd continuous
       transmission / 2 × 25.78125 GBd burst mode reception, medium
       power class, as specified in Clause 141";
  }

  identity pmd-type-50GBASE-PQG-D3 {
    base pmd-type;
    description
      "One single mode fiber, 2 × 25.78125 GBd continuous
       transmission / 2 × 25.78125 GBd burst mode reception, high
       power class, as specified in Clause 141";
  }

  identity pmd-type-50GBASE-PQG-U2 {
    base pmd-type;
    description
      "One single mode fiber, 2 × 25.78125 GBd continuous reception
       / 2 × 25.78125 GBd burst mode transmission, medium power
       class, as specified in Clause 141";
  }

  identity pmd-type-50GBASE-PQG-U3 {
    base pmd-type;
    description
      "One single mode fiber, 2 × 25.78125 GBd continuous reception
       / 2 × 25.78125 GBd burst mode transmission, high power class,
       as specified in Clause 141";
  }

  identity pmd-type-50GBASE-PQX-D2 {
    base pmd-type;
    description
      "One single mode fiber, 2 × 25.78125 GBd continuous
       transmission / 2 × 25.78125 GBd burst mode reception, medium
       power class, as specified in Clause 141";
  }

  identity pmd-type-50GBASE-PQX-D3 {
    base pmd-type;
    description
      "One single mode fiber, 2 × 25.78125 GBd continuous
       transmission / 2 × 25.78125 GBd burst mode reception, high
       power class, as specified in Clause 141";
  }

  identity pmd-type-50GBASE-PQX-U2 {
    base pmd-type;
    description
      "One single mode fiber, 2 × 25.78125 GBd continuous reception
       / 2 × 25.78125 GBd burst mode transmission, medium power
       class, as specified in Clause 141";
  }

  identity pmd-type-50GBASE-PQX-U3 {
    base pmd-type;
    description
      "One single mode fiber, 2 × 25.78125 GBd continuous reception
       / 2 × 25.78125 GBd burst mode transmission, high power class,
       as specified in Clause 141";
  }

  identity pmd-type-50GBASE-R {
    base pmd-type;
    description
      "Multi-lane PCS as specified in Clause 133 with PMA as
       specified in Clause 135 over undefined PMD";
  }

  identity pmd-type-50GBASE-SR {
    base pmd-type;
    description
      "50GBASE-R PCS/PMA over multimode fiber PMD as specified in
       Clause 138";
  }

  identity pmd-type-100CR1 {
    base pmd-type;
    description
      "100GBASE-CR1 as specified in Clause 162 or 100GBASE-KR1 as
       specified in Clause 163";
  }

  identity pmd-type-100GBASE-CR2 {
    base pmd-type;
    description
      "100GBASE-R PCS/PMA over 2 lane shielded copper balanced cable
       PMD as specified in Clause 136";
  }

  identity pmd-type-100GBASE-CR4 {
    base pmd-type;
    description
      "100GBASE-R PCS/PMA over 4 lane shielded copper balanced cable
       PMD as specified in Clause 92";
  }

  identity pmd-type-100GBASE-CR10 {
    base pmd-type;
    description
      "100GBASE-R PCS/PMA over 10 lane shielded copper balanced
       cable PMD as specified in Clause 85";
  }

  identity pmd-type-100GBASE-DR {
    base pmd-type;
    description
      "100GBASE-R PCS/PMA over single mode fiber PMD as specified in
       Clause 140";
  }

  identity pmd-type-100GBASE-ER4 {
    base pmd-type;
    description
      "100GBASE-R PCS/PMA over 4 WDM lane single mode fiber PMD,
       with extended reach, as specified in Clause 88";
  }

  identity pmd-type-100GBASE-FR1 {
    base pmd-type;
    description
      "100GBASE-R PCS/PMA over single-mode fiber PMD with reach up
       to at least 2 km as specified in Clause 140";
  }

  identity pmd-type-100GBASE-KP4 {
    base pmd-type;
    description
      "100GBASE-P PCS/PMA over an electrical backplane PMD as
       specified in Clause 94";
  }

  identity pmd-type-100GBASE-KR2 {
    base pmd-type;
    description
      "100GBASE-R PCS/PMA over an electrical backplane PMD as
       specified in Clause 137";
  }

  identity pmd-type-100GBASE-KR4 {
    base pmd-type;
    description
      "100GBASE-R PCS/PMA over an electrical backplane PMD as
       specified in Clause 93";
  }

  identity pmd-type-100GBASE-LR1 {
    base pmd-type;
    description
      "100GBASE-R PCS/PMA over single-mode fiber PMD with reach up
       to at least 10 km as specified in Clause 140";
  }

  identity pmd-type-100GBASE-LR4 {
    base pmd-type;
    description
      "100GBASE-R PCS/PMA over 4 WDM lane single mode fiber PMD,
       with long reach, as specified in Clause 88";
  }

  identity pmd-type-100GBASE-R {
    base pmd-type;
    description
      "Multi-lane PCS as specified in Clause 82 over undefined
       100GBASE-R or 100GBASE-P PMA/PMD";
  }

  identity pmd-type-100GBASE-SR1 {
    base pmd-type;
    description
      "100GBASE-R PCS/PMA over multimode fiber PMD with
       reach up to at least 100 m as specified in Clause 167";
  }

  identity pmd-type-100GBASE-SR2 {
    base pmd-type;
    description
      "100GBASE-R PCS/PMA over 2 lane multimode fiber PMD as
       specified in Clause 138";
  }

  identity pmd-type-100GBASE-SR4 {
    base pmd-type;
    description
      "100GBASE-R PCS/PMA over 4 lane multimode fiber PMD as
       specified in Clause 95";
  }

  identity pmd-type-100GBASE-SR10 {
    base pmd-type;
    description
      "100GBASE-R PCS/PMA over 10 lane multimode fiber PMD as
       specified in Clause 86";
  }

  identity pmd-type-100GBASE-VR1 {
    base pmd-type;
    description
      "100GBASE-R PCS/PMA over multimode fiber PMD with
       reach up to at least 50 m as specified in Clause 167";
  }

  identity pmd-type-100GBASE-ZR {
    base pmd-type;
    description
      "100GBASE-R PCS/100GBASE-ZR PMA over a PMD with reach up to at
       least 80 km as specified in Clause 154";
  }

  identity pmd-type-200GBASE-CR2 {
    base pmd-type;
    description
      "200GBASE-CR2 as specified in Clause 162 or 200GBASE-KR2 as
       specified in Clause 163";
  }

  identity pmd-type-200GBASE-CR4 {
    base pmd-type;
    description
      "200GBASE-R PCS/PMA over 4 lane shielded copper balanced cable
       PMD as specified in Clause 136 ";
  }

  identity pmd-type-200GBASE-DR4 {
    base pmd-type;
    description
      "200GBASE-R PCS/PMA over 4-lane single-mode fiber PMD as
       specified in Clause 121";
  }

  identity pmd-type-200GBASE-ER4 {
    base pmd-type;
    description
      "200GBASE-R PCS/PMA over 4 WDM lane single-mode fiber PMD with
       reach up to at least 40 km as specified in Clause 122";
  }

  identity pmd-type-200GBASE-FR4 {
    base pmd-type;
    description
      "200GBASE-R PCS/PMA over 4 WDM lane single-mode fiber PMD with
       reach up to at least 2 km as specified in Clause 122";
  }

  identity pmd-type-200GBASE-KR2 {
    base pmd-type;
    description
      "200GBASE-R PCS/PMA over an electrical backplane PMD
       as specified in Clause 163";
  }

  identity pmd-type-200GBASE-KR4 {
    base pmd-type;
    description
      "200GBASE-R PCS/PMA over an electrical backplane PMD as
       specified in Clause 137";
  }

  identity pmd-type-200GBASE-LR4 {
    base pmd-type;
    description
      "200GBASE-R PCS/PMA over 4 WDM lane single-mode fiber PMD with
       reach up to at least 10 km as specified in Clause 122";
  }

  identity pmd-type-200GBASE-R {
    base pmd-type;
    description
      "Multi-lane PCS as specified in Clause 119 over undefined
       PMA/PMD";
  }

  identity pmd-type-200GBASE-SR2 {
    base pmd-type;
    description
      "200GBASE-R PCS/PMA over 2 lane multimode fiber PMD with
       reach up to at least 100 m as specified in Clause 167";
  }

  identity pmd-type-200GBASE-SR4 {
    base pmd-type;
    description
      "200GBASE-R PCS/PMA over 4 lane multimode fiber PMD as
       specified in Clause 138";
  }

  identity pmd-type-200GBASE-VR2 {
    base pmd-type;
    description
      "200GBASE-R PCS/PMA over 2 lane multimode fiber PMD with
       reach up to at least 50 m as specified in Clause 167";
  }

  identity pmd-type-400GBASE-DR4 {
    base pmd-type;
    description
      "400GBASE-R PCS/PMA over 4-lane single-mode fiber PMD as
       specified in Clause 124";
  }

  identity pmd-type-400GBASE-DR4-2 {
    base pmd-type;
    description
      "400GBASE-R PCS/PMA over 4 single-mode fibers in each
       direction PMD with reach up to at least 2 km as specified
       in Clause 124";
  }

  identity pmd-type-400GBASE-ER8 {
    base pmd-type;
    description
      "400GBASE-R PCS/PMA over 8 WDM lane single-mode fiber PMD with
       reach up to at least 40 km as specified in Clause 122";
  }

  identity pmd-type-400GBASE-FR4 {
    base pmd-type;
    description
      "400GBASE-R PCS/PMA over 4 WDM lane single-mode fiber PMD with
       reach up to at least 2 km as specified in Clause 151";
  }

  identity pmd-type-400GBASE-FR8 {
    base pmd-type;
    description
      "400GBASE-R PCS/PMA over 8 WDM lane single-mode fiber PMD with
       reach up to at least 2 km as specified in Clause 122";
  }

  identity pmd-type-400GBASE-LR4-6 {
    base pmd-type;
    description
      "400GBASE-R PCS/PMA over 4 WDM lane single-mode fiber PMD with
       reach up to at least 6 km as specified in Clause 151";
  }

  identity pmd-type-400GBASE-LR8 {
    base pmd-type;
    description
      "400GBASE-R PCS/PMA over 8 WDM lane single-mode fiber PMD with
       reach up to at least 10 km as specified in Clause 122";
  }

  identity pmd-type-400GBASE-R {
    base pmd-type;
    description
      "Multi-lane PCS as specified in Clause 119 over undefined
       PMA/PMD";
  }

  identity pmd-type-400GBASE-SR4 {
    base pmd-type;
    description
      "400GBASE-R PCS/PMA over 4 lane multimode fiber PMD with
       reach up to at least 100 m as specified in Clause 167";
  }

  identity pmd-type-400GBASE-SR4d2 {
    base pmd-type;
    description
      "400GBASE-R PCS/PMA over 8-lane multimode fiber PMD as
       specified in Clause 150";
  }

  identity pmd-type-400GBASE-SR8 {
    base pmd-type;
    description
      "400GBASE-R PCS/PMA over 8-lane multimode fiber PMD as
       specified in Clause 138";
  }

  identity pmd-type-400GBASE-SR16 {
    base pmd-type;
    description
      "400GBASE-R PCS/PMA over 16-lane multimode fiber PMD as
       specified in Clause 123";
  }

  identity pmd-type-400GBASE-VR4 {
    base pmd-type;
    description
      "400GBASE-R PCS/PMA over 4 lane multimode fiber PMD with
       reach up to at least 50 m as specified in Clause 167";
  }

  identity pmd-type-800GBASE-CR8 {
    base pmd-type;
    description
      "800GBASE-R PCS/PMA over 8-lane shielded balanced copper cable
       PMD as specified in Clause 162";
  }

  identity pmd-type-800GBASE-DR8 {
    base pmd-type;
    description
      "800GBASE-R PCS/PMA over 8 single-mode fibers in each
          direction PMD with reach up to at least 500 m as specified
          in Clause 124";
  }

  identity pmd-type-800GBASE-DR8-2 {
    base pmd-type;
    description
      "800GBASE-R PCS/PMA over 8 single-mode fibers in each
       direction PMD with reach up to at least 2 km as specified
       in Clause 124";
  }

  identity pmd-type-800GBASE-KR8 {
    base pmd-type;
    description
      "800GBASE-R PCS/PMA over an electrical backplane PMD as
       specified in Clause 163";
  }

  identity pmd-type-800GBASE-R {
    base pmd-type;
    description
      "Multi-lane PCS as specified in Clause 172 over
       undefined PMA/PMD";
  }

  identity pmd-type-800GBASE-SR8 {
    base pmd-type;
    description
      "800GBASE-R PCS/PMA over 8 multimode fibers in each
       direction PMD with reach up to at least 100 m as specified
       in Clause 167";
  }

  identity pmd-type-800GBASE-VR8 {
    base pmd-type;
    description
      "800GBASE-R PCS/PMA over 8 multimode fibers in each
       direction PMD with reach up to at least 50 m as specified
       in Clause 167";
  }

  typedef pmd-type-list {
    type bits {
      /* 802.3-2022 */
      bit bOther {
        description
          "Other";
      }
      bit b10baseT {
        description
          "10BASE-T";
      }
      bit b10baseFL {
        description
          "10BASE-FL";
      }
      bit b100baseTX {
        description
          "100BASE-TX";
      }
      bit b100baseFX {
        description
          "100BASE-FX";
      }
      bit b1000baseX {
        description
          "1000BASE-X";
      }
      bit b1000baseLX {
        description
          "1000BASE-LX";
      }
      bit b1000baseSX {
        description
          "1000BASE-SX";
      }
      bit b1000baseCX {
        description
          "1000BASE-CX";
      }
      bit b1000baseT {
        description
          "1000BASE-T";
      }
      bit b10GbaseX {
        description
          "10GBASE-X";
      }
      bit b10GbaseLX4 {
        description
          "10GBASE-LX4";
      }
      bit b10GbaseR {
        description
          "10GBASE-R";
      }
      bit b10GbaseER {
        description
          "10GBASE-ER";
      }
      bit b10GbaseLR {
        description
          "10GBASE-LR";
      }
      bit b10GbaseSR {
        description
          "10GBASE-SR";
      }
      bit b10GbaseSW {
        description
          "10GBASE-SW";
      }
      bit b10GbaseCX4 {
        description
          "10GBASE-CX4";
      }
      bit b100BaseBX10D {
        description
          "100BASE-BX10D";
      }
      bit b100BaseBX10U {
        description
          "100BASE-BX10U";
      }
      bit b100BaseLX10 {
        description
          "100BASE-LX10";
      }
      bit b1000BaseBX10D {
        description
          "1000BASE-BX10D";
      }
      bit b1000BaseBX10U {
        description
          "1000BASE-BX10U";
      }
      bit b1000BaseLX10 {
        description
          "1000BASE-LX10";
      }
      bit b1000BasePX10D {
        description
          "1000BASE-PX10D";
      }
      bit b1000BasePX10U {
        description
          "1000BASE-PX10U";
      }
      bit b1000BasePX20D {
        description
          "1000BASE-PX20D";
      }
      bit b1000BasePX20U {
        description
          "1000BASE-PX20U";
      }
      bit b10GbaseT {
        description
          "10GBASE-T";
      }
      bit b10GbaseLRM {
        description
          "10GBASE-LRM";
      }
      bit b1000baseKX {
        description
          "1000BASE-KX";
      }
      bit b10GbaseKX4 {
        description
          "10GBASE-KX4";
      }
      bit b10GbaseKR {
        description
          "10GBASE-KR";
      }
      bit b10G1GbasePRXD1 {
        description
          "10/1GBASE-PRXD1";
      }
      bit b10G1GbasePRXD2 {
        description
          "10/1GBASE-PRXD2";
      }
      bit b10G1GbasePRXD3 {
        description
          "10/1GBASE-PRXD3";
      }
      bit b10G1GbasePRXU1 {
        description
          "10/1GBASE-PRXU1";
      }
      bit b10G1GbasePRXU2 {
        description
          "10/1GBASE-PRXU2";
      }
      bit b10G1GbasePRXU3 {
        description
          "10/1GBASE-PRXU3";
      }
      bit b10GbasePRD1 {
        description
          "10GBASE-PRD1";
      }
      bit b10GbasePRD2 {
        description
          "10GBASE-PRD2";
      }
      bit b10GbasePRD3 {
        description
          "10GBASE-PRD3";
      }
      bit b10GbasePRU1 {
        description
          "10GBASE-PRU1";
      }
      bit b10GbasePRU3 {
        description
          "10GBASE-PRU3";
      }
      bit b40GbaseKR4 {
        description
          "40GBASE-KR4";
      }
      bit b40GbaseCR4 {
        description
          "40GBASE-CR4";
      }
      bit b40GbaseSR4 {
        description
          "40GBASE-SR4";
      }
      bit b40GbaseFR {
        description
          "40GBASE-FR";
      }
      bit b40GbaseLR4 {
        description
          "40GBASE-LR4";
      }
      bit b100GbaseCR10 {
        description
          "100GBASE-CR10";
      }
      bit b100GbaseSR10 {
        description
          "100GBASE-SR10";
      }
      bit b100GbaseLR4 {
        description
          "100GBASE-LR4";
      }
      bit b100GbaseER4 {
        description
          "100GBASE-ER4";
      }
      bit b1000baseT1 {
        description
          "1000BASE-T1";
      }
      bit b1000basePX30D {
        description
          "1000BASE-PX30D";
      }
      bit b1000basePX30U {
        description
          "1000BASE-PX30U";
      }
      bit b1000basePX40D {
        description
          "1000BASE-PX40D";
      }
      bit b1000basePX40U {
        description
          "1000BASE-PX40U";
      }
      bit b10G1GbasePRXD4 {
        description
          "10/1GBASE-PRXD4";
      }
      bit b10G1GbasePRXU4 {
        description
          "10/1GBASE-PRXU4";
      }
      bit b10GbasePRD4 {
        description
          "10GBASE-PRD4";
      }
      bit b10GbasePRU4 {
        description
          "10GBASE-PRU4";
      }
      bit b25GbaseCR {
        description
          "25GBASE-CR";
      }
      bit b25GbaseCRS {
        description
          "25GBASE-CRS";
      }
      bit b25GbaseKR {
        description
          "25GBASE-KR";
      }
      bit b25GbaseKRS {
        description
          "25GBASE-KRS";
      }
      bit b25GbaseR {
        description
          "25GBASE-R";
      }
      bit b25GbaseSR {
        description
          "25GBASE-SR";
      }
      bit b25GbaseT {
        description
          "25GBASE-T";
      }
      bit b40GbaseER4 {
        description
          "40GBASE-ER4";
      }
      bit b40GbaseR {
        description
          "40GBASE-R";
      }
      bit b40GbaseT {
        description
          "40GBASE-T";
      }
      bit b100GbaseCR4 {
        description
          "100GBASE-CR4";
      }
      bit b100GbaseKR4 {
        description
          "100GBASE-KR4";
      }
      bit b100GbaseKP4 {
        description
          "100GBASE-KP4";
      }
      bit b100GbaseR {
        description
          "100GBASE-R";
      }
      bit b100GbaseSR4 {
        description
          "100GBASE-SR4";
      }
      bit b2p5GbaseT {
        description
          "2.5GBASE-T";
      }
      bit b5GbaseT {
        description
          "5GBASE-T";
      }
      bit b100baseT1 {
        description
          "100BASE-T1";
      }
      bit b1000baseRHA {
        description
          "1000BASE-RHA";
      }
      bit b1000baseRHB {
        description
          "1000BASE-RHB";
      }
      bit b1000baseRHC {
        description
          "1000BASE-RHC";
      }
      bit b2p5GbaseKX {
        description
          "2.5GBASE-KX";
      }
      bit b2p5GbaseX {
        description
          "2.5GBASE-X";
      }
      bit b5GbaseKR {
        description
          "5GBASE-KR";
      }
      bit b5GbaseR {
        description
          "5GBASE-R";
      }
      bit b10GpassXR {
        description
          "10GPASS-XR";
      }
      bit b25GbaseLR {
        description
          "25GBASE-LR";
      }
      bit b25GbaseER {
        description
          "25GBASE-ER";
      }
      bit b50GbaseR {
        description
          "50GBASE-R";
      }
      bit b50GbaseCR {
        description
          "50GBASE-CR";
      }
      bit b50GbaseKR {
        description
          "50GBASE-KR";
      }
      bit b50GbaseSR {
        description
          "50GBASE-SR";
      }
      bit b50GbaseFR {
        description
          "50GBASE-FR";
      }
      bit b50GbaseLR {
        description
          "50GBASE-LR";
      }
      bit b50GbaseER {
        description
          "50GBASE-ER";
      }
      bit b100GbaseCR2 {
        description
          "100GBASE-CR2";
      }
      bit b100GbaseKR2 {
        description
          "100GBASE-KR2";
      }
      bit b100GbaseSR2 {
        description
          "100GBASE-SR2";
      }
      bit b100GbaseDR {
        description
          "100GBASE-DR";
      }
      bit b200GbaseR {
        description
          "200GBASE-R";
      }
      bit b200GbaseDR4 {
        description
          "200GBASE-DR4";
      }
      bit b200GbaseFR4 {
        description
          "200GBASE-FR4";
      }
      bit b200GbaseLR4 {
        description
          "200GBASE-LR4";
      }
      bit b200GbaseCR4 {
        description
          "200GBASE-CR4";
      }
      bit b200GbaseKR4 {
        description
          "200GBASE-KR4";
      }
      bit b200GbaseSR4 {
        description
          "200GBASE-SR4";
      }
      bit b200GbaseER4 {
        description
          "200GBASE-ER4";
      }
      bit b400GbaseR {
        description
          "400GBASE-R";
      }
      bit b400GbaseSR16 {
        description
          "400GBASE-SR16";
      }
      bit b400GbaseDR4 {
        description
          "400GBASE-DR4";
      }
      bit b400GbaseFR8 {
        description
          "400GBASE-FR8";
      }
      bit b400GbaseLR8 {
        description
          "400GBASE-LR8";
      }
      bit b400GbaseER8 {
        description
          "400GBASE-ER8";
      }
      bit b10baseT1L {
        description
          "10BASE-T1L";
      }
      bit b10baseT1S {
        description
          "10BASE-T1S";
      }
      bit b10baseT1SMD {
        description
          "10BASE-T1SMD";
      }
      bit b100GbaseFR1 {
        description
          "100GBASE-FR1";
      }
      bit b100GbaseLR1 {
        description
          "100GBASE-LR1";
      }
      bit b100GBASE-CR1 {
        description
          "100GBASE-LR1";
      }
      bit b400GbaseFR4 {
        description
          "400GBASE-FR4";
      }
      bit b400GbaseLR46 {
        description
          "400GBASE-LR46";
      }
      bit b400GbaseSR8 {
        description
          "400GBASE-SR8";
      }
      bit b400GbaseSR4p2 {
        description
          "400GBASE-SR4p2";
      }
      bit b2p5GbaseT1 {
        description
          "2.5GBASE-T1";
      }
      bit b5GbaseT1 {
        description
          "5GBASE-T1";
      }
      bit b10GbaseT1 {
        description
          "10GBASE-T1";
      }
      bit b25G10GbasePQGD2 {
        description
          "25/10GBASE-PQGD2";
      }
      bit b25G10GbasePQGD3 {
        description
          "25/10GBASE-PQGD3";
      }
      bit b25G10GbasePQGU2 {
        description
          "25/10GBASE-PQGU2";
      }
      bit b25G10GbasePQGU3 {
        description
          "25/10GBASE-PQGU3";
      }
      bit b25G10GbasePQXD2 {
        description
          "25/10GBASE-PQXD2";
      }
      bit b25G10GbasePQXD3 {
        description
          "25/10GBASE-PQXD3";
      }
      bit b25G10GbasePQXU2 {
        description
          "25/10GBASE-PQXU2";
      }
      bit b25G10GbasePQXU3 {
        description
          "25/10GBASE-PQXU3";
      }
      bit b25GbasePQGD2 {
        description
          "25GBASE-PQGD2";
      }
      bit b25GbasePQGD3 {
        description
          "25GBASE-PQGD3";
      }
      bit b25GbasePQGU2 {
        description
          "25GBASE-PQGU2";
      }
      bit b25GbasePQGU3 {
        description
          "25GBASE-PQGU3";
      }
      bit b25GbasePQXD2 {
        description
          "25GBASE-PQXD2";
      }
      bit b25GbasePQXD3 {
        description
          "25GBASE-PQXD3";
      }
      bit b25GbasePQXU2 {
        description
          "25GBASE-PQXU2";
      }
      bit b25GbasePQXU3 {
        description
          "25GBASE-PQXU3";
      }
      bit b50G10GbasePQGD2 {
        description
          "50/10GBASE-PQGD2";
      }
      bit b50G10GbasePQGD3 {
        description
          "50/10GBASE-PQGD3";
      }
      bit b50G10GbasePQGU2 {
        description
          "50/10GBASE-PQGU2";
      }
      bit b50G10GbasePQGU3 {
        description
          "50/10GBASE-PQGU3";
      }
      bit b50G10GbasePQXD2 {
        description
          "50/10GBASE-PQXD2";
      }
      bit b50G10GbasePQXD3 {
        description
          "50/10GBASE-PQXD3";
      }
      bit b50G10GbasePQXU2 {
        description
          "50/10GBASE-PQXU2";
      }
      bit b50G10GbasePQXU3 {
        description
          "50/10GBASE-PQXU3";
      }
      bit b50G25GbasePQGD2 {
        description
          "50/25GBASE-PQGD2";
      }
      bit b50G25GbasePQGD3 {
        description
          "50/25GBASE-PQGD3";
      }
      bit b50G25GbasePQGU2 {
        description
          "50/25GBASE-PQGU2";
      }
      bit b50G25GbasePQGU3 {
        description
          "50/25GBASE-PQGU3";
      }
      bit b50G25GbasePQXD2 {
        description
          "50/25GBASE-PQXD2";
      }
      bit b50G25GbasePQXD3 {
        description
          "50/25GBASE-PQXD3";
      }
      bit b50G25GbasePQXU2 {
        description
          "50/25GBASE-PQXU2";
      }
      bit b50G25GbasePQXU3 {
        description
          "50/25GBASE-PQXU3";
      }
      bit b50GbasePQGD2 {
        description
          "50GBASE-PQGD2";
      }
      bit b50GbasePQGD3 {
        description
          "50GBASE-PQGD3";
      }
      bit b50GbasePQGU2 {
        description
          "50GBASE-PQGU2";
      }
      bit b50GbasePQGU3 {
        description
          "50GBASE-PQGU3";
      }
      bit b50GbasePQXD2 {
        description
          "50GBASE-PQXD2";
      }
      bit b50GbasePQXD3 {
        description
          "50GBASE-PQXD3";
      }
      bit b50GbasePQXU2 {
        description
          "50GBASE-PQXU2";
      }
      bit b50GbasePQXU3 {
        description
          "50GBASE-PQXU3";
      }
      bit b100GbaseZR {
        description
          "100GBASE-ZR";
      }
      bit b10GbaseBR10D {
        description
          "10GBASE-BR10D";
      }
      bit b10GbaseBR10U {
        description
          "10GBASE-BR10U";
      }
      bit b10GbaseBR20D {
        description
          "10GBASE-BR20D";
      }
      bit b10GbaseBR20U {
        description
          "10GBASE-BR20U";
      }
      bit b10GbaseBR40D {
        description
          "10GBASE-BR40D";
      }
      bit b10GbaseBR40U {
        description
          "10GBASE-BR40U";
      }
      bit b25GbaseBR10D {
        description
          "25GBASE-BR10D";
      }
      bit b25GbaseBR10U {
        description
          "25GBASE-BR10U";
      }
      bit b25GbaseBR20D {
        description
          "25GBASE-BR20D";
      }
      bit b25GbaseBR20U {
        description
          "25GBASE-BR20U";
      }
      bit b25GbaseBR40D {
        description
          "25GBASE-BR40D";
      }
      bit b25GbaseBR40U {
        description
          "25GBASE-BR40U";
      }
      bit b50GbaseBR10D {
        description
          "50GBASE-BR10D";
      }
      bit b50GbaseBR10U {
        description
          "50GBASE-BR10U";
      }
      bit b50GbaseBR20D {
        description
          "50GBASE-BR20D";
      }
      bit b50GbaseBR20U {
        description
          "50GBASE-BR20U";
      }
      bit b50GbaseBR40D {
        description
          "50GBASE-BR40D";
      }
      bit b50GbaseBR40U {
        description
          "50GBASE-BR40U";
      }
      /* 802.3ck-2022 */
      bit b100GBaseCR1 {
        description
          "100GBASE-CR1";
      }
      bit b100GBaseKR1 {
        description
          "100GBASE-KR1";
      }
      bit b200GBaseCR2 {
        description
          "200GBASE-CR2";
      }
      bit b200GBaseKR2 {
        description
          "200GBASE-KR2";
      }
      bit b400GBaseCR4 {
        description
          "400GBASE-CR4";
      }
      bit b400GBaseKR4 {
        description
          "400GBASE-KR4";
      }
      /* 802.3cs-2022 */
      bit b10G2p5GBaseSP1Dx {
        description
          "10/2.5GBASE-SP1-Dx";
      }
      bit b10G2p5GBaseSP1Uxy {
        description
          "10/2.5GBASE-SP1-Uxy";
      }
      bit b10GBaseSP1Dx {
        description
          "10GBASE-SP1-Dx";
      }
      bit b10GBaseSP1Uxy {
        description
          "10GBASE-SP1-Uxy";
      }
      /* 802.3db-2022 */
      bit b100GBaseSR1 {
        description
          "100GBASE-SR1";
      }
      bit b100GBaseVR1 {
        description
          "100GBASE-VR1";
      }
      bit bit200GBaseSR2 {
        description
          "200GBASE-SR2";
      }
      bit bit200GBaseVR2 {
        description
          "200GBASE-VR2";
      }
      bit bit400GBaseSR4 {
        description
          "400GBASE-SR4";
      }
      bit bit400GBaseVR4 {
        description
          "400GBASE-VR4";
      }
      /* 802.3cz-2023 */
      bit b2p5GbaseAU {
        description
          "2.5GBASE-AU";
      }
      bit b5GbaseAU {
        description
          "5GBASE-AU";
      }
      bit b10GbaseAU {
        description
          "10GBASE-AU";
      }
      bit b25GbaseAU {
        description
          "25GBASE-AU";
      }
      bit b50GbaseAU {
        description
          "50GBASE-AU";
      }
      /* 802.3cy-2023 */
      bit b25GbaseT1 {
        description
          "25GBASE-T1";
      }
      /* 802.3ca-2023 */
      bit bit400GBaseDR4d2 {
        description
          "400GBASE-DR4-2";
      }
      bit bit800GBaseCR8 {
        description
          "800GBASE-CR8";
      }
      bit bit800GBaseDR8 {
        description
          "800GBASE-DR8";
      }
      bit bit800GBaseDR8d2 {
        description
          "800GBASE-DR8-2";
      }
      bit bit800GBaseKR8 {
        description
          "800GBASE-KR8";
      }
      bit bit800GBaseR {
        description
          "800GBASE-R";
      }
      bit bit800GBaseSR8 {
        description
          "800GBASE-SR8";
      }
      bit bit800GBaseVR8 {
        description
          "800GBASE-VR8";
      }
    }
    description
      "This data type is used to report the set of pmd-type values
       an interface can implement.";
    reference
      "IEEE Std 802.3, Clause 30.5.1.1.3 aMAUTypeList";
  }

  typedef media-available-type {
    type enumeration {
      /* 802.3-2022 */
      enum other {
        description
          "Undefined";
      }
      enum unknown {
        description
          "initializing, true state not yet known";
      }
      enum available {
        description
          "link or light normal, loopback normal";
      }
      enum notAvailable {
        description
          "link loss or low light, no loopback";
      }
      enum remoteFault {
        description
          "remote fault with no detail";
      }
      enum remoteJabber {
        description
          "remote fault, reason known to be jabber";
      }
      enum remoteLinkLoss {
        description
          "remote fault, reason known to be far-end link loss";
      }
      enum remoteTest {
        description
          "remote fault, reason known to be test";
      }
      enum offline {
        description
          "offline, applies only to Clause 37 Auto-Negotiation";
      }
      enum autoNegError {
        description
          "Auto-Negotiation Error, applies only to Clause 37
                auto-Negotiation";
      }
      enum pmdLinkFault {
        description
          "PMD/PMA receive link fault";
      }
      enum pcsLinkFault {
        description
          "PCS receive link fault";
      }
      enum excessiveBER {
        description
          "PCS Bit Error Ratio monitor reporting excessive error
           ratio";
      }
      enum dxsLinkFault {
        description
          "DTE XGXS receive link fault, applies only to XAUI ";
      }
      enum pxsLinkFault {
        description
          "PHY XGXS transmit link fault, applies only to XAUI";
      }
    }
    description
      "This data type is used to report media availability.";
    reference
      "IEEE Std 802.3, Clause 30.5.1.1.4 aMediaAvailable";
  }

  typedef auto-neg-ability-bits {
    type bits {
      /* Not PHY specific */
      bit bOther {
        description
          "Other abilities beyond the scope of this module.";
      }
      bit bHalfDuplex {
        description
          "Half duplex";
      }
      bit bFullDuplex {
        description
          "Full duplex";
      }
      bit bPause {
        description
          "PAUSE operation as defined in Annex 31B";
      }
      bit bAPause {
        description
          "Asymmetric PAUSE operation as defined in
           Clause 37, Annex 28B, and Annex 31B";
      }
      bit bSPause {
        description
          "Symmetric PAUSE operation as defined in
           Clause 37, Annex 28B, and Annex 31B";
      }
      bit bBPause {
        description
          "Asymmetric and Symmetric PAUSE operation
           as defined in Clause 37, Annex 28B, and Annex 31B";
      }
      bit bRemFault {
        description
          "Remote fault bit (RF) as specified in Clause 73
           and Clause 98";
      }
      bit bRemFault1 {
        description
          "Remote fault bit 1 (RF1) as specified in Clause 37";
      }
      bit bRemFault2 {
        description
          "Remote fault bit 2 (RF2) as specified in Clause 37";
      }
      bit bFECCapable {
        description
          "FEC ability as specified in Clause 73 (see 73.6.5)
           and Clause 74";
      }
      bit bFECRequested {
        description
          "FEC requested as specified in Clause 73 (see 73.6.5)
           and Clause 74";
      }
      bit bRSFEC25Greq {
        description
          "25G RS-FEC requested as specified in Clause 73 (see 73.6.5)
           and Clause 108";
      }
      bit bBaseFEC25Greq {
        description
          "25Gb/s BASE-R FEC ";
      }
      bit bForceMS {
        description
          "Force MASTER-SLAVE as specified in Clause 98 (see
           98.2.1.2.5)";
      }
      /* PHY/PMD  */
      bit b10baseT {
        description
          "10BASE-T as defined in Clause 14";
      }
      bit b10baseT1L {
        description
          "10BASE-T1L as specified in Clause 146";
      }
      bit b10baseT1S {
        description
          "10BASE-T1S as specified in Clause 147";
      }
      bit b100baseTX {
        description
          "100BASE-TX as defined in Clause 25";
      }
      bit b1000baseX {
        description
          "1000BASE-X half duplex as specified in Clause 36";
      }
      bit b1000baseT {
        description
          "1000BASE-T PHY as specified in Clause 40";
      }
      bit b1000baseT1 {
        description
          "1000BASE-T1 as specified in Clause 97";
      }
      bit b2p5GbaseT {
        description
          "2.5GBASE-T PHY as specified in Clause 126";
      }
      bit b2p5GbaseT1 {
        description
          "2.5GBASE-T1 as specified in Clause 149";
      }
      bit b2p5GbaseKX {
        description
          "2.5GBASE-KX as specified in Clause 128";
      }
      bit b5GBaseT {
        description
          "5GBASE-T PHY as specified in Clause 126";
      }
      bit b5GbaseT1 {
        description
          "5GBASE-T1 as specified in Clause 149";
      }
      bit b5GbaseKR {
        description
          "5GBASE-KR as specified in Clause 130";
      }
      bit b10GbaseT {
        description
          "10GBASE-T PHY as specified in Clause 55";
      }
      bit b1000baseKX {
        description
          "1000BASE-KX as specified in Clause 70";
      }
      bit b10GbaseKX4 {
        description
          "10GBASE-KX4 as specified in Clause 71";
      }
      bit b10GbaseKR {
        description
          "10GBASE-KR as specified in Clause 72";
      }
      bit b25GbaseT {
        description
          "25GBASE-T as specified in Clause 113";
      }
      bit b25GbaseRS {
        description
          "25GBASE-CR-S as specified in Clause 110 or
           25GBASE-KR-S as specified in Clause 111";
      }
      bit b25GbaseR {
        description
          "25GBASE-CR as specified in Clause 110 or
           25GBASE-KR as specified in Clause 111";
      }
      bit b25GbaseT1 {
        description
          "25GBASE-T1 as specified in Clause 165";
      }
      bit b40GbaseKR4 {
        description
          "40GBASE-KR4 as specified in Clause 84";
      }
      bit b40GbaseCR4 {
        description
          "40GBASE-CR4 as specified in Clause 85";
      }
      bit b40GbaseT {
        description
          "40GBASE-T as specified in Clause 113";
      }
      bit b50GbaseR {
        description
          "50GBASE-CR as specified in Clause 136 or
           50GBASE-KR as specified in Clause 137";
      }
      bit b100GbaseCR10 {
        description
          "100GBASE-CR10 as specified in Clause 85";
      }
      bit b100GbaseCR4 {
        description
          "100GBASE-CR4 as specified in Clause 92";
      }
      bit b100GbaseKR4 {
        description
          "100GBASE-KR4 as specified in Clause 93";
      }
      bit b100GbaseKP4 {
        description
          "100GBASE-KP4 as specified in Clause 94";
      }
      bit b100GbaseR2 {
        description
          "100GBASE-CR2 as specified in Clause 136 or
           100GBASE-KR2 as specified in Clause 137";
      }
      bit b200GbaseR4 {
        description
          "200GBASE-CR4 as specified in Clause 136
           or 200GBASE-KR4 as specified in Clause 137";
      }
    }
    description
      "This data type is used as the syntax of the
       ieee802-eth-phy-auto-neg-capability-bits,
       ieee802-eth-phy-auto-neg-cap-advertised-bits,
       and ieee802-eth-phy-auto-neg-cap-received-bits
       objects in ieee802-eth-phy-auto-neg-table.";
    reference
      "IEEE Std 802.3, Clause 30.6.1.1.5";
  }
}
