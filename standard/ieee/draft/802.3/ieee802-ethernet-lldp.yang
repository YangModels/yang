module ieee802-ethernet-lldp {
  yang-version 1.1;
  namespace "urn:ieee:std:802.3:yang:ieee802-ethernet-lldp";
  prefix ieee802-eth-lldp;

  import ieee802-dot1ab-lldp {
    prefix lldp;
    reference
      "IEEE Std 802.1ABcu-2021";
  }
  import ieee802-ethernet-phy-type {
    prefix ieee802-phy;
    reference
      "IEEE Std 802.3-2022";
  }

  organization
    "IEEE Std 802.3 Ethernet Working Group
     Web URL: http://www.ieee802.org/3/";
  contact
    "Web URL: http://www.ieee802.org/3/";
  description
    "This module contains YANG definitions for configuring LLDP for
     802.3 Ethernet Interfaces.
     In this YANG module, 'Ethernet interface' can be interpreted
     as referring to 'IEEE Std 802.3 compliant Ethernet
     interfaces'.";

  revision 2025-04-17 {
    description
      "Updates under IEEE Std 802.3.2-202x, Draft D3.3";
    reference
      "IEEE Std 802.3-2022, unless dated explicitly";
  }

  typedef port-class-type {
    type enumeration {
      enum p-class-pse {
        value 0;
        description
          "Power Sourcing Equipment";
      }
      enum p-class-pd {
        value 1;
        description
          "Powered Device";
      }
    }
    description
      "Enumeration for the power port class";
    reference
      "IEEE Std 802.3, 30.12.2.1.5";
  }

  typedef pse-pinout-type {
    type enumeration {
      enum signal {
        value 0;
        description
          "PSE Pinout Alternative A";
      }
      enum spare {
        value 1;
        description
          "PSE Pinout Alternative B";
      }
    }
    description
      "Enumeration for the pinout alternatives used for PD
       detection and power ";
    reference
      "IEEE Std 802.3, 30.12.2.1.9";
  }

  typedef pse-power-class-type {
    type enumeration {
      enum class0 {
        value 0;
        description
          "Class 0 PD";
      }
      enum class1 {
        value 1;
        description
          "Class 1 PD";
      }
      enum class2 {
        value 2;
        description
          "Class 2 PD";
      }
      enum class3 {
        value 3;
        description
          "Class 3 PD";
      }
      enum class4 {
        value 4;
        description
          "Class 4 PD";
      }
    }
    description
      "Enumeration for the PD class";
    reference
      "IEEE Std 802.3, 30.12.2.1.10";
  }

  typedef power-class-ext-AB-type {
    type enumeration {
      enum singlesig {
        value 0;
        description
          "Single-signature PD or 2-pair only PSE";
      }
      enum class1 {
        value 1;
        description
          "Class 1";
      }
      enum class2 {
        value 2;
        description
          "Class 2";
      }
      enum class3 {
        value 3;
        description
          "Class 3";
      }
      enum class4 {
        value 4;
        description
          "Class 4";
      }
      enum class5 {
        value 5;
        description
          "Class 5";
      }
    }
    description
      "Enumeration for the assigned power class ";
    reference
      "IEEE Std 802.3, 30.12.3.1.26";
  }

  typedef power-class-ext-type {
    type enumeration {
      enum dualsig {
        value 0;
        description
          "Dual-signature PD";
      }
      enum class1 {
        value 1;
        description
          "Class 1";
      }
      enum class2 {
        value 2;
        description
          "Class 2";
      }
      enum class3 {
        value 3;
        description
          "Class 3";
      }
      enum class4 {
        value 4;
        description
          "Class 4";
      }
      enum class5 {
        value 5;
        description
          "Class 5";
      }
      enum class6 {
        value 6;
        description
          "Class 6";
      }
      enum class7 {
        value 7;
        description
          "Class 7";
      }
      enum class8 {
        value 8;
        description
          "Class 8";
      }
    }
    description
      "Enumeration for the assigned power class ";
    reference
      "IEEE Std 802.3, 30.12.3.1.28";
  }

  typedef power-type {
    type enumeration {
      enum type4dualsigPD {
        value 0;
        description
          "Type 4 dual-signature PD";
      }
      enum type4singlesigPD {
        value 1;
        description
          "Type 4 single-signature PD";
      }
      enum type3dualsigPD {
        value 2;
        description
          "Type 3 dual-signature PD";
      }
      enum type3singlesigPD {
        value 3;
        description
          "Type 3 single-signature PD";
      }
      enum type4PSE {
        value 4;
        description
          "Type 4 PSE";
      }
      enum type3PSE {
        value 5;
        description
          "Type 3 PSE";
      }
    }
    description
      "Enumeration for the PD class";
    reference
      "IEEE Std 802.3, 30.12.2.1.29";
  }

  typedef power-priority-type {
    type enumeration {
      enum low {
        value 0;
        description
          "low priority PD";
      }
      enum high {
        value 1;
        description
          "high priority PD";
      }
      enum critical {
        value 2;
        description
          "critical priority PD";
      }
      enum unknown {
        value 3;
        description
          "priority unknown";
      }
    }
    description
      "Enumeration for possible priorities of a PD system";
    reference
      "IEEE Std 802.3, 30.12.2.1.16";
  }

  typedef power-source-type {
    type enumeration {
      enum pse-primary {
        value 0;
        description
          "PSE powered by a primary power source";
      }
      enum pse-backup {
        value 1;
        description
          "PSE powered by a backup power source";
      }
      enum pse-unknwon {
        value 2;
        description
          "PSE powered by an unkown power source";
      }
      enum pd-pse-and-local {
        value 3;
        description
          "PD powered by a PSE and locally";
      }
      enum pd-local-only {
        value 4;
        description
          "PD powered only locally";
      }
      enum pd-pse-only {
        value 5;
        description
          "PD powered by PD only";
      }
      enum pd-unknown {
        value 6;
        description
          "PD powered by an uknown source";
      }
    }
    description
      "Enumeration for the power sources of the
       remote system. When the remote system is a PSE, it
       indicates whether it is being powered by a primary
       power source; a backup power source; or unknown.
       When the remote system is a PD, it indicates whether
       it is being powered by a PSE and locally;
       locally only; by a PSE only; or unknown.";
    reference
      "IEEE Std 802.3, 30.12.2.1.15";
  }

  typedef powering-status-type {
    type enumeration {
      enum 4PdualsigPD {
        value 0;
        description
          "4-pair powering a dual-signature PD";
      }
      enum 4PsinglesigPD {
        value 1;
        description
          "4-pair powering a single-signature PD";
      }
      enum 2P {
        value 2;
        description
          "2-pair powering";
      }
    }
    description
      "Enumeration for the power status of the PSE";
    reference
      "IEEE Std 802.3, 30.12.2.1.23";
  }

  typedef powered-status-type {
    type enumeration {
      enum 4PdualsigPD {
        value 0;
        description
          "4-pair powered dual-signature PD";
      }
      enum 2PdualsigPD {
        value 1;
        description
          "2-pair powered dual-signature PD";
      }
      enum singlesigPD {
        value 2;
        description
          "powered single-signature PD";
      }
    }
    description
      "Enumeration for the power status of the PSE";
    reference
      "IEEE Std 802.3, 30.12.2.1.24";
  }

  typedef power-pairs-type {
    type enumeration {
      enum altA {
        value 0;
        description
          "Alternative A";
      }
      enum altB {
        value 1;
        description
          "Alternative B";
      }
      enum both {
        value 2;
        description
          "both";
      }
    }
    description
      "Enumeration for the PSE Pinout Alternative";
    reference
      "IEEE Std 802.3, 30.12.2.1.25";
  }

  typedef measurement-source-type {
    type enumeration {
      enum noRequest {
        description
          "No Request";
      }
      enum altA {
        description
          "Pairset Alternative A / Mode A";
      }
      enum altB {
        description
          "Pairset Alternative B / Mode B";
      }
      enum total {
        description
          "Port total";
      }
    }
    description
      "PoE measurement source";
    reference
      "IEEE Std 802.3, 30.12.2.1.42 and 30.12.3.1.42";
  }

  augment "/lldp:lldp/lldp:port" {
    description
      "Augments port with 802.3 port read-only objects";
    leaf auto-negotiation-supported {
      type boolean;
      config false;
      description
        "True if the port supports Auto-negotiation";
      reference
        "IEEE Std 802.3, 30.12.2.1.1";
    }
    leaf auto-negotiation-enabled {
      type boolean;
      config false;
      description
        "True if Auto-negotiation is enabled";
      reference
        "IEEE Std 802.3, 30.12.2.1.2";
    }
    /* Deprecated MAU objects */
    leaf auto-negotiation-cap {
      type binary {
        length "2";
      }
      config false;
      status deprecated;
      description
        "A read-only 2-octet value that contains the value (bitmap)
         of the ifMauAutoNegCapAdvertisedBits object
         (defined in IETF RFC 4836) which is associated with the
         given port on the local system.
         Superseeded by auto-negotiation-cap-bits.";
      reference
        "IEEE Std802.3, 30.12.2.1.3";
    }
    leaf operational-mau-type {
      type int32;
      config false;
      status deprecated;
      description
        "32-bit integer value that indicates the operational MAU
         type of the given port.
         Superseeded by operational-pmd-type.";
      reference
        "IEEE Std 802.3, 30.12.2.1.4";
    }
    leaf auto-negotiation-cap-bits {
      type ieee802-phy:auto-neg-ability-bits;
      description
        "The capabilities advertised by the local Auto-Negotiation
         entity.";
      reference
        "IEEE Std 802.3, 30.6.1.1.6,
         aAutoNegadvertisedTechnologyAbility.";
    }
    leaf operational-pmd-type {
      type identityref {
        base ieee802-phy:pmd-type;
      }
      description
        "Operational PMD type of the given port";
      reference
        "IEEE Std 802.3, Clause 30.5.1.1.2 aMAUType";
    }
    /* Clause 30 & 145 PoE related LLDP definitions */
    leaf power-port-class {
      type port-class-type;
      description
        "A read-only value that identifies the port Class of the
         given port";
      reference
        "IEEE Std 802.3, 30.12.2.1.5";
    }
    leaf mdi-power-supported {
      type boolean;
      description
        "True if MDI power is supported";
      reference
        "IEEE Std 802.3, 30.12.2.1.6";
    }
    leaf mdi-power-enabled {
      type boolean;
      description
        "True if MDI power is enabled";
      reference
        "IEEE Std 802.3, 30.12.2.1.7";
    }
    leaf power-pair-controlable {
      type boolean;
      description
        "True if the pair selection can be controlled";
      reference
        "IEEE Std 802.3, 30.12.2.1.8";
    }
    leaf power-pairs {
      type pse-pinout-type;
      description
        "Indicates which pinout alernative is used for PD detection
         and power";
      reference
        "IEEE Std 802.3, 30.12.2.1.9";
    }
    leaf local-power-class {
      type pse-power-class-type;
      description
        "PD Power Class";
      reference
        "IEEE Std 802.3, 30.12.2.1.10";
    }
    /* Obsolete Link Aggregation objects 
        Link aggregation has not been part of 802.3 since IEEE 802.1AX-2008
        */            
    leaf link-aggregation-status {
      type bits {
        bit aggregation-capability {
          position 0;
          description
            "IEEE Std 802.3, 79.3.3.1";
        }
        bit aggregation-status {
          position 1;
          description
            "IEEE Std 802.3, 79.3.3.1";
        }
      }
      config false;
      status obsolete;
      description
        "The bitmap value which contains the link aggregation
         capabilities and the current aggregation
         status of the link";
      reference
        "IEEE Std 802.3, 30.12.2.1.11";
    }
    leaf aggregation-port-id {
      type int32;
      config false;
      status obsolete;
      description
        "The unique identifier allocated to this Aggregation Port
         by the local System.";
      reference
        "IEEE Std 802.3, 30.12.2.1.12";
    }
    leaf local-max-frame-size {
      type int32;
      config false;
      status obsolete;
      description
        "An integer value indicating the maximum supported frame
         size in octets on the given port of the local system.";
      reference
        "IEEE Std 802.3, 30.12.2.1.13";
    }
    leaf power-type {
      type bits {
        bit type1-or-greater {
          position 0;
          description
            "0-type1, 1-greater than type1";
        }
        bit pse-or-pd {
          position 1;
          description
            "0-pse, 1-pd";
        }
      }
      config false;
      description
        "A read-only attribute that returns a bit string indicating
         whether the local system is a PSE or a PD and whether it
         is Type 1 or greater than Type 1. The first bit indicates
         Type 1 or greater than Type 1. The second bit indicates
         PSE or PD. A PSE sets this bit to indicate a PSE. A PD sets
         this bit to indicate a PD. See also aLldpXdot3LocPowerTypeExt.
         Superseeded by power-support";
      reference
        "IEEE Std 802.3, 30.12.2.1.14";
    }
    leaf power-support {
      type bits {
        bit pse-pd {
          description
            "0-PD, 1-PSE";
        }
        bit pse-power-support {
          description
            "0-not supported, 1-supported";
        }
        bit pse-power-state {
          description
            "0-disabled 1-enabled";
        }
        bit pse-pairs-selection {
          description
            "0-pair selection not controllable
             1-pair selection  controllable";
        }
      }
      description
        "A read-only attribute that returns a bit string indicating
         whether local system PoE support.";
      reference
        "IEEE Std 802.3, 79.3.2.1 MDI power support";
    }
    leaf power-source {
      type power-source-type;
      config false;
      description
        "Indicates the power sources of the local system. A PSE
         indicates whether it is being powered by a primary power
         source; a backup power source; or unknown. A PD indicates
         whether it is being powered by a PSE and locally; by a PSE
         only; or unknown.;";
      reference
        "IEEE Std 802.3, 30.12.2.1.15";
    }
    leaf pd-requested-power-value {
      type int32;
      config false;
      description
        "PD requested power value. For a PD, it is the power value
         that the PD has currently requested from the remote
         system. For a PSE, it is the power value that the PSE
         mirrors back to the remote system";
      reference
        "IEEE Std 802.3, 30.12.2.1.17";
    }
    leaf pd-requested-power-value-a {
      type int32;
      config false;
      description
        "A read-only attribute that returns the PD requested power
         value for the Mode A pairset in units of 0.1 W. For a PD,
         it's the power value that the PD has currently requested
         from the remote system for the Mode A pairset. For a PSE,
         it is the power value for the Alternative A pairset that
         the PSE echoes back to the remote system";
      reference
        "IEEE Std 802.3, 30.12.2.1.18";
    }
    leaf pd-requested-power-value-b {
      type int32;
      config false;
      description
        "A read-only attribute that returns the PD requested power
         value for the Mode B pairset in units of 0.1 W.
         For a PD, it is the power value that the PD has currently
         requested from the remote system for the Mode B pairset.
         For a PSE, it is the power value for the Alternative B
         pairset that the PSE echoes back to the remote system";
      reference
        "IEEE Std 802.3, 30.12.2.1.19";
    }
    leaf pse-allocated-power-value {
      type int32;
      config false;
      description
        "PSE allocated power value. For a PSE, it is the power
         value that the PSE has currently allocated to the remote
         system. For a PD, it is the power value that the PD mirrors
         back to the remote syste";
      reference
        "IEEE Std 802.3, 30.12.2.1.20";
    }
    leaf pse-allocated-power-value-a {
      type int32;
      config false;
      description
        " PSE allocated power value for the Alternative A pairset
          in units of 0.1 W.For a PSE, it is the power value for the
          Alternative A pairset that the PSE has currently allocated
          to the remote system. For a PD, it is the power value for
          the Mode A pairset that the PD echoes back to the remote
          system.";
      reference
        "IEEE Std 802.3, 30.12.2.1.21";
    }
    leaf pse-allocated-power-value-b {
      type int32;
      config false;
      description
        "PSE allocated power value for the Alternative B pairset
         in units of 0.1 W. For a PSE, it is the power value for the
         Alternative B pairset that the PSE has currently
         allocated to the remote system. For a PD, it is the power
         value for the Mode B pairset that the PD echoes back to the
         remote system.";
      reference
        "IEEE Std 802.3, 30.12.2.1.22";
    }
    leaf pse-powering-status {
      type powering-status-type;
      config false;
      description
        "A read only value that indicates the powering status of
         the PSE. For a PD, the contents of this
         attribute are undefined.";
      reference
        "IEEE Std 802.3, 30.12.2.1.23";
    }
    leaf pd-powered-status {
      type powered-status-type;
      config false;
      description
        "A read only value that indicates the powering status of
         the PD. For a PSE, the contents of this attribute are
         undefined";
      reference
        "IEEE Std 802.3, 30.12.2.1.24";
    }
    leaf power-pairs-ext {
      type power-pairs-type;
      config false;
      description
        "A read-only value that identifies the supported PSE
         Pinout Alternative specified in 145.2.4. For a PSE, this
         attribute contains the value of the aPSEPowerPairs
          attribute (see 30.9.1.1.4). For a PD, the contents of this
          attribute are undefined";
      reference
        "IEEE Std 802.3, 30.12.2.1.25";
    }
    leaf power-class-ext-A {
      type power-class-ext-AB-type;
      config false;
      description
        "For a dual-signature PD, a read-only value that indicates
         the requested Class for Mode A during Physical Layer
         Classification (see 145.3.6). For a single-signature PD, a
         read-only value set to ‘singlesig’.For a PSE connected to
         a dual-signature PD, a read-only value that indicates the
         currently assigned Class for Mode A (see 145.2.8). For a
         PSE connected to a single-signature PD or a PSE that
         operates only in 2-pair mode, a read-only value set to
         ‘singlesig’";
      reference
        "IEEE Std 802.3, 30.12.2.1.26";
    }
    leaf power-class-ext-B {
      type power-class-ext-AB-type;
      config false;
      description
        "For a dual-signature PD, a read-only value that indicates
         the requested Class for Mode B during Physical Layer
         Classification (see 145.3.6). For a single-signature PD,
         a read-only value set to ‘singlesig’.For a PSE connected to
         a dual-signature PD, a read-only value that indicates the
         currently assigned Class for Mode B (see 145.2.8). For a
         PSE connected to a single-signature PD or a PSE that
         operates only in 2-pair mode, a read-only value set to
         ‘singlesig’";
      reference
        "IEEE Std 802.3, 30.12.2.1.27";
    }
    leaf power-class-ext {
      type power-class-ext-type;
      config false;
      description
        "For a single-signature PD, a read-only value that
         indicates the requested Class during Physical
         Layer Classification (see 145.3.6). For a dual-signature
         PD, a read-only value set to ‘dualsig’.
         For a PSE connected to a single-signature PD or a PSE that
         operates only in 2-pair mode, a read-only value that
         indicates the currently assigned Class (see 145.2.8).
         For a PSE connected to a dual-signature PD,
         a read-only value set to ‘dualsig’.’";
      reference
        "IEEE Std 802.3, 30.12.2.1.28";
    }
    leaf power-type-ext {
      type power-type;
      config false;
      description
        "A read-only attribute that returns a value to indicate if
         the local system is a Type 3 or Type 4 PSE or PD and, in
         the case of a Type 3 or Type 4 PD, if it is a
         single-signature PD or a dual-signature
         PD";
      reference
        "IEEE Std 802.3, 30.12.2.1.29";
    }
    leaf pd-load {
      type boolean;
      config false;
      description
        "For a dual-signature PD, a read-only attribute that
         returns whether the load of a dual-signature PD is
         electrically isolated, as defined in 79.3.2.10.2. For a
         single-signature PD or a PSE, the value of this attribute
         is FALSE";
      reference
        "IEEE Std 802.3, 30.12.2.1.30";
    }
    leaf pd-4pid {
      type boolean;
      config false;
      description
        "A read-only Boolean attribute indicating whether the local
         PD system supports powering of both PD Modes.";
      reference
        "IEEE Std 802.3, 30.12.2.1.31";
    }
    leaf pse-max-avail-power {
      type int32;
      config false;
      description
        "A read-only attribute that returns the local PSE maximum
         available power value in units of 0.1 W";
      reference
        "IEEE Std 802.3, 30.12.2.1.32";
    }
    leaf pse-autoclass-support {
      type boolean;
      config false;
      description
        "Indicates whether the local PSE system supports Autoclass.";
      reference
        "IEEE Std 802.3, 30.12.2.1.33";
    }
    leaf autoclass-completed {
      type boolean;
      config false;
      description
        "Indicates whether the local PSE system has completed the
         Autoclass measurement.";
      reference
        "IEEE Std 802.3, 30.12.2.1.34";
    }
    leaf autoclass-request {
      type boolean;
      config false;
      description
        "A read-only Boolean attribute indicating whether the local
         PD system is requesting an Autoclass measurement;";
      reference
        "IEEE Std 802.3, 30.12.2.1.35";
    }
    leaf power-down-request {
      type int32;
      description
        "A read-write attribute that indicates the local PD system
         is requesting a power down when the value is  0x1D.;";
      reference
        "IEEE Std 802.3, 30.12.2.1.36";
    }
    leaf power-down-time {
      type int32;
      description
        "A read-write attribute that indicates the number of
         seconds the PD requests to stay powered off. A value of
         zero indicates an indefinite amount of time;";
      reference
        "IEEE Std 802.3, 30.12.2.1.37";
    }
    /* PoE measurement objects */
    leaf meas-voltage-support {
      type boolean;
      description
        "A read-only attribute that indicates the local device is
         capable of providing a voltage measurement.;";
      reference
        "IEEE Std 802.3, 30.12.2.1.38";
    }
    leaf meas-current-support {
      type boolean;
      description
        "A read-only attribute that indicates the local device is
         capable of providing a current measurement.;";
      reference
        "IEEE Std 802.3, 30.12.2.1.39";
    }
    leaf meas-power-support {
      type boolean;
      description
        "A read-only attribute that indicates the local device is
         capable of providing a power measurement.;";
      reference
        "IEEE Std 802.3, 30.12.2.1.40";
    }
    leaf meas-energy-support {
      type boolean;
      description
        "A read-only attribute that indicates the local device is
         capable of providing a energy measurement.;";
      reference
        "IEEE Std 802.3, 30.12.2.1.41";
    }
    /* NOTE - What do these values mean? */
    leaf measurement-source {
      type bits {
        bit bit1 {
          position 0;
          description
            "????";
        }
        bit bit2 {
          position 1;
          description
            "-";
        }
      }
      status obsolete;
      description
        "A read-write attribute value that indicates to local
         device on which Alternative or Mode the measurement
         is to be taken";
      reference
        "IEEE Std 802.3, 30.12.2.1.42";
    }
    leaf meas-voltage-request {
      type boolean;
      config false;
      description
        "A read-only attribute that indicates the local device is
         requesting a voltage measurement from the remote device.";
      reference
        "IEEE Std 802.3, 30.12.2.1.43";
    }
    leaf meas-current-request {
      type boolean;
      config false;
      description
        "A read-only attribute that indicates the local device is
         requesting a current measurement from the remote device.";
      reference
        "IEEE Std 802.3, 30.12.2.1.44";
    }
    leaf meas-power-request {
      type boolean;
      config false;
      description
        "A read-only attribute that indicates the local device is
         requesting a power measurement from the remote device.";
      reference
        "IEEE Std 802.3, 30.12.2.1.45";
    }
    leaf meas-energy-request {
      type boolean;
      config false;
      description
        "A read-only attribute that indicates the local device is
         requesting an energy measurement from the remote device.";
      reference
        "IEEE Std 802.3, 30.12.2.1.46";
    }
    leaf meas-voltage-valid {
      type boolean;
      config false;
      description
        "A read-only attribute that indicates the local device’s
         voltage measurement is valid.";
      reference
        "IEEE Std 802.3, 30.12.2.1.47";
    }
    leaf meas-current-valid {
      type boolean;
      config false;
      description
        "A read-only attribute that indicates the local device’s
         current measurement is valid.";
      reference
        "IEEE Std 802.3, 30.12.2.1.48";
    }
    leaf meas-power-valid {
      type boolean;
      config false;
      description
        "A read-only attribute that indicates the local device’s
         power measurement is valid.";
      reference
        "IEEE Std 802.3, 30.12.2.1.49";
    }
    leaf meas-energy-valid {
      type boolean;
      config false;
      description
        "A read-only attribute that indicates the local device’s
         energy measurement is valid.";
      reference
        "IEEE Std 802.3, 30.12.2.1.50";
    }
    leaf meas-voltage-uncertainty {
      type int32;
      config false;
      description
        "A read-only attribute that indicates the expanded
         uncertainty (coverage factor k = 2) for the device’s
         voltage measurement.";
      reference
        "IEEE Std 802.3, 30.12.2.1.51";
    }
    leaf meas-current-uncertainty {
      type int32;
      config false;
      description
        "A read-only attribute that indicates the expanded
         uncertainty (coverage factor k = 2) for the device’s
         current measurement.";
      reference
        "IEEE Std 802.3, 30.12.2.1.52";
    }
    leaf meas-power-uncertainty {
      type int32;
      config false;
      description
        "A read-only attribute that indicates the expanded
         uncertainty (coverage factor k = 2) for the device’s
         power measurement.";
      reference
        "IEEE Std 802.3, 30.12.2.1.53";
    }
    leaf meas-energy-uncertainty {
      type int32;
      config false;
      description
        "A read-only attribute that indicates the expanded
         uncertainty (coverage factor k = 2) for the device’s
         energy measurement.";
      reference
        "IEEE Std 802.3, 30.12.2.1.54";
    }
    leaf voltage-measurement {
      type int32;
      config false;
      description
        "A read-only attribute that returns the measured device
         voltage.";
      reference
        "IEEE Std 802.3, 30.12.2.1.55";
    }
    leaf current-measurement {
      type int32;
      config false;
      description
        "A read-only attribute that returns the measured device
         current.";
      reference
        "IEEE Std 802.3, 30.12.2.1.56";
    }
    leaf power-measurement {
      type int32;
      config false;
      description
        "A read-only attribute that returns the measured device
         power.";
      reference
        "IEEE Std 802.3, 30.12.2.1.57";
    }
    leaf energy-measurement {
      type int32;
      config false;
      description
        "A read-only attribute that returns the measured device
         energy.";
      reference
        "IEEE Std 802.3, 30.12.2.1.58";
    }
    leaf pse-power-price-index {
      type int32;
      config false;
      description
        "A read-only attribute that returns an index of the price
         of power being sourced by the PSE. For a PD, this value
         is undefined";
      reference
        "IEEE Std 802.3, 30.12.2.1.59";
    }
    leaf local-response {
      type int32;
      config false;
      description
        "The maximum time required to update
         pse-allocated-power-value";
      reference
        "IEEE Std 802.3, 30.12.2.1.60";
    }
    leaf local-system-ready {
      type boolean;
      config false;
      description
        "Initialization status of the Data Link Layer
         classification engine on the local system";
      reference
        "IEEE Std 802.3, 30.12.2.1.61";
    }
    leaf tx-system-value {
      type int32;
      config false;
      description
        "Returns the value of Tw_sys_tx that the local system can
         support in the transmit direction.";
      reference
        "IEEE Std 802.3, 30.12.2.1.62";
    }
    leaf tx-system-value-echo {
      type int32;
      config false;
      description
        "Returns the value of Tw_sys_tx that the emote system is
         advertising that it can support in the transmit direction
         and is echoed by the local system under the control of the
         EEE DLL receiver state diagram.";
      reference
        "IEEE Std 802.3, 30.12.2.1.63";
    }
    leaf rx-system-value {
      type int32;
      config false;
      description
        "Returns the value of Tw_sys_tx that the local system is
         requesting in the receive direction.";
      reference
        "IEEE Std 802.3, 30.12.2.1.64";
    }
    leaf rx-system-value-echo {
      type int32;
      config false;
      description
        "Returns the value of Tw_sys_tx that the remote system is
         advertising that it is requesting in the receive direction
         and is echoed by the local system under the control of the
         EEE DLL transmitter state diagram.";
      reference
        "IEEE Std 802.3, 30.12.2.1.65";
    }
    leaf fallback-system-value {
      type int32;
      config false;
      description
        "Returns the value of the fallback Tw_sys_tx that the local
         system is advertising to the remote system.";
      reference
        "IEEE Std 802.3, 30.12.2.1.66";
    }
    /* LDP EEE objects */
    leaf tx-dll-ready {
      type boolean;
      config false;
      description
        "Returns the initialization status of the EEE transmit Data
         Link Layer management function on the local system.";
      reference
        "IEEE Std 802.3, 30.12.2.1.67";
    }
    leaf rx-dll-ready {
      type boolean;
      config false;
      description
        "Returns the initialization status of the EEE receive Data
         Link Layer management function on the local system.";
      reference
        "IEEE Std 802.3, 30.12.2.1.68";
    }
    leaf dll-enabled {
      type boolean;
      config false;
      description
        "Returns the status of the EEE capability negotiation on
         the local system.";
      reference
        "IEEE Std 802.3, 30.12.2.1.69";
    }
    leaf tx-system-fw {
      type boolean;
      config false;
      description
        "Returns the value of LPI_FW that the local system can
         support in the transmit direction.";
      reference
        "IEEE Std 802.3, 30.12.2.1.70";
    }
    leaf tx-system-fw-echo {
      type boolean;
      config false;
      description
        "Returns the value of LPI_FW that the remote system is
         advertising that it can support in the transmit direction
         and is echoed by the local system under the control of the
         EEE DLL receiver state diagram.";
      reference
        "IEEE Std 802.3, 30.12.2.1.71";
    }
    leaf rx-system-fw {
      type boolean;
      config false;
      description
        "Returns the value of LPI_FW that the local system is
         requesting in the receive direction.";
      reference
        "IEEE Std 802.3, 30.12.2.1.72";
    }
    leaf rx-system-fw-echo {
      type boolean;
      config false;
      description
        "Returns the value of LPI_FW that the remote system is
         advertising that it is requesting in the receive direction
         and is echoed by the local system under the control of the
         EEE DLL transmitter state diagram.";
      reference
        "IEEE Std 802.3, 30.12.2.1.73";
    }
    /* LLDP preemption objects */
    leaf preemption-supported {
      type boolean;
      config false;
      description
        "Indicates whether the given port (associated with the local
         System) supports the preemption capability.";
      reference
        "IEEE Std 802.3, 30.12.2.1.74";
    }
    leaf preemption-enabled {
      type boolean;
      config false;
      description
        "Indicates whether the preemption capability is enabled on
         the given port associated with the local System.";
      reference
        "IEEE Std 802.3, 30.12.2.1.75";
    }
    leaf preemption-active {
      type boolean;
      config false;
      description
        "Indicates whether the preemption capability is active on
         the given port associated with the local System.;";
      reference
        "IEEE Std 802.3, 30.12.2.1.76";
    }
    leaf additional-fragment-size {
      type int32;
      config false;
      description
        "Indicate the minimum size of non-final fragments supported
         by the receiver on the given port associated with the local
         System. This value is expressed in units of 64 octets of
         additional fragment length.";
      reference
        "IEEE Std 802.3, 30.12.2.1.77";
    }
  }

  augment "/lldp:lldp/lldp:port" {
    description
      "Augments port with 802.3 port read-write objects";
    leaf tlvs-port-config-enable {
      type bits {
        bit mac-phy-config-status {
          position 0;
          description
            "IEEE Std 802.3, 30.12.1.1.1";
        }
        bit power-via-mdi {
          position 1;
          description
            "IEEE Std 802.3, 30.12.1.1.1";
        }
        bit unused {
          position 2;
          description
            "IEEE Std 802.3, 30.12.1.1.1";
        }
        bit max-frame-size {
          position 3;
          description
            "IEEE Std 802.3, 30.12.1.1.1";
        }
        bit eee-tlv {
          position 4;
          description
            "IEEE Std 802.3, 30.12.1.1.1";
        }
        bit eee-fast-wake-tlv {
          position 5;
          description
            "IEEE Std 802.3, 30.12.1.1.1";
        }
        bit additional-ethernet-capabilities-tlv {
          position 6;
          description
            "IEEE Std 802.3, 30.12.1.1.1";
        }
      }
      description
        "Bitmap that corresponds to an IEEE 802.3 subtype
         associated with a specific IEEE 802.3 port config TLV";
      reference
        "IEEE Std 802.3, 30.12.1.1.1";
    }
    leaf local-power-priority {
      type power-priority-type;
      description
        "Priority of a PD system. For a PSE, this is the priority
         that the PSE assigns to the PD. For a PD, this is the
         priority that the PD requests from the PSE.";
      reference
        "IEEE Std 802.3, 30.12.2.1.16";
    }
    leaf local-measurement-source {
      type measurement-source-type;
      description
        "A read-write attribute value that indicates to local
         device on which Alternative or Mode the measurement
         is to be taken.";
      reference
        "IEEE Std 802.3, 30.12.2.1.42";
    }
  }

  /* NOTE - lldp:remote-systems-data container is "config false;" */

  augment "/lldp:lldp/lldp:port/lldp:remote-systems-data" {
    description
      "Augments port with 802.3 port config tlvs";
    leaf auto-negotiation-supported {
      type boolean;
      description
        "True if the port supports Auto-negotiation";
      reference
        "IEEE Std 802.3, 30.12.3.1.1";
    }
    leaf auto-negotiation-enabled {
      type boolean;
      description
        "True if Auto-negotiation is enabled";
      reference
        "IEEE Std 802.3, 30.12.3.1.2";
    }
    /* Obsolete */
    leaf auto-negotiation-cap {
      type binary {
        length "2";
      }
      status obsolete;
      description
        "A read-only 2-octet value that contains the value (bitmap)
         of the ifMauAutoNegCapAdvertisedBits object (defined in
         IETF RFC 4836)which is associated with the given port on
         the local system.
         Supersceeded by auto-negotiation-cap-bits.";
      reference
        "IEEE Std 802.3, 30.12.3.1.3";
    }
    leaf operational-mau-type {
      type int32;
      status obsolete;
      description
        "32-bit integer value that indicates the operational MAU
         type of the given port.
         Supersceeded by operational-pmd-type.";
      reference
        "IEEE Std 802.3, 30.12.3.1.4";
    }
    leaf auto-negotiation-cap-bits {
      type ieee802-phy:auto-neg-ability-bits;
      description
        "The capabilities advertised by the remote Auto-Negotiation
         entity.";
      reference
        "IEEE Std 802.3, 30.12.3.1.3,
         aAutoNegadvertisedTechnologyAbility.";
    }
    leaf operational-pmd-type {
      type identityref {
        base ieee802-phy:pmd-type;
      }
      description
        "The operational PMD type of the given port";
      reference
        "IEEE Std 802.3, 30.12.3.1.4";
    }
    leaf power-port-class {
      type port-class-type;
      description
        "A read-only value that identifies the port Class of the
         given port";
      reference
        "IEEE Std 802.3, 30.12.3.1.5";
    }
    leaf mdi-power-supported {
      type boolean;
      description
        "True if MDI power is supported";
      reference
        "IEEE Std 802.3, 30.12.3.1.6";
    }
    leaf mdi-power-enabled {
      type boolean;
      description
        "True if MDI power is enabled";
      reference
        "IEEE Std 802.3, 30.12.3.1.7";
    }
    leaf power-pair-controlable {
      type boolean;
      description
        "True if pair selection can be controlled";
      reference
        "IEEE Std 802.3, 30.12.3.1.8";
    }
    leaf power-pairs {
      type pse-pinout-type;
      description
        "Indicates which pinout alernative is used for PD
         detection and power";
      reference
        "IEEE Std 802.3, 30.12.3.1.9";
    }
    leaf power-class {
      type pse-power-class-type;
      description
        "PD Power Class";
      reference
        "IEEE Std 802.3, 30.12.3.1.10";
    }
    /* Obsolete Link Aggregation objects 
        Link aggregation has not been part of 802.3 since IEEE 802.1AX-2008
        */
    leaf link-aggregation-status {
      type bits {
        bit aggregation-capability {
          position 0;
          description
            "IEEE Std 802.3, 79.3.3.1";
        }
        bit aggregation-status {
          position 1;
          description
            "IEEE Std 802.3, 79.3.3.1";
        }
        bit bit2-reserved {
          position 2;
          description
            "IEEE Std 802.3, 79.3.3.1";
        }
        bit bit3-reserved {
          position 3;
          description
            "IEEE Std 802.3, 79.3.3.1";
        }
        bit bit4-reserved {
          position 4;
          description
            "IEEE Std 802.3, 79.3.3.1";
        }
        bit bit5-reserved {
          position 5;
          description
            "IEEE Std 802.3, 79.3.3.1";
        }
        bit bit6-reserved {
          position 6;
          description
            "IEEE Std 802.3, 79.3.3.1";
        }
        bit bit7-reserved {
          position 7;
          description
            "IEEE Std 802.3, 79.3.3.1";
        }
      }
      status obsolete;
      description
        "The bitmap value which contains the link aggregation
         capabilities and the current aggregation status
         of the link";
      reference
        "IEEE Std 802.3, 30.12.3.1.11";
    }
    leaf aggregation-port-id {
      type int32;
      status obsolete;
      description
        "The unique identifier allocated to this Aggregation Port
         by the local System.";
      reference
        "IEEE Std 802.3, 30.12.3.1.12";
    }
    leaf local-max-frame-size {
      type int32;
      status obsolete;
      description
        "An integer value indicating the maximum supported frame
         size in octets on the given port of the local system.";
      reference
        "IEEE Std 802.3, 30.12.3.1.13";
    }
    /* POE objects
        Consistency errors between PoE definitions in 30.9 (PoE), 
        30.12 (LLDP), 79.3.2 (PoE TLV), 79.3.8 (PoE measurement TLV).
        Need to get these clauses reviewed against clause 145 and each other
        */
    leaf power-type {
      type bits {
        bit type1-or-greater {
          position 0;
          description
            "0-type1, 1-greater than type1";
        }
        bit pse-or-pd {
          position 1;
          description
            "0-pse, 1-pd";
        }
      }
      status obsolete;
      description
        "A read-only attribute that returns a bit string indicating
         whether the local system is a PSE or a PD and whether it
         is Type 1 or greater than Type 1. The first bit indicates
         Type 1 or greater than Type 1. The second bit indicates
         PSE or PD. A PSE sets this bit to indicate a PSE. A PD
         sets this bit to indicate a PD. See also
         aLldpXdot3LocPowerTypeExt.";
      reference
        "IEEE Std 802.3, 30.12.3.1.14";
    }
    leaf power-source {
      type power-source-type;
      description
        "Indicates the power sources of the remote system. A PSE
         indicates whether it is being powered by a primary power
         source; a backup power source; or unknown. A PD indicates
         whether it is being powered by a PSE and locally; by a PSE
         only; or unknown.;";
      reference
        "IEEE Std 802.3, 30.12.3.1.15";
    }
    leaf power-priority {
      type power-priority-type;
      description
        "The priority of the PD system received from the remote
         system";
      reference
        "IEEE Std 802.3, 30.12.3.1.16";
    }
    leaf pd-requested-power-value {
      type int32;
      description
        "PD requested power value that was used by the remote
         system to compute the power value that is has currently
         allocated to the PD.";
      reference
        "IEEE Std 802.3, 30.12.3.1.17";
    }
    leaf pd-requested-power-value-a {
      type int32;
      description
        "A read-only attribute that returns the PD requested power
         value for the Mode A pairset that was used by the remote
         system to compute the power value that it has currently
         allocated to the PD. For a PSE, it is the PD requested
         power value for the Alternative A pairset received from
         the remote system. For a PD, it is the PD requested power
         value for the Alternative A pairset that the PSE echoes
         back to the remote system. The definition and encoding of
         PD requested power value for the Mode A pairset is the same
         as described in aLldpXdot3LocPDRequestedPowerValueA";
      reference
        "IEEE Std 802.3, 30.12.3.1.18";
    }
    leaf pd-requested-power-value-b {
      type int32;
      description
        "A read-only attribute that returns the PD requested power
         value for the Mode B pairset that was used by the remote
         system to compute the power value that it has currently
         allocated to the PD. For a PSE, it is the PD requested
         power value for the Alternative B pairset received from
         the remote system. For a PD, it is the PD requested power
         value for the Alternative B pairset that the PSE echoes
         back to the remote system. The definition and encoding of
         PD requested power value for the Mode B pairset is the
         same as described in aLldpXdot3LocPDRequestedPowerValueB";
      reference
        "IEEE Std 802.3, 30.12.3.1.19";
    }
    leaf pse-allocated-power-value {
      type int32;
      description
        "PSE allocated power value. For a PSE, it is the power value
         that the PSE has currently allocated to the remote system.
         For a PD, it is the power value that the PD mirrors back to
         the remote syste";
      reference
        "IEEE Std 802.3, 30.12.3.1.20";
    }
    leaf pse-allocated-power-value-a {
      type int32;
      description
        "A read-only attribute that returns the PSE allocated power
         value for the Alternative A pairset received from the
         remote system. For a PSE, it is the PSE allocated power
         value for the Alternative A pairset that was echoed back
         by the remote PD. For a PD, it is the PSE allocated power
         value for the Mode A pairset received from the remote
         system. The definition and encoding of PSE allocated power
         value for the Alternative A pairset is the same as
         described in aLldpXdot3LocPSEAllocatedPowerValueA";
      reference
        "IEEE Std 802.3, 30.12.3.1.21";
    }
    leaf pse-allocated-power-value-b {
      type int32;
      description
        "A read-only attribute that returns the PSE allocated power
         value for the Alternative B pairset received from the
         value for the Alternative B pairset that was echoed back
         by the remote PD. For a PD, it is the PSE allocated power
         value for the Mode B pairset received from the remote
         system. The definition and encoding of PSE allocated power
         value for the Alternative B pairset is the same as
         described in aLldpXdot3LocPSEAllocatedPowerValueB";
      reference
        "IEEE Std 802.3, 30.12.3.1.22";
    }
    leaf pse-powering-status {
      type powering-status-type;
      description
        "A read only value that indicates the powering status of
         the remote PSE. For a PD, the contents of this attribute
         are undefined.";
      reference
        "IEEE Std 802.3, 30.12.3.1.23";
    }
    leaf pd-powered-status {
      type powered-status-type;
      description
        "A read only value that indicates the powering status of
         the PD. For a PSE, the contents of this attribute are
         undefined";
      reference
        "IEEE Std 802.3, 30.12.3.1.24";
    }
    leaf power-pairs-ext {
      type power-pairs-type;
      description
        "A read-only value that identifies the supported PSE
         Pinout Alternative specified in 145.2.4. For a PD, this
         attribute contains the value of the aPSEPowerPairs
         attribute (see 30.9.1.1.4). For a PSE, the contents of
         this attribute are undefined";
      reference
        "IEEE Std 802.3, 30.12.3.1.25";
    }
    leaf power-class-ext-A {
      type power-class-ext-AB-type;
      description
        "For a dual-signature PD, a read-only value that indicates
         the currently assigned Class for Mode A by the remote
         4-pair PSE. For a single-signature PD or a dual-signature
         PD connected to a 2-pair only PSE, a read-only value set
         to ‘singlesig’ by the remote PSE. For a PSE connected to a
         dual-signature PD, a read-only value that indicates the
         requested Class for Mode A during Physical Layer
         classification (see 145.2.8) by the remote PD. For a PSE
         connected to a single-signature PD, a read-only value set
         to ‘singlesig’ by the remote PD";
      reference
        "IEEE Std 802.3, 30.12.3.1.26";
    }
    leaf power-class-ext-B {
      type power-class-ext-AB-type;
      description
        "For a dual-signature PD, a read-only value that indicates
         the currently assigned Class for Mode B by the remote
         4-pair PSE. For a single-signature PD or a dual-signature
         PD connected to a 2-pair only PSE, a read-only value set
         to ‘singlesig’ by the remote PSE. For a PSE connected to a
         dual-signature PD, a read-only value that indicates the
         requested Class for Mode B during Physical Layer
         classification (see 145.2.8) by the remote PD. For a PSE
         connected to a single-signature PD, a read-only value set
         to ‘singlesig’ by the remote PD";
      reference
        "IEEE Std 802.3, 30.12.3.1.27";
    }
    leaf power-class-ext {
      type power-class-ext-type;
      description
        "For a single-signature PD or a dual-signature PD connected
         to a 2-pair only PSE, a read-only value that indicates the
         currently assigned Class by the remote PSE. For a
         dual-signature PD connected to a 4-pair capable PSE, a
         read-only value set to ‘dualsig’ by the remote PSE. For a
         PSE connected to a single-signature PD, a read-only value
         that indicates the requested Class during Physical Layer
         classification (see 145.2.8) by the remote PD. For a PSE
         connected to a dual-signature PD, a read-only value set to
         ‘dualsig’ by the remote PD.";
      reference
        "IEEE Std 802.3, 30.12.3.1.28";
    }
    leaf power-type-ext {
      type power-type;
      description
        "A read-only attribute that returns a value to indicate if
         the remote system is a Type 3 or Type 4 PSE or PD and, in
         the case of a Type 3 or Type 4 PD, if it is a
         single-signature PD or dual-signature PD.";
      reference
        "IEEE Std 802.3, 30.12.3.1.29";
    }
    leaf pd-load {
      type boolean;
      description
        "For a PSE, a read-only attribute that returns whether the
         load of the remote dual-signature PD is electrically
         isolated, as defined in 79.3.2.10.2. For a PD, this
         attribute is set to FALSE.";
      reference
        "IEEE Std 802.3, 30.12.3.1.30";
    }
    leaf pd-4pid {
      type boolean;
      description
        "A read-only Boolean attribute indicating whether the
         remote PD system supports powering of both PD Modes.";
      reference
        "IEEE Std 802.3, 30.12.3.1.31";
    }
    leaf pse-max-avail-power {
      type int32;
      description
        "A read-only attribute that returns the remote PSE maximum
         available power value in units of 0.1 W";
      reference
        "IEEE Std 802.3, 30.12.3.1.32";
    }
    leaf pse-autoclass-support {
      type boolean;
      description
        "Indicates whether the remote PSE system supports
         Autoclass.";
      reference
        "IEEE Std 802.3, 30.12.3.1.33";
    }
    leaf autoclass-completed {
      type boolean;
      description
        "Indicates whether the remote PSE system has completed the
         Autoclass measurement.";
      reference
        "IEEE Std 802.3, 30.12.3.1.34";
    }
    leaf autoclass-request {
      type boolean;
      description
        "A read-only Boolean attribute indicating whether the
         remote PD system is requesting an Autoclass measurement.";
      reference
        "IEEE Std 802.3, 30.12.3.1.35";
    }
    leaf power-down-request {
      type int32;
      description
        "A read-write attribute that indicates the remote PD system
         is requesting a power down when the value is  0x1D.;";
      reference
        "IEEE Std 802.3, 30.12.3.1.36";
    }
    leaf power-down-time {
      type int32;
      description
        "A read-only attribute that indicates the number of seconds
         the remote PD requests to stay powered off. A value of zero
         indicates an indefinite amount of time";
      reference
        "IEEE Std 802.3, 30.12.3.1.37";
    }
    /* PoE measurement objects */
    leaf meas-voltage-support {
      type boolean;
      description
        "A read-only attribute that indicates the remote device is
         capable of providing a voltage measurement.;";
      reference
        "IEEE Std 802.3, 30.12.3.1.38";
    }
    leaf meas-current-support {
      type boolean;
      description
        "A read-only attribute that indicates the remote device is
         capable of providing a current measurement.;";
      reference
        "IEEE Std 802.3, 30.12.3.1.39";
    }
    leaf meas-power-support {
      type boolean;
      description
        "A read-only attribute that indicates the remote device is
         capable of providing a power measurement.;";
      reference
        "IEEE Std 802.3, 30.12.3.1.40";
    }
    leaf meas-energy-support {
      type boolean;
      description
        "A read-only attribute that indicates the remote device is
         capable of providing a energy measurement.;";
      reference
        "IEEE Std 802.3, 30.12.3.1.41 ";
    }
    leaf measurement-source {
      type bits {
        bit bit1 {
          position 0;
          description
            "-";
        }
        bit bit2 {
          position 1;
          description
            "-";
        }
      }
      status obsolete;
      description
        "A read-write attribute value that indicates on which
         Alternative or Mode the measurement was taken by the remote
         device.
         Superseded by rem-measurement-source.";
      reference
        "IEEE Std 802.3, 30.12.3.1.42";
    }
    leaf rem-measurement-source {
      type measurement-source-type;
      description
        "A read-only attribute that indicates which Alternative or
         Mode the measurement is to be taken";
      reference
        "IEEE Std 802.3, 30.12.3.1.42";
    }
    leaf meas-voltage-request {
      type boolean;
      description
        "A read-only attribute that indicates the remote device is
         requesting a voltage measurement from the local device.";
      reference
        "IEEE Std 802.3, 30.12.3.1.43";
    }
    leaf meas-current-request {
      type boolean;
      description
        "A read-only attribute that indicates the remote device is
         requesting a current measurement from the local device.";
      reference
        "IEEE Std 802.3, 30.12.3.1.44";
    }
    leaf meas-power-request {
      type boolean;
      description
        "A read-only attribute that indicates the remote device is
         requesting a power measurement from the local device.";
      reference
        "IEEE Std 802.3, 30.12.3.1.45";
    }
    leaf meas-energy-request {
      type boolean;
      description
        "A read-only attribute that indicates the remote device is
         requesting an energy measurement from the local device.";
      reference
        "IEEE Std 802.3, 30.12.3.1.46";
    }
    leaf meas-voltage-valid {
      type boolean;
      description
        "A read-only attribute that indicates the remote device’s
         voltage measurement is valid.";
      reference
        "IEEE Std 802.3, 30.12.3.1.47";
    }
    leaf meas-current-valid {
      type boolean;
      description
        "A read-only attribute that indicates the remote device’s
         current measurement is valid.";
      reference
        "IEEE Std 802.3, 30.12.3.1.48";
    }
    leaf meas-power-valid {
      type boolean;
      description
        "A read-only attribute that indicates the remote device’s
         power measurement is valid.";
      reference
        "IEEE Std 802.3, 30.12.3.1.49";
    }
    leaf meas-energy-valid {
      type boolean;
      description
        "A read-only attribute that indicates the remote device’s
         energy measurement is valid.";
      reference
        "IEEE Std 802.3, 30.12.3.1.50";
    }
    leaf meas-voltage-uncertainty {
      type int32;
      description
        "A read-only attribute that indicates the expanded
         uncertainty (coverage factor k = 2) for the remote device’s
         voltage measurement.";
      reference
        "IEEE Std 802.3, 30.12.3.1.51";
    }
    leaf meas-current-uncertainty {
      type int32;
      description
        "A read-only attribute that indicates the expanded
         uncertainty (coverage factor k = 2) for the remote device’s
         current measurement.";
      reference
        "IEEE Std 802.3, 30.12.3.1.52";
    }
    leaf meas-power-uncertainty {
      type int32;
      description
        "A read-only attribute that indicates the expanded
         uncertainty (coverage factor k = 2) for the remote device’s
         power measurement.";
      reference
        "IEEE Std 802.3, 30.12.3.1.53";
    }
    leaf meas-energy-uncertainty {
      type int32;
      description
        "A read-only attribute that indicates the expanded
         uncertainty (coverage factor k = 2) for the remote device’s
         energy measurement.";
      reference
        "IEEE Std 802.3, 30.12.3.1.54";
    }
    leaf voltage-measurement {
      type int32;
      description
        "A read-only attribute that returns the measured remote
         device voltage.";
      reference
        "IEEE Std 802.3, 30.12.3.1.55";
    }
    leaf current-measurement {
      type int32;
      description
        "A read-only attribute that returns the measured remote
         device current.";
      reference
        "IEEE Std 802.3, 30.12.3.1.56";
    }
    leaf power-measurement {
      type int32;
      description
        "A read-only attribute that returns the measured remote
         device power.";
      reference
        "IEEE Std 802.3, 30.12.3.1.57";
    }
    leaf energy-measurement {
      type int32;
      description
        "A read-only attribute that returns the measured remote
         device energy.";
      reference
        "IEEE Std 802.3, 30.12.3.1.58";
    }
    leaf pse-power-price-index {
      type int32;
      description
        "A read-only attribute that returns an index of the price
         of power being sourced by the remote PSE. For a PSE, this
         value is undefined.";
      reference
        "IEEE Std 802.3, 30.12.3.1.59";
    }
    leaf tx-system-value {
      type int32;
      description
        "Returns the value of Tw_sys_tx that the remote system can
         support in the transmit direction.";
      reference
        "IEEE Std 802.3, 30.12.3.1.60";
    }
    leaf tx-system-value-echo {
      type int32;
      description
        "Returns the value of Tw_sys_tx that the local system is
         advertising that it can support in the transmit direction
         and is echoed by the local system under the control of the
         EEE DLL receiver state diagram.";
      reference
        "IEEE Std 802.3, 30.12.3.1.61";
    }
    leaf rx-system-value {
      type int32;
      description
        "Returns the value of Tw_sys_tx that the remote system is
         requesting in the receive direction.";
      reference
        "IEEE Std 802.3, 30.12.3.1.62";
    }
    leaf rx-system-value-echo {
      type int32;
      description
        "Returns the value of Tw_sys_tx that the local system is
         advertising that it is requesting in the receive direction
         and is echoed by the local system under the control of the
         EEE DLL transmitter state diagram.";
      reference
        "IEEE Std 802.3, 30.12.3.1.63 ";
    }
    leaf fallback-system-value {
      type int32;
      description
        "Returns the value of the fallback Tw_sys_tx that the
         remote system is advertising to the remote system.";
      reference
        "IEEE Std 802.3, 30.12.3.1.64";
    }
    /* LDP EEE objects */
    leaf tx-system-fw {
      type boolean;
      description
        "Returns the value of LPI_FW that the remote system can
         support in the transmit direction.";
      reference
        "IEEE Std 802.3, 30.12.3.1.65";
    }
    leaf tx-system-fw-echo {
      type boolean;
      description
        "Returns the value of LPI_FW that the local system is
         advertising that it can support in the transmit direction
         and is echoed by the local system under the control of the
         EEE DLL receiver state diagram.";
      reference
        "IEEE Std 802.3, 30.12.3.1.66";
    }
    leaf rx-system-fw {
      type boolean;
      description
        "Returns the value of LPI_FW that the remote system is
         requesting in the receive direction.";
      reference
        "IEEE Std 802.3, 30.12.3.1.67";
    }
    leaf rx-system-fw-echo {
      type boolean;
      description
        "Returns the value of LPI_FW that the local system is
         advertising that it is requesting in the receive direction
         and is echoed by the local system under the control of the
         EEE DLL transmitter state diagram.";
      reference
        "IEEE Std 802.3, 30.12.3.1.68";
    }
    /* LLDP preemption objects */
    leaf preemption-supported {
      type boolean;
      description
        "Indicates whether the given port (associated with the
         remote System) supports the preemption capability.";
      reference
        "IEEE Std 802.3, 30.12.3.1.69";
    }
    leaf preemption-enabled {
      type boolean;
      description
        "Indicates whether the preemption capability is enabled on
         the given port associated with the remote System.";
      reference
        "IEEE Std 802.3, 30.12.3.1.70";
    }
    leaf preemption-active {
      type boolean;
      description
        "Indicates whether the preemption capability is active on
         the given port associated with the remote System.;";
      reference
        "IEEE Std 802.3, 30.12.3.1.72";
    }
    leaf additional-fragment-size {
      type int32;
      description
        "Indicate the minimum size of non-final fragments supported
         by the receiver on the given port associated with the
         remote System. This value is expressed in units of 64
         octets of additional fragment length.";
      reference
        "IEEE Std 802.3, 30.12.3.1.72 ";
    }
  }
}
