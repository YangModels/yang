module ieee802-ethertype {

  namespace "urn:ieee:std:802.1Q:yang:ieee802-ethertype";
  prefix "ieee-ethertype";

  organization
    "IEEE 802.1 Working Group";

  contact
    "WG-URL: http://ieee802.org/1/
     WG-EMail: stds-802-1@ieee.org

     Contact: IEEE 802.1 Working Group Chair
     Postal: C/O IEEE 802.1 Working Group
             IEEE Standards Association
             445 Hoes Lane
             Piscataway
             NJ 08854
             USA

     E-mail: stds-802-1-chairs@ieee.org";

  description
    "This module contains a subset of commonly used 802 network EtherTypes.

     Copyright (C) IEEE (2023).

     This version of this YANG module is part of the IEEE Std 802;
     see the standard itself for full legal notices.";

  revision "2023-04-17" {
    description
      "Initial revision.";
    reference
      "IEEE Std 802f, Overview and Architecture -
       YANG Data Model for EtherTypes";
  }

  typedef ethertype {
    type enumeration {
      enum ipv4 {
        value 2048;
        description
          "08-00  Internet Protocol version 4 (IPv4)";
        reference
          "Organization: Xerox, US
          Reference: IETF RFC 894";
      }
      enum arp {
        value 2054;
        description
          "08-06  Address Resolution Protocol (ARP)";
        reference
          "Organization: Symbolics, Inc.
          Reference: IETF RFC 826, IETF RFC 7042";
      }
      enum wol {
        value 2114;
        description
          "08-42  Wake-on-LAN";
        reference
          "Organization: None
          Reference: IEEE Std 802";
      }
      enum msp {
        value 8930;
        description
          "22-E2  MAC Status Protocol (MSP)";
        reference
          "Organization: IEEE 802.1 Working Group
          Reference: IEEE Std 802.1Q";
      }
      enum cnm {
        value 8935;
        description
          "22-E7  Congestion Notification Message (CNM)";
        reference
          "Organization: IEEE 802.1 Working Group
          Reference: IEEE Std 802.1Q";
      }
      enum cn-tag {
        value 8937;
        description
          "22-E9  Congestion Notification Tag (CN-TAG)";
        reference
          "Organization: IEEE 802.1 Working Group
          Reference: IEEE Std 802.1Q";
      }
      enum msrp {
        value 8938;
        description
          "22-EA  Multiple Stream Reservation Protocol (MSRP)";
        reference
          "Organization: IEEE 802.1 Working Group
          Reference: IEEE Std 802.1Q";
      }
      enum trill {
        value 8947;
        description
          "22-F3  Transparent Interconnection of Lots of Links";
        reference
          "Organization: IETF TRILL Working Group
          Reference: IETF RFC 6325";
      }
      enum decnet {
        value 24579;
        description
          "60-03  DECnet DNA Routing";
        reference
          "Organization: DEC
          Reference: DECnet DIGITAL Network Architecture - Ethernet
          Data Link Architectural Specification v1.0.0";
      }
      enum rarp {
        value 32821;
        description
          "80-35  Reverse Address Resolution Protocol";
        reference
          "Organization: Private
          Reference: IETF RFC 903";
      }
      enum appletalk {
        value 32923;
        description
          "80-9B  Appletalk (Ethertalk)";
        reference
          "Organization: Private
          Reference: Inside Appletalk, Second Edition";
      }
      enum aarp {
        value 33011;
        description
          "80-F3  Appletalk Address Resolution Protocol";
        reference
          "Organization: Private
          Reference: Inside Appletalk, Second Edition";
      }
      enum c-tag {
        value 33024;
        description
          "81-00  Customer VLAN Tag (C-TAG)";
        reference
          "Organization: IEEE 802.1 Working Group
          Reference: IEEE Std 802.1Q";
      }
      enum ipx {
        value 33079;
        description
          "81-37  Internetwork Packet Exchange (IPX)";
        reference
          "Organization: Novell, Inc.
          Reference: Internetwork Packet Exchange - Novell, Inc.";
      }
      enum qnx {
        value 33284;
        description
          "82-04  QNX Qnet";
        reference
          "Organization: Quantum Software Systems, Ltd.
          Reference: QNX - Quantum Software Systems, Ltd.";
      }
      enum ipv6 {
        value 34525;
        description
          "86-DD  Internet Protocol Version 6 (IPv6)";
        reference
          "Organization: USC/ISI
          Reference: IETF RFC 2464";
      }
      enum efc {
        value 34824;
        description
          "88-08  Multipoint Control Protocol (MPCP)";
        reference
          "Organization: IEEE 802.3 Working Group
          Reference: IEEE Std 802.3";
      }
      enum esp {
        value 34825;
        description
          "88-09  Ethernet Slow Protocol";
        reference
          "Organization: IEEE 802.3 Working Group
          Reference: IEEE Std 802.3";
      }
      enum cobranet {
        value 34841;
        description
          "88-19  CobraNet";
        reference
          "Organization: Peak Audio
          Reference: CobraNet Programmer's Reference, Version 2.5";
      }
      enum mpls-unicast {
        value 34887;
        description
          "88-47  Multiprotocol Label Switching (MPLS) unicast
          traffic";
        reference
          "Organization: Cisco Systems
          Reference: IETF RFC 3031";
      }
      enum mpls-multicast {
        value 34888;
        description
          "88-48  Multiprotocol Label Switching (MPLS) multicast";
        reference
          "Organization: Cisco Systems
          Reference: IETF RFC 3031";
      }
      enum pppoe-discovery {
        value 34915;
        description
          "88-63  Point-to-Point Protocol over Ethernet (PPPoE)
          Discovery Stage";
        reference
          "Organization: UUNET Technologies, Inc.
          Reference: IETF RFC 2516";
      }
      enum pppoe-session {
        value 34916;
        description
          "88-64  Point-to-Point Protocol over Ethernet (PPPoE)
          Session Stage";
        reference
          "Organization: UUNET Technologies, Inc.
          Reference: IETF RFC 2516";
      }
      enum intel-ans {
        value 34925;
        description
          "88-6D  Intel Advanced Networking Services Probe Packets";
        reference
          "Organization: Intel Corporation
          Reference: Intel(R) Advanced Network Services (Intel(R) ANS)
          Advanced Settings for Teams";
      }
      enum llc-encaps {
        value 34928;
        description
          "88-70  LLC Encapsulation";
        reference
          "Organization: IEEE 802.1 Working Group
          Reference: IEEE Std 802.1AC";
      }
      enum homeplug {
        value 34939;
        description
          "88-7B  Homeplug";
        reference
          "Organization: Intellon Corporation
          Reference:  INT51X1 datasheet";
      }
      enum eapol {
        value 34958;
        description
          "88-8E  Port Access Entity (PAE) EtherType, Extensible
          Authentication Protocol over LANs (EAPOL)";
        reference
          "Organization: IEEE 802.1 Working Group
          Reference: IEEE Std 802.1X";
      }
      enum profinet {
        value 34962;
        description
          "88-92  PROFINET";
        reference
          "Organization: PROFIBUS International
          Reference: IEC 61158-6-10";
      }
      enum hyperscsi {
        value 34970;
        description
          "88-9A  Small Computer System Interface (SCSI) over
          Ethernet.";
        reference
          "Organization: Data Storage Institute
          Reference: An Ethernet Based Data Storage Protocol for Home
          Network";
      }
      enum aoe {
        value 34978;
        description
          "88-A2  Advanced Technology Attachment (ATA) over Ethernet.";
        reference
          "Organization: Coraid Inc
          Reference: AoE (ATA over Ethernet)";
      }
      enum ethercat {
        value 34980;
        description
          "88-A4  Ethernet for Control Automation Technology
          (EtherCAT)";
        reference
          "Organization: Beckhoff Automation GmbH & Co KG
          Reference: IEC 61158-4-12";
      }
      enum s-tag {
        value 34984;
        description
          "88-A8  Service VLAN Tag (S-TAG) or Backbone VLAN Tag
          (B-TAG)";
        reference
          "Organization: IEEE 802.1 Working Group
          Reference: IEEE Std 802.1Q";
      }
      enum ethernet-powerlink {
        value 34987;
        description
          "88-AB  Ethernet Powerlink";
        reference
          "Organization: Ethernet Powerlink Standardization Group
          (EPSG)
          Reference: IEC 61158-4-13";
      }
      enum exp1 {
        value 34997;
        description
          "88-B5  Local experimental EtherType 1";
        reference
          "Organization: IEEE 802.1 Working Group
          Reference: IEEE Std 802";
      }
      enum exp2 {
        value 34998;
        description
          "88-B6  Local experimental EtherType 2";
        reference
          "Organization: IEEE 802.1 Working Group
          Reference: IEEE Std 802";
      }
      enum oui-ext {
        value 34999;
        description
          "88-B7  OUI Extended EtherType";
        reference
          "Organization: IEEE 802.1 Working Group
          Reference: IEEE Std 802";
      }
      enum goose {
        value 35000;
        description
          "88-B8  IEC 61850 Generic Object Oriented Substation Event
          (GOOSE)";
        reference
          "Organization: IEC TC57
          Reference: IEC 61850-8-1";
      }
      enum gse {
        value 35001;
        description
          "88-B9  IEC 61850 Generic Substation Events (GSE) management
          services";
        reference
          "Organization: IEC TC57
          Reference: IEC 61850-8-1";
      }
      enum sv {
        value 35002;
        description
          "88-BA  IEC 61850 Sampled Value Transmission (SV)";
        reference
          "Organization: IEC TC57
          Reference: IEC 61850-8-2";
      }
      enum pre-auth {
        value 35015;
        description
          "88-C7  RSNA Pre-Authentication";
        reference
          "Organization: IEEE 802.11 Working Group
          Reference: IEEE Std 802.11";
      }
      enum lldp {
        value 35020;
        description
          "88-CC  Link Layer Discovery Protocol (LLDP)";
        reference
          "Organization: IEEE 802.1 Working Group
          Reference: IEEE Std 802.1AB";
      }
      enum sercos {
        value 35021;
        description
          "88-CD  Sercos Interface";
        reference
          "Organization: sercos international e.V.
          Reference: IEC 61158-4-19";
      }
      enum wsmp {
        value 35036;
        description
          "88-DC  WAVE Short Message Protocol (WSMP)";
        reference
          "Organization: IEEE P1609 WG
          Reference: IEEE Std 1609";
      }
      enum homeplug-av-mme {
        value 35041;
        description
          "88-E1  HomePlug AV Mobile Management Entity (MME)";
        reference
          "Organization: HomePlug Powerline Alliance, Inc.
          Reference: HomePlug AV Specification";
      }
      enum mrp {
        value 35043;
        description
          "88-E3  Media Redundancy Protocol";
        reference
          "Organization: Siemens AG
          Reference: IEC 62439-2";
      }
      enum macsec {
        value 35045;
        description
          "88-E5  MACsec EtherType";
        reference
          "Organization: IEEE 802 LAN/MAN Standards Committee
          Reference: IEEE Std 802.1AE";
      }
      enum i-tag {
        value 35047;
        description
          "88-E7  Backbone Service Instance Tag";
        reference
          "Organization: IEEE 802.1 Working Group
          Reference: IEEE Std 802.1Q";
      }
      enum mvrp {
        value 35061;
        description
          "88-F5  Multiple VLAN Registration Protocol (MVRP)";
        reference
          "Organization: IEEE 802.1 Working Group
          Reference: IEEE Std 802.1Q";
      }
      enum mmrp {
        value 35062;
        description
          "88-F6  Multiple MAC Registration Protocol (MMRP)";
        reference
          "Organization: IEEE 802.1 Working Group
          Reference: IEEE Std 802.1Q";
      }
      enum ptp {
        value 35063;
        description
          "88-F7  Precision Time Protocol";
        reference
          "Organization: IEEE I&M Society TC9
          Reference: IEEE Std 1588";
      }
      enum cfm {
        value 35074;
        description
          "89-02  IEEE 802.1Q Connectivity Fault Management (CFM) PDU
          Encapsulation EtherType";
        reference
          "Organization: IEEE 802.1 Working Group
          Reference: IEEE Std 802.1Q";
      }
      enum fcoe {
        value 35078;
        description
          "89-06  Fibre Channel over Ethernet (FCoE)";
        reference
          "Organization: Cisco Systems, Inc
          Reference: T11 FC-BB-5";
      }
      enum wlan-mgmt {
        value 35085;
        description
          "89-0D  802.11 Management Protocol";
        reference
          "Organization: IEEE 802.11 Working Group
          Reference: IEEE Std 802.11";
      }
      enum encap {
        value 35088;
        description
          "89-10  Backbone Service Encapsulated Addresses";
        reference
          "Organization: IEEE 802.1 Working Group
          Reference: IEEE Std 802.1Q";
      }
      enum fip {
        value 35092;
        description
          "89-14  FCoE Initialization Protocol";
        reference
          "Organization: Brocade Communications Systems LLC
          Reference: T11 FC-BB-5";
      }
      enum roce {
        value 35093;
        description
          "89-15  Remote Direct Memory Access (RDMA) over Converged
          Ethernet (RoCEv1)";
        reference
          "Organization: Mellanox Technologies, Inc.
          Reference: InfiniBand(TM) Architecture Specification";
      }
      enum mis {
        value 35095;
        description
          "89-17  Media Independent Service (MIS) Protocol";
        reference
          "Organization: IEEE 802.21 Working Group
          Reference: IEEE Std 802.21";
      }
      enum tte {
        value 35101;
        description
          "89-1D  Time-Triggered Ethernet (TTE) Protocol Control
          Frame";
        reference
          "Organization: TTTech Computertechnik AG
          Reference: SAE AS6802";
      }
      enum mirp {
        value 35113;
        description
          "89-29  Multiple I-SID Registration Protocol (MIRP)";
        reference
          "Organization: IEEE 802.1 Working Group
          Reference: IEEE Std 802.1Q";
      }
      enum hsr {
        value 35119;
        description
          "89-2F  High-availability Seamless Redundancy (HSR)";
        reference
          "Organization: International Electrotechnical Commission
          Reference: IEC 62439-3";
      }
      enum e-tag {
        value 35135;
        description
          "89-3F  Bridge Port Extension Tag (E-TAG)";
        reference
          "Organization: IEEE 802.1 Working Group
          Reference: IEEE Std 802.1BR";
      }
      enum ecp {
        value 35136;
        description
          "89-40  Edge Control Protocol";
        reference
          "Organization: IEEE 802.1 Working Group
          Reference: IEEE Std 802.1Q";
      }
      enum f-tag {
        value 35147;
        description
          "89-4B  Flow Filtering Tag (F-TAG)";
        reference
          "Organization: IEEE 802.1 Working Group
          Reference: IEEE Std 802.1Q";
      }
      enum drcp {
        value 35154;
        description
          "89-52  Distributed Relay Control Protocol (DRCP)";
        reference
          "Organization: IEEE 802.1 Working Group
          Reference: IEEE Std 802.1AX";
      }
      enum cim {
        value 35234;
        description
          "89-A2  Congestion Isolation Message (CIM)";
        reference
          "Organization: IEEE 802.1 Working Group
          Reference: IEEE Std 802.1Q";
      }
      enum llc-legacy {
        value 51665;
        description
          "C9-D1  LLC Encapsulation (obsolete)";
        reference
          "Organization: IEEE 802.1 Working Group
          Reference: IEEE Std 802.1AC";
      }
      enum mpp {
        value 57915;
        description
          "E2-3B  MAC Privacy protection Protocol";
        reference
          "Organization:
          Reference: IEEE Std 802.1AE";
      }
      enum r-tag {
        value 61889;
        description
          "F1-C1  Frame Replication and Elimination for Reliability
          (FRER) Redundancy Tag (R-TAG)";
        reference
          "Organization: IEEE 802.1 Working Group
          Reference: IEEE Std 802.1CB";
      }
    }
    description
      "IEEE Std 802 EtherTypes subset.";
  }

}
