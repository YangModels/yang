module ieee1906-dot1-neuron
{
  yang-version 1.1;
  namespace "urn:ieee:std:1906.1:yang:ieee1906-dot1-neuron";
  prefix "ieee1906-neuron";

  import ieee1906-dot1-types { prefix types; }
  import ieee1906-dot1-math { prefix math; }
  import ieee1906-dot1-si-units { prefix si-units; }
  import ieee1906-dot1-system { prefix system; }

  organization "P1906.1.1/D1.0 Draft Standard Data Model for Nanoscale Communication Systems Working Group";

  contact 	"IEEE P1906.1.1 Working Group
		 Chair: Stephen F. Bush <bushsf@research.ge.com>
		 Secretary: Guillaume Mantelet <gmantelet@voltigeurnetworks.com>";

  description	"This is an example illustrating how to refine the 1906.1 framework
                 to include specific component hierarchy to model a simple neuron.
                 This example reuses part of the model described in reference";

  reference     "A. Banerjee, J. L. Paluh, A. Mukherjee, K. G. Kumar, A. Ghosh, 
                 M. K. Naskar (2017) ”Modeling the neuron as a nano communication 
                 system to identify spatiotemporal molecular events in neurodegenerative 
                 disease”. International J Nanomedicine, in press.";

  revision 2020-07-07
  {
    description "Initial version.";
  }


  //
  // Here, we simply want to report a non standard property for this model.
  // There is a Poisson process at stake in which BDNF and Ca2+ ions are
  // generated.
  //
  identity poisson-process
  {
    base types:non-standard-physics;
    description "The Poisson process can be used to simulate the generation
                 of message, or something that acts to the message, such as
                 a perturbation.";
  }

  //
  // Next identity defines a new (specialized) type of motor (Message Carrier).
  //
  identity dcv-bdnf 
  {
    base types:motor;
    description "It is a molecular motor-vesicle cargo loaded with DCV-BDNF";
  }


  //
  // So because we define a new type of motor, we thought it was the perfect
  // moment to introduce a new type of metrics that is closely related to this
  // new component. It is the percentage of the message that is lost during
  // transport by this vesicle cargo!
  // 
  grouping unrealized-dcv-bdnf-percentage
  {
    leaf unrealized-dcv-bdnf-percentage
    {
      when "derived-from-or-self(../type-of-component, 'poisson-process')";
      type math:percent;
      description "The parent component must have a leaf of type 'dcv-bdnf' in
                   order to be eligible to use this container.";
    }

    description "The corresponding message deliverability of the system.";
  }

  grouping average-traversal-time-per-bdnf-molecule
  {
    container average-traversal-time-per-bdnf-molecule
    {
      description "This is a measure of latency or response time of a
                   system";

      leaf average-time-due-to-diffusion 
      {
        type si-units:time;
        description "A function of the distance between the point of
                     consideration and generation and the diffusion
                     coefficient";
      }

      leaf average-clearance-time 
      {
        type si-units:time;
        description "Average clearance time of BDNF through microtubule
                     gates using gate selection process.";
      }
    }
  }

  //
  // We are now ready to augment existing framework!
  // Note that in this example, we have no interest augmenting ietf interface.
  // 
  container neuron-model
  {
    description "Redefined nanoscale-system for our neuron model, which is 
                 enriched with new metrics, and this is only the beginning."; 

    uses system:system
    {
      augment components/component
      {
        uses unrealized-dcv-bdnf-percentage;

        description "Augment nanoscale system with the poisson process defined
                     in neuron model.";
      }

      augment system-metrics
      {
        uses average-traversal-time-per-bdnf-molecule;
        description "test";
      }
    }
    uses average-traversal-time-per-bdnf-molecule;
  }    
}
