module ieee1906-dot1-nanosensor
{
  yang-version 1.1;
  namespace "urn:ieee:std:1906.1:yang:ieee1906-dot1-nanosensor";
  prefix "ieee1906-nanosensor";

  import ietf-interfaces { prefix if; }
  import ieee1906-dot1-components { prefix components; }
  import ieee1906-dot1-components { prefix definitions; }
  import ieee1906-dot1-types { prefix types; }

  organization "P1906.1.1/D1.0 Draft Standard Data Model for Nanoscale Communication Systems Working Group";

  contact 	"IEEE P1906.1.1 Working Group
		 Chair: Stephen F. Bush <bushsf@research.ge.com>
		 Secretary: Guillaume Mantelet <gmantelet@voltigeurnetworks.com>";

  description	"This is an example illustrating how to refine the 1906.1 framework
                 to include specific details regarding Nanosensors. The framework
                 augments ietf-interface.yang module, this means that our nanosensor 
                 can be now described as an IETF interface system.";

  revision 2020-07-07
  {
    description "Initial version.";
  }

  //
  // Let us control how ieth-interface can be augmented. Only for systems
  // that implement naniosensor. Other systems may find no value in it.
  //
  feature nanosensor
  {
    description "This nanoscale interface is a nanosensor.";
  }

  //
  // Here, we simply want to report a non standard property for this model.
  // Note that our impact of scale on resonance is also considered a kind
  // of motion, and then, this keyword can also be reused to define a 
  // component!
  //
  identity impact-of-scale-on-resonance
  {
    base types:non-standard-physics;
    description "Apparently, scale of the system has an impact on its resonance
                 its motion.";
  }


  //
  // Next identity defines a new type of perturbation.
  //
  identity radio-frequency-modulation 
  {
    base types:perturbation;
    description "The instantaneous frequency deviation in carrier waves 
                 transport message acting in our model as a perturbation. In
                 this model, modulation is performed over oscillations in the
                 range of 20Khz – 300GHz, and beyond.";
  }

  //
  // So because we define a new type of motion, we thought it was the perfect
  // moment to introduce a new type of metrics that is closely related to this
  // new component. Well... it is an empty shell, but still, it is a good
  // example.
  // 
  grouping resonance-metrics
  {
    container resonance-metrics
    {
      when "derived-from-or-self(../definitions:type-of-definition, 'impact-of-scale-on-resonance')";
      description "The parent component must have a leaf of type 'impact-of-
                   scale-on-resonance' in order to be eligible to use this 
                   container.";
    }

    description "This is a placeholder for Resonance metrics being used as 
                 non-standard physics in this model.";
  }


  //
  // We are now ready to augment existing framework!
  // Note that in this example, we have no interest augmenting ietf interface.
  // 
  augment "/if:interfaces/if:interface/components:nanoscale-interface/definitions:definitions/definitions:definition"
  {
    if-feature nanosensor;
    uses resonance-metrics;

    description "Augment nanoscale interface with the resonance defined
                 in nanosensor example.";
  }  
}
