module ieee1906-dot1-thermodynamics
{
  yang-version 1.1;
  namespace "urn:ieee:std:1906.1:yang:ieee1906-dot1-thermodynamics";
  prefix "ieee1906-dot1-thermodynamics";

  import ieee1906-dot1-math {  prefix ieee1906-dot1-math;  }
  import ieee1906-dot1-function {  prefix ieee1906-dot1-function;  }
  import ieee1906-dot1-si-units {  prefix ieee1906-dot1-si-units;  }

  organization "IEEE 1906.1-2015 - Recommended Practice for Nanoscale and Molecular Communication
                Framework Working Group";

  contact  "Stephen F. Bush <bushsf@research.ge.com>
	    Guillaume Mantelet <gmantelet@voltigeurnetworks.com>";

  description "Trying to define here whatever can be used in thermodynamics.

               +----------------------+----+------------+---------------------------------------+
               | name                 |symb| units      | equation                              |
               +----------------------+----+------------+---------------------------------------+
               | flow-velocity        |  v | m.s-1      |                                       |
               | mass-flow-rate       |mdot| kg.s-1     | mdot = rho.Q = rho.v.A = jm.A         |
               | mass-flux            | jm | kg.s-1.m-2 | jm = rho.v                            |
               | volumetric-flow-rate |  Q | m3.s-1     | Q = v.A                               |
               +----------------------+----+------------+---------------------------------------+
               ";

  revision 2020-07-07
  {
    description "Initial version.";

	reference "";
  }

  typedef diffusion-coefficient
  {
	type ieee1906-dot1-function:variable;
	units meter^2.second-1;
	description "Diffusivity or diffusion coefficient is a proportionality
	             constant between the molar flux due to molecular diffusion
	             and the gradient in the concentration of the species (or the
	             driving force for diffusion).";
  }

  grouping flow-velocity
  {
    uses ieee1906-dot1-math:vector;
    ieee1906-dot1-si-units:units meter/second;
    description "The flow velocity of the mass of the message carriers.";
  }

  grouping mass-flux
  {
    ieee1906-dot1-math:equation mass-flux
    {
      ieee1906-dot1-math:symbol jm;
      ieee1906-dot1-math:value;
      ieee1906-dot1-si-units:units kilogram.second^-1.meter^-2;
  
      ieee1906-dot1-math:expression
      {
        leaf density
        {
          ieee1906-dot1-math:symbol rho;
          type ieee1906-dot1-si-units:mass-density;
          description "The mass density of the fluid";
        }
        uses flow-velocity;
      }
    }
  
    description "A reusable mass flux equation.";
  }

  //typedef mass-flux
  //{
  //  type ieee1906-dot1-function:variable;
  //  ieee1906-dot1-si-units:units kilogram.second^-1.meter^-2;
  //  description "A reusable mass flux equation.";
  //}

  grouping volumetric-flow-rate
  {
    ieee1906-dot1-math:equation volumetric-flow-rate
    {
      ieee1906-dot1-math:symbol "Vdot Q";
      ieee1906-dot1-math:value;
      ieee1906-dot1-si-units:units meter^3.second^-1;

      ieee1906-dot1-math:expression
      {
        uses flow-velocity;
        uses ieee1906-dot1-math:vector-area;
      }

      description "Volume of fluid which passes per unit time. The volume flow rate of the
                   message carrier.";
    }

    description "A volumetric flow rate equation.";
  }


  grouping mass-flow-rate
  {
    ieee1906-dot1-math:equation mass-flow-rate
    {
      ieee1906-dot1-math:symbol mdot;
      ieee1906-dot1-math:value;
      ieee1906-dot1-si-units:units kilogram.second-1;

      ieee1906-dot1-math:expression
      {
        leaf density
        {
          ieee1906-dot1-math:symbol rho;
          type ieee1906-dot1-si-units:mass-density;
          description "A mass density.";
        }
        uses volumetric-flow-rate;
      }

      ieee1906-dot1-math:expression
      {
        leaf density
        {
          ieee1906-dot1-math:symbol rho;
          type ieee1906-dot1-si-units:mass-density;
          description "A mass density.";
        }
        uses flow-velocity;
        uses ieee1906-dot1-math:vector-area;
      }

      ieee1906-dot1-math:expression
      {
        uses mass-flux;
        uses ieee1906-dot1-math:vector-area;
      }
    }

    description "A reusable mass flow rate equation.";
  }
}
