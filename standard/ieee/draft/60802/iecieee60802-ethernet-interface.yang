module iecieee60802-ethernet-interface {
  yang-version 1.1;
  namespace
    "urn:ieee:std:60802:yang:iecieee60802-ethernet-interface";
  prefix ia-eth-if;

  import ieee802-ethernet-interface {
    prefix eth-if;
  }
  import ietf-interfaces {
    prefix if;
  }

  organization
    "IEEE 802.1 Working Group and IEC subcommittee 65C:
     Industrial networks, of IEC technical committee 65:
     Industrial-process measurement, control and automation";
  contact
    "WG-URL: http://ieee802.org/1/
     WG-EMail: stds-802-1-l@ieee.org

     Contact: IEEE 802.1 Working Group Chair
              Postal: C/O IEEE 802.1 Working Group
              IEEE Standards Association
              445 Hoes Lane
              Piscataway, NJ 08854
              USA

     E-mail: stds-802-1-chairs@ieee.org";
  description
    "Management objects that provide information about IEC/IEEE 60802
     IA-Stations as specified in IEC/IEEE 60802.

     Copyright (C) IEC/IEEE (2025).
     This version of this YANG module is part of IEC/IEEE 60802;
     see the standard itself for full legal notices.";

  revision 2025-03-12 {
    description "Published as part of IEC/IEEE 60802-2025.
      The following reference statement identifies each referenced
      IEEE Standard as updated by applicable amendments.";
    reference
      "IEC/IEEE 60802 TSN profile for industrial automation:
      IEC/IEEE 60802-2025.
      IEEE Std 802.1Q Bridges and Bridged Networks:
      IEEE Std 802.1Q-2022, IEEE Std 802.1Qcz-2023,
      IEEE Std 802.1Qcw-2023, IEEE Std 802.1Qdj-2024,
      IEEE Std 802.1Qdx-2024, IEEE Std 802.1Qdy-2025.";
  }

  augment "/if:interfaces/if:interface/eth-if:ethernet" {
    description
      "Augment IEEE Std 802.3 ethernet.";
    list supported-mau-types {
      key "mau-type";
      config false;
      description
        "Contains a list of supported MAU parameters.";
      leaf mau-type {
        type int32;
        config false;
        description
          "The value is the supported MAU Type derived from the list
           position of the corresponding dot3MauType as listed in
           Clause 5 of IETF RFC 4836.";
        reference
          "Item a) in 6.4.10.3.2.1 of IEC/IEEE 60802";
      }
      leaf preemption-supported {
        type boolean;
        config false;
        description
          "The Boolean value indicates if preemption is supported by
           the MAU Type.";
        reference
          "Item b) in 6.4.10.3.2.1 of IEC/IEEE 60802";
      }
    }
  }
}
