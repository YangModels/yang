module iecieee60802-proxy-target {
  yang-version 1.1;
  namespace "urn:ieee:std:60802:yang:iecieee60802-proxy-target";
  prefix cd;

  organization
    "IEEE 802.1 Working Group and IEC subcommittee 65C:
     Industrial networks, of IEC technical committee 65:
     Industrial-process measurement, control and automation";
  contact
    "WG-URL: http://ieee802.org/1/
     WG-EMail: stds-802-1-l@ieee.org

     Contact: IEEE 802.1 Working Group Chair
              Postal: C/O IEEE 802.1 Working Group
              IEEE Standards Association
              445 Hoes Lane
              Piscataway, NJ 08854
              USA

     E-mail: stds-802-1-chairs@ieee.org";
  description
    "Capability information for IEC/IEEE 60802 proxy targets as
     specified in IEC/IEEE 60802.

     Copyright (C) IEC/IEEE (2025).
     This version of this YANG module is part of IEC/IEEE 60802;
     see the standard itself for full legal notices.";

  revision 2025-01-08 {
    description
      "Published as part of IEC/IEEE 60802-2025.
       The following reference statement identifies each referenced
       IEEE Standard as updated by applicable amendments.";
    reference
      "IEC/IEEE 60802 TSN profile for industrial automation:
       IEC/IEEE 60802-2025.
       IEEE Std 802.1Q Bridges and Bridged Networks:
       IEEE Std 802.1Q-2022, IEEE Std 802.1Qcz-2023,
       IEEE Std 802.1Qcw-2023, IEEE Std 802.1Qdj-2024,
       IEEE Std 802.1Qdx-2024, IEEE Std 802.1Qdy-2025.";
  }

  container proxy-target {
    presence "The presence of this container indicates that an IA station
               is a proxy target that requires a proxy device";
    description
      "This container provides information about a
       60802 proxy target device.";
    reference
      "IEC/IEEE 60802 - YANG Data Model";
    leaf required-proxy-type {
      type string {
        pattern '[0-9A-F]{2}(-[0-9A-F]{2}){2}';
      }
      config false;
      description
        "OID of proxy that this proxy target requires.";
      reference
        "6.4.10.3.10.1 of IEC/IEEE 60802";
    }
  }
}
