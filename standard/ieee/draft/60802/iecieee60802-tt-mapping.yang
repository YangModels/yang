module iecieee60802-tt-mapping {
  yang-version "1.1";
  namespace "urn:ieee:std:60802:yang:iecieee60802-tt-mapping";
  prefix tt-mapping;

  import ieee802-dot1q-types {
    prefix dot1q-types;
  }

  organization
    "IEEE 802.1 Working Group and IEC subcommittee 65C:
     Industrial networks, of IEC technical committee 65:
     Industrial-process measurement, control and automation";
  contact
    "WG-URL: http://ieee802.org/1/
    WG-EMail: stds-802-1-l@ieee.org
    
    Contact: IEEE 802.1 Working Group Chair
    Postal: C/O IEEE 802.1 Working Group
           IEEE Standards Association
           445 Hoes Lane
           Piscataway, NJ 08854
           USA
    
    E-mail: stds-802-1-chairs@ieee.org";
  description
    "This module provides information on characteristics of traffic classes
     configured in a network to allow applications to map application traffic
     classes to them.
    
    Copyright (C) IEC/IEEE (2025).
    
    This version of this YANG module is part of IEC/IEEE 60802;
    see the standard itself for full legal notices.";
  revision 2024-12-13 {
    description
      "Published as part of IEC/IEEE 60802-2025.

      The following reference statement identifies each referenced
      IEEE Standard as updated by applicable amendments.";
    reference
      "IEC/IEEE 60802 TSN profile for industrial automation:
      IEC/IEEE 60802-2025.
      IEEE Std 802.1Q Bridges and Bridged Networks:
      IEEE Std 802.1Q-2022, IEEE Std 802.1Qcz-2023,
      IEEE Std 802.1Qcw-2023, IEEE Std 802.1Qdj-2024,
      IEEE Std 802.1Qdx-2024, IEEE Std 802.1Qdy-2025.";
  }

  container tt-mapping {
    description
      "Top-level container for the traffic class module.";
    list network {
      key "network-name";
      description
        "A list of networks, each containing one or more sets of traffic class
         characteristics.";
      leaf network-name {
        type string;
        description
          "The network-name uniquely identifies a network.";
      }
      list traffic-type {
        key "traffic-type-name";
        description
          "A list of traffic types in the network, each with its associated 
          traffic type characteristics.";
        leaf traffic-type-name {
          type string;
          description
            "The traffic-type-name uniquely identifies the traffic type.";
        }
        leaf cyclic {
          type boolean;
          description
            "Indicates if cyclic transmission is mandatory (TRUE) or optional (FALSE)
             for this traffic type.";
          reference
            "4.7.2 of IEC/IEEE 60802-2025";
        }
        leaf data-delivery-req {
          type enumeration {
            enum frame-latency {
              value 0;
              description
                "Data delivery of a frame for a given Talker-Listener pair 
                 occurs within a bounded timespan.";
            }
            enum flow-latency {
              value 1;
              description
                "Data delivery up to a certain number of frames or data size
                 (including bursts of frames) occurring over a defined
                 period.";
            }
            enum deadline {
              value 2;
              description
                "Data delivery of a frame to a given Listener occurs at or
                 before a specific point in time.";
            }
            enum no {
              value 3;
              description
                "No special data delivery requirements.";
          }
        }
        description
          "The data-delivery-req provides information on the data 
           delivery requirements for this traffic type.";
        reference
            "4.7.2 of IEC/IEEE 60802-2025";
        }
        leaf time-triggered {
          type boolean;
          description
            "Indicates if it is required (TRUE) or optional (FALSE) that
             transmission occurs at a specific point in time based upon
             the Working Clock.";
          reference
            "4.7.2 of IEC/IEEE 60802-2025";
        }
        leaf stream-based {
          type boolean;
          default true;
          description
            "Indicates if traffic of this traffic type requires
             registering a stream, i.e., allocating dedicated 
             resources, for the  traffic, before a given Talker
             can start transmitting data (TRUE), or if registering
             a stream is not required (FALSE).";
          reference
            "4.7.2 of IEC/IEEE 60802-2025";
        }
        leaf vlan-id {
          type dot1q-types:vlanid; 
          description
            "The VID this traffic type is mapped to.";
        }
      list redundancy {
        key "vlan-id-redundant";
        description
          "A list of VIDs this traffic type is mapped to for redundant
           transmission. There is one entry in the list per redundant
           transmission ";
        leaf vlan-id-redundant {
          type dot1q-types:vlanid; 
          description
            "The VID this traffic type is mapped for a redundant transmission.";
        }
      }
        leaf priority-value {
          type dot1q-types:priority-type;
          description
            "The PCP this traffic type is mapped to.";
        }
      }
    }
  }
}
