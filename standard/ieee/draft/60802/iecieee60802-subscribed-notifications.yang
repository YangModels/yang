module iecieee60802-subscribed-notifications {
  yang-version 1.1;
  namespace
    "urn:ieee:std:60802:yang:iecieee60802-subscribed-notifications";
  prefix ia-sn;

  import ietf-subscribed-notifications {
    prefix sn;
  }

  organization
    "IEEE 802.1 Working Group and IEC subcommittee 65C:
     Industrial networks, of IEC technical committee 65:
     Industrial-process measurement, control and automation";
  contact
    "WG-URL: http://ieee802.org/1/
     WG-EMail: stds-802-1-l@ieee.org

     Contact: IEEE 802.1 Working Group Chair
              Postal: C/O IEEE 802.1 Working Group
              IEEE Standards Association
              445 Hoes Lane
              Piscataway, NJ 08854
              USA

     E-mail: stds-802-1-chairs@ieee.org";
  description
    "Management objects that provide information about IEC/IEEE 60802
     IA-Stations as specified in IEC/IEEE 60802.

     Copyright (C) IEC/IEEE (2025).
     This version of this YANG module is part of IEC/IEEE 60802;
     see the standard itself for full legal notices.";

  revision 2024-02-21 {
    description "Published as part of IEC/IEEE 60802-2025.
      The following reference statement identifies each referenced
      IEEE Standard as updated by applicable amendments.";
    reference
      "IEC/IEEE 60802 TSN profile for industrial automation:
      IEC/IEEE 60802-2025.
      IEEE Std 802.1Q Bridges and Bridged Networks:
      IEEE Std 802.1Q-2022, IEEE Std 802.1Qcz-2023,
      IEEE Std 802.1Qcw-2023, IEEE Std 802.1Qdj-2024,
      IEEE Std 802.1Qdx-2024, IEEE Std 802.1Qdy-2025.";
  }

  augment "/sn:subscriptions" {
    description
      "Augment subscriptions in ietf-subscribed-notifications.";
    leaf max-subscriptions {
      type uint16;
      config false;
      description
        "The value is the maximum number of supported NETCONF Server
         subscriptions.";
      reference
        "6.4.10.3.8.1 of IEC/IEEE 60802";
    }
    leaf max-on-change-subscription-leaves {
      type uint16;
      config false;
      description
        "The value is the maximum number of supported leaves for
         NETCONF Server on-change subscriptions according to IETF
         RFC 8641.";
      reference
        "6.4.10.3.8.2 of IEC/IEEE 60802";
    }
    leaf max-periodic-subscription-leaves {
      type uint16;
      config false;
      description
        "The value is the maximum number of supported leaves for
         NETCONF Server periodic subscriptions according to IETF
         RFC 8641.";
      reference
        "6.4.10.3.8.3 of IEC/IEEE 60802";
    }
    leaf min-periodic-subscription-interval {
      type uint16;
      config false;
      description
        "The value is the minimum periodic subscription interval in
         centiseconds (0.01 seconds) for NETCONF Server periodic 
         subscriptions according to IETF RFC 8641.";
      reference
        "6.4.10.3.8.4 of IEC/IEEE 60802";
    }
  }
}
