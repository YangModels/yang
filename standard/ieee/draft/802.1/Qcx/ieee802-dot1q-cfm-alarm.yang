module ieee802-dot1q-cfm-alarm {
  yang-version 1.1;

  namespace "urn:ieee:std:802.1Q:yang:ieee802-dot1q-cfm-alarm";
  prefix "dot1q-cfm-alarm";
  
  import ieee802-dot1q-cfm { prefix "dot1q-cfm"; }
  
  organization
    "IEEE 802.1 Working Group";

  contact
    "WG-URL: http://www.ieee802.org/1/
    WG-EMail: stds-802-1-L@ieee.org

    Contact: IEEE 802.1 Working Group Chair
    Postal: C/O IEEE 802.1 Working Group
            IEEE Standards Association
            445 Hoes Lane
            Piscataway
            NJ 08854
            USA
  
    E-mail: STDS-802-1-L@IEEE.ORG";

  description
    "Connectivity Fault Management (CFM) comprises capabilities
    for detecting, verifying, and isolating connectivity failures
    in Virtual Bridged Local Area Networks. These capabilities
    can be used in networks operated by multiple independent
    organizations, each with restricted management access to each 
    other's equipment.";
  
  revision 2019-09-30 {
    description
      "Creation for Working Group review.";
    reference
      "IEEE Std 802.1Q-2018, Bridges and Bridged Networks.";
  }
     
  /* -------------------------------------------------------------
   *  Augmentations of objects defined in generic CFM YANG module
   *  (ieee802-dot1q-cfm) to define CFM alarms.
   * -------------------------------------------------------------
   */
   
  augment "/dot1q-cfm:cfm/dot1q-cfm:maintenance-group"   
         + "/dot1q-cfm:mep" {
    when "dot1q-cfm:mep-id";
      description
      "Augment the MEP object defined in the ieee802-dot1q-cfm
      (CFM MEP) YANG module with CFM alarm specific attributes.";
    
      notification mep-fault-alarm {
        description
          "To alert the Manager to the existence of a fault in a
          monitored MA by issuing a Fault Alarm.";
        leaf mep-priority-defect {
          type leafref {
            path "../../dot1q-cfm:continuity-check/dot1q-cfm:highest-priority-defect";
          }
          config false;
          mandatory true;
          description
            "The highest priority defect that has been present
            since the MEPs Fault Notification Generator state
            machine was last in the FNG_RESET state.";
        }
        reference
          "12.14.7.7.2c of IEEE Std 802.1Q-2018";
      }
    }
  
} // ieee802-dot1q-cfm-alarm
