module ieee802-dot1ae-types {
  yang-version 1.1;
  namespace "urn:ieee:std:802.1AE:yang:ieee802-dot1ae-types";
  prefix dot1ae-types;

  organization
    "Institute of Electrical and Electronics Engineers";
  contact
    "WG-URL: http://grouper.ieee.org/groups/802/1/
     WG-EMail: stds-802-1@ieee.org
       Contact: IEEE 802.1 Working Group Chair
       Postal: C/O IEEE 802.1 Working Group
       IEEE Standards Association
            445 Hoes Lane
            P.O. Box 1331
            Piscataway
            NJ 08855-1331
            USA

     E-mail: STDS-802-1-L@LISTSERV.IEEE.ORG";
  description
    "Common types used within dot1ae modules";

  revision 2019-05-09 {
    description
      "Updates based upon comment resolution on draft TBD ";
    reference
      "IEEE 802.1AE-2018, Media Access Control (MAC) Security.";
  }

  typedef sec-an-type {
    type uint8 {
      range "0..3";
    }
    description
      "A 2 bit number that is concatenated with a MACsec Secure Channel
       Identifier to identify a Secure Association. Indicates an
       Association Number (AN) assigned by the Key Server for use with
       the key number for transmission.

       Each SC is comprised of a succession of SAs, each with a different
       SAK, identified by a Secure Association Identifier (SAI) comprising
       an SCI concatenated with a two-bit AN.  The SAI is unique for SAs
       used by SecYs participating in a given CA at any instant.";
    reference
      "IEEE 802.1X-2010 Clause 9.8, Clause 9.16";
  }

  typedef sec-pn-type {
    type uint64;
    description
      "This is the Packet Number. It may be a 32 bit or a 64 bit
       unsigned value. A monotonically increasing value that is
       guaranteed unique for each MACsec frame transmitted using
       a given Secure Association Key (SAK).";
    reference
      "IEEE 802.1X-2010 Clause 9.8, Clause 9.16";
  }

  typedef sec-sci-type {
    type binary {
      length "8";
    }
    description
      "The Secure Channel Identifier is 8 bytes (SCI). The SCI is
       an 8 octet binary number, where the first 6 octets represents the MAC
       Address (in canonical format), and the next 2 octets represents
       the Port Identifier.";
    reference
      "IEEE 802.1X-2010 Clause 7.1.2, Clause 9.16";
  }

  typedef sec-eui64-type {
    type uint64;
    description
      "A 64 bit Identifier.";
  }

  typedef sec-key-identifier-type {
    type string {
      length "32";
    }
    description
      "The keyIdentifier is an octet string, whose format and
       interpretation depends on the key agreement protocol in use. It
       does not contain any information about the SAK other than that
       explicitly chosen by the key agreement protocol to publicly identify
       the key. If MKA is being used, it is the 128-bit Key Identifier
       (KI) specified by IEEE Std 802.1X encoded in an octet string as
       specified by that standard.";
  }
}
