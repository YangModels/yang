module ieee802-dot1q-psfp-bridge {
  yang-version "1.1";
  namespace urn:ieee:std:802.1Q:yang:ieee802-dot1q-psfp-bridge;
  prefix psfp-bridge;
  import ieee802-dot1q-bridge {
    prefix dot1q;
  }
  import ieee802-dot1q-psfp {
    prefix psfp;
  }
  organization
    "IEEE 802.1 Working Group";
  contact
    "WG-URL: http://www.ieee802.org/1/
    WG-EMail: stds-802-1-l@ieee.org
    
    Contact: IEEE 802.1 Working Group Chair
    Postal: C/O IEEE 802.1 Working Group
    IEEE Standards Association
    445 Hoes Lane
    Piscataway, NJ 08854
    USA
    
    E-mail: STDS-802-1-CHAIRS@IEEE.ORG";
  description
    "This module provides management of IEEE Std 802.1Q Bridge
    components that support Per-Stream Filtering and Policing (PSFP).
    
    Copyright (C) IEEE (2023).
    
    This version of this YANG module is part of IEEE Std 802.1Q; see the
    standard itself for full legal notices.";
  revision 2023-10-26 {
    description
      "Published as part of IEEE Std 802.1Qcw-2023.
      
      The following reference statement identifies each referenced IEEE
      Standard as updated by applicable amendments.";
    reference
      "IEEE Std 802.1Q Bridges and Bridged Networks: 
      IEEE Std 802.1Q-2022, IEEE Std 802.1Qcz-2023, IEEE Std 802.1Qcw-2023."; 
  }
  feature psfp {
    description
      "Per-Stream Filtering and Policing supported.";
    reference
      "IEEE Std 802.1Q";
  }
  augment "/dot1q:bridges/dot1q:bridge/dot1q:component" {
    description
      "Augment bridge with Per-Stream Filtering and Policing configuration";
    uses psfp:psfp-parameters;
  }
}
