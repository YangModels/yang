module ieee802-dot1q-lldp-tr-tlv {
  yang-version "1.1";
  namespace urn:ieee:std:802.1Q:yang:ieee802-dot1q-lldp-tr-tlv;
  prefix lldp-tr-tlv;
  import ieee802-dot1ab-lldp {
    prefix lldp;
  }
  organization
    "Institute of Electrical and Electronics Engineers";
  contact
    "WG-URL: http://ieee802.org/1/
    WG-EMail: stds-802-1-l@ieee.org
      Contact: IEEE 802.1 Working Group Chair
      Postal: C/O IEEE 802.1 Working Group
      IEEE Standards Association
           445 Hoes Lane
           Piscataway, NJ 08854
           USA
    
    E-mail: stds-802-1-chairs@ieee.org";
  description
    "IEEE Std 802.1Q extension TLVs for LLDP from the Topology
    Recognition set (trSet)
    
    References in this YANG module to IEEE Std 802.1Q are to IEEE Std 
    802.1Q-2022 as amended by IEEE Std 802.1Qcz-2023.

    Copyright (C) IEEE (2023).
    
    This version of this YANG module is part of IEEE Std 802.1Q; see the
    standard itself for full legal notices.";
  revision 2023-07-03 {
    description
      "LLDP extension TLVs for the trSet. Published as part of IEEE Std
      802.1Qcz-2023.";
    reference
      "Annex D of IEEE Std 802.1Q";
  }
  grouping topology-recognition-tlv-lldp {
    description
      "System level components of Topology Recognition TLV";
    reference
      "D.2.16 of IEEE Std 802.1Q";
    leaf device-type {
      type enumeration {
        enum end-station {
          value 0;
          description
            "Indicates that the device is a non-relay end-station or
            server.";
        }
        enum bridge {
          value 1;
          description
            "Indicates that the device is a layer-2 bridge.";
        }
        enum router {
          value 2;
          description
            "Indicates that the device is a layer-3 router.";
        }
        enum unknown {
          value 255;
          description
            "Indicates that the device type is unknown.";
        }
      }
      config false;
      description
        "Identifies the type of system performing Topology Recognition";
      reference
        "D.2.16.3 of IEEE Std 802.1Q";
    }
    leaf topology-level {
      type uint8;
      description
        "A single octet unsigned integer that indicates the system’s
        understanding of its current level in the topology. The value of
        0 indicates the edge of the topology and the value 255 indicates
        the level is currently unknown. Other non-zero values indicate
        the minimum number of links between the system and the edge of
        the topology. Initially systems may not know their position in
        the topology and will use the value of unknown by default. As
        systems discover the device type and topology level of their
        peers the topology level of the sending system may change.";
      reference
        "D.2.16.4 of IEEE Std 802.1Q";
    }
  }
  grouping topology-recognition-tlv-port {
    description
      "Port level components of Topology Recognition TLV";
    reference
      "D.2.16 of IEEE Std 802.1Q";
    leaf port-orientation {
      type enumeration {
        enum uplink {
          value 0;
          description
            "Indicates that the port is facing a system deeper in the
            topology.";
        }
        enum downlink {
          value 1;
          description
            "Indicates that the port is facing a system closer to the
            edge of the topology.";
        }
        enum crosslink {
          value 2;
          description
            "Indicates that the port is facing a system at the same level
            in the topology.";
        }
        enum unknown {
          value 255;
          description
            "Indicates that the port orientation is unknown.";
        }
      }
      description
        "Indicates whether the port is facing an uplink, downlink,
        crosslink or the orientation is currently unknown. Initially
        systems may not know the port orientation and will use the value
        of unknown by default. As systems discover the device type and
        topology level of their peers the port orientation of the sending
        system may change.";
      reference
        "D.2.16.5 of IEEE Std 802.1Q";
    }
  }
  augment "/lldp:lldp" {
    description
      "Augments lldp with information at the system level needed to
      construct Topology Recognition TLVs";
    reference
      "D.2.16 of IEEE Std 802.1Q";
    container topology-recognition-tlv-extension {
      description
        "The system level components of the Topology Recognition TLV";
      uses topology-recognition-tlv-lldp;
    }
  }
  augment "/lldp:lldp/lldp:port" {
    when
      "lldp:name";
    description
      "Augments port with Topology Recognition extension TLVs";
    leaf tlvs-tx-org-tr-enable {
      type bits {
        bit topology-recognition {
          position 0;
          description
            "Enables transmission of the Topology Recognition TLV in the
            trSet";
        }
      }
      description
        "Bitmap that includes the trSet of TLVs from Table D-1 of
        IEEE Std 802.1Q";
      reference
        "D.2 of IEEE Std 802.1Q";
    }
    container topology-recognition-tlv-extension {
      description
        "The port level components of the Topology Recognition TLV";
      uses topology-recognition-tlv-port;
    }
  }
  augment "/lldp:lldp/lldp:port/lldp:remote-systems-data" {
    description
      "Augments port remote-systems-data with received Topology
      Recognition extension TLVs";
    container congestion-isolation-tlv-extension {
      description
        "Holds a received Topology Recognition TLV";
      uses topology-recognition-tlv-lldp;
      uses topology-recognition-tlv-port;
    }
  }
}
