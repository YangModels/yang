module ieee802-dot1q-cbsa {
  namespace "urn:ieee:std:802.1Q:yang:ieee802-dot1q-cbsa";
  prefix cbsa;

  import ieee802-dot1q-types {
    prefix dot1q-types;
  }

  organization
    "IEEE 802.1 Working Group";
  contact
    "WG-URL: http://www.ieee802.org/1/
    WG-EMail: stds-802-1-L@ieee.org

    Contact: IEEE 802.1 Working Group Chair
    Postal: C/O IEEE 802.1 Working Group
    IEEE Standards Association
    445 Hoes Lane 
    Piscataway, NJ 08854
    USA

    E-mail: stds-802-1-chairs@ieee.org";
  description
    "This module provides for management of IEEE Std 802.1Q components
    that support the credit-based shaper algorithm.

    Copyright (C) IEEE (2023)

    This version of this YANG module is part of IEEE Std 802.1Q; see the
    standard itself for full legal notices.";

  revision 2023-12-26 {
    description
      "Published as part of IEEE Std 802.1Qdx-2024.
      
      The following reference statement identifies each referenced IEEE
      Standard as updated by applicable amendments.";
    reference
      "IEEE Std 802.1Q Bridges and Bridged Networks:
      IEEE Std 802.1Q-2022, IEEE Std 802.1Qcz-2023, IEEE Std 802.1Qcw-2023,
      IEEE Std 802.1Qcj-2023, IEEE Std 802.1Qdx-2024.";
  }

  grouping cbsa-config {
    description
      "cbsa-config comprises all the parameters associated
      with the credit-based shaper algorithm.";
    container cbsa-parameters {
      description
        "This container comprises all credit-based shaper algorithm related
        nodes.";
      list cbsa-parameter-table {
        key "traffic-class";
        description
          "There is one cbsa-parameter-table list per Port. Each list entry
          corresponds to the set of parameters (12.20.1)for each traffic class
          configured for use with the credit-based shaper algorithm (8.6.8.2).
          The cbsa-parameter-table list is valid for a Bridge Port only when 
          used in the absence of the stream reservation protocol.";
        reference
          "8.6.8.2, 34.3, 34.6, and 12.20.1 of IEEE Std 802.1Q";
        leaf traffic-class {
          type dot1q-types:traffic-class-type;
          description
            "An 802.1 traffic class value. This is the numerical value
            associated with a traffic class. Larger values are associated with
			higher priority traffic classes.";
          reference
            "8.6.8 of IEEE Std 802.1Q";
        }
        leaf admin-idle-slope {
          type uint64;
          units "bits/second";
          default "0";
          description
            "The bandwidth, in bits per second, that has been requested by 
            management to be reserved for use by the queue associated with
            this traffic class.

            If the stream reservation protocol is in operation for this traffic
            class, this parameter has no effect.
                
            If the stream reservation protocol is not in operation for this 
            traffic class, then the value of oper-idle-slope is equal to the 
            value of admin-idle-slope";
          reference
            "34.3 of IEEE Std 802.1Q";
        }
        leaf oper-idle-slope {
          type uint64;
          units "bits/second";
          default "0";
          config false;
          description
            "The actual bandwidth, in bits per second, that is currently 
            reserved for use by the queue associated with this traffic class
            (see 34.6.1 and 34.6.2).";
          reference
            "34.3, 34.6.1, and 34.6.2 of IEEE Std 802.1Q";
        }
      }
    }
  }
}
