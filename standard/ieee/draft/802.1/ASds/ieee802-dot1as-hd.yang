module ieee802-dot1as-hd {
  yang-version 1.1;
  namespace "urn:ieee:std:802.1AS:yang:ieee802-dot1as-hd";
  prefix dot1as-hd;

  import ieee1588-ptp-tt {
    prefix ptp-tt;
  }
  import ieee802-dot1as-gptp {
    prefix dot1as-gptp;
  }
  import ieee802-dot1as-hs {
    prefix dot1as-hs;
  }

  organization
    "IEEE 802.1 Working Group";
  contact
    "WG-URL: http://ieee802.org/1/
     WG-EMail: stds-802-1-l@ieee.org

     Contact: IEEE 802.1 Working Group Chair
              Postal: C/O IEEE 802.1 Working Group
              IEEE Standards Association
              445 Hoes Lane
              Piscataway, NJ 08854
              USA

     E-mail: stds-802-1-chairs@ieee.org";
  description
    "Management objects that control MAC operating in half-duplex as
     specified in IEEE Std 802.1ASds.

     References in this YANG module to IEEE Std 802.1AS are to
     IEEE Std 802.1AS-2020 as modified by
     IEEE Std 802.1AS-2020/Cor-1-2021, and amended by
     IEEE Std 802.1ASdr, IEEE Std 802.1ASdn,
     IEEE Std 802.1ASdm, and IEEE Std 802.1ASds.

     Copyright (C) IEEE (2024).
     This version of this YANG module is part of IEEE Std 802.1AS;
     see the standard itself for full legal notices.";

  revision 2024-07-25 {
    description
      "Published as part of IEEE Std 802.1ASds-2024.
       Initial version.";
    reference
      "IEEE Std 802.1AS - YANG Data Model";
  }

  augment "/ptp-tt:ptp/ptp-tt:instances/ptp-tt:instance"
        + "/ptp-tt:ports/ptp-tt:port/ptp-tt:port-ds" {
    description
      "Augment IEEE Std 1588 portDS.";
    leaf pdelay-req-send-disabled {
      type boolean;
      description
        "A boolean that is administratively set to TRUE
         if Pdelay_Req messages are not transmitted by this port.
         The default value for this variable shall be FALSE.";
      reference
        "11.2.19.2.14 of IEEE Std 802.1ASds";
    }
    leaf pdelay-resp-send-disabled {
      type boolean;
      description
        "A boolean that is administratively set to TRUE
         if Pdelay_Resp messages are not transmitted by this port.
         The default value for this variable shall be FALSE.";
      reference
        "11.2.20.2.6 of IEEE Std 802.1ASds";
    }
  }
}
