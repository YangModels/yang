module ieee802-dot1dc-cbsa-if {
  yang-version "1.1";
  namespace urn:ieee:std:802.1Q:yang:ieee802-dot1dc-cbsa-if;
  prefix cbsa-if;
  
  import ietf-interfaces {
    prefix if;
  }
  import ieee802-dot1q-cbsa {
    prefix cbsa;
  }

  organization
    "Institute of Electrical and Electronics Engineers";
  contact
    "WG-URL: http://ieee802.org/1/
     WG-EMail: stds-802-1-l@ieee.org
       Contact: IEEE 802.1 Working Group Chair
       Postal: C/O IEEE 802.1 Working Group
       IEEE Standards Association
            445 Hoes Lane
            Piscataway
            NJ 08854
            USA

    E-mail: stds-802-1-chairs@ieee.org";

  description
    "This module provides for management of General Frame Quality of
    Service (GFQoS) systems that support the Credit-Based Shaper
    transmission selection algorithm.
  
    Copyright (C) IEEE (2024).

    This version of this YANG module is part of IEEE Std 802.1DC;
    see the standard itself for full legal notices.";

  revision 2024-07-15 {
    description
      "Published as part of IEEE Std 802.1DC.

      The following reference statement identifies each referenced
      IEEE Standard as updated by applicable amendments.";

    reference
      "IEEE Std 802.1DC:
      IEEE Std 802.1DC - Quality of Service Provision by
      Network Systems.";
  }

  augment "/if:interfaces/if:interface" {
    
    description
      "Augment interface with Credit-Based Shaper configuration.";
    
    uses cbsa:cbsa-parameters;
  }
}
