module ieee802-dot1as-fttm {
  yang-version 1.1;
  namespace "urn:ieee:std:802.1AS:yang:ieee802-dot1as-fttm";
  prefix dot1as-fttm;

  import ieee1588-ptp-tt {
    prefix ptp-tt;
  }

  organization
    "IEEE 802.1 Working Group";
  contact
    "WG-URL: http://www.ieee802.org/1/
    WG-EMail: stds-802-1-L@ieee.org

    Contact: IEEE 802.1 Working Group Chair
    Postal: C/O IEEE 802.1 Working Group
    IEEE Standards Association
    445 Hoes Lane 
    Piscataway, NJ 08854
    USA

    E-mail: stds-802-1-chairs@ieee.org";
  description
    "This module provides for management of IEEE Std 802.1ASed components
    that support a fault-tolerant timing module.

    Copyright (C) IEEE (2024).
    This version of this YANG module is part of IEEE Std 802.1AS;
    see the standard itself for full legal notices.";

  revision 2024-09-02 {
    description
      "Published as part of IEEE Std 802.1ASed-2024.
	  
      The following reference statement identifies each referenced IEEE
      Standard as updated by applicable amendments.";
    reference
      "IEEE Std 802.1AS-2020 as modified by
       IEEE Std 802.1AS-2020/Cor-1-2021, and amended by
       IEEE Std 802.1ASdr, IEEE Std 802.1ASdn,
       IEEE Std 802.1ASdm,IEEE Std 802.1ASds, and IEEE Std 802.1ASed.";
  }


  feature fttm {
    description
      "This feature indicates that the device supports the Fault-tolerant
       timing module (FTTM) functionality.";
  }

  typedef fttm-output-trust-state {
    type enumeration {
      enum NOT-TRUSTED {
        value 0;
        description
          "Not trusted";
      }
      enum TIME-TRUSTED {
        value 1;
        description
          "Time trusted";
      }
      enum FREQ-TRUSTED {
        value 2;
        description
          "Frequency trusted";
      }
      enum NOT_VALID {
        value 3;
        description
          "The trust state is not valid";
      }
      enum TRUST-STATE-4 {
        value 4;
        description
          "Trust state 4, reserved";
      }
      enum TRUST-STATE-5 {
        value 5;
        description
          "Trust state 5, reserved";
      }
      enum TRUST-STATE-6 {
        value 6;
        description
          "Trust state 6, reserved";
      }
      enum TRUST-STATE-7 {
        value 7;
        description
          "Trust state 7, reserved";
      }
    }
    description
      "The fttmOutputTrustState type is an enumerated value that holds
      the output trust state of a TSF or of the FTTM.";
    reference
      "6.4.3.11 of IEEE Std 802.1ASed";
  }

  typedef uint48 {
    type uint64 {
      range "0..281474976710655"; 
    }
    description
      "Unsigned 48-bit integer.";
  }

  grouping fault-tolerant-timing-module-group {
    description
      "Management of a single FTTM.";
    reference
      "14.23 of IEEE Std 802.1ASed";
    leaf dtsf-max-num-time-indexes {
      type uint8;
      config false;
      description
        "Implementation-specific. Gives the maximum number of input
        ClockTarget Interfaces available on each of the DTSFs in the
        FTTM.";
      reference
        "IEEE Std 802.1ASed 14.23.2";
    }
    uses fttm-collected-tod-group; 
    uses fttm-map-dtsf-to-itsf-group; 
    uses fttm-map-index-to-tsf-group; 
    uses fttm-map-ptp-instance-to-index-group; 
    uses fttm-hyst-group;
	
    leaf fttm-invoke-status-avail {
      type boolean;
      default "false";
      config false;
      description
        "The fttmInvokeStatusAvail object indicates that the FTTM has
        updated the values of the fttmCollectedTod status, after an
        invoke event from the ClockTarget";
      reference
        "14.23.8 of IEEE Std 802.1ASed";
    }
    leaf fttm-invoke-status-avail-clr {
      type boolean;
      default "false";
      description
        "The fttmInvokeStatusAvailClr object is used to clear the
        fttmInvokeStatusAvail object";
      reference
        "IEEE 802.1ASed 14.23.9";
    }
    uses max-as-group; 
    leaf fttm-max-num-dtsfs {
      type uint8 {
        range "0..126";
      }
      config false;
      description
        "Implementation-specific. Maximum number of DTSF instances
        available in the FTTM.
        The value is restricted to the range of 0 to 126.";
      reference
        "IEEE Std 802.1ASed 14.23.11";
    }
    leaf fttm-max-num-time-indexes {
      type uint8 {
        range "0..255";
      }
      config false;
      description
        "Implementation-specific. Maximum number of input ClockTarget
        Interfaces available on the FTTM.";
      reference
        "IEEE Std 802.1ASed 14.23.12";
    }
    leaf fttm-num-active-dtsfs {
      type uint8;
      config false;
      description
        "Number of active DTSF instances currently used in the FTTM.";
      reference
        "IEEE Std 802.1ASed 14.23.13";
    }
    leaf fttm-num-active-time-indexes {
      type uint8;
      config false;
      description
        "The number of input ClockTarget Interfaces currently active on
        the FTTM.";
      reference
        "IEEE Std 802.1ASed 14.23.14";
    }
    leaf fttm-sel-instance-index {
      type uint32;
      config false;
      description
        "Gives the instanceIndex value of the PTP Instance that is the
        source of the ClockTarget interface that was selected by the FTTM
        as its trusted time.";
      reference
        "IEEE Std 802.1ASed 14.23.15";
    }
    leaf fttm-sel-time-index-change-cnt {
      type uint16;
      config false;
      description
        "The fttmItsfSelTimeIndexChangeCnt object gives the number of times
        the ITSF has changed its time index selection.";
      reference
        "IEEE 802.1ASed 14.23.16";
    }
    leaf fttm-sel-time-rate-ratio-offset {
      type uint32;
      default "0";
      description
        "The fttmSelTimeRateRatioOffset object gives the maximum rate-ratio
        offset magnitude, between the FTTM’s selected time clock rate and
        the FTTM’s local clock (OSC_CLK) rate, that is deemed to be acceptable
        to go to or remain in the FREQ_TRUSTED state (see 20.3.3.3).";
      reference
        "IEEE Std 802.1ASed 14.23.17";
    }
    leaf fttm-sel-time-std-dev-rate-ratio-offset {
      type uint32;
      default "0";
      description
        "The fttmSelTimeStdDevRateRatioOffset object gives the maximum standard
        deviation of the rate-ratio offset, between the FTTM’s selected time
        clock rate and the FTTM’s local clock (OSC_CLK) rate, that is deemed to be
        acceptable to go to or remain in the FREQ_TRUSTED state (see 20.3.3.3).";
      reference
        "IEEE Std 802.1ASed 14.23.19";
    }
    leaf fttm-trust-state {
      type fttm-output-trust-state;
      default "NOT-TRUSTED";
      config false;
      description
        "The fttmTrustState object holds the output trust state of the FTTM.
         Valid values are NOT_TRUSTED, TIME_TRUSTED, FREQ_TRUSTED, and NOT_VALID.";
      reference
        "IEEE Std 802.1ASed 14.23.20";
    }
    uses fttm-sel-change-thresh-group;
    uses fttm-tsf-algo-name-group; 
    uses fttm-tsf-sel-time-index-group;
    leaf fttm-use-osc-clk {
      type boolean;
      config false;
      description
        "implementation-specific. Defines whether the OSC_CLK frequency is
        used as a reference for time integrity.";
      reference
        "IEEE Std 802.1ASed 14.23.23";
    }
  }

  grouping instance-index-group {
    description
      "An index number that identifies a ptp-instance input to the FTTM
      from the 1588e YANG module.";
    reference
      "IEEE Std IEEE Std 1588e-2024 15.3.3.2 Structure";
    leaf instance-index {
      type uint32;
      description
        "An index number that identifies a ptp-instance input to the FTTM
        from the 1588e YANG module.";
      reference
        "IEEE Std IEEE Std 1588e-2024 15.3.3.2 Structure";
    }
  }

  grouping fttm-collected-tod-group { 
    description
      "The fttmCollectedTod object is a vector of collected extended timestamps
      that correspond to the latest ClockTarget invoke event. The vector member
      fttmCollectedTod[x] holds the latest timeReceiverTimeCallback result for
      input ClockTarget interface x to the FTTM.";
    reference
      "IEEE Std 802.1ASed 14.23.3";
    list fttm-collected-tod-list {
      key "fttm-input-index-number";
      description
        "The fttmCollectedTod object is a vector of collected extended
        timestamps that correspond to the latest ClockTarget invoke event.
        The vector member fttmCollectedTod[x] holds the latest
        timeReceiverTimeCallback result for input ClockTarget
        interface x to the FTTM.";
      reference
        "IEEE Std 802.1ASed 14.23.3.";
      leaf fttm-input-index-number {
        type uint8;
        description
          "The FTTM input index number.";
        reference
          "IEEE Std 802.1ASed 14.23.3";
      }
      list extended-timestamp-list {
        key "seconds fractional-nanoseconds";
        config false;
        description
          "The ExtendedTimestamp type represents a positive time with
          respect to the epoch.";
        reference
          "IEEE 802.1AS-2020 6.4.3.5";
        leaf seconds {
          type uint48;
          description
            "The integer portion of the timestamp in units of seconds.";
        }
        leaf fractional-nanoseconds {
          type uint48;
          description
            "The fractional portion of the timestamp in units of 2^-16 ns.";
        }
      }
    }
  }

  grouping fttm-map-dtsf-to-itsf-group {
    description
      "The fttmMapDtsfToItsf object provides the mapping for all the FTTM’s
      DTSF output ClockTarget Interfaces to the ITSF and its input indexes.
      See J.7.";
    reference
      "IEEE Std 802.1ASed 14.23.4";
    list fttm-map-dtsf-to-itsf-list {
      key "tsf-instance-number";
      description
        "This grouping allows associations of all the DTSF output ClockTarget
        interfaces to ITSF input index numbers.";
      reference
        "IEEE Std 802.1ASed 14.23.4";
      leaf tsf-instance-number {
        type uint8;
        description
          "The DTSF instance number.";
        reference
          "IEEE Std 802.1ASed 14.23.4";
      }
      leaf itsf-input-index-number {
        type uint8;
        default "0";
        description
          "The ITSF’s input ClockTarget index number. ";
        reference
          "IEEE Std 802.1ASed 14.23.4";
      }
    }
  }

  grouping fttm-map-index-to-tsf-group {
    description
      "The fttmMapIndexToTsf object provides the mapping for all of the
      FTTM’s input ClockTarget Interface index numbers to a Time Selection
      Function (TSF) instance number and its input ClockTarget Interface
      index number. See J.6.";
    reference
      "IEEE Std 802.1ASed 14.23.5";
    list fttm-map-index-to-tsf-list {
      key "fttm-input-index-number";
      description
        "This grouping allows associations of the FTTM input index numbers
        to DTSF input index numbers and ITSF input index numbers.";
      reference
        "IEEE Std 802.1ASed 14.23.5";
      leaf fttm-input-index-number {
        type uint8;
        description
          "The FTTM input index number.";
        reference
          "IEEE Std 802.1ASed";
      }
      leaf tsf-instance-number {
        type uint8;
        description
          "The TSF instance number that the FTTM input index number is
          connected to. A value of 0 represents the ITSF. Other values
          represent the DTSF instance numbers.";
        reference
          "IEEE Std 802.1ASed 14.23.5";
      }
      leaf tsf-input-index-number {
        type uint8;
        description
          "The input index number of the TSF (DTSF or ITSF)";
        reference
          "IEEE Std 802.1ASed 14.23.5 ";
      }
    }
  }

  grouping fttm-map-ptp-instance-to-index-group {
    description
      "The fttmMapPtpInstanceToIndex object provides the mapping of the
      instance index number of the PTP Instance to the FTTM input index
      number.";
    reference
      "IEEE Std 802.1ASed 14.23.6";
    list fttm-map-ptp-instance-to-index-list {
      key "fttm-input-index-number";
      description
        "This grouping allows associations of the index numbers of PTP
        Instances to FTTM input index numbers.";
      reference
        "IEEE Std 802.1ASed 14.23.6";
      uses instance-index-group;
      leaf fttm-input-index-number {
        type uint8;
        description
          "The FTTM input index number for the FTTM input ClockTarget
           Interface associated with the PTP Instance with the
           corresponding index number.";
        reference
          "IEEE Std 802.1ASed 14.23.6";
      }
    }
  }

  grouping fttm-hyst-group {
    description
      "The fttmHyst object holds the hysteresis to be added to fttmMaxAs[x][y]
      (see 14.23.10) for the times of the two input FTTM input ClockTarget
      interfaces with index numbers x and y.";
    reference
      "IEEE Std 802.1ASed 14.23.7";
    list fttm-hyst-lists {
      key "fttm-input-index-number";
      description
        "The x index.";
      reference
        "IEEE Std 802.1ASed 14.23.7";
      leaf fttm-input-index-number {
        type uint8;
        description
          "The first FTTM input index number of the two-dimensional array .";
        reference
          "IEEE Std 802.1ASed 14.23.7";
      }
      list fttm-hyst-list {
        key "fttm-input-index-number";
        description
          "The y index.";
        reference
          "IEEE Std 802.1ASed 14.23.7";
        leaf fttm-input-index-number {
          type uint8;
          description
            "The second FTTM input index number of the two-dimensional array .";
          reference
            "IEEE Std 802.1ASed 14.23.7";
        }
        leaf fttm-hyst {
          type uint32;
          units "2^-16 nanoseconds";
          default "0";
          description
            "The object fttmHyst[x][y] holds the hysteresis to be added to
            fttmMaxAs[x][y] (see 14.23.13) for the times of the two input
            FTTM input ClockTarget interfaces with index numbers x and y.";
          reference
            "IEEE Std 802.1ASed 14.23.7 ";
        }
      }
    }
  }

  grouping max-as-group {
    description
      "The fttmMaxAs[x][y] object gives the maximum magnitude of expected
      skew between times provided by the FTTM input ClockTarget interfaces
      of index x and index y when those times are not faulty. This value
      is used as the criteria to determine the trustworthiness of the times
      being compared. See maxASxy in M.5";
    reference
      "IEEE Std 802.1ASed 14.23.10";
    list fttm-max-as-lists {
      key "fttm-input-index-number";
      description
        "The index x.";
      reference
        "IEEE Std 802.1ASed 14.23.10";
      leaf fttm-input-index-number {
        type uint8;
        description
          "The first FTTM input index number of the two-dimensional array.";
        reference
          "IEEE Std 802.1ASed 14.23.10";
      }
      list fttm-max-as-list {
        key "fttm-input-index-number";
        description
          "The index y.";
        reference
          "IEEE Std 802.1ASed 14.23.10";
        leaf fttm-input-index-number {
          type uint8;
          description
            "The second FTTM input index number of the two-dimensional array.";
          reference
            "IEEE Std 802.1ASed 14.23.10";
        }
        leaf fttm-max-as {
          type uint32;
          units "2^-16 nanoseconds";
          default "0";
          description
            "The maximum magnitude of expected skew between times provided
            by the input ClockTarget interfaces of index x and index y when
            those times are not faulty.";
          reference
            "IEEE Std 802.1ASed 14.23.10";
        }
      }
    }
  }

  grouping fttm-sel-change-thresh-group {
    description
      "The fttmSelChangeThresh object gives the time difference change
      threshold that is used by each TSF instance to determine whether
      it continues to use the previously selected time index or to change
      to the current time index that best satisfies the selection criteria
      (e.g., the time index that currently satisfies the mid-value selection
      criteria of the MVTISA, see 20.3.5).";
    reference
      "IEEE Std 802.1ASed 14.23.15";
    list fttm-sel-change-thresh-list {
      key "tsf-instance-number";
      description
        "The fttmSelChangeThresh object gives the time difference change
        threshold that is used by each TSF instance to determine whether
        it continues to use the previously selected time index or to change
        to the current time index that best satisfies the selection criteria.";
      reference
        "IEEE Std 802.1ASed 14.23.15";
      leaf tsf-instance-number {
        type uint8;
        description
          "The TSF instance number that the fttmSelChangeThresh object
          is associated with. A value of 0 represents the ITSF. Other
          values represent the DTSF instance numbers.";
        reference
          "IEEE Std 802.1ASed 14.23.15";
      }
      leaf seconds {
        type uint48;
        default "0";
        description
          "The integer portion of the timestamp in units of seconds.";
      }
      leaf fractional-nanoseconds {
        type uint48;
        default "0";
        description
          "The fractional portion of the timestamp in units of 2^-16 ns.";
      }
    }
  }

  grouping fttm-tsf-algo-name-group { 
    description
      "The fttmTsfAlgoName object is a vector of strings, where each vector
      member provides the name of the algorithm used by each active TSF
      instance number (the ITSF and the active DTSFs).";
    reference
      "IEEE Std 802.1ASed 14.23.21";
    list fttm-tsf-algo-name-list {
      key "tsf-instance-number";
      description
        "The fttmTsfAlgoName object is a vector of strings, where each vector
        member provides the name of the algorithm used by each active TSF
        instance number (the ITSF and the active DTSFs)";
      reference
        "IEEE Std 802.1ASed 14.23.21";
      leaf tsf-instance-number {
        type uint8;
        description
          "The TSF instance number for which the algorithm is to be queried.";
        reference
          "IEEE Std 802.1ASed 20.3.2.2";
      }
      leaf fttm-tsf-algo-name {
        type string;
        config false;
        description
          "Each fttmTsfAlgoName[x] member, where x is a value from 0 to
          fttmNumActiveDtsfs (see 14.23.13) and represents the TSF instance
          number, is a 128 octet that contains a string with the name of
          the algorithm for the TSF instance number.";
        reference
          "IEEE Std 802.1ASed 14.23.21";
      }
    }
  }

  grouping fttm-tsf-sel-time-index-group {
    description
      "The fttmTsfSelTimeIndex object gives the input time index that is
	  selected by each TSF instance.";
    reference
      "IEEE Std 802.1ASed 14.23.22";
    list fttm-tsf-sel-time-index-list {
      key "tsf-instance-number";
      description
        "The fttmTsfSelTimeIndex object gives the input time index that is
        selected by each TSF instance.";
      reference
        "IEEE Std 802.1ASed 14.23.22";
      leaf tsf-instance-number {
        type uint8;
        description
          "The TSF instance number for which the selected time-index is
          to be queried.";
        reference
          "IEEE Std 802.1ASed 14.23.8";
      }
      leaf fttm-tsf-sel-time-index {
        type uint16;
        default "511";
        config false;
        description
          "Gives the input time index that is selected to be the output of
          the TSF instance.";
        reference
          "IEEE Std 802.1ASed 14.23.22";
      }
    }
  }

  augment "/ptp-tt:ptp/ptp-tt:common-services" {
    description
      "Augment IEEE Std 1588 commonServices with fault-tolerant-timing-module service.";
    container fault-tolerant-timing-module-service {
      if-feature "fttm";
      description
        "The Fault-Tolerant Timing Module Service structure contains the
         fttmSystemList, which is a list of instances of the Fault-Tolerant
         Timing Module Service.";
      reference
        "14.23 of IEEE Std 802.1AS";
      list fttm-system {
        key "fttm-system-index";
        description
          "Indexed list of FTTM systems in the FTTM Service";
        leaf fttm-system-index {
          type uint8;
          description
            "Index for the FTTM system.";
        }
        container fttm-system-ds {
          description
            "The fttmSystemDS describes the attributes of the
             respective instance of the Fault-Tolerant Timing Module Service.";
          reference
            "14.23 of IEEE Std 802.1AS";
          uses fault-tolerant-timing-module-group;
        }
        container fttm-system-description-ds {
          description
            "The fttmSystemDescriptionDS contains descriptive information for
             the respective instance of the Fault-Tolerant Timing Module Service.";
          reference
            "14.24 Fault-Tolerant Timing Module System Description Parameter
             Data Set (fttmSystemDescriptionDS) of IEEE Std 802.1ASed";
          leaf user-description {
            type string {
              length "0..128";
            }
            description
              "Configuration description of the Fault-Tolerant Timing Module system.";
            reference
              "14.24.3 of IEEE Std 802.1ASed";
          }
        }
      }
    }
  }
}
