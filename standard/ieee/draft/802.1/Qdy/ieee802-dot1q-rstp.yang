module ieee802-dot1q-rstp {
  yang-version 1.1;
  namespace "urn:ieee:std:802.1Q:yang:ieee802-dot1q-rstp";
  prefix rstp;

  import ietf-yang-types {
    prefix yang;
  }
  import ietf-interfaces {
    prefix if;
  }
  import ieee802-dot1q-bridge {
    prefix dot1q;
  }

  organization
    "IEEE 802.1 Working Group";
  contact
    "WG-URL: http://www.ieee802.org/1/
     WG-EMail: stds-802-1-l@ieee.org

     Contact: IEEE 802.1 Working Group Chair
     Postal: C/O IEEE 802.1 Working Group
            IEEE Standards Association
            445 Hoes Lane
            Piscataway, NJ 08854
            USA

     E-mail: stds-802-1-chairs@ieee.org";
  description
    "This module provides management of 802.1Q bridge components that
     support the Rapid Spanning Tree Algorithm and Protocol (RSTP).

     Copyright (C) IEEE (2024).

     This version of this YANG module is part of IEEE Std 802.1Q; see the
     standard itself for full legal notices.";

  revision 2023-11-23 {
    description
      "Published as part of IEEE Std 802.1Qcy-2024.

       The following reference statement identifies each referenced IEEE
       Standard as updated by applicable amendments.";
    reference
      "IEEE Std 802.1Q Bridges and Bridged Networks:
       IEEE Stds 802.1Q-2022, 802.1Qcy-2024.";
  }

  feature rstp {
    description
      "Rapid Spanning Tree Algorithm and Protocol supported.";
    reference
      "13.4 of IEEE Std 802.1Q";
  }

  augment "/dot1q:bridges/dot1q:bridge/dot1q:component" {
    description
      "Augment bridge with RSTP configuration";
    container rstp {
      if-feature "rstp";
      leaf protocol-specification {
        type enumeration {
          enum unknown {
            value 1;
          }
          enum decLb100 {
            value 2;
          }
          enum ieee8021d {
            value 3;
          }
          enum ieee8021q {
            value 4;
          }
        }
        config false;
        description
          "An indication of what version of the Spanning Tree Protocol is
           being run.  The value 'decLb100(2)' indicates the DEC LANbridge
           100 Spanning Tree protocol.  IEEE 802.1D implementations will
           return 'ieee8021d(3)'.  New enumerated values may be added in
           the future to the definition of this object to reflect future
           versions of the IEEE Spanning Tree protocol.";
      }
      leaf priority {
        type int32 {
          range "0..65535";
        }
        config true;
        description
          "The value of the write-able portion of the Bridge ID
           (i.e., the first two octets of the (8 octet long) Bridge
           ID).  The other (last) 6 octets of the Bridge ID are
           given by the value of ieee8021BridgeBaseBridgeAddress.
           On Bridges supporting IEEE 802.1t or IEEE 802.1w,
           permissible values are 0-61440, in steps of 4096.

           The value of this object MUST be retained across
           reinitializations of the management system.";
        reference
          "Item a) in 12.8.1.1.3 of IEEE Std 802.1Q";
      }
      leaf time-since-topology-change {
        type yang:timeticks;
        units "centi-seconds";
        config false;
        description
          "The time (in hundredths of a second) since the
           last time a topology change was detected by the
           Bridge entity.
           For RSTP, this reports the time since the tcWhile
           timer for any port on this Bridge was nonzero.";
        reference
          "Item b) in 12.8.1.1.3  of IEEE Std 802.1Q";
      }
      leaf topology-changes {
        type yang:counter64;
        units "topology changes";
        config false;
        description
          "The total number of topology changes detected by
           this Bridge since the management entity was last
           reset or initialized.

           Discontinuities in the value of the counter can occur
           at re-initialization of the management system.";
        reference
          "Item c) in 12.8.1.1.3 of IEEE Std 802.1Q";
      }
      leaf designated-root {
        type uint64;
        config false;
        description
          "The Bridge identifier of the root of the spanning
           tree, as determined by the Spanning Tree Protocol,
           as executed by this node.  This value is used as
           the Root Identifier parameter in all Configuration
           Bridge PDUs originated by this node.";
        reference
          "Item e) in 12.8.1.1.3 of IEEE Std 802.1Q";
      }
      leaf root-cost {
        type int32;
        config false;
        description
          "The cost of the path to the root as seen from
           this Bridge.";
        reference
          "Item f) of 12.8.1.1.3 of IEEE Std 802.1Q";
      }
      leaf root-port {
        type uint16;
        config false;
        description
          "The port number of the port that offers the lowest
           cost path from this Bridge to the root Bridge.";
        reference
          "Item g) in 12.8.1.1.3 of IEEE Std 802.1Q";
      }
      leaf max-age {
        type uint32;
        units "centi-seconds";
        config false;
        description
          "The maximum age of Spanning Tree Protocol information
           learned from the network on any port before it is
           discarded, in units of hundredths of a second.  This is
           the actual value that this Bridge is currently using.";
        reference
          "Item h) in 12.8.1.1.3 of IEEE Std 802.1Q";
      }
      leaf hello-time {
        type uint32;
        units "centi-seconds";
        config false;
        description
          "The amount of time between the transmission of
           Configuration Bridge PDUs by this node on any port when
           it is the root of the spanning tree, or trying to become
           so, in units of hundredths of a second.  This is the
           actual value that this Bridge is currently using.";
        reference
          "Item k) in 12.8.1.1.3 of IEEE Std 802.1Q";
      }
      leaf hold-time {
        type int32;
        units "centi-seconds";
        config false;
        description
          "This time value determines the interval length
           during which no more than two Configuration Bridge
           PDUs shall be transmitted by this node, in units
           of hundredths of a second.";
        reference
          "Item m) in 12.8.1.1.3 of IEEE Std 802.1Q";
      }
      leaf forward-delay {
        type uint32;
        units "centi-seconds";
        config false;
        description
          "This time value, measured in units of hundredths of a
           second, controls how fast a port changes its spanning
           state when moving towards the Forwarding state.  The
           value determines how long the port stays in each of the
           Listening and Learning states, which precede the
           Forwarding state.  This value is also used when a
           topology change has been detected and is underway, to
           age all dynamic entries in the Filtering Database.
           [Note that this value is the one that this Bridge is
           currently using, in contrast to
           ieee8021SpanningTreeBridgeForwardDelay, which is the
           value that this Bridge and all others would start using
           if/when this Bridge were to become the root.]";
        reference
          "Item i) in 12.8.1.1.3 of IEEE Std 802.1Q";
      }
      leaf bridge-max-age {
        type uint32 {
          range "600..4000";
        }
        units "centi-seconds";
        config true;
        description
          "The value that all Bridges use for MaxAge when this
           Bridge is acting as the root.  Note that IEEE Std 802.1D-1998
           specifies that the range for this parameter is related
           to the value of ieee8021SpanningTreeBridgeHelloTime.  The
           granularity of this timer is specified by IEEE Std 802.1D-1998
           to be 1 second.  An agent may return an SNMP badValue error
           (or its equivalent if another protocol is used) if a set
           is attempted to a value that is not a whole number of
           seconds.

           The value of this object MUST be retained across
           reinitializations of the management system.";
        reference
          "Item j) in 12.8.1.1.3";
      }
      leaf bridge-hello-time {
        type uint32 {
          range "100..1000";
        }
        units "centi-seconds";
        config true;
        description
          "The value that all Bridges use for HelloTime when this
           Bridge is acting as the root.  The granularity of this
           timer is specified by IEEE Std 802.1D-1998 to be 1 second.
           An agent may return an SNMP badValue error (or its equivalent
           if another protocol is used) if a set is attempted to a
           value that is not a whole number of seconds.

           The value of this object MUST be retained across
           reinitializations of the management system.";
        reference
          "Item k) in 12.8.1.1.3 of IEEE Std 802.1Q";
      }
      leaf bridge-forward-delay {
        type uint32 {
          range "400..3000";
        }
        units "centi-seconds";
        config true;
        description
          "The value that all Bridges use for ForwardDelay when
           this Bridge is acting as the root.  Note that IEEE Std
           802.1D-1998 specifies that the range for this parameter
           is related to the value of ieee8021SpanningTreeBridgeMaxAge.
           The granularity of this timer is specified by IEEE Std 802.1D-1998
           to be 1 second.  An agent may return an SNMP badValue error
           (or its equivalent if another protocol is used) if a set is
           attempted to a value that is not a whole number of seconds.

           The value of this object MUST be retained across
           reinitializations of the management system.";
        reference
          "Item l) in 12.8.1.1.3 of IEEE Std 802.1Q";
      }
      leaf version {
        type enumeration {
          enum stp {
            value 0;
          }
          enum rstp {
            value 2;
          }
          enum mstp {
            value 3;
          }
        }
        config true;
        description
          "The version of Spanning Tree Protocol the Bridge is
           currently running.  The values are directly from
           the IEEE standard.  New values may be defined as future
           versions of the protocol become available.

           The value 'stp(0)' indicates the Bridge is running the
           Spanning Tree Protocol specified in IEEE Std 802.1D-1998.

           The value 'rstp(2)' indicates the Bridge is running RSTP
           specified in IEEE 802.1Q.

           The value 'mstp(3)' indicates the Bridge is running
           MSTP specified in Clause 13 of IEEE Std 802.1Q.

           The value of this object MUST be retained across
           reinitializations of the management system.";
        reference
          "Item n) in 12.8.1.1.3 of IEEE Std 802.1Q";
      }
      leaf rstp-tx-hold-count {
        type int32 {
          range "1..10";
        }
        config true;
        description
          "The value used by the Port Transmit state machine to limit
           the maximum transmission rate.  This is used by Bridges
           that are running RSTP.

           The value of this object MUST be retained across
           reinitializations of the management system.";
        reference
          "Item m) in 12.8.1.1.3, 13.26.12 of IEEE Std 802.1Q";
      }
    }
  }

  augment "/if:interfaces/if:interface/dot1q:bridge-port" {
    description
      "Augment bridge port with RSTP configuration";
    container rstp {
      if-feature "rstp";
      leaf priority {
        type int32 {
          range "0..255";
        }
        config true;
        description
          "The value of the priority field that is contained in
           the first (in network byte order) octet of the (2 octet
           long) Port ID.  The other octet of the Port ID is given
           by the value of ieee8021SpanningTreePort.
           On Bridges supporting IEEE 802.1t or IEEE 802.1w,
           permissible values are 0-240, in steps of 16.

           The value of this object MUST be retained across
           reinitializations of the management system.";
        reference
          "Item c) in 12.8.2.1.3 of IEEE Std 802.1Q";
      }
      leaf state {
        type enumeration {
          enum disabled {
            value 1;
          }
          enum blocking {
            value 2;
          }
          enum listening {
            value 3;
          }
          enum learning {
            value 4;
          }
          enum forwarding {
            value 5;
          }
          enum broken {
            value 6;
          }
        }
        config false;
        description
          "The port's current state, as defined by application of
           the Spanning Tree Protocol.  This state controls what
           action a port takes on reception of a frame.  If the
           Bridge has detected a port that is malfunctioning, it
           will place that port into the broken(6) state.  For
           ports that are disabled (see
           ieee8021SpanningTreePortEnabled), this object will have a
           value of disabled(1).  The values disabled, blocking,
           listening, and broken correspond to the Clause 12 port
           state of 'Discarding'. The value learning corresponds to
           the Clause 12 port state of 'Learning'. The value forwarding
           corresponds to the Clause 12 port state of 'Forwarding'.";
        reference
          "Item b) in 12.8.2.1.3 of IEEE Std 802.1Q";
      }
      leaf enabled {
        type boolean;
        config true;
        description
          "The enabled/disabled status of the port.  A value of true(1)
           means the spanning-tree protocol is enabled for this port.

           The value of this object MUST be retained across
           reinitializations of the management system.";
        reference
          "Item m) in 12.8.2.1.3 of IEEE Std 802.1Q";
      }
      leaf path-cost {
        type int32 {
          range "1..200000000";
        }
        config true;
        description
          "The contribution of this port to the path cost of
           paths towards the spanning tree root that include
           this port.  Table 13-4 recommends defaults and ranges
           for Port Path Cost values, in inverse proportion
           to the speed of the attached LAN. If this object is used
           to set the Path Cost it is possible to restore the
           default setting using the
           ieee8021SpanningTreeRstpPortAdminPathCost object.

           Table 13-4 recommends defaults and ranges for Port
           Path Cost values, in inverse proportion to the speed of the
           attached LAN. If this object is used to set the Path
           Cost it is possible to restore the default
           setting using the ieee8021MstpPortAdminPathCost object.

           The value of this object MUST be retained across
           reinitializations of the management system.";
        reference
          "Item d) in 12.8.2.1.3 of IEEE Std 802.1Q";
      }
      leaf designated-root {
        type uint32;
        config false;
        description
          "The unique Bridge Identifier of the Bridge
           recorded as the Root in the Configuration BPDUs
           transmitted by the Designated Bridge for the
           segment to which the port is attached.";
        reference
          "Item e) in 12.8.2.1.3 of IEEE Std 802.1Q";
      }
      leaf designated-cost {
        type int32;
        config false;
        description
          "The path cost of the Designated Port of the segment
           connected to this port.  This value is compared to the
           Root Path Cost field in received Bridge PDUs.";
        reference
          "Item f) in 12.8.2.1.3 of IEEE Std 802.1Q";
      }
      leaf designated-bridge {
        type uint32;
        config false;
        description
          "The Bridge Identifier of the Bridge that this
           port considers to be the Designated Bridge for
           this port's segment.";
        reference
          "Item g) in 12.8.2.1.3 of IEEE Std 802.1Q";
      }
      leaf designated-port {
        type binary {
          length "2";
        }
        config false;
        description
          "The Port Identifier of the port on the Designated
           Bridge for this port's segment.";
        reference
          "Item h) in 12.8.2.1.3 of IEEE Std 802.1Q";
      }
      leaf forward-transitions {
        type yang:counter64;
        units "forwarding transitions";
        config false;
        description
          "The number of times this port has transitioned
           from the Learning state to the Forwarding state.

           Discontinuities in the value of the counter can occur
           at re-initialization of the management system, and at
           other times as indicated by the value of
           ifCounterDiscontinuityTime object of the associated
           interface (if any).";
      }
      leaf protocol-migration {
        type boolean;
        config true;
        description
          "When operating in RSTP (version 2) mode, writing true(1)
           to this object forces this port to transmit RSTP BPDUs.
           Any other operation on this object has no effect and
           it always returns false(2) when read.";
        reference
          "12.8.2.5 of IEEE Std 802.1Q";
      }
      leaf admin-edge-port {
        type boolean;
        config true;
        description
          "The administrative value of the Edge Port parameter.
           A value of true(1) indicates that this port should be
           assumed as an edge-port, and a value of false(2) indicates
           that this port should be assumed as a non-edge-port.

           Setting this object will also cause the corresponding
           instance of ieee8021SpanningTreeRstpPortOperEdgePort to
           change to the same value.  Note that even when this
           object's value is true(1), the value of the corresponding
           instance of ieee8021SpanningTreeRstpPortOperEdgePort can
           be false(2) if a BPDU has been received.

           The value of this object MUST be retained across
           reinitializations of the management system.";
        reference
          "Item k) in 12.8.2.1.3 of IEEE Std 802.1Q";
      }
      leaf oper-edge-port {
        type boolean;
        config false;
        description
          "The operational value of the Edge Port parameter.  The
           object is initialized to the value of the corresponding
           instance of ieee8021SpanningTreeRstpPortAdminEdgePort.
           When the corresponding instance of
           ieee8021SpanningTreeRstpPortAdminEdgePort is set, this
           object will be changed as well.  This object will also be
           changed to false(2) on reception of a BPDU.";
        reference
          "Item l) in 12.8.2.1.3 of IEEE Std 802.1Q";
      }
      leaf admin-path-cost {
        type int32 {
          range "0..200000000";
        }
        config true;
        description
          "The administratively assigned value for the contribution
           of this port to the path cost of paths toward the spanning
           tree root.

           Writing a value of '0' assigns the automatically calculated
           default Path Cost value to the port.  If the default Path
           Cost is being used, this object returns '0' when read.

           This complements the object ieee8021SpanningTreePortPathCost,
           which returns the operational value of the path cost.

           The value of this object MUST be retained across
           reinitializations of the management system.";
        reference
          "Item d) in 12.8.2.1.3 of IEEE Std 802.1Q";
      }
      leaf auto-edge-port {
        type boolean;
        config true;
        description
          "The administrative value of the Auto Edge Port parameter.
           A value of true(1) indicates if the Bridge detection state
           machine (BDM, 13.33) is to detect other Bridges
           attached to the LAN, and set
           ieee8021SpanningTreeRstpPortOperEdgePort automatically.
           The default value is true(1)

           This is optional and provided only by implementations
           that support the automatic identification of edge ports.

           The value of this object MUST be retained across
           reinitializations of the management system.";
        reference
          "Item m) in 12.8.2.1.3 of IEEE Std 802.1Q";
      }
      leaf auto-isolate-port {
        type boolean;
        config false;
        description
          "The operational value of the Isolate Port parameter.

           A value of true(1) indicates a Designated Port will
           transition to discarding if both
           ieee8021SpanningTreeRstpPortAdminEdgePort and
           ieee8021SpanningTreeRstpPortAutoEdgePort are FALSE and
           the other Bridge presumed to be attached to the same
           point-to-point LAN does not transmit periodic BPDUs.

           This is optional and provided only by implementations
           that support the automatic identification of edge ports.";
        reference
          "Item n) in 12.8.2.1.3 of IEEE Std 802.1Q";
      }
      leaf isolate-port {
        type boolean;
        config false;
        description
          "The operational value of the Isolate Port parameter.

           A value of true(1), Set by the Bridge detection state
                machine (BDM, 13.33), indicates when the Spanning Tree
                Protocol Entity of a neighboring Bridge has apparently
           failed .";
        reference
          "Item o) in 12.8.2.1.3 of IEEE Std 802.1Q";
      }
    }
  }

  notification new-root {
    description
      "The new-root notification indicates that
       the sending agent has become the new root of the Spanning Tree;
       the notification is sent by a Bridge soon after its election
       as the new root, e.g., upon expiration of the Topology Change
       Timer, immediately subsequent to its election.";
  }

  notification topology-change {
    description
      "A topology-change notification is sent
       by a Bridge when any of its configured ports transitions from
       the Learning state to the Forwarding state, or from the
       Forwarding state to the Blocking state.  The notification
       is not sent if a ieee8021SpanningTreeNewRoot notification
       is sent for the same transition.";
  }
}
