module ieee802-dot1dd-rap {
  yang-version 1.1;
  namespace "urn:ieee:std:802.1DD:yang:ieee802-dot1dd-rap";
  prefix rap;

  import ieee802-dot1q-types {
    prefix dot1qtypes;
  }
  import ieee802-dot1q-tsn-types {
    prefix tsn;
  }
  import ieee802-types {
    prefix ieeetypes;
  }

  organization
    "IEEE 802.1 Working Group";
  contact
    "WG-URL: http://www.ieee802.org/1/
     WG-EMail: stds-802-1-l@ieee.org

     Contact: IEEE 802.1 Working Group Chair
     Postal: C/O IEEE 802.1 Working Group
            IEEE Standards Association
            445 Hoes Lane
            Piscataway, NJ 08854
            USA

     E-mail: stds-802-1-chairs@ieee.org";
  description
    "This module provides management of 802.1Q Bridge components that
     support the Resource Allocation Protocol (RAP).

     Copyright (C) IEEE (202x).

     This version of this YANG module is part of IEEE Std 802.1DD;
     see the standard itself for full legal notices.";

  revision 2026-09-23 {
    description
      "Published as part of IEEE Std 802.1DD-202x.

       The following reference statement identifies each referenced
       IEEE Standard as updated by applicable amendments.";
    reference
      "IEEE Std 802.1DD Resource Allocation Protocol:
       IEEE Std 802.1Q Bridges and Bridged Networks:
       IEEE Std 802.1Q-2022, IEEE Std 802.1Qcz-2023,
       IEEE Std 802.1Qcw-2023, IEEE Std 802.1Qcj-2023,
       IEEE Std 802.1Qdj-2024, IEEE Std 802.1Qdx-2024,
       IEEE Std 802.1Qdy-2024";
  }

  grouping rap-talker-announce {
    description
      "Grouping for RAP Talker Announce.";
    leaf stream-id {
      type tsn:stream-id-type;
      description
        "An 8-octet field encoding the StreamID element as specified in
         46.2.3.1 of IEEE Std 802.1Q.";
      reference
        "6.4.3.1 of IEEE Std 802.1DD";
    }
    leaf stream-rank {
      type uint8;
      description
        "A 1-octet field encoding a Rank value as specified in
         46.2.3.2.1 of IEEE Std 802.1Q.";
      reference
        "6.4.3.2 of IEEE Std 802.1DD";
    }
    leaf accumulated-max-latency {
      type uint32;
      description
        "A 4-octet field encoding the AccumulatedLatency element as
         specified in 46.2.5.2 of IEEE Std 802.1Q.";
      reference
        "6.4.3.3 of IEEE Std 802.1DD";
    }
    leaf accumulated-min-latency {
      type uint32;
      description
        "A 4-octet unsigned integer, indicating the minimum latency, in
         nanoseconds, that a single frame of the stream can encounter when
         transmitted from the Talker along a given path to the Port
         declaring this attribute.";
      reference
        "6.4.3.4 of IEEE Std 802.1DD";
    }
    leaf destination-mac-address {
      type ieeetypes:mac-address;
      description
        "A 6-octet destination MAC address of the data frames of the
         stream.";
      reference
        "6.4.3.5.1 of IEEE Std 802.1DD";
    }
    leaf priority {
      type dot1qtypes:priority-type;
      description
        "A 3-bit unsigned integer, indicating the priority to be encoded in
         the PCP field of the VLAN tag, with which the data frames of the
         stream are tagged. This priority value is used by each receiving
         Bridge to associate the stream to a local RA class of the same
         priority.";
      reference
        "6.4.3.5.2 of IEEE Std 802.1DD";
    }
    leaf vid {
      type uint16 {
        range "1..4094";
      }
      description
        "A 12-bit VID. The semantics of this field is dependent on the type
         of a Talker Announcement in which the Talker Announce attribute is
         used, as follows:
         a) In the case of a Single-Context Talker
         Announcement, this field indicates a VID to be encoded in the VLAN
         tag with which the data frames of the stream are tagged, and also
         a single VLAN Context used by the Talker Announce attribute.
         b) In the case of a Multi-Context Talker Announcement, this field
         is set to the numerically smallest VlanContextId value contained
         in a VLAN Context Information sub-TLV.";
      reference
        "6.4.3.5.3 of IEEE Std 802.1DD";
    }
    leaf talker-token-bucket-tspec {
      type boolean;
      description
        "This parameter returns a Boolean value that indicates whether a
         Token Bucket TSpec sub-TLV is contained in the TalkerTSpec field
         of the Talker Announce attribute (TRUE) or not (FALSE).";
      reference
        "7.9.1 of IEEE Std 802.1DD";
    }
    leaf talker-token_bucket_tspec_value {
      type binary;
      description
        "When talkerTokenBucketTSpec is TRUE, this parameter returns an
         octet string that is copied from the whole of the Value field of a
         Token Bucket TSpec sub-TLV contained in the TalkerTSpec field of
         the Talker Announce attribute.";
      reference
        "7.9.2 of IEEE Std 802.1DD";
    }
    leaf talker-msrp-tspec {
      type boolean;
      description
        "This parameter returns a Boolean value that indicates whether a
         MSRP TSpec sub-TLV is contained in the TalkerTSpec field of the
         Talker Announce attribute.";
      reference
        "7.9.3 of IEEE Std 802.1DD";
    }
    leaf talker-msrp-tspec-value {
      type binary;
      description
        "When talkerMsrpTSpec is TRUE, this parameter returns an octet
         string that is copied from the whole of the Value field of a MSRP
         TSpec sub-TLV contained in the TalkerTSpec field of the Talker
         Announce attribute.";
      reference
        "7.9.4 of IEEE Std 802.1DD";
    }
    leaf network-tspec {
      type boolean;
      description
        "This parameter returns a Boolean value that indicates whether a
         Token Bucket TSpec sub-TLV is contained in the NetworkTSpec field
         of the Talker Announce attribute (TRUE) or not (FALSE).";
      reference
        "7.9.5 of IEEE Std 802.1DD";
    }
    leaf network-tspec-value {
      type binary;
      description
        "When networkTSpec is TRUE, this parameter returns an octet string
         that is copied from the whole of the Value field of a Token Bucket
         TSpec sub-TLV contained in the NetworkTSpec field of the Talker
         Announce attribute.";
      reference
        "7.9.6 of IEEE Std 802.1DD";
    }
    leaf redundancy-control {
      type boolean;
      description
        "This parameter returns a Boolean value that indicates whether a
         Redundancy Control sub-TLV is contained in the Talker Announce
         attribute (TRUE) or not (FALSE).";
      reference
        "7.9.7 of IEEE Std 802.1DD";
    }
    leaf redundancy-control-value {
      type binary;
      description
        "When redundancyControl is TRUE, this parameter returns an octet
         string that is copied from the whole of the Value field of a
         Redundancy Control sub-TLV contained in the Talker Announce
         attribute.";
      reference
        "7.9.8 of IEEE Std 802.1DD";
    }
    leaf failure-info {
      type boolean;
      description
        "This parameter returns a Boolean value that indicates whether a
         Failure Information sub-TLV is contained in the Talker Announce
         attribute (TRUE) or not (FALSE).";
      reference
        "7.9.9 of IEEE Std 802.1DD";
    }
    leaf failure-info-value {
      type binary;
      description
        "When failureInfo is TRUE, this parameter returns an octet string
         that is copied from the whole of the Value field of a Failure
         Information sub-TLV contained in the Talker Announce attribute.";
      reference
        "7.9.10 of IEEE Std 802.1DD";
    }
    leaf org-defined-info {
      type boolean;
      description
        "This parameter returns a Boolean value that indicates whether an
         Organizationally Defined sub-TLV is contained in the Talker
         Announce attribute (TRUE) or not (FALSE).";
      reference
        "7.9.11 of IEEE Std 802.1DD";
    }
    leaf org-defined-info-value {
      type binary;
      description
        "When orgDefinedInfo is TRUE, this parameter returns an octet
         string that is copied from the whole of the Value field of an
         Organizationally Defined sub-TLV contained in the Talker Announce
         attribute.";
      reference
        "7.9.12 of IEEE Std 802.1DD";
    }
    leaf invalid {
      type boolean;
      description
        "A Boolean indicating whether the Talker Announce registration is
         invalid (TRUE) or not (FALSE), as determined by the isTaInvalid()
         procedure (6.8.5.3).";
      reference
        "Item c) in 6.8.4.1 of IEEE Std 802.1DD";
    }
    leaf ingress-blocked {
      type boolean;
      description
        "A Boolean indicating whether the Talker Announce registration is
         ingress blocked (TRUE) or not (FALSE), as determined by the
         isTaIngressBlocked() procedure (6.8.5.4).";
      reference
        "Item d) in 6.8.4.1 of IEEE Std 802.1DD";
    }
  }

  grouping rap-listener-attach {
    description
      "Grouping for RAP Listener Attachment.";
    leaf stream-id {
      type tsn:stream-id-type;
      description
        "An 8-octet field encoding the StreamID element as specified in
         46.2.3.1 of IEEE Std 802.1Q.";
      reference
        "6.4.4.1 of IEEE Std 802.1DD";
    }
    leaf vid {
      type uint16 {
        range "1..4094";
      }
      description
        "A 12-bit integer, indicating a VID to be encoded in the VLAN tag
         with which the data frames of the stream are tagged.";
      reference
        "6.4.4.2 of IEEE Std 802.1DD";
    }
    leaf listener-attach-status {
      type enumeration {
        enum attach-ready {
          value 1;
          description
            "listener-attach-status is ATTACH_READY.";
        }
        enum attach-fail {
          value 2;
          description
            "listener-attach-status is ATTACH_FAIL.";
        }
        enum attach-partial-fail {
          value 3;
          description
            "listener-attach-status is ATTACH_PARTIAL_FAIL.";
        }
      }
      description
        "An enumeration indicating the listener attach status.";
      reference
        "6.4.4.3 of IEEE Std 802.1DD";
    }
    leaf vlan-context-status {
      type boolean;
      description
        "This parameter returns a Boolean value that indicates whether a
         VLAN Context Status sub-TLV is contained in the Listener Attach
         attribute (TRUE) or not (FALSE).";
      reference
        "7.11.1 of IEEE Std 802.1DD";
    }
    leaf vlan-context-status-value {
      type binary;
      description
        "When vlanContextStatus is TRUE, this parameter returns an octet
         string that is copied from the whole of the Value field of a VLAN
         Context Status sub-TLV contained in the Listener Attach
         attribute.";
      reference
        "6.4.4.4 of IEEE Std 802.1DD";
    }
  }

  grouping rap-component-parameters {
    description
      "Augment Bridge with RAP configuration.";
    reference
      "Clause 6 of IEEE Std 802.1DD";
    container rap-map-bridge-table {
      description
        "Container RAP MAP Bridge Table.";
      leaf frer-capable {
        type boolean;
        config false;
        description
          "A Boolean value, indicating whether the Bridge is a
           FRER-capable Bridge (TRUE) or not (FALSE).";
        reference
          "6.7.6.11 of IEEE Std 802.1DD";
      }
      leaf max-processing-delay {
        type uint32;
        config false;
        description
          "An unsigned integer, indicating the maximum delay, in
           nanoseconds, that a frame can experience during the
           forwarding process of the Bridge until it is placed into an
           outbound queue.";
        reference
          "6.7.6.12 of IEEE Std 802.1DD";
      }
      leaf min-processing-delay {
        type uint32;
        config false;
        description
          "An unsigned integer, indicating the minimum delay, in
           nanoseconds, that a frame can experience during the
           forwarding process of the Bridge until it is placed into an
           outbound queue.";
        reference
          "6.7.6.13 of IEEE Std 802.1DD";
      }
    }
    list ra-class-bridge-table {
      key "ra-class-id";
      description
        "Each table row contains a set of parameters that defines a
         single RA class.";
      leaf ra-class-id {
        type uint8 {
          range "0 .. 255";
        }
        description
          "The RA class ID is an integer in the range of 0 through 255
           that identifies an RA class supported by an end station or
           Bridge.";
        reference
          "6.3.2.1 of IEEE Std 802.1DD";
      }
      leaf ra-class-priority {
        type int8 {
          range "0 .. 7";
        }
        description
          "Each RA class supported by an end station or Bridge is
           associated with a unique priority value in the range 0
           through 7, termed RA class priority. The RA class priority
           indicates the received priority of the frames which are to
           be mapped to the traffic class(es) with which that RA class
           is associated.";
        reference
          "6.3.2.2 of IEEE Std 802.1DD";
      }
      leaf rt-id {
        type int32;
        description
          "An RA class template is identified by an RA Class Template
           Identifier (RTID), which encodes a 3-octet OUI or CID value
           identifying the organization that defines that template,
           followed by a 1-octet index allocated by that
           organization.";
        reference
          "6.3.2.3 of IEEE Std 802.1DD";
      }
      leaf templated-defined-data {
        type binary;
        description
          "The encoding of this field and the semantics associated
           with its values if any, is specific to the RA class
           template identified by the value contained in rt-id.";
        reference
          "6.4.2.2.5 of IEEE Std 802.1DD";
      }
    }
    list ra-class-port-pair {
      key "index";
      description
        "Each table row corresponds to an RA class configured in the
         RA Class Bridge Table and contains a set of parameters
         associated with a reception Port and a transmission Port.";
      leaf index {
        type uint16;
        description
          "The index for the list.";
      }
      leaf reception-port {
        type dot1qtypes:port-number-type;
        description
          "The port number of the associated reception Port.";
        reference
          "Item a) in 6.7.6.9 of IEEE Std 802.1DD";
      }
      leaf transmission-port {
        type dot1qtypes:port-number-type;
        description
          "The port number of the associated transmission Port.";
        reference
          "Item b) in 6.7.6.9 of IEEE Std 802.1DD";
      }
      leaf ra-class-id {
        type int8;
        description
          "The RA class ID of the associated local RA class.";
        reference
          "Item c) in 6.7.6.9 of IEEE Std 802.1DD";
      }
      leaf max-hop-latency {
        type uint32;
        description
          "An unsigned integer, containing the administratively
           configured maximum latency value, in nanoseconds, that is
           used as an upper bound latency in the latency constraint
           imposed on each stream reserved in the RA class, received
           on the reception Port, and transmitted on the transmission
           Port. The latency is measured from a point located in an
           upstream station connected via a LAN to the reception Port,
           to a point located in the transmission Port, where the
           exact measurement points are specific to and defined by the
           RA class template being used by the RA class.";
        reference
          "Item d) in 6.7.6.9 of IEEE Std 802.1DD";
      }
    }
    list rap-redundancy-context {
      key "redundancy-context-id";
      description
        "Each table row contains a set of parameters associated with a
         Redundancy Context supported by the Bridge.";
      leaf redundancy-context-id {
        type uint16 {
          range "1..4096";
        }
        description
          "The Redundancy Context ID of the Redundancy Context.";
        reference
          "Item a) in 6.7.6.10 of IEEE Std 802.1DD";
      }
      list vlan-context-list {
        key "vlan-context";
        description
          "The list of VLAN Context IDs associated with the Redundancy
           Context.";
        reference
          "Item b) in 6.7.6.10 of IEEE Std 802.1DD";
        leaf vlan-context {
          type uint16 {
            range "1..4096";
          }
          description
            "VLAN Context ID.";
        }
      }
    }
  }

  grouping rap-port-parameters {
    description
      "Augment Bridge Port with RAP configuration.";
    reference
      "Clause 6 of IEEE Std 802.1DD";
    container rap-mad-table {
      description
        "Container RAP MAD table.";
      leaf rap-port-enabled {
        type boolean;
        description
          "A Boolean variable indicating whether RAP MAD is enabled for this Port.";
        reference
          "6.6.4.1 of IEEE Std 802.1DD";
      }
      leaf rap-port-enable-msrp-compatibility {
        type boolean;
        description
          "A Boolean variable indicating whether MSRP compatibility mode is enabled for this Port.";
        reference
          "6.3.4.1 of IEEE Std 802.1DD";
      }
    }
    container rap-map-port-table {
      description
        "Container RAP MAP Port Table.";
      leaf stream-da-pruning-enabled {
        type boolean;
        description
          "A Boolean indicating whether Stream DA Pruning (51.3.4.1.2 of IEEE 802.1Q)
           is administratively enabled (TRUE) or disabled (FALSE) on the
           Port.";
        reference
          "Item a) in 6.7.6.7 of IEEE Std 802.1DD";
      }
      leaf max-interfering-frame-size {
        type uint32;
        config false;
        description
          "An unsigned integer, indicating the maximum frame size, in
           bytes, including media-dependent overhead (12.4.2.2 of IEEE 802.1Q), that is
           allowed to be transmitted through the Port. The value of this
           parameter is determined by the operation of the underlying
           MAC Service.";
        reference
          "Item b) in 6.7.6.7 of IEEE Std 802.1DD";
      }
      leaf max-propagation-delay {
        type uint32;
        config false;
        description
          "An unsigned integer, indicating the maximum latency, in
           nanoseconds, a frame can experience when transmitted from the
           underlying physical medium on the Port to a reception port
           connected via a LAN to the Port.";
        reference
          "Item c) in 6.7.6.7 of IEEE Std 802.1DD";
      }
      leaf min-propagation-delay {
        type uint32;
        config false;
        description
          "An unsigned integer, indicating the minimum latency, in
           nanoseconds, a frame can experience when transmitted from the
           underlying physical medium on the Port to a reception port
           connected via a LAN to the Port.";
        reference
          "Item d) in 6.7.6.7 of IEEE Std 802.1DD";
      }
    }
    list ra-class-port-table {
      key "ra-class-id";
      description
        "Each table row contains a set of parameters that defines a
         single RA class.";
      leaf ra-class-id {
        type uint8 {
          range "0 .. 255";
        }
        description
          "The RA class ID of the associated local RA class.";
        reference
          "Item a) in 6.7.6.8 of IEEE Std 802.1DD";
      }
      leaf domain-boundary-status {
        type boolean;
        config false;
        description
          "A Boolean indicating whether the Port is a domain boundary
           port for the RA class (TRUE) or not (FALSE).";
        reference
          "Item b) in 6.7.6.8 of IEEE Std 802.1DD";
      }
      leaf max-bandwidth {
        type uint32;
        description
          "An unsigned integer, indicating the maximum amount of
           bandwidth that can be allocated to the streams reserved in
           the RA class on the Port. The bandwidth value is represented
           as a percentage of the portTransmitRate value on that Port
           and expressed as a fixed-point number scaled by a factor of
           1,000,000; i.e., 100,000,000 (the maximum value)represents
           100%.";
        reference
          "Item c) in 6.7.6.8 of IEEE Std 802.1DD";
      }
      leaf allocated-bandwidth {
        type uint32;
        config false;
        description
          "An unsigned integer, indicating the amount of bandwidth that has
           been allocated to the streams reserved in the RA class on the
           Port. The bandwidth value is represented as a percentage of the
           portTransmitRate value on that Port and expressed as a fixed-
           point number scaled by a factor of 1,000,000; i.e., 100,000,000
           (the maximum value) represents 100%.";
        reference
          "Item d) in 6.7.6.8 of IEEE Std 802.1DD";
      }
    }
    list rap-priority-regeneration-override {
      key "received-priority";
      description
        "Each table row contains a set of parameters for a received
         priority value that is associated with an RA class.";
      leaf received-priority {
        type dot1qtypes:priority-type;
        description
          "Received priority value.";
        reference
          "7.7.1 of IEEE Std 802.1DD";
      }
      leaf regenerated-priority {
        type dot1qtypes:priority-type;
        description
          "Priority regeneration value.";
        reference
          "7.7.2 of IEEE Std 802.1DD";
      }
    }
    list rap-talker-announce-registration {
      key "stream-id vid";
      config false;
      description
        "Each table row in the table associated with a Port corresponds
         to a registration of the Talker Announce attribute on that Port,
         and contains a set of parameters.";
      uses rap-talker-announce;
    }
    list rap-talker-announce-declaration {
      key "stream-id vid";
      config false;
      description
        "Each table row in the Table associated with a Port corresponds
         to a declaration of the Talker Announce attribute on that Port,
         and contains the same set of parameters as in the Talker Announce
         Registration.";
      uses rap-talker-announce;
    }
    list rap-listener-attach-registration {
      key "stream-id vid";
      config false;
      description
        "Each table row in the Table associated with a Port corresponds to
         a registration of the Listener Attach attribute on that Port and
         contains a set of parameters.";
      uses rap-listener-attach;
      leaf reservation-age {
        type uint32;
        description
          "A 32-bit unsigned integer, indicating the time, in seconds,
           since a reservation associated with the Listener Attach
           registration was successfully made, and set to zero when the
           reservation is removed.";
        reference
          "Item e) in 6.8.4.3 of IEEE Std 802.1DD";
      }
      leaf ingress-status {
        type enumeration {
          enum not-propagated {
            value 0;
            description
              "ingress-status is NOT_PROPAGATED.";
          }
          enum attach-ready {
            value 1;
            description
              "ingress-status is ATTACH_READY.";
          }
          enum attach-fail {
            value 2;
            description
              "ingress-status is ATTACH_FAIL.";
          }
          enum attach-partial-fail {
            value 3;
            description
              "ingress-status is ATTACH_PARTIAL_FAIL.";
          }
        }
        description
          "The ingress status of the Listener Attach registration.";
        reference
          "Item f) in 6.8.4.3 of IEEE Std 802.1DD";
      }
    }
    list rap-listener-attach-declaration {
      key "stream-id vid";
      config false;
      description
        "Each table row in the Table associated with a Port corresponds to
         a declaration of the Listener Attach attribute on that Port and
         contains the same set of parameters except the reservationAge
         parameter as in the Listener Attach Registration.";
      uses rap-listener-attach;
    }
  }
}
