module ieee802-dot1dd-rap-bridge {
  yang-version 1.1;
  namespace "urn:ieee:std:802.1Q:yang:ieee802-dot1dd-rap-bridge";
  prefix rap-bridge;

  import ietf-interfaces {
    prefix if;
  }
  import ieee802-dot1q-bridge {
    prefix dot1q;
  }
  import ieee802-dot1dd-rap {
    prefix rap;
  }

  organization
    "IEEE 802.1 Working Group";
  contact
    "WG-URL: http://www.ieee802.org/1/
     WG-EMail: stds-802-1-l@ieee.org

     Contact: IEEE 802.1 Working Group Chair
     Postal: C/O IEEE 802.1 Working Group
            IEEE Standards Association
            445 Hoes Lane
            Piscataway, NJ 08854
            USA

     E-mail: stds-802-1-chairs@ieee.org";
  description
    "This module provides management of 802.1Q Bridge components that
     support the Resource Allocation Protocol (RAP).

     Copyright (C) IEEE (202x).

     This version of this YANG module is part of IEEE Std 802.1DD; see the
     standard itself for full legal notices.";

  revision 2026-09-23 {
    description
      "Published as part of IEEE Std 802.1DD-202x.

       The following reference statement identifies each referenced IEEE
       Standard as updated by applicable amendments.";
    reference
      "IEEE Std 802.1DD Resource Allocation Protocol:
       IEEE Std 802.1Q Bridges and Bridged Networks:
       IEEE Std 802.1Q-2022, IEEE Std 802.1Qcz-2023,
       IEEE Std 802.1Qcw-2023, IEEE Std 802.1Qcj-2023,
       IEEE Std 802.1Qdj-2024, IEEE Std 802.1Qdx-2024,
       IEEE Std 802.1Qdy-2024";
  }

   augment "/dot1q:bridges/dot1q:bridge/dot1q:component" {
    description
      "Augment Bridge Component with RAP configuration.";
    reference
      "Clause 6 of IEEE Std 802.1DD";
    uses rap:rap-component-parameters;
  }
  augment "/if:interfaces/if:interface/dot1q:bridge-port" {
    description
      "Augment Bridge Port with RAP configuration.";
    reference
      "Clause 6 of IEEE Std 802.1DD";
    uses rap:rap-port-parameters;
  }
}
