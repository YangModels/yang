module ieee802-dot1q-congestion-isolation-bridge {
  yang-version "1.1";
  namespace
    urn:ieee:std:802.1Q:yang:ieee802-dot1q-congestion-isolation-bridge;
  prefix ci-bridge;
  import ietf-interfaces {
    prefix if;
  }
  import ieee802-dot1q-bridge {
    prefix dot1q;
  }
  import ieee802-dot1q-congestion-isolation {
    prefix ci;
  }
  import ieee802-dot1q-stream-filters-gates {
    prefix sfsg;
  }
  organization
    "IEEE 802.1 Working Group";
  contact
    "WG-URL: https://1.ieee802.org/
    WG-EMail: stds-802-1@ieee.org
    Contact: IEEE 802.1 Working Group Chair
    Postal: C/O IEEE 802.1 Working Group
           IEEE Standards Association
           445 Hoes Lane
           Piscataway, NJ 08855
           USA
    
    E-mail: stds-802-1-chairs@listserv.ieee.org";
  description
    "This module provides management of IEEE Std 802.1Q bridge
    components that support Congestion Isolation.
    
    Copyright (C) IEEE (2023).
    
    This version of this YANG module is part of IEEE Std 802.1Q; see the
    standard itself for full legal notices.";
  revision 2023-07-03 {
    description
      "Published as part of IEEE Std 802.1Qcz-2023.";
    reference
      "IEEE Std 802.1Qcz-2023 - Bridges and Bridged Networks - Amendment:
      Congestion Isolation.";
  }
  feature congestion-isolation-bridge {
    description
      "Feature Congestion Isolation in Bridges";
  }
  augment "/dot1q:bridges/dot1q:bridge/dot1q:component" {
    if-feature "congestion-isolation-bridge";
    description
      "Augments the Bridge component with stream filters and stream
      gates.";
    uses ci:cip-parameters;
    uses sfsg:sfsg-parameters {
      augment
        "stream-filters/stream-filter-instance-table/stream-handle-spec" {
        if-feature "congestion-isolation-bridge";
        description
          "Dot1q Congestion Isolation";
        case null-handle {
          description
            "Congestion isolation specific stream_handle specifications.";
          leaf null-handle {
            type empty;
            description
              "The stream_handle specification represents the value when
              no stream_handle is provided.";
          }
        }
      }
    }
  }
  augment "/if:interfaces/if:interface/dot1q:bridge-port" {
    if-feature "congestion-isolation-bridge";
    description
      "Augment a bridge port with Congestion Isolation specific
      configuration.";
    uses ci:cip-port-parameters;
  }
}
