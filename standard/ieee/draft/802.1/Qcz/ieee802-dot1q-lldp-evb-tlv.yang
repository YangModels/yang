module ieee802-dot1q-lldp-evb-tlv {
  yang-version "1.1";
  namespace urn:ieee:std:802.1Q:yang:ieee802-dot1q-lldp-evb-tlv;
  prefix lldp-evb-tlv;
  import ieee802-dot1ab-lldp {
    prefix lldp;
  }
  organization
    "Institute of Electrical and Electronics Engineers";
  contact
    "WG-URL: http://ieee802.org/1/
    WG-EMail: stds-802-1-l@ieee.org
    Contact: IEEE 802.1 Working Group Chair
    Postal: C/O IEEE 802.1 Working Group
    IEEE Standards Association
         445 Hoes Lane
         Piscataway, NJ 08854
         USA
    
    E-mail: stds-802-1-chairs@ieee.org";
  description
    "IEEE Std 802.1Q extension TLVs for LLDP
    
    References in this YANG module to IEEE Std 802.1Q are to IEEE Std 
    802.1Q-2022 as amended by IEEE Std 802.1Qcz-2023.

    Copyright (C) IEEE (2023).
    
    This version of this YANG module is part of IEEE Std 802.1Q; see the
    standard itself for full legal notices.";
  revision 2023-07-03 {
    description
      "LLDP extension tlv for EVB. Published as part of IEEE Std
      802.1Qcz-2023.";
    reference
      "Annex D of IEEE Std 802.1Q";
  }
  grouping evb-tlv {
    description
      "Edge Virtual Bridging (EVB) TLV";
    reference
      "D.2.12 of IEEE Std 802.1Q";
    leaf evb-tlv-info-string {
      type binary {
        length "0..9";
      }
      config false;
      description
        "Opaque string containing EVB TLV information string. As the
        elements within the string are not individually manipulated by
        management (they are of concern only to the state machines), the
        sub-structure of the string is not visible as separate objects
        within the local database.";
      reference
        "D.2.12 of IEEE Std 802.1Q";
    }
  }
  grouping cdcp-tlv {
    description
      "Channel Discovery and Configuration TLV";
    reference
      "D.2.13 of IEEE Std 802.1Q";
    leaf cdcp-tlv-info-string {
      type binary {
        length "0..511";
      }
      config false;
      description
        "Opaque string containing CDCP TLV information. Up to 167
        S-channel numbers are supported. As the elements within the
        string are not individually manipulated by management (they are
        of concern only to the state machines), the sub-structure of the
        string is not visible as separate objects within the local
        database.";
      reference
        "D.2.13 and D.2.13.8 of IEEE Std 802.1Q";
    }
  }
  augment "/lldp:lldp/lldp:port" {
    description
      "Augments port with the EVB TLV";
    leaf tlvs-tx-org-evb-enable {
      type bits {
        bit evb {
          position 0;
          description
            "D.2.12 of IEEE Std 802.1Q";
        }
        bit cdcp {
          position 1;
          description
            "D.2.13 of IEEE Std 802.1Q";
        }
      }
      description
        "Bitmap that includes the evbSet of TLVs from Table D-1 of
        IEEE Std 802.1Q";
      reference
        "D.1 of IEEE Std 802.1Q";
    }
    container evb-tlv-extension {
      description
        "The EVB TLV";
      uses evb-tlv;
    }
    container cdcp-tlv-extension {
      description
        "The CDCP TLV";
      uses cdcp-tlv;
    }
  }
  augment "/lldp:lldp/lldp:port/lldp:remote-systems-data" {
    description
      "Augments port remote-systems-data with received EVB TLVs";
    container evb-tlv-extension {
      description
        "Holds a received EVB TLV";
      uses evb-tlv;
    }
    container cdcp-tlv-extension {
      description
        "Holds a received CDCP TLV";
      uses cdcp-tlv;
    }
  }
}
