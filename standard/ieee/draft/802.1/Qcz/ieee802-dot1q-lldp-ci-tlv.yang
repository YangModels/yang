module ieee802-dot1q-lldp-ci-tlv {
  yang-version "1.1";
  namespace urn:ieee:std:802.1Q:yang:ieee802-dot1q-lldp-ci-tlv;
  prefix lldp-ci-tlv;
  import ieee802-dot1ab-lldp {
    prefix lldp;
  }
  import ieee802-dot1q-congestion-isolation {
    prefix dot1q-ci;
  }
  import ietf-inet-types {
    prefix inet;
  }
  import ieee802-types {
    prefix ieee;
  }
  import ieee802-dot1q-types {
    prefix dot1q-types;
  }
  organization
    "Institute of Electrical and Electronics Engineers";
  contact
    "WG-URL: http://ieee802.org/1/
    WG-EMail: stds-802-1-l@ieee.org
      Contact: IEEE 802.1 Working Group Chair
      Postal: C/O IEEE 802.1 Working Group
      IEEE Standards Association
           445 Hoes Lane
           Piscataway, NJ 08854
           USA
    
    E-mail: stds-802-1-chairs@ieee.org";
  description
    "IEEE Std 802.1Q extension TLVs for LLDP from the Congestion
    Isolation set (ciSet).
    
    References in this YANG module to IEEE Std 802.1Q are to IEEE Std 
    802.1Q-2022 as amended by IEEE Std 802.1Qcz-2023.

    Copyright (C) IEEE (2023).
    
    This version of this YANG module is part of IEEE Std 802.1Q; see the
    standard itself for full legal notices.";
  revision 2023-07-03 {
    description
      "LLDP extension TLVs for the ciSet. Published as part of IEEE Std
      802.1Qcz-2023.";
    reference
      "Annex D of IEEE Std 802.1Q";
  }
  grouping congestion-isolation-tlv {
    description
      "Congestion Isolation TLV";
    reference
      "D.2.15 of IEEE Std 802.1Q";
    list queue-map {
      key "priority";
      description
        "Eight integer octets, one entry for each traffic class indexed
        by priority. Each octet specifies a value that can be translated
        to the numeric value of the traffic class to be used as either
        the congesting traffic class or the monitored traffic class for
        the traffic class specified by the index. The octets range in
        value from -8 to 8. A value of 0 in the list specifies that the
        traffic class is not participating in congestion isolation. A
        positive number specifies a traffic class for a monitored queue
        that is one less than the value (e.g., a value of 5 represents
        traffic class 4). A negative number specifies a traffic class for
        a congesting queue that is one less than the absolute value
        (e.g., a value of -4 represents traffic class 3).";
      reference
        "D.2.15.3 of IEEE Std 802.1Q";
      leaf priority {
        type dot1q-types:priority-type;
        description
          "There are eight values of Priority that map to an absolute
          value that is a traffic class plus one, or the value 0 which
          indicates the traffic class is not used by congestion
          isolation.";
        reference
          "D.2.15.3 of IEEE Std 802.1Q";
      }
      leaf queue-config {
        type dot1q-ci:abs-traffic-class-plus-one-type;
        description
          "A value that can be translated to represent a traffic class or
          an indication of non-use. A value of 0 specifies that the
          traffic class is not participating in congestion isolation. A
          positive number specifies a traffic class for a monitored
          queue, and a negative number specifies a traffic class for a
          congesting queue.";
        reference
          "D.2.15.3 of IEEE Std 802.1Q";
      }
    }
    leaf cim-encap-length {
      type uint16;
      description
        "The minimum number of octets to include in the Encapsulated MSDU
        field of each CIM generated. The default value is 48.";
      reference
        "D.2.15.4 of IEEE Std 802.1Q";
    }
    leaf mac-address {
      type ieee:mac-address;
      config false;
      description
        "The MAC address to be used as the destination MAC address of a
        CIM sent by the peer to reach this station.";
      reference
        "D.2.15.5 of IEEE Std 802.1Q";
    }
    leaf udp-port-number {
      type inet:port-number;
      config false;
      description
        "The UDP port number to be used as the destination port number of
        a layer-3 CIM sent by the peer to reach this station.";
      reference
        "D.2.15.6 of IEEE Std 802.1Q";
    }
    leaf ip-address {
      type inet:ip-address;
      config false;
      description
        "This leaf holds the IP address that will be used to populate
        both the address family and IP address fields of the TLV. The IP
        address field in the TLV is an octect string to be encoded in
        network octet order with length of 0, 4, or 16 octets dependent
        upon the address family. If this leaf is an IPv4 address, the
        address family field is 1 and the IP address field is 4 octets
        representing the IPv4 address (e.g., IPv4 address 192.0.2.10
        would be encoded as C0-00-02-0A). If this leaf is an IPv6
        address, the address family field is 2 and the IP address field
        is 16 octets representing the IPv6 address. No address shall be
        provided for any other address families.";
      reference
        "D.2.15.7 and D.2.15.8 of IEEE Std 802.1Q";
    }
  }
  augment "/lldp:lldp/lldp:port" {
    description
      "Augments port with Congestion Isolation extension TLVs";
    leaf tlvs-tx-org-ci-enable {
      type bits {
        bit congestion-isolation {
          position 0;
          description
            "Enables transmission of the Congestion Isolation TLV in the
            ciSet";
        }
      }
      description
        "Bitmap that includes the ciSet of TLVs from Table D-1 of
        802.1Q";
      reference
        "D.2 of IEEE Std 802.1Q";
    }
    container congestion-isolation-tlv-extension {
      description
        "The Congestion Isolation TLV";
      uses congestion-isolation-tlv;
    }
  }
  augment "/lldp:lldp/lldp:port/lldp:remote-systems-data" {
    description
      "Augments port remote-systems-data with received Congestion
      Isolation extension TLVs";
    container congestion-isolation-tlv-extension {
      description
        "Holds a received Congestion Isolation TLV";
      uses congestion-isolation-tlv;
    }
  }
}
