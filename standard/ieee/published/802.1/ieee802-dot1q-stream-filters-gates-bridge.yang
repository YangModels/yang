module ieee802-dot1q-stream-filters-gates-bridge {
  yang-version "1.1";
  namespace
    urn:ieee:std:802.1Q:yang:ieee802-dot1q-stream-filters-gates-bridge;
  prefix sfsg-bridge;
  import ieee802-dot1q-bridge {
    prefix dot1q;
  }
  import ieee802-dot1q-stream-filters-gates {
    prefix sfsg;
  }
  organization
    "IEEE 802.1 Working Group";
  contact
    "WG-URL: https://1.ieee802.org/
    WG-EMail: stds-802-1@ieee.org
    Contact: IEEE 802.1 Working Group Chair
    Postal: C/O IEEE 802.1 Working Group
           IEEE Standards Association
           445 Hoes Lane
           Piscataway, NJ 08855
           USA
    
    E-mail: STDS-802-1-CHAIRS@LISTSERV.IEEE.ORG";
  description
    "This module provides management of IEEE 802.1Q Bridge components
    that support Stream Filters and Stream Gates.
    
    Copyright (C) IEEE (2023).
    
    This version of this YANG module is part of IEEE Std 802.1Q; see the
    standard itself for full legal notices.";
  revision 2023-07-03 {
    description
      "Published as part of IEEE Std 802.1Qcz-2023.";
    reference
      "IEEE Std 802.1Qcz-2023 - Bridges and Bridged Networks - Amendment:
      Congestion Isolation.";
  }
  augment "/dot1q:bridges/dot1q:bridge/dot1q:component" {
    description
      "Augments the Bridge component with stream filters and stream
      gates.";
    uses sfsg:sfsg-parameters;
  }
}
