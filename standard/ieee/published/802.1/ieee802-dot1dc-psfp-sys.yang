module ieee802-dot1dc-psfp-sys {
  yang-version "1.1";
  namespace urn:ieee:std:802.1Q:yang:ieee802-dot1dc-psfp-sys;
  prefix psfp-sys;
  
  import ietf-system {
    prefix sys;
  }
  import ieee802-dot1q-psfp {
    prefix q-psfp;
  }

  organization
    "Institute of Electrical and Electronics Engineers";
  contact
    "WG-URL: http://ieee802.org/1/
     WG-EMail: stds-802-1-l@ieee.org
       Contact: IEEE 802.1 Working Group Chair
       Postal: C/O IEEE 802.1 Working Group
       IEEE Standards Association
            445 Hoes Lane
            Piscataway
            NJ 08854
            USA

    E-mail: stds-802-1-chairs@ieee.org";

  description
    "This module provides management of General Frame Quality of
    Service (GFQoS) systems that support IEEE Std 802.1Q Per-
    Stream Filtering and Policing (PSFP).
  
    Copyright (C) IEEE (2024).

    This version of this YANG module is part of IEEE Std 802.1DC;
    see the standard itself for full legal notices.";

  revision 2024-09-26 {
    description
      "Published as part of IEEE Std 802.1DC-2024.

      The following reference statement identifies each referenced
      IEEE Standard as updated by applicable amendments.";

    reference
      "IEEE Std 802.1DC:
      IEEE Std 802.1DC-2024 Quality of Service Provision by
      Network Systems.";
  }

  feature psfp {
    description
      "Per-Stream Filtering and Policing supported.";
    reference
      "6.2.8 of IEEE Std 802.1DC";
  }

  augment "/sys:system" {
    description
      "Augment system with Per-Stream Filtering and Policing
      configuration";
    uses q-psfp:psfp-parameters;
  }
}
