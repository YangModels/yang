module ieee802-dot1q-lldp-cn-tlv {
  yang-version "1.1";
  namespace urn:ieee:std:802.1Q:yang:ieee802-dot1q-lldp-cn-tlv;
  prefix lldp-cn-tlv;
  import ieee802-dot1ab-lldp {
    prefix lldp;
  }
  organization
    "Institute of Electrical and Electronics Engineers";
  contact
    "WG-URL: http://ieee802.org/1/
    WG-EMail: stds-802-1-l@ieee.org
    Contact: IEEE 802.1 Working Group Chair
    Postal: C/O IEEE 802.1 Working Group
    IEEE Standards Association
         445 Hoes Lane
         Piscataway, NJ 08854
         USA
    
    E-mail: stds-802-1-chairs@ieee.org";
  description
    "IEEE Std 802.1Q extension TLVs for LLDP
      
    References in this YANG module to IEEE Std 802.1Q are to IEEE Std 
    802.1Q-2022 as amended by IEEE Std 802.1Qcz-2023.

    Copyright (C) IEEE (2023).
      
    This version of this YANG module is part of IEEE Std 802.1Q; see
    the standard itself for full legal notices.";
  revision 2023-07-03 {
    description
      "LLDP extension tlv for congestion notification.";
    reference
      "Annex D of IEEE Std 802.1Q";
  }
  grouping congestion-notification-tlv {
    description
      "Congestion Notification TLV";
    reference
      "D.2.7 of IEEE Std 802.1Q";
    typedef congestion-notification-bit-vector {
      type bits {
        bit priority0 {
          position 0;
          description
            "status for priority0, 0 is FALSE, 1 is TRUE";
        }
        bit priority1 {
          position 1;
          description
            "status for priority1, 0 is FALSE, 1 is TRUE";
        }
        bit priority2 {
          position 2;
          description
            "status for priority2, 0 is FALSE, 1 is TRUE";
        }
        bit priority3 {
          position 3;
          description
            "status for priority3, 0 is FALSE, 1 is TRUE";
        }
        bit priority4 {
          position 4;
          description
            "status for priority4, 0 is FALSE, 1 is TRUE";
        }
        bit priority5 {
          position 5;
          description
            "status for priority5, 0 is FALSE, 1 is TRUE";
        }
        bit priority6 {
          position 6;
          description
            "status for priority6, 0 is FALSE, 1 is TRUE";
        }
        bit priority7 {
          position 7;
          description
            "status for priority7, 0 is FALSE, 1 is TRUE";
        }
      }
      description
        "Describes a bit vector used in Congestion Notification Objects";
      reference
        "32.4.7, 32.4.8 of IEEE Std 802.1Q";
    }
    leaf per-priority-xmit-cnpv-capable {
      type congestion-notification-bit-vector;
      description
        "Indicates if a priority on this Port is operating as a CNPV";
      reference
        "D.2.7.3, 32.4.7 of IEEE Std 802.1Q";
    }
    leaf per-priority-xmit-ready {
      type congestion-notification-bit-vector;
      description
        "Indicates if the priority remap defenses for this Port and CNPV
        have been disabled";
      reference
        "D.2.7.4, 32.4.8 of IEEE Std 802.1Q";
    }
  }
  augment "/lldp:lldp/lldp:port" {
    description
      "Augments port with the congestion notification extension tlv";
    leaf tlvs-tx-org-congestion-notification-enable {
      type boolean;
      description
        "Leaf that indicates if congestion notification tlv is enabled
        from Table D-1 of IEEE Std 802.1Q";
      reference
        "D.2 of IEEE Std 802.1Q";
    }
    container congestion-notification-tlv-extension {
      description
        "The Congestion Notification TLV";
      uses congestion-notification-tlv;
    }
  }
  augment "/lldp:lldp/lldp:port/lldp:remote-systems-data" {
    description
      "Augments port remote-systems-data with received cn extension TLVs";
    container congestion-notification-tlv-extension {
      description
        "Holds a received Congestion Notification TLV";
      uses congestion-notification-tlv;
    }
  }
}
