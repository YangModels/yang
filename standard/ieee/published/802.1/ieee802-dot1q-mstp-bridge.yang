module ieee802-dot1q-mstp-bridge {
  yang-version 1.1;
  namespace "urn:ieee:std:802.1Q:yang:ieee802-dot1q-mstp-bridge";
  prefix mstp-bridge;

  import ietf-interfaces {
    prefix if;
  }
  import ieee802-dot1q-bridge {
    prefix dot1q;
  }
  import ieee802-dot1q-rstp-bridge {
    prefix rstp-bridge;
  }
  import ieee802-dot1q-mstp {
    prefix mstp;
  }

  organization
    "IEEE 802.1 Working Group";
  contact
    "WG-URL: http://www.ieee802.org/1/
    WG-EMail: stds-802-1-l@ieee.org

    Contact: IEEE 802.1 Working Group Chair
    Postal: C/O IEEE 802.1 Working Group
            IEEE Standards Association
            445 Hoes Lane
            Piscataway, NJ 08854
            USA

    E-mail: stds-802-1-chairs@ieee.org";
  description
    "This module provides management of IEEE Std 802.1Q Bridge components 
    that support the Multiple Spanning Tree Algorithm and Protocol (MSTP).

    Copyright (C) IEEE (2025).

    This version of this YANG module is part of IEEE Std 802.1Q; see the
    standard itself for full legal notices.";

  revision 2025-02-04 {
    description
      "Published as part of IEEE Std 802.1Qdy-2025.

      The following reference statement identifies each referenced IEEE
      Standard as updated by applicable amendments.";
    reference
      "IEEE Std 802.1Q Bridges and Bridged Networks:
      IEEE Std 802.1Q-2022, IEEE Std 802.1Qcz-2023, 
      IEEE Std 802.1Qcw-2023, IEEE Std 802.1Qcj-2023, 
      IEEE Std 802.1Qdj-2024, IEEE Std 802.1Qdx-2024, 
      IEEE Std 802.1Qdy-2025.";
  }

  augment "/dot1q:bridges/dot1q:bridge/dot1q:component/dot1q:bridge-mst" {
    when '../rstp-bridge:rstp';
    description
      "Augment RSTP-capable Bridge component with MSTP configuration and
       management.";
    reference
      "13.24, 13.25, and 13.26 of IEEE Std 802.1Q.";
    uses mstp:bridge-component-parameters;
  }

  augment "/if:interfaces/if:interface/dot1q:bridge-port" {
    when 'rstp-bridge:rstp';
    description
      "Augment RSTP Bridge Port with MSTP configuration.";
    reference
      "13.24, 13.25, and 13.27 of IEEE Std 802.1Q.";
    uses mstp:bridge-port-parameters;
  }
}
