module ieee802-dot1dc-gfqos {
  yang-version "1.1";
  namespace urn:ieee:std:802.1Q:yang:ieee802-dot1dc-gfqos;
  prefix dot1dc;
  import ietf-yang-types {
    prefix yang;
  }
  import ietf-interfaces {
    prefix if;
  }
  import ieee802-dot1q-types {
    prefix dot1qtypes;
  }
  import ieee802-dot1q-bridge {
    prefix dot1q;
  }

  organization
    "Institute of Electrical and Electronics Engineers";
  contact
    "WG-URL: http://ieee802.org/1/
     WG-EMail: stds-802-1-l@ieee.org
       Contact: IEEE 802.1 Working Group Chair
       Postal: C/O IEEE 802.1 Working Group
       IEEE Standards Association
            445 Hoes Lane
            Piscataway
            NJ 08854
            USA

    E-mail: stds-802-1-chairs@ieee.org";

  description
    "This module provides for management of General Frame Quality of
    Service (GFQoS) systems that support the Enhanced Internal Sublayer
    Service (EISS).
    
  
    Copyright (C) IEEE (2024).

    This version of this YANG module is part of IEEE Std 802.1DC;
    see the standard itself for full legal notices.";

  revision 2024-09-26 {
    description
      "Published as part of IEEE Std 802.1DC-2024.

      The following reference statement identifies each referenced
      IEEE Standard as updated by applicable amendments.";

    reference
      "IEEE Std 802.1DC:
      IEEE Std 802.1DC-2024 Quality of Service Provision by Network
      Systems.
      IEEE Std 802.1Q:
      IEEE Std 802.1Q-2022 Bridges and Bridged Networks.";
  }

  feature eiss {
    description
      "Each GFQoS interface may support the Enhanced Internal Sublayer
      Service (EISS). This is one useful method for dealing with VLAN
      tags.";
    reference
      "7.3.2 of IEEE Std 802.1DC";
  }
  augment "/if:interfaces/if:interface" {
    description
      "Augment the interface model with the GFQoS interface";
    container gfqos-ifc {
      description
        "GFQoS interface is an extension of the IETF Interfaces model
        (IETF RFC 7223).";
      leaf pvid {
        if-feature "eiss";
        type dot1qtypes:vlan-index-type;
        default "1";
        description
          "The port VID assigned to the interface.";
        reference
          "12.10.1, item m) of 5.4 of IEEE Std 802.1Q";
      }
      leaf acceptable-frame {
        if-feature "eiss";
        type enumeration {
          enum admit-only-VLAN-tagged-frames {
            description
              "Admit only VLAN-tagged frames.";
          }
          enum admit-only-untagged-and-priority-tagged {
            description
              "Admit only untagged and priority-tagged frames.";
          }
          enum admit-all-frames {
            description
              "Admit all frames.";
          }
        }
        default "admit-all-frames";
        description
          "To configure the Acceptable Frame Types parameter associated
          with one or more GFQoS interfaces, only if EISS is supported";
        reference
          "12.10.1.3, 6.9 of IEEE Std 802.1Q";
      }
      container transmission-selection-algorithm-table {
        description
          "The Transmission Selection Algorithm Table for a given
          interface assigns, for each traffic class that the interface
          supports, the transmission selection algorithm that is to be
          used to select frames for transmission from the corresponding
          queue. Transmission Selection Algorithm Tables may be managed,
          and allow the identification of vendor-specific transmission
          selection algorithms. The transmission selection algorithms
          are identified in the Transmission Selection Algorithm Table
          by means of integer identifiers.";
        reference
          "12.20.2, 8.6.8 of IEEE Std 802.1Q";
        uses dot1qtypes:transmission-selection-table-grouping;
      }
      leaf media-dependent-overhead {
        type uint8;
        units "octets";
        config false;
        description
          "The portMediaDependentOverhead parameter provides the number
          of additional octets for media-dependent framing. The overhead
          includes all octets prior the first octet of the Destination
          Address field and all octets after the last octet of the frame
          check sequence.";
        reference
          "12.4.2 of IEEE Std 802.1Q";
      }
      container statistics {
        config false;
        description
          "Container of operational state node information associated
          with the GFQoS interface.";
        uses dot1qtypes:bridge-port-statistics-grouping;
        leaf discard-on-ingress-filtering {
          if-feature "dot1q:ingress-filtering";
          type yang:counter64;
          description
            "The number of frames that were discarded as a result of
            Ingress Filtering being enabled.
            
            Discontinuities in the value of this counter can occur at
            re-initialization of the management system, and at other
            times as indicated by the value of 'discontinuity-time'.";
          reference
            "12.6.1.1.3 of IEEE Std 802.1Q";
        }
      }
    }
  }
}
