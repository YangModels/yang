module ieee802-ethernet-interface-half-duplex {
  yang-version 1.1;
  namespace
    "urn:ieee:std:802.3:yang:ieee802-ethernet-interface-half-duplex";
  prefix ieee802-eth-half-duplex;

  import ietf-yang-types {
    prefix yang;
    reference
      "IETF RFC 6991";
  }
  import ietf-interfaces {
    prefix if;
    reference
      "IETF RFC 8343";
  }
  import iana-if-type {
    prefix ianaift;
    reference
      "http://www.iana.org/assignments/yang-parameters/
       iana-if-type@2023-01-26.yang";
  }
  import ieee802-ethernet-interface {
    prefix ieee802-eth-if;
  }

  organization
    "IEEE Std 802.3 Ethernet Working Group
     Web URL: http://www.ieee802.org/3/";
  contact
    "Web URL: http://www.ieee802.org/3/";
  description
    "This module contains YANG definitions for half duplex
     Ethernet interfaces, e.g., 10BASE-T1S.";

  revision 2025-09-10 {
    description
      "Updates under IEEE Std 802.3.2-2025";
    reference
      "IEEE Std 802.3-2022, unless dated explicitly";
  }

  feature dynamic-rate-control {
    status obsolete;
    description
      "This feature indicates that the device supports Ethernet
       interfaces lowering the average data rate of the MAC
       sublayer, with frame granularity, by using Rate Control to
       dynamically increase the interpacket gap for some types of
       Ethernet interface.
       Only valid for Ethernet interfaces operating at speeds
       (data rates) above 1000 Mb/s.";
    reference
      "IEEE Std 802.3, 30.3.1.1.33 aRateControlAbility";
  }

  feature csma-cd {
    description
      "This feature indicates that the device supports Ethernet
       interfaces running at half-duplex using CSMA/CD.";
  }

  typedef dynamic-rate-control-type {
    type enumeration {
      enum disabled {
        description
          "Dynamic rate control is disabled";
      }
      enum sonet-oc192 {
        value 2;
        description
          "Dynamic rate control is enabled for a 10 Gb/s Ethernet
           interface to SONET/SDH OC192/STM64.";
      }
    }
    default "disabled";
    status obsolete;
    description
      "Allowed values for dynamic-rate-control.";
    reference
      "IEEE Std 802.3, 4.4.2 ipgStretchRatio and 30.3.1.1.34
       aRateControlStatus";
  }

  augment "/if:interfaces/if:interface/ieee802-eth-if:ethernet" {
    when "derived-from-or-self(../if:type, 'ianaift:ethernetCsmacd')
          and ieee802-eth-if:duplex = 'half'" {
      description
        "Applies to half-duplex Ethernet interfaces.";
    }
    status obsolete;
    description
      "Augment with Ethernet interface configuration parameters
       for half-duplex operation.";
    leaf dynamic-rate-control {
      if-feature "dynamic-rate-control";
      type dynamic-rate-control-type;
      status obsolete;
      description
        "Enables dynamic rate control and specifies what speed
         (data rate) the dynamic rate control is operating at.
         The value of this attribute is constrained by the MAC
         data rate and hardware support.
         The default value is implementation dependent.";
      reference
        "IEEE Std 802.3, 30.3.1.1.34 aRateControlStatus";
    }
  }

  augment "/if:interfaces/if:interface/ieee802-eth-if:ethernet/"
        + "ieee802-eth-if:capabilities" {
    when "derived-from-or-self(../../if:type,
          'ianaift:ethernetCsmacd')
           and ../ieee802-eth-if:duplex = 'half'" {
      description
        "Applies to half-duplex Ethernet interfaces";
    }
    status obsolete;
    description
      "Augment with configuration capabilities for half-duplex
       Ethernet interface.";
    leaf dynamic-rate-control-supported {
      if-feature "dynamic-rate-control";
      type boolean;
      default "false";
      status obsolete;
      description
        "Indicates whether the Ethernet interface supports lowering
         the average data rate of the MAC sublayer, with frame
         granularity, by using Rate Control to dynamically increase
         the interpacket gap.
         Only valid for Ethernet interfaces operating at speeds
         (data rates) above 1000 Mb/s.";
      reference
        "IEEE Std 802.3, 30.3.1.1.33 aRateControlAbility";
    }
  }

  augment "/if:interfaces/if:interface/ieee802-eth-if:ethernet/"
        + "ieee802-eth-if:statistics/ieee802-eth-if:frame" {
    when "derived-from-or-self(../../../if:type,
          'ianaift:ethernetCsmacd') and
              ../../ieee802-eth-if:duplex = 'half'" {
      description
        "Applies to half-duplex Ethernet interfaces.";
    }
    description
      "Augment with statistics for half-duplex Ethernet interface.";
    container csma-cd {
      if-feature "csma-cd";
      description
        "Holds counters that are specific to CDMA/CD half-duplex
         operation of Ethernet interfaces.
         This counter does not increment on Ethernet interfaces
         operating at speeds (data rates) greater than 10 Mb/s, or
         on Ethernet interfaces operating in full-duplex mode.
         Discontinuities in the value of this counter can occur at
         re-initialization of the management system, and at other
         times as indicated by the value of the
         'discontinuity-time' leaf defined in the ietf-interfaces
         YANG module (IETF RFC 8343).";
      leaf in-errors-sqe-test {
        type yang:counter64;
        units "errors";
        description
          "A count of times that the SQE TEST ERROR is received on
           a particular interface. The SQE TEST ERROR is set in
           accordance with the rules for verification of the SQE
           detection mechanism in the PLS Carrier Sense function as
           described in IEEE Std 802.3, 7.2.4.6.";
        reference
          "IEEE Std 802.3, 7.2.4.6, and 30.3.2.1.4 aSQETestErrors";
      }
      leaf out-frames-collision-single {
        type yang:counter64;
        units "frames";
        description
          "A count of frames that are involved in a single
           collision, and are subsequently transmitted
           successfully. A frame that is counted by an instance of
           this object is also counted by the corresponding
           instance of either 'out-unicast-frames',
           'out-broadcast-frames', or 'out-multicast-frames',
           and is not counted by the corresponding instance of the
           'out-frames-collision-multiple'.";
        reference
          "IEEE Std 802.3, 30.3.1.1.3 aSingleCollisionFrames";
      }
      leaf out-frames-collision-multiple {
        type yang:counter64;
        units "frames";
        description
          "A count of frames that are involved in multiple
           collisions, and are subsequently transmitted
           successfully. A frame that is counted by an instance of
           this object is also counted by the corresponding
           instance of either 'out-unicast-frames',
           'out-broadcast-frames', or 'out-multicast-frames', and
           is not counted by the corresponding instance of the
           'out-frames-collision-single'.";
        reference
          "IEEE Std 802.3, 30.3.1.1.4 aMultipleCollisionFrames";
      }
      leaf out-frames-deferred {
        type yang:counter64;
        units "frames";
        description
          "A count of frames for which the first transmission
           attempt on a particular Ethernet interface is delayed
           because the medium is busy.
           A deferred frame that is not subject to any number of
           collisions is not counted by an instance of
           'out-frames-collision-single' or
           'out-frames-collision-multiple' objects.";
        reference
          "IEEE Std 802.3, 30.3.1.1.9
           aFramesWithDeferredXmissions";
      }
      leaf out-frames-collisions-excessive {
        type yang:counter64;
        units "frames";
        description
          "A count of frames for which transmission on a particular
           Ethernet interface fails due to excessive collisions.";
        reference
          "IEEE Std 802.3, 30.3.1.1.11 aFramesAbortedDueToXSColls";
      }
      leaf out-collisions-late {
        type yang:counter64;
        units "collisions";
        description
          "The number of times that a collision is detected on a
           particular Ethernet interface later than one slotTime
           into the transmission of a packet.
           A (late) collision included in a count represented by an
           instance of this object is also considered as a
           (generic) collision for purposes of other
           collision-related statistics.";
        reference
          "IEEE Std 802.3, 30.3.1.1.10 aLateCollisions";
      }
      leaf out-errors-carrier-sense {
        type yang:counter64;
        units "errors";
        description
          "The number of times that the carrier sense condition was
           lost or never asserted when attempting to transmit a
           frame on a particular Ethernet interface.
           The count represented by an instance of this object is
           incremented at most once per transmission attempt, even
           if the carrier sense condition fluctuates during a
           transmission attempt.";
        reference
          "IEEE Std 802.3, 30.3.1.1.13 aCarrierSenseErrors";
      }
      list collision-histogram {
        key "collision-count";
        description
          "A collection of collision histograms for a particular
           interface.";
        reference
          "IEEE Std 802.3, 30.3.1.1.30 aCollisionFrames";
        leaf collision-count {
          type yang:counter64;
          units "collisions";
          description
            "The number of per-frame media collisions for which a
             particular collision histogram cell represents the
             frequency on a particular interface.";
        }
        leaf collision-count-frames {
          type yang:counter64;
          units "frames";
          description
            "A count of individual MAC frames for which the
             transmission (successful or otherwise) on a particular
             interface occurs after the frame has experienced
             exactly the number of collisions in the associated
             dot3CollCount object.
             For example, a frame which is transmitted on an
             interface after experiencing exactly 4 collisions
             would be indicated by incrementing only the
             collision-count-frames object associated with the
             collision-count value of 4. No other instance of
             collision-count-frames would be incremented in this
             example.";
        }
      }
    }
  }
}
