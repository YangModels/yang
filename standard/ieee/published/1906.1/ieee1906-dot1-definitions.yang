module ieee1906-dot1-definitions
{
  yang-version 1.1;
  namespace "urn:ieee:std:1906.1:yang:ieee1906-dot1-definitions";
  prefix "ieee1906-definitions";

  import ieee1906-dot1-types { prefix ieee1906-dot1-types; }
  import ieee1906-dot1-metrics { prefix ieee1906-dot1-metrics; }
  import ieee1906-dot1-properties { prefix properties; }

  organization "IEEE Std 1906.1-2015 - Recommended Practice for Nanoscale and
                Molecular Communication Framework Working Group";

  contact 	"IEEE 1906.1.1 Working Group
		 Chair: Stephen F. Bush <bushsf@research.ge.com>
		 Secretary: Guillaume Mantelet <gmantelet@voltigeurnetworks.com>";

  description	"This is the YANG model for the IEEE 1906.1-2015 - Recommended
                 Practice for Nanoscale and Molecular Communication Framework.
                 Clause 4 - Definition of a molecular and nanoscale communication
                 network.

			 	 This module defines definitions (transmitter, receiver, message etc.).";

  revision 2020-12-07
  {
    description "Initial version.";

	reference	"[1] P1906.1.1/D1.0 Draft Standard for Nanoscale and Molecular
					 Communication Framework.

				 [2] 'IEEE Recommended Practice for Nanoscale and Molecular
				 	 Communication Framework,' in IEEE Std 1906.1-2015, pp.1-64,
					 Jan. 11 2016 doi: 10.1109/IEEESTD.2016.7378262.

				 [3] S. F. Bush, 'Active network architecture' in Nanoscale
					 Communication Networks, pp. 209-217, 2010, Artech House.

				 [4] S. F. Bush, J. L. Paluh, G. Piro, V. Rao, R. V. Prasad and
					 A. Eckford, 'Defining Communication at the Bottom,' in IEEE
					 Transactions on Molecular, Biological and Multi-Scale
					 Communications, vol. 1, no. 1, pp. 90-96, March 2015.
					 doi: 10.1109/TMBMC.2015.2465513.";
  }

  grouping definition
  {
    list definition
    {
      key identifier;

      leaf name
      {
	    type string;
	    description "An optional name to describe what is this definition
			  	     in the non-1906.1 model.";
	  }

      leaf description
      {
        type string;
        description "An optional string to describe what does this 
                     definition in the non-1906.1 model.";
      }

      leaf identifier
      {
        type string;
        description "A unique identifier for this definition to be
                     associated to the non-1906.1 model.";
      }

      leaf human-designed
      {
        type boolean;
        description "'Human-designed' means a system that occurs as a
                     result of conscious human intervention. For clarity,
                     human-designed systems may include naturally 
                     occurring components in an arrangement or for a 
                     purpose that is not otherwise naturally occurring.";
        default false;
      }

      container properties
      {
        uses properties:property;
        description "This containers stores the list of optional 
                     properties that provide extra definition of the 
                     component, or make this component attribute 
                     supersedes corresponding system (or parent
                     component) corresponding attribute.";
      }

      leaf type-of-definition
      {
         type identityref { base 'ieee1906-dot1-types:definition'; }
         mandatory true;
         description  "Identifies the IEEE 1906.1 definition
                       extended in this model.";
      }

      leaf-list sub-definition
      {
        type instance-identifier { require-instance false; }
        description "Identifies the list of child definitions that are 
                     part of this definition. There shall be 0 or more 
                     child definition and child definition shall be of any 
                     type.";
      }

      leaf-list next-definition
      {
        type instance-identifier { require-instance false; }
        description "Identifies the list of sibling definitions attached
                     to this definition in a unidirectional way. There 
                     shall be 0 or more definitions and next definition 
                     shall be of any type.

                     This leaf-list helps identify the components along
                     the data path of a message, and shall help build a
                     tree or a bus.";
      }

      leaf-list sub-component
      {
        type instance-identifier { require-instance false; }
        description "Identifies the list of child components that are 
                     part of this definition. There shall be 0 or more
                     child components and child components shall be of any 
                     type.";
      }

      leaf-list next-component
      {
        type instance-identifier { require-instance false; }
        description "Identifies the list of next components that are
                     interfaced to this definition. There shall be 0 or 
                     more next components and next components shall be of
                     any type. However, model shall clearly identify next 
                     components that make valid interfaces from IEEE 
                     1906.1 perspective.

                     For example, if this definition is of type 
                     'message', then suitable 'next-component' would be 
                     of type 'message-carrier'";
      }

      uses ieee1906-dot1-metrics:message-metrics;

      description "A list of IEEE 1906.1 compatible objects.";
    }

  description "This is the main grouping for the IEEE 1906.1
               framework. This relates any conceptual object to a
               'definition'.";
  }
}
