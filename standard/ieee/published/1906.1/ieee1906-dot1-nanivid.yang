module ieee1906-dot1-nanivid
{
  yang-version 1.1;
  namespace "urn:ieee:std:1906.1:yang:ieee1906-dot1-nanivid";
  prefix "ieee1906-nanivid";

  import ieee1906-dot1-system { prefix system; }
  import ieee1906-dot1-types { prefix types; }

  organization "IEEE 1906.1.1 Working Group";

  contact 	"IEEE 1906.1.1 Working Group
		 Chair: Stephen F. Bush <bushsf@research.ge.com>
		 Secretary: Guillaume Mantelet <gmantelet@voltigeurnetworks.com>";

  description	"This is an example illustrating how to refine the 1906.1 framework
                 to include specific details regarding NANIVID experiment.";

  revision 2020-12-07
  {
    description "Initial version.";
  }

  //
  // Let us control how nanoscale-system can be augmented. Only for systems
  // that implement nanivid experiment. Other systems may find no value in it.
  //
  feature nanivid
  {
    description "This nanoscale system is part of nanivid experiment.";
  }

  //
  // Here, we simply want to report a non standard property for this model.
  // Note that our brownian motion is also considered a kind of motion, and
  // then, this keyword can also be reused to define a component!
  //
  identity brownian-motion 
  {
    base types:diffusion;             // A component
    base types:non-standard-physics;  // That is also listed as a definition
    description "A diffusion-based motion ruled by the laws of Brownian 
                 movement. Because it inherits from diffusion which 
                 itself inherits from motion, a component pointing to 
                 this type shall have access to motion metrics.";
  }

  //
  // Next identity defines a new type of message-carrier.
  //
  identity diffusion-from-concentrated-source 
  {
    base types:message-carrier;
    description "A transmitter emits a time-sensitive amount of solute that 
                 defines the intensity of a signal. Above a certain 
                 concentration, the transmitter signals a 'one', 'on' or 'true'
                 message, otherwise it can be considered 'zero', 'off', or 
                 'false'. The signal moves through the medium by diffusion and
                 the receiver measures the corresponding 'concentration' as a 
                 function of time.";
  }

  //
  // So because we define a new type of motion, we thought it was the perfect
  // moment to introduce a new type of metrics that is closely related to this
  // new component. Well... it is an empty shell, but still, it is a good
  // example.
  // 
  grouping brownian-motion-metrics
  {
    container brownian-motion-metrics
    {
      when "derived-from-or-self(../type-of-component, 'brownian-motion')";
      description "The parent component must have a leaf of type 'brownian-
                   motion' in order to be eligible to use this container.";
    }

    description "This is a placeholder for Brownian motion metrics being used 
                 as non-standard physics in this model.";
  }


  //
  // We are now ready to augment existing framework!
  // Note that in this example, we have no interest augmenting ietf interface.
  // 
  container nanivid
  {
    description "Redefined nanoscale-system for our nanivid experiment, in 
                 which we provide an extra subtree."; 

    uses system:system
    {
      augment components/component
      {
        if-feature nanivid;
        uses brownian-motion-metrics;

        description "Augment nanoscale system with the brownian motion defined
                     in NANIVID example.";
      }
    }
  }  
}
