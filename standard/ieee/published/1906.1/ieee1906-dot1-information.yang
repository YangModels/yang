module ieee1906-dot1-information
{
  yang-version 1.1;
  namespace "urn:ieee:std:1906.1:yang:ieee1906-dot1-information";
  prefix "ieee1906-dot1-information";

  import ieee1906-dot1-math {  prefix ieee1906-dot1-math;  }
  import ieee1906-dot1-si-units {  prefix ieee1906-dot1-si-units;  }

  organization "IEEE Std 1906.1-2015 - Recommended Practice for Nanoscale and Molecular Communication
                Framework Working Group";

  contact  "Stephen F. Bush <bushsf@research.ge.com>
	    Guillaume Mantelet <gmantelet@voltigeurnetworks.com>";

  description "Trying to define here whatever can be used in information theory.

               +------------------------+---+-----------+---------------------------------------+
               | name                   |sym| units     | equation                              |
               +------------------------+---+-----------+---------------------------------------+
               | amount-of-information  |   | bit       |                                       |
               | bandwidth              |   | bit.s-1   |                                       |
               | information-density    |   | bit.m-x   |                                       |
               | bandwidth-delay-product|   | bit       |                                       |
               +------------------------+---+-----------+---------------------------------------+
               ";

  revision 2020-12-07
  {
    description "Initial version.";

	reference "";
  }

  typedef amount-of-information
  {
    type ieee1906-dot1-math:scalar;
    ieee1906-dot1-si-units:units bit;
    description "The amount of information of a system in bits.";
  }

  typedef bandwidth
  {
    type ieee1906-dot1-math:scalar;
	ieee1906-dot1-si-units:units bit/second;
	description "Bandwidth in bits per second of a communication channel.";
  }

  grouping information-density
  {
    ieee1906-dot1-math:equation information-density;
    ieee1906-dot1-si-units:units m^-X;                // This is a surface, it can have two or more dimensions, hence the 'X'
    ieee1906-dot1-math:value;                         // So basically, what I am trying to tell you here (without new required 
    ieee1906-dot1-math:expression;                    // tools) is that your math:equation is either a math:value or an
    container information-density                     // expression, with following container to stay vanilla.
    {
      uses ieee1906-dot1-math:surface;
      leaf amount-of-information
      {
        type amount-of-information;
        description "Amount of information.";
      }
    }

    description "A reusable equation representing information density.";
  }

  grouping bandwidth-delay-product 
  {
    ieee1906-dot1-math:equation bandwidth-delay-product 
    {
      ieee1906-dot1-si-units:units bit;
      ieee1906-dot1-math:value;

      ieee1906-dot1-math:expression 
      {
        leaf bandwidth 
        {
          type bandwidth;
          description "The bits per second transported by the 
                       nanoscale communication channel.";
        }

        leaf delay 
        {
          type ieee1906-dot1-si-units:time;
          description "The time for a message to propagate from 
                       one end of a channel to the other.";
        }
      }
    }
    description "A reusable equation representing bandwidth delay product.";
  }
}
