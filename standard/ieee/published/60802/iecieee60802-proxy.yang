module iecieee60802-proxy {
  yang-version 1.1;
  namespace "urn:ieee:std:60802:yang:iecieee60802-proxy";
  prefix pr;

  import ieee802-types {
    prefix ieee;
  }
  import ietf-inet-types {
    prefix inet;
  }

  organization
    "IEEE 802.1 Working Group and IEC subcommittee 65C:
     Industrial networks, of IEC technical committee 65:
     Industrial-process measurement, control and automation";
  contact
    "WG-URL: http://ieee802.org/1/
     WG-EMail: stds-802-1-l@ieee.org

     Contact: IEEE 802.1 Working Group Chair
              Postal: C/O IEEE 802.1 Working Group
              IEEE Standards Association
              445 Hoes Lane
              Piscataway, NJ 08854
              USA

     E-mail: stds-802-1-chairs@ieee.org";
  description
    "Configuration and capability information for IEC/IEEE 60802 proxy
     targets as specified in IEC/IEEE 60802.

     Copyright (C) IEC/IEEE (2025).
     This version of this YANG module is part of IEC/IEEE 60802;
     see the standard itself for full legal notices.";

  revision 2025-03-12 {
    description
      "Published as part of IEC/IEEE 60802-2025.
       The following reference statement identifies each referenced
       IEEE Standard as updated by applicable amendments.";
    reference
      "IEC/IEEE 60802 TSN profile for industrial automation:
       IEC/IEEE 60802-2025.
       IEEE Std 802.1Q Bridges and Bridged Networks:
       IEEE Std 802.1Q-2022, IEEE Std 802.1Qcz-2023,
       IEEE Std 802.1Qcw-2023, IEEE Std 802.1Qdj-2024,
       IEEE Std 802.1Qdx-2024, IEEE Std 802.1Qdy-2025.";
  }

  container proxy {
    presence "The presence of this container indicates that this IA station provides proxy functionality for proxy targets";
    description
      "This container provides information about a
       60802 IA station with proxy functionality.";
    reference
      "IEC/IEEE 60802 - YANG Data Model";
    leaf max-num-proxy-targets {
      type uint16;
      config false;
      description
        "The value indicates how many proxy targets can be handled by this proxy component.";
      reference
        "6.4.10.3.9.1 of IEC/IEEE 60802";
    }
    list proxy-types {
      key "proxy-type";
      config false;
      description
        "Supported proxy types";
      leaf proxy-type {
        type string {
          pattern '[0-9A-F]{2}(-[0-9A-F]{2}){2}';
        }
        config false;
        description
          "OID of proxy targets handled by this proxy.";
        reference
          "6.4.10.3.9.2 of IEC/IEEE 60802";
      }
      list proxy-targets {
        key "device";
        description
          "List of proxy targets that are connected to this proxy";
        leaf device {
          type string;
          description
            "The identification of the device.";
          reference
            "6.4.10.3.9.3 of IEC/IEEE 60802";
        }
        leaf device-type {
          type string;
          description
            "The type of the device.";
          reference
            "6.4.10.3.9.4 of IEC/IEEE 60802";
        }
        container proxy-addr {
          description
            "This container provides the address information 
             that is used by the CNC to configure the proxy target.";
          leaf ip-addr {
            type inet:ip-address;
            description
              "The ip-address that is used by the CNC to configure 
               the proxy target.";
            reference
              "6.4.10.3.9.5 of IEC/IEEE 60802";
          }
          leaf port {
            type inet:port-number;
            description
              "The port-number that is used by the CNC to configure 
               the proxy target.";
            reference
              "6.4.10.3.9.6 of IEC/IEEE 60802";
          }
        }
        container device-addr {
          description
            "This container provides the address information 
             that is used by the proxy to address the proxy target.";
          leaf ip-addr {
            type inet:ip-address;
            description
              "The ip-address that is used by the proxy to address 
               the proxy target.";
            reference
              "6.4.10.3.9.7 of IEC/IEEE 60802";
          }
          leaf mac-addr {
            type ieee:mac-address;
            description
              "The mac-address that is used by the proxy to address
               the proxy target.";
            reference
              "6.4.10.3.9.8 of IEC/IEEE 60802";
          }
        }
      }
    }
  }
}
