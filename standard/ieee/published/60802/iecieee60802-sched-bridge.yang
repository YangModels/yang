module iecieee60802-sched-bridge {
  yang-version 1.1;
  namespace "urn:ieee:std:60802:yang:iecieee60802-sched-bridge";
  prefix ia-sched-bridge;

  import ieee802-types {
    prefix ieee802;
  }
  import ieee802-dot1q-bridge {
    prefix bridge;
  }
  import ieee802-dot1q-sched-bridge {
    prefix sched-bridge;
  }
  import ietf-interfaces {
    prefix if;
  }

  organization
    "IEEE 802.1 Working Group and IEC subcommittee 65C:
     Industrial networks, of IEC technical committee 65:
     Industrial-process measurement, control and automation";
  contact
    "WG-URL: http://ieee802.org/1/
     WG-EMail: stds-802-1-l@ieee.org

     Contact: IEEE 802.1 Working Group Chair
              Postal: C/O IEEE 802.1 Working Group
              IEEE Standards Association
              445 Hoes Lane
              Piscataway, NJ 08854
              USA

     E-mail: stds-802-1-chairs@ieee.org";
  description
    "Management objects that provide information about IEC/IEEE 60802
     IA-Stations as specified in IEC/IEEE 60802.

     Copyright (C) IEC/IEEE (2025).
     This version of this YANG module is part of IEC/IEEE 60802;
     see the standard itself for full legal notices.";

  revision 2025-03-12 {
    description "Published as part of IEC/IEEE 60802-2025.
      The following reference statement identifies each referenced
      IEEE Standard as updated by applicable amendments.";
    reference
      "IEC/IEEE 60802 TSN profile for industrial automation:
      IEC/IEEE 60802-2025.
      IEEE Std 802.1Q Bridges and Bridged Networks:
      IEEE Std 802.1Q-2022, IEEE Std 802.1Qcz-2023,
      IEEE Std 802.1Qcw-2023, IEEE Std 802.1Qdj-2024,
      IEEE Std 802.1Qdx-2024, IEEE Std 802.1Qdy-2025.";
  }

  augment "/if:interfaces/if:interface/bridge:bridge-port/sched-bridge:gate-parameter-table" {
    description
      "Augment IEEE Std 802.1 bridge/gate-parameter-table.";
    list min-gating-times {
      key "speed";
      config false;
      description
        "The list of minimum gating times per supported line speed.";
      reference
        "6.4.10.3.4.3 of IEC/IEEE 60802";
      leaf speed {
        type uint32;
        config false;
        description
          "This value is the line speed in Mbps.";
      }
      container min-cycle-time {
        uses ieee802:rational-grouping;
        description
          "The value is the minimum value supported by this port of
           the AdminCycleTime and OperCycleTime parameters given as
           rational number of seconds.";
        reference
          "Item a) in 6.4.10.3.4.3 of IEC/IEEE 60802";
      }
      leaf min-interval-time {
        type uint32;
        description
          "The value is the minimum value supported by this port of
           the TimeIntervalValue parameter in nanoseconds.";
        reference
          "Item b) in 6.4.10.3.4.3 of IEC/IEEE 60802";
      }
    }
  }
}
