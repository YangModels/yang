submodule bbf-vdsl-status-monitoring {
  yang-version 1.1;

  belongs-to bbf-vdsl {
    prefix bbf-vdsl;
  }

  import ietf-interfaces {
    prefix if;
  }

  import bbf-fastdsl {
    prefix bbf-fastdsl;
  }

  include bbf-vdsl-base-body;
  include bbf-vdsl-line-status-body;
  include bbf-vdsl-xtu-line-status-body;
  include bbf-vdsl-xtu-band-status-body;
  include bbf-vdsl-xtu-annex-c-status-body;
  include bbf-vdsl-xtu-channel-status-body;

  include bbf-vdsl-line;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for
     managing status monitoring for VDSL interfaces.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  // 6 Object model for xDSL Status Monitoring

  // 6.1 xTU Line Status

  augment '/if:interfaces-state/if:interface/bbf-fastdsl:line/bbf-'
        + 'vdsl:line' {
    description
      "6.1 xTU Line Status.";

    container status {
      description
        "The xTU Line Status object represents current line status
         and measurements at a particular xTU.";

      uses line-status;
      uses xtu-line-status;

      container xtu-c {
        description
          "xTU-C Line Status.";
        uses xtu-c-status;
        // 6.1.1 xTU Band Status
        container band-status {
          config false;
          description
            "Per band status parameters. For ADSL systems,
             a single parameter is defined for band = 0.";
          uses xtu-band-status;
        }
      }
      container xtu-r {
        description
          "xTU-R Line Status.";
        uses xtu-r-status;
        // 6.1.1 xTU Band Status
        container band-status {
          config false;
          description
            "Per band status parameters. For ADSL systems,
             a single parameter is defined for band = 0.";
          uses xtu-band-status;
        }
      }
    }
  }

  // 6.1.2 xTU Channel Status

  augment '/if:interfaces-state/if:interface/bbf-fastdsl:line/bbf-'
        + 'vdsl:line/bbf-vdsl:channel' {
    description
      "6.1.2 xTU Channel Status.";

    container status {
      description
        "xTU channel status.";

      container xtu-c {
        description
          "xTU-C channel status. This contains status parameters 
           for transmission in the upstream direction.";
        container upstream {
          description
            "These objects apply to the upstream direction of
             transmission.";
          uses xtu-channel-status;
          uses actual-ndr-inp-rein;
        }
      }

      container xtu-r {
        description
          "xTU-R channel status. This contains status parameters
           for transmission in the downstream direction.";
        container downstream {
          description
            "These objects apply to the downstream direction of
             transmission.";
          uses xtu-channel-status;
          uses actual-ndr-inp-rein;
        }
      }
    }
  }

  // 6.1.3 xTU Annex C G.992.3,5 Status

  augment '/if:interfaces-state/if:interface/bbf-fastdsl:line/bbf-'
        + 'vdsl:line/bbf-vdsl:status/bbf-vdsl:xtu-c' {
    description
      "6.1.3 xTU-C Annex C G.992.3,5 Status";

    uses xtu-annex-c-status;
  }

  augment '/if:interfaces-state/if:interface/bbf-fastdsl:line/bbf-'
        + 'vdsl:line/bbf-vdsl:status/bbf-vdsl:xtu-r' {
    description
      "6.1.3 xTU-R Annex C G.992.3,5 Status";

    uses xtu-annex-c-status;
  }
}
