submodule bbf-vdsl-spectrum-profiles {
  yang-version 1.1;

  belongs-to bbf-vdsl {
    prefix bbf-vdsl;
  }

  import bbf-yang-types {
    prefix bbf-yang;
  }

  include bbf-vdsl-base-body;
  include bbf-vdsl-line-spectrum-profile-body;
  include bbf-vdsl-mode-specific-psd-profile-body;
  include bbf-vdsl-upstream-power-back-off-profile-body;
  include bbf-vdsl-downstream-power-back-off-profile-body;
  include bbf-vdsl-radio-frequency-interference-profile-body;

  include bbf-vdsl-base;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for
     managing VDSL spectrum profiles.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef line-spectrum-profile-ref {
    type leafref {
      path '/bbf-vdsl:vdsl/bbf-vdsl:spectrum/bbf-vdsl:line-'
         + 'spectrum-profile/bbf-vdsl:name';
    }
    description
      "Line Spectrum Profile identifier.";
  }

  typedef mode-specific-psd-profile-ref {
    type leafref {
      path '/bbf-vdsl:vdsl/bbf-vdsl:spectrum/bbf-vdsl:mode-'
         + 'specific-psd-profile/bbf-vdsl:name';
    }
    description
      "Mode Specific PSD Profile identifier.";
  }

  typedef upstream-power-back-off-profile-ref {
    type leafref {
      path '/bbf-vdsl:vdsl/bbf-vdsl:spectrum/bbf-vdsl:upstream-'
         + 'power-back-off-profile/bbf-vdsl:name';
    }
    description
      "UPBO Profile identifier.";
  }

  typedef downstream-power-back-off-profile-ref {
    type leafref {
      path '/bbf-vdsl:vdsl/bbf-vdsl:spectrum/bbf-vdsl:downstream-'
         + 'power-back-off-profile/bbf-vdsl:name';
    }
    description
      "DPBO Profile identifier.";
  }

  typedef radio-frequency-interference-profile-ref {
    type leafref {
      path '/bbf-vdsl:vdsl/bbf-vdsl:spectrum/bbf-vdsl:radio-'
         + 'frequency-interference-profile/bbf-vdsl:name';
    }
    description
      "RFI Profile identifier.";
  }


  // 5.6 Spectrum related profiles

  augment '/bbf-vdsl:vdsl/bbf-vdsl:spectrum' {
    description
      "5.6 Spectrum related profiles.";

    list line-spectrum-profile {
      key "name";
      description
        "Line Spectrum Profile.";

      leaf name {
        type bbf-yang:string-ascii64;
        description
          "Line Spectrum Profile identifier.";
      }
      uses line-spectrum-profile;
    }

    list mode-specific-psd-profile {
      key "name";
      description
        "Mode Specific PSD Profile.";

      leaf name {
        type bbf-yang:string-ascii64;
        description
          "Mode Specific PSD Profile identifier.";
      }
      uses mode-specific-psd-profile;
    }

    list xtse {
      key "ts";
      leaf ts {
        type xts-descriptor;
        description
          "Transmission system type.";
        reference
          "ITU-T G.997.1 clause 7.3.1.1.1 xTU transmission system
           enabling (XTSE).";
      }

      leaf mode-specific-psd-profile {
        type bbf-vdsl:mode-specific-psd-profile-ref;
        mandatory true;
        description
          "Mode Specific PSD Profile identifier for this 
           transmission system.";
      }

      description
        "Defines the transmission system types to be allowed by the
         near-end xTU on this line, and defines the 
         mode-specific-psd-profile associated to each allowed
         transmission system type. Only the transmission systems 
         included in this list are allowed.";
    }

    list upstream-power-back-off-profile {
      key "name";
      description
        "UPBO Profile.";

      leaf name {
        type bbf-yang:string-ascii64;
        description
          "UPBO Profile identifier.";
      }

      uses upstream-power-back-off-profile;
    }

    list downstream-power-back-off-profile {
      key "name";
      description
        "DPBO Profile.";

      leaf name {
        type bbf-yang:string-ascii64;
        description
          "DPBO Profile identifier.";
      }

      uses downstream-power-back-off-profile;
    }

    list radio-frequency-interference-profile {
      key "name";
      description
        "RFI Profile.";

      leaf name {
        type bbf-yang:string-ascii64;
        description
          "RFI Profile identifier.";
      }

      uses radio-frequency-interference-profile;
    }
  }
}
