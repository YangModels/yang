submodule bbf-vdsl-xtu-annex-c-status-body {
  yang-version 1.1;
  belongs-to bbf-vdsl {
    prefix bbf-vdsl;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 6.1.3 xTU Annex C 
     G.992.3,5 Status.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping xtu-annex-c-status {
    description
      "The xTU Annex C G.992.3,5 Status object represents current
       measurements at a particular xTU.";

    /*
    FEXT Downstream Signal-to-Noise Ratio Margin (FEXT SNRMds)
    NEXT Downstream Signal-to-Noise Ratio Margin (NEXT SNRMds)
    FEXT Upstream Signal-to-Noise Ratio Margin (FEXT SNRMus)
    NEXT Upstream Signal-to-Noise Ratio Margin (NEXT SNRMus)
    FEXT Downstream Maximum Attainable Data Rate (FEXT ATTNDRds)
    NEXT Downstream Maximum Attainable Data Rate (NEXT ATTNDRds)
    FEXT Upstream Maximum Attainable Data Rate (FEXT ATTNDRus)
    NEXT Upstream Maximum Attainable Data Rate (NEXT ATTNDRus)
    FEXT Downstream Actual Power Spectral Density (FEXT ACTPSDds)
    NEXT Downstream Actual Power Spectral Density (NEXT ACTPSDds)
    FEXT Upstream Actual Power Spectral Density (FEXT ACTPSDus)
    NEXT Upstream Actual Power Spectral Density (NEXT ACTPSDus)
    FEXT Downstream Actual Aggregate Transmit Power (FEXT ACTATPds)
    NEXT Downstream Actual Aggregate Transmit Power (NEXT ACTATPds)
    FEXT Upstream Actual Aggregate Transmit Power (FEXT ACTATPus)
    NEXT Upstream Actual Aggregate Transmit Power (NEXT ACTATPus)
     */
  } // end grouping xtu-annex-c-status
} // end submodule xtu-annex-c-status-body
