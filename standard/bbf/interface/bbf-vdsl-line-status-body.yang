submodule bbf-vdsl-line-status-body {
  yang-version 1.1;
  belongs-to bbf-vdsl {
    prefix bbf-vdsl;
  }

  include bbf-vdsl-base-body;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 5.1 xDSL Line.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping line-status {

    description
      "The xDSL Line status object represents status/state objects 
       for an individual physical transmission line.";

    leaf xdsl-transmission-system {
      type xts-descriptor;
      description
        "This indicates the current xDSL Transmission System.";
      reference
        "ITU-T G.997.1 clause 7.3.1.1.1 xTU transmission system
         enabling (XTSE)";
    }

    leaf line-power-management-state {
      type enumeration {
        enum "L0" {
          description
            "Synchronized - This line state (L0) is when
             the line has full transmission (i.e., showtime).";
        }
        enum "L1" {
          description
            "Power down data transmission - This line state
             (L1) is when there is transmission on the line but the
             net data rate is reduced (e.g., only for OAM and higher
             layer connection and session control). This state
             applies to [ITU-T G.992.2] only.";
        }
        enum "L2" {
          description
            "Power down data transmission - This line state
             (L2) is when there is transmission on the line but the
             net data rate is reduced (e.g., only for OAM and higher
             layer connection and session control). This state
             applies to [ITU-T G.992.3] and [ITU-T G.992.4] only.";
        }
        enum "L3" {
          description
            "No-power - This line state (L3) is when there
             is no power transmitted on the line at all.";
        }
      }
      description
        "This parameter identifies the power management state of
         the line.";
      reference
        "ITU-T G.997.1 clause 7.5.1.5 Line power management
         state";
    }

    leaf initialization-success-failure-cause {
      type enumeration {
        enum "0" {
          description
            "Successful";
        }
        enum "1" {
          description
            "Configuration error. This error occurs with
             inconsistencies in configuration parameters. For
             example, when the line is initialized in an xDSL
             transmission system where an xTU does not support the
             configured maximum delay or the configured minimum or
             maximum data rate for one or more bearer channels.";
        }
        enum "2" {
          description
            "Configuration not feasible on the line. This error
             occurs if the minimum data rate cannot be reached on
             the line with the minimum noise margin, maximum PSD
             level, maximum delay and maximum bit error ratio for
             one or more bearer channels.";
        }
        enum "3" {
          description
            "Communication problem. This error occurs, for example,
             due to corrupted messages or bad syntax messages or if
             no common mode can be selected in the G.994.1
             handshaking procedure or due to a timeout.";
        }
        enum "4" {
          description
            "No peer xTU detected. This error occurs if the peer
             xTU is not powered or not connected or if the line is
             too long to allow detection of a peer xTU.";
        }
        enum "5" {
          description
            "Any other or unknown initialization failure cause.";
        }
        enum "6" {
          description
            "ITU T G.998.4 retransmission mode was not selected
             while RTX_MODE = FORCED or with
             RTX_MODE = RTX_TESTMODE.";
        }
      }
      description
        "This parameter indicates whether the last full
         initialization procedure was successful. If the last
         initialization procedure was not successful, this
         parameter provides the reason.";
      reference
        "ITU-T G.997.1 clause 7.5.1.6 Initialization
         success/failure cause";
    }
  } // end grouping line-status
} // end submodule line-status-body
