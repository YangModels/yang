module bbf-vdsl {
  yang-version 1.1;

  namespace "urn:bbf:yang:bbf-vdsl";
  prefix bbf-vdsl;

  include bbf-vdsl-base-body;

  // 5 Object Model for xDSL Configuration Management

  // 5.1 xDSL Line (base)
  // 5.2 xDSL Channel (base)
  include bbf-vdsl-test-mode-body;
  include bbf-vdsl-channel-body;
  include bbf-vdsl-base;
  include bbf-vdsl-line;

  // 5.3 xDSL Termination Unit (xTU)
  include bbf-vdsl-inventory-body;
  include bbf-vdsl-xtu;

  // 5.5 Service related profiles
  include bbf-vdsl-data-rate-profile-body;
  include bbf-vdsl-service-profiles;

  // 5.6 Spectrum related profiles
  include bbf-vdsl-line-spectrum-profile-body;
  include bbf-vdsl-mode-specific-psd-profile-body;
  include bbf-vdsl-upstream-power-back-off-profile-body;
  include bbf-vdsl-downstream-power-back-off-profile-body;
  include bbf-vdsl-radio-frequency-interference-profile-body;
  include bbf-vdsl-spectrum-profiles;

  // 5.7 DSL Quality Management related profiles
  include bbf-vdsl-noise-margin-profile-body;
  include bbf-vdsl-impulse-noise-protection-delay-profile-body;
  include bbf-vdsl-virtual-noise-profile-body;
  include bbf-vdsl-sos-profile-body;
  include bbf-vdsl-impulse-noise-monitoring-profile-body;
  include bbf-vdsl-re-initialization-policy-profile-body;
  include bbf-vdsl-vectoring-profile-body;
  include bbf-vdsl-data-gathering-profile-body;
  include bbf-vdsl-quality-profiles;

  // 6 Object model for xDSL Status Monitoring
  include bbf-vdsl-line-status-body;
  include bbf-vdsl-xtu-line-status-body;
  include bbf-vdsl-xtu-band-status-body;
  include bbf-vdsl-xtu-annex-c-status-body;
  include bbf-vdsl-xtu-channel-status-body;
  include bbf-vdsl-status-monitoring;

  // 7 Object model for xDSL Performance Management
  include bbf-vdsl-xtu-line-performance-body;
  include bbf-vdsl-xtu-channel-performance-body;
  include bbf-vdsl-performance-management;

  // 8 Object model for xDSL Performance Threshold Management
  include bbf-vdsl-xtu-line-threshold-profile-body;
  include bbf-vdsl-xtu-channel-threshold-profile-body;
  include bbf-vdsl-threshold-management;

  // 9 Object model for xDSL Testing / Diagnostics
  include bbf-vdsl-xtu-sub-carrier-status-body;
  include bbf-vdsl-xtu-data-gathering-report-body;
  include bbf-vdsl-test-diagnostics;

  // 5.4 xDSL Line Configuration Vector
  // 8.1 xDSL Line Threshold Template
  include bbf-vdsl-pointers;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This module contains a collection of YANG definitions for 
     supporting Vector of Profiles for VDSL lines.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }
}
