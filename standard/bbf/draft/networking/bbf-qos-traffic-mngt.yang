module bbf-qos-traffic-mngt {
  yang-version 1.1;
  namespace "urn:bbf:yang:bbf-qos-traffic-mngt";

  prefix bbf-qos-tm;

  import ietf-interfaces {
    prefix if;
  }

  import iana-if-type {
    prefix ianaift;
  }

  import bbf-yang-types {
    prefix bbf-yang;
  }

  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "This module contains a collection of YANG definitions for 
     supporting the Broadband Forum requirements on the management of
     Quality of Service (QoS) as applicable to access network 
     equipment. As such, this module is specific to access network 
     equipment (e.g., BBF-specified Access Nodes and FTTdp DPUs).

     Specifically, this module contains a collection of functions for 
     QoS traffic management (TM).

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-383 Common YANG Modules project.

     Please see the revision information (given below) for further
     details of this release, e.g. documentation, license validity
     dates and availability of more recent draft or final releases.";

  revision 2017-05-09 {
    description
      "WT-383_draft1";
    reference
      "https://www.broadband-forum.org/software#WT-383_draft1";
  }

  feature pre-emption {
    description
      "This feature indicates whether the network element supports
       pre-emption.";
  }

  feature tc-id-2-queue-id-mapping-config {
    description
      "This feature indicates whether the network element supports 
       configuring traffic-class-id to queue-id mapping profiles.";
  }


  typedef queue-id {
    type uint32 {
      range "0..7";
    }
    description
      "An integer number identifying a queue within the context from 
       which traffic will be scheduled. It is an abstract identifier: 
       its value does NOT represent the priority of the queue itself.
       This queue-id value is determined by means of a 
       traffic-class-id to queue-id mapping profile.";
  }

  typedef traffic-class-id {
    type uint32 {
      range "0..7";
    }
    description
      "The identifier of a traffic class. A traffic class refers to
       a set of packets that are processed with the same Quality of 
       Service characteristic.";
  }

  typedef scheduling-priority {
    type uint8 {
      range "0..7";
    }
    description
      "This number represents the priority of the queue or a scheduler
       competing with others in the context of scheduling traffic.
       Value 7 means highest priority and 0 means lowest priority.";
  }

  typedef scheduling-weight {
    type uint8;
    description
      "If scheduling is to be performed from multiple queues or
       schedulers with the same priority, then the scheduling-weight 
       assigns a weight to each of them.";
  }

  identity bac-type {
    description
      "Base identity of a Buffer Acceptance Control (BAC) type.";
  }

  identity taildrop {
    base bac-type;
    description
      "Taildrop BAC type.";
  }

  identity red {
    base bac-type;
    description
      "Random Early Detection (RED) BAC type.";
  }

  identity wtaildrop {
    base bac-type;
    description
      "Weighted taildrop BAC type.";
  }


  identity wred {
    base bac-type;
    description
      "Weighted Random Early Detection (WRED) BAC type.";
  }


  grouping min-threshold {
    description
      "Definition of minimum threshold.";

    leaf min-threshold {
      type bbf-yang:percent;
      description
        "The threshold from which the system begins to discard 
         incoming packets in a random way.

         The value is a percentage to be calculated on the value of 
         the leaf max-queue-size of the queue on which the BAC is 
         applied.";
    }
  }

  grouping max-threshold {
    description
      "Definition of maximum threshold.";

    leaf max-threshold {
      type bbf-yang:percent;

      description
        "The threshold to discard all incoming packets.

         The value is a percentage to be calculated on the value of 
         the leaf max-queue-size.";
    }
  }

  grouping max-probability {
    description
      "Definition of maximum probability.";

    leaf max-probability {
      type bbf-yang:percent;

      description
        "The maximum discard probability of packets before the 
         maximum threshold is reached.";
    }
  }

  grouping common-random-early-detection-parameters {
    description
      "A set of parameters common to RED and WRED BAC algorithms.";

    uses min-threshold;

    uses max-threshold;

    uses max-probability;
  }

  container tm-profiles {
    description
      "A set of types of profiles for traffic management
       configuration.";

    list tc-id-2-queue-id-mapping-profile {
      if-feature "tc-id-2-queue-id-mapping-config";

      key "name";

      description
        "A list of traffic-class-id to queue-id mapping profiles.";

      leaf name {
        type bbf-yang:string-ascii64;
        description
          "The name of a traffic-class-id to queue-id mapping 
           profile.";
      }

      list mapping-entry {
        key "traffic-class-id";
        description
          "A traffic-class-id to queue-id mapping profile. One profile
           maps each of the traffic-class-ids to a queue-id.";

        leaf traffic-class-id {
          type traffic-class-id;
          description
            "A traffic-class-id.";
        }

        leaf local-queue-id {
          type queue-id;
          mandatory true;
          description
            "The identification of a queue locally within a parent 
             node context.";
        }
      }
    }

    list bac-entry {
      key "name";

      description
        "A list of BAC entries.";

      leaf name {
        type bbf-yang:string-ascii64;
        description
          "The name of a bac-entry.";
      }

      leaf max-queue-size {
        type uint32;
        units "bytes";
        description
          "The maximum queue length.";
      }

      choice bac-type {
        mandatory true;
        description
          "Choice of BAC types";

        case taildrop {
          description
            "Applicable when the BAC type is 'taildrop'.";

          container taildrop {
            description
              "Management objects associated with taildrop.";

            uses max-threshold;
          }
        }

        case red {
          description
            "Applicable when the BAC type is 'red'.";

          container red {
            description
              "Management objects associated with Random Early 
               Detection (RED).";

            uses common-random-early-detection-parameters;
          }
        }

        case wtaildrop {
          description
            "Applicable when the BAC type is 'wtaildrop'.";

          container wtaildrop {
            description
              "Management objects associated with weighted taildrop.";

            container color {
              description
                "Management objects associated with the marked color 
                 of the packet.";

              container green {
                description
                  "Green packets.";

                uses max-threshold;
              }

              container yellow {
                description
                  "Yellow packets.";

                uses max-threshold;
              }

              container red {
                description
                  "Red packets.";

                uses max-threshold;
              }
            }
          }
        }

        case wred {
          description
            "Applicable when the BAC type is 'wred'.";

          container wred {
            description
              "Management objects associated with Weighted 
               Random Early Detection.";

            container color {
              description
                "Management objects associated with the marked color 
                 of the packet.";

              container green {
                description
                  "Green packets.";

                uses common-random-early-detection-parameters;
              }

              container yellow {
                description
                  "Yellow packets.";

                uses common-random-early-detection-parameters;
              }

              container red {
                description
                  "Red packets.";

                uses common-random-early-detection-parameters;
              }
            }
          }
        }
      }
    }
  }

  grouping tc-id-2-queue-id-mapping-profile-ref {
    description
      "A reference to a traffic-class-id to queue-id mapping 
       profile.";

    leaf tc-id-2-queue-id-mapping-profile-name {
      if-feature "tc-id-2-queue-id-mapping-config";
      type leafref {
        path '/bbf-qos-tm:tm-profiles/bbf-qos-tm:tc-id-2-queue-id-'
           + 'mapping-profile/bbf-qos-tm:name';
      }
      description
        "The name of a referenced traffic-class-id to queue-id mapping
         profile.";
    }
  }

  grouping bac-ref {
    description
      "A reference to a bac-entry.";

    leaf bac-name {
      type leafref {
        path '/bbf-qos-tm:tm-profiles/bbf-qos-tm:bac-entry/bbf-qos-'
           + 'tm:name';
      }
      description
        "The name of a referenced BAC entry.";
    }
  }

  grouping scheduling-gen-attr {
    description
      "Configuration data for scheduling traffic from queues.";

    leaf priority {
      type scheduling-priority;
      description
        "The priority used to schedule packets from a queue or 
         scheduler, relative to the priority assigned to other queues 
         or schedulers that are defined in the same traffic scheduling
         context. For example the set of queues defined for a 
         particular interface form the context for scheduling outgoing
         traffic to this interface.";
    }

    leaf weight {
      type scheduling-weight;
      description
        "Queues or schedulers that are defined in a particular 
         context, e.g. queues defined to schedule outgoing traffic to 
         an interface, can have the same priority. The weight defines 
         the the portion of traffic that will be taken from this queue
         or scheduler by comparing the weight of this queue or 
         scheduler against the sum of the weights of all queues or 
         schedulers with the same scope and the same priority.";
    }
  }

  grouping queues {
    description
      "Configuration data for queues.";

    list queue {
      key "local-queue-id";

      description
        "A list of queues.";

      leaf local-queue-id {
        type queue-id;
        description
          "The identification of a queue within the context of this 
           list.";
      }

      uses bac-ref;

      choice queue-scheduling-cfg-type {
        description
          "Choice of queue scheduling types.";

        case inline {
          description
            "The queue parameters are directly configured here.";

          uses scheduling-gen-attr;
        }
      }

      leaf pre-emption {
        if-feature "pre-emption";
        type boolean;
        description
          "Indicates whether the transmission of a packets from this
           queue can be interrupted in favor of packets from a higher 
           priority queue.";
      }
    }
  }

  grouping tm-root {
    description
      "The root for traffic management data. 
       Traffic management involves the following aspects: 
       - the forwarding decision determined to egress a frame through
         an outgoing traffic container (which can be an interface).
       - the traffic container (which can be a bottleneck) is 
         associated to a scheduler resolving the contention of 
         different queues competing to access the traffic container. 
       - so after the outgoing traffic container is determined, the 
         system needs to determine in which queue of the traffic 
         container the frame must be directed. This takes place based 
         on the frame's traffic-class by means of the traffic-class-id
         to queue-id mapping concept.
       - at any time, the scheduler resolves which queue should 
         deliver the next frame to the egress traffic container by
         looking at the scheduling-priority and scheduling-weight
         of each of queues.
       The tm-root represents the scheduling stage directly attached 
       to the bottleneck resource (typically an interface).";

    container tm-root {
      description
        "The attributes of the root in the scheduling tree.";

      choice children-type {
        description
          "Choice of chidren types of a scheduler node.";

        case queues {
          description
            "In this mode the interface related to the tm-root can
             directly be selected by the forwarding process and has
             its own set of queues. Hence the scheduling of a frame
             from a forwarder to the egress queue takes place in a
             single stage.";
          uses queues;
        }
      }

      uses tc-id-2-queue-id-mapping-profile-ref;
    }
  }

  augment '/if:interfaces/if:interface' {
    when
      "derived-from-or-self(if:type, 'ianaift:ethernetCsmacd') or
       derived-from-or-self(if:type, 'ianaift:ieee8023adLag') or
       derived-from-or-self(if:type, 'ianaift:ptm') " {
      description
        "Augmentation for interfaces that can have queues assigned.";
    }
    description
      "Augments the interface with traffic management data.";

    uses tm-root;
  }
}
