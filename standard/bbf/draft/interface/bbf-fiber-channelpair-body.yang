submodule bbf-fiber-channelpair-body {
  yang-version 1.1;
  belongs-to bbf-fiber {
    prefix fiber;
  }


  import bbf-fiber-types {
    prefix fiber-types;
  }

  import ietf-interfaces {
    prefix if;
  }

  import bbf-fiber-if-type {
    prefix bbffiberift;
  }

  include bbf-fiber-wavelength-profile-body;



  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "This module contains channelpair data

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }


  grouping channelpair-config-data {
    description
      "All config data for a channelpair.";

    leaf channelgroup-ref {
      type if:interface-ref;
      must
        "/if:interfaces/if:interface[if:name=current()]
         /if:type='bbffiberift:channelgroup'" {
        error-message
          "must reference a channelgroup";
      }
      // [Temporary comment by Robert Peschi, 17 Feb 2017]
      // I am working on a (much) more elaborate "must" constraint
      // insuring that neither downsream channel-id, upstream
      // channel-id nor wavelength of different channelpairs can
      // conflict on the same channelgroup and that only one XGS-PON,
      // XG-PON and G-PON can be on same channelgroup.
      // I hope that I can get through and deliver it in a separate
      // upload.
      description
        "Reference to channel-group.";
    }
    leaf channelpartition-ref {
      type if:interface-ref;
      must
        "/if:interfaces/if:interface[if:name=current()]
         /if:type='bbffiberift:channelpartition'
         and
         /if:interfaces/if:interface[if:name=current()]
         /channelpartition/channelgroup-ref=../channelgroup-ref" {
        error-message
          "must reference a channelpartition and
           associated with same channelgroup-ref";
      }
      description
        "Reference to channel-partition.";
    }
    leaf wavelength-prof-ref {
      when
        "../channelpair-type=('fiber-types:ngpon2-twdm' or
         'fiber-types:ngpon2-ptp') or
         'fiber-types:xgs'";
      type leafref {
        path '/fiber:fiber-wavelength-profiles/fiber:wavelength-'
           + 'profile/fiber:name';
      }
      description
        "An NGPO2 channelpair needs to point to an existing wavelength
         profile. Similar for XGS-PON (ref: G.9807.1 A.8.2: Basic
         Wavelength and Optional Wavelength sets). The wavelength for
         XG-PON and G-PON is fixed per ITU-T standards and needs not
         be configured via a wavelength profile.";
    }
    leaf channelpair-type {
      type identityref {
        base fiber-types:channelpair-type-base;
      }
      mandatory true;
      description
        "Represents the type of channelpair
         (e.g. TWDM NG-PON2, PtP NG-PON2, XGS-PON, XG-PON,
         G-PON).";
    }
    leaf channelpair-linerate {
      when
        "../channelpair-type=('fiber-types:ngpon2-twdm'or
                                     'fiber-types:ngpon2-ptp')";
      type identityref {
        base fiber-types:channelpair-linerate-profile-base;
      }
      default "fiber-types:unplanned-cp-linerate";
      description
        "Represents the planned downstream/upstream channel pair
         speed for NG-PON2. The line rates for
             XGS-PON (DS:10Gbps/US:10Gbps),
             XG-PON(DS:10Gbps/US:2.5Gbps) and
             G-PON (DS:2.5Gbps/US:1.2Gbps)
         are fixed per ITU-T standards and need not be configured.";
    }

    leaf gpon-ponid-interval {
      when "../channelpair-type='fiber-types:gpon'";
      type uint16 {
        range "0..60";
      }
      units "seconds";
      default "0";
      description
        "This attribute is used to specify the frequency of
         transmission of the periodic downstream PON-ID PLOAM
         message for this G-PON. See G.984.3 C1. The default value
         '0' allows not to generate this PLOAM message, fulfilling
         G.984.3 C2 requirement.
         In XG-PON, XGS-PON and NG-PON2, this leaf is not relevant
         since pon-id is carried in the header of each frame rather
         than via PLOAM messages.";
    }

    leaf gpon-ponid-odn-class {
      when "../channelpair-type='fiber-types:gpon'";
      type fiber-types:ponid-odn-class-type;
      default "class-auto";
      description
        "This attribute is used to specify the Optical Class field
         of the G-PON laser in the PON-ID PLOAM message for this
         G-PON.
         In XG-PON, XGS-PON and NG-PON2, this leaf is not relevant
         since ponid-odn-class is carried in the header of each
         frame rather than via PLOAM messages.";
    }
  }

  grouping channelpair-oper-data {
    description
      "All oper data for a channelpair";

    leaf actual-downstream-wavelength {
      type uint32 {
        range "0 | 148000..162000";
      }
      default "0";
      description
        "Represents the Actual Downstream wavelength for the
         channelpair for any of the NG-PON2, XGS-PON, XG-PON or
         G-PON case. It is expressed in hundredths of nm to fit
         ITU-T precision requirements.";
    }

    leaf primary-ct-assigned {
      type boolean;
      default "false";
      description
        "When true this means that a channeltermination with
         Primary type B role has been assigned to this channelpair.
         More details over type B protection are available in
         G.989.3 section 18.2, per ITU Amendment 1 (11/2016).";
    }

    leaf secondary-ct-assigned {
      type boolean;
      default "false";
      description
        "When true this means that a channeltermination with
         Secondary type B role has been assigned to this
         channelpair.
         More details over type B protection are available in
         G.989.3 section 18.2, per ITU Amendment 1 (11/2016).";
    }
  }
}
