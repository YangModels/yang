submodule bbf-fiber-ontani-body {
  yang-version 1.1;
  belongs-to bbf-fiber {
    prefix fiber;
  }

  include bbf-fiber-tcont-body;
  include bbf-fiber-gemport-body;

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "This module contains the data of the actual ONUs.
     The actual ONU is 1-1 associated to the ONU unique ontani
     interface. This module should not be confused with the
     bbf-fiber-v-ontani-body which contains the data of the ONU image
     seen by the OLT

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  grouping ontani-data {
    description
      "All config data for an actual ONU.";
    uses ontani-config;
  }

  grouping ontani-oper-data {
    description
      "All oper data for an actual ONU.";
    uses ontani-oper;
  }

  grouping ontani-config {
    container ontani-config {
      leaf upstream-fec-indicator {
        type boolean;
        default "false";
        description
          "Used to Enable/Disable use of FEC in Upstream
           direction for this specific ONU.";
      }
      leaf mgnt-gemport-aes-indicator {
        type boolean;
        default "false";
        description
          "Used to designate whether AES should be
           enabled/disabled for all bi-directional
           GEM ports associated with this ONU.
           NOTE: this setting excludes the GEM ports
           associated with dynamic multicast and incidental
           broadcast.";
      }
      description
        "ONU config container.";
    }
    description
      ".";
  }

  grouping ontani-oper {
    container ontani-oper {
      config false;
      leaf onu-id {
        type uint32 {
          range "0..1020";
        }
        description
          "This is a 10-bit identifier that
           the OLT assigns to an ONU during
           the ONU's activation using the
           Assign_ONU-ID PLOAM message.";
        reference
          "G.989.3 section 6.1.5.6";
      }
      leaf channel-partition-id {
        type uint8;
        description
          "An index of the operator-specified channel
           subset in a NG-PON2 system.  During operation,
           the ONUs can be re-tuned between the channels within
           a channel partition, but not across the boundaries
           of the channel partition.";
      }
      description
        "All oper data for an ONU.";
    }
    description
      ".";
  }
}
