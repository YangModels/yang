submodule bbf-fiber-channeltermination-body {
  yang-version 1.1;

  belongs-to bbf-fiber {
    prefix fiber;
  }

  import ietf-interfaces {
    prefix if;
  }

  import bbf-fiber-types {
    prefix fiber-types;
  }

  import bbf-fiber-if-type {
    prefix bbffiberift;
  }

  import ietf-inet-types {
    prefix ietf-inet;
  }

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "This module contains channeltermination data

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  grouping channeltermination-config-data {
    description
      "All config data for a channeltermination";

    leaf channelpair-ref {
      type if:interface-ref;
      must
        "/if:interfaces/if:interface[if:name=current()]/
          if:type='bbffiberift:channelpair' and
         ( ../fiber:meant-for-type-b-primary-role and
           not(/if:interfaces-state/if:interface
                                   [if:name=current()]/
                fiber:channelpair/fiber:primary-ct-assigned) or
           not(../fiber:meant-for-type-b-primary-role) and
               not(/if:interfaces-state/if:interface
                    [if:name=current()]/fiber:channelpair/
                    fiber:secondary-ct-assigned))" {
        error-message
          "must reference a channelpair interface and
           the intended type B role of the CT must not
           yet be fulfilled in the channelpair";
      }
      // the use of channelpair oper states makes xPON model
      // efficient and scalable by avoiding walking through
      // entire if:interfaces list to enforce this must statement
      description
        "Reference to a channelpair.";
    }

    leaf meant-for-type-b-primary-role {
      type boolean;
      description
        "When true, the channeltermination is meant to play type B
         protection Primary role when it refers to a channelpair.
         When false, the channeltermination is meant to play
         type B protection Secondary role when it refers to a
         channelpair.";
    }

    leaf ngpon2-twdm-admin-label {
      when
        "/if:interfaces/if:interface[if:name = current()/../
          fiber:channelpair-ref]/fiber:channelpair/
          fiber:channelpair-type = 'fiber-types:ngpon2-twdm'";
      type uint32 {
        range "0..268435455";
        // this is 2**28-1
      }
      description
        "For TWDM NG-PON2, the admin-label is configurable and is
         28 bit long. It is the configurable part of the PON-ID
         which is available as state data.";
      reference
        "G.989.3 section 6.1.5.3";
    }

    leaf ngpon2-ptp-admin-label {
      when
        "/if:interfaces/if:interface[if:name = current()/../
          fiber:channelpair-ref]/fiber:channelpair/
          fiber:channelpair-type = 'fiber-types:ngpon2-ptp'";
      type uint32 {
        range "0..4194303";
        // this is 2**22-1
      }
      description
        "For PtP NG-PON2, the admin-label is configurable and is
         22 bit long. It is the configurable part of the PON-ID
         which is available as state data.";
      reference
        "G.989.3 section 6.1.5.3";
    }

    leaf xgs-ponid {
      when
        "/if:interfaces/if:interface[if:name = current()/../
         fiber:channelpair-ref]/fiber:channelpair/
         fiber:channelpair-type = 'fiber-types:xgs'";
      type uint32 {
        range "0..4294967295";
        // this is 2**32-1
      }
      description
        "For XGS-PON, the ponid is entirely configurable and is
         32 bit long. The PON-ID is also available as state
         data.";
      reference
        "G.9807.1 section C.10.1.1.1.3";
    }

    leaf xgpon-ponid {
      when
        "/if:interfaces/if:interface[if:name = current()/../
          fiber:channelpair-ref]/fiber:channelpair/
          fiber:channelpair-type = 'fiber-types:xgpon'";
      type uint32 {
        range "0..4294967295";
        // this is 2**32-1
      }
      description
        "For XG-PON, the ponid is entirely configurable and is
         32 bit long. The PON-ID is also available as state
         data.";
      reference
        "G.987.3 section E.2";
    }

    leaf gpon-ponid {
      when
        "/if:interfaces/if:interface[if:name = current()/../
          fiber:channelpair-ref]/fiber:channelpair/
          fiber:channelpair-type = 'fiber-types:gpon'";
      type fiber-types:string7only;
      // any binary value over 7 bytes
      description
        "For G-PON, the ponid is entirely configurable and is
         7 bytes long. The PON-ID is also available as state
         data.";
      reference
        "G.984.3 section C.2.2";
    }


    leaf pon-tag {
      when
        "/if:interfaces/if:interface[if:name = current()/../
          fiber:channelpair-ref]/fiber:channelpair/
          fiber:channelpair-type != 'fiber-types:gpon'";
      type string {
        pattern '[0-9a-fA-F]{16}';
      }
      description
        "8 bytes.  Each octet is represented by two hex values.
         Used to specify channelpair-TAG attribute in NG-PON2,
         XGS-PON and XG-PON downstream PLOAM messages.
         The PON-TAG is not relevant for G-PON.";
    }

    leaf ber-calc-period {
      // Temporary comment from Robert Peschi (per Sam Chen Jira's)
      // 12 March 2017]: ITU ref welcome...
      type uint32 {
        range "1..864000";
      }
      units "tenths of a second";
      default "10";
      description
        "Measurement period used to determine if an SDi alarm
         has occurred for an ONT.";
    }

    leaf location {
      type identityref {
        base fiber-types:location-base;
      }
      description
        "Indicates whether the CT is physically inside the OLT i.e.
         can be related to a port in the OLT hardware model or
         physically part of another OLT.";
    }

    leaf url-to-reach {
      when "../location = 'fiber-types:outside-olt'";
      type ietf-inet:uri;
      description
        "Indicates where to reach the remote CT, part of another
         OLT.";
    }
  }

  grouping channeltermination-oper-data {
    description
      "All oper data for a channeltermination";

    leaf ponid-display {
      type fiber-types:ponid-display-type;
      description
        "The PON-ID of the channeltermination.
         Per G.989.3, G.9807.1, G.987.3 and G.984.3, depending of the
         xPON type some part of this object is configured by the
         operator and the other part is genuine operational data
         determined by the system.";
    }

    leaf type-b-state {
      type identityref {
        base fiber-types:type-b-state-base;
      }
      description
        "The type B protection state of the CT; it will typically
         be active/standby. When the channeltermination is not yet
         referring to a channelpair, it is not part of any type B
         protection scheme (and not usable either, btw); in that
         case its type-b-state has the value 'not-part-of-type-b.
         More details over type B protection are available in
         G.989.3 section 18.2, per ITU Amendment 1 (11/2016)";
    }
  }
}
