submodule bbf-fiber-base {
  yang-version 1.1;
  belongs-to bbf-fiber {
    prefix fiber;
  }

  import ietf-interfaces {
    prefix if;
  }

  import bbf-fiber-if-type {
    prefix bbffiberift;
  }

  include bbf-fiber-wavelength-profile-body;
  include bbf-fiber-traffic-descriptor-profile-body;
  include bbf-fiber-tcont-body;
  include bbf-fiber-channelgroup-body;
  include bbf-fiber-channelpartition-body;
  include bbf-fiber-channelpair-body;
  include bbf-fiber-channeltermination-body;
  include bbf-fiber-ontani-body;
  include bbf-fiber-v-ontani-body;

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "This module contains a collection of YANG definitions for
     managing top level G-PON/NG-PON2 configuration and augmentations
     to ietf-interfaces.

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  augment '/if:interfaces/if:interface' {
    when "if:type = 'bbffiberift:channelgroup'";
    //when 'derived-from-or-self(if:type,"bbffiberift:channelgroup")';
    description
      "Configuration of xPON channelgroup.";

    container channelgroup {
      presence "Indicates that the interface is of type channelgroup";
      description
        "Channelgroup configuration data for all xPON variants
         (NG-PON2, XGS-PON, XG-PON and G-PON).";
      uses channelgroup-config-data;
    }
  }

  augment '/if:interfaces/if:interface' {
    when "if:type = 'bbffiberift:channelpartition'";
    description
      "Configuration of xPON channelpartition.";

    container channelpartition {
      presence
        "Indicates that the interface is of type
         channelpartition";
      description
        "Channelpartition configuration data for all xPON variants
         (NG-PON2, XGS-PON, XG-PON and G-PON).";
      uses channelpartition-config-data;
    }
  }

  augment '/if:interfaces/if:interface' {
    when "if:type = 'bbffiberift:channelpair'";
    description
      "Data nodes for the configuration of xPON channelpair.";

    container channelpair {
      presence "Indicates that the interface is of type channelpair";
      description
        "Channelpair configuration data for all xPON variants
         (NG-PON2, XGS-PON, XG-PON and G-PON).";

      uses channelpair-config-data;
    }
  }

  augment '/if:interfaces/if:interface' {
    when "if:type = 'bbffiberift:channeltermination'";
    description
      "Data nodes for the configuration of xPON channeltermination.";

    container channeltermination {
      presence
        "Indicates that the interface is of type
         channeltermination";
      description
        "Channeltermination configuration data for all xPON variants
         (NG-PON2, XGS-PON, XG-PON and G-PON).";

      uses channeltermination-config-data;
    }
  }

  augment '/if:interfaces/if:interface' {
    when "if:type = 'bbffiberift:ontani'";
    description
      "Data nodes for the configuration of ONTs.";

    container ontani {
      presence
        "If present, indicates that the interface is of type
         ONT ANI";
      description
        "ONT ANI configuration.";
      uses ontani-data;
    }
  }

  augment '/if:interfaces/if:interface' {
    when "if:type = 'bbffiberift:v-ontani'";
    description
      "Data nodes for configuring ONTs on the OLT.";

    container v-ontani {
      presence "Indicates that the interface is of type virtual ANI";
      description
        "Virtual ANI configuration.";
      uses v-ontani-config-data;
    }
  }

  /*
   * operational data to be updated
   */

  augment '/if:interfaces-state/if:interface' {
    when "if:type = 'bbffiberift:channelgroup'";
    description
      "Data nodes for the operational state of xPON lines.";
    container channelgroup {
      presence "Indicates that the interface supports a xPON line";

      description
        "Line operational state data for xPON interfaces.";
      uses channelgroup-oper-data;
    }
  }

  augment '/if:interfaces-state/if:interface' {
    when "if:type = 'bbffiberift:channelpartition'";
    description
      "Data nodes for the operational state of channelgroup";
    container channelpartition {
      presence
        "Indicates that the interface supports a channel
         group";

      description
        "Line operational state data for channel-group interfaces.";
      uses channelpartition-oper-data;
    }
  }

  augment '/if:interfaces-state/if:interface' {
    when "if:type = 'bbffiberift:channelpair'";
    description
      "Data nodes for the operational state of channelpair lines.";
    container channelpair {
      presence "Indicates that the interface supports a channel pair";

      description
        "Line operational state data for channel pair interfaces.";
      uses channelpair-oper-data;
    }
  }

  augment '/if:interfaces-state/if:interface' {
    when "if:type = 'bbffiberift:channeltermination'";
    description
      "Operational state of channeltermination lines.";
    container channeltermination {
      presence
        "Indicates that the interface supports a
         channeltermination";

      description
        "Line operational state data for channeltermination
         interfaces.";
      uses channeltermination-oper-data;
    }
  }

  augment '/if:interfaces-state/if:interface' {
    when "if:type = 'bbffiberift:ontani'";
    description
      "Data nodes for the ONT operational state.";
    container ontani {
      presence "Indicates that the interface supports an ONT ANI";

      description
        "Line operational state data for ONT ANI interface.";
      uses ontani-oper-data;
    }
  }

  augment '/if:interfaces-state/if:interface' {
    when "if:type = 'bbffiberift:v-ontani'";
    description
      "Data nodes for the ONT operational state as seen by
       the OLT.";
    container v-ontani {
      presence "Indicates that the interface supports a virtual ANI";

      description
        "Line operational state data for virtual ANI interface.";
      uses v-ontani-oper-data;
    }
  }
}
