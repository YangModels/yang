module bbf-fiber-if-type {
  yang-version 1.1;
  namespace "urn:bbf:yang:bbf-fiber-if-type";
  prefix bbffiberitf;

  import ietf-interfaces {
    prefix if;
  }

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "A YANG module which defines xPON interface types that are needed
     for BBF applications but are not defined in iana-if-type. Some
     day this module could be merged with 'urn:bbf:yang:bbf-if-type'
     module.

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  identity bbf-fiber-interface-type {
    base if:interface-type;
    description
      "This identity is used as a base for all xPON interface types
       defined by the BBF that are not in the 'ifType definitions'
       registry maintained by IANA.";
  }

  identity channelgroup {
    base bbf-fiber-interface-type;
    description
      "A set of channel pairs carried over a common fiber.";
  }

  identity channelpartition {
    base bbf-fiber-interface-type;
    description
      "Any of the operator-specified non-overlapping subsets of TWDM 
       or PtP WDM channels in an NG-PON2 system.";
  }

  identity channelpair {
    base bbf-fiber-interface-type;
    description
      "A set of one downstream wavelength channel and one upstream 
       wavelength channel that provides connectivity between an OLT 
       and one or more ONUs.";
  }

  identity channeltermination {
    base bbf-fiber-interface-type;
    description
      "A logical function that resides at the OLT network element and 
       terminates a single PtP WDM channel in a PtP WDM system or a 
       single TWDM channel in a TWDM system.";
  }

  identity ontani {
    base bbf-fiber-interface-type;
    description
      "The Access Network Interface located on the ONT.";
  }

  identity v-ontani {
    base bbf-fiber-interface-type;
    description
      "A virtual representation of the 'ontani' on the OLT.";
  }
}
