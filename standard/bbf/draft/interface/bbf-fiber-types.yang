module bbf-fiber-types {
  yang-version 1.1;
  namespace "urn:bbf:yang:bbf-fiber-types";
  prefix fiber-types;

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "An experimental YANG module supporting xPON.

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  identity type-b-state-base {
    description
      "This identity is used as the base for possible
       channelterminations states for type B protection.";
  }
  identity active {
    base type-b-state-base;
    description
      "This identity is used to denote active state in type B
       protection.";
  }
  identity standby {
    base type-b-state-base;
    description
      "This identity is used to denote standby state in type B
       protection.";
  }
  identity not-part-of-type-b {
    base type-b-state-base;
    description
      "This identity is used to denote that the object is not part
       of a type B protection scheme.";
    // this is the case when a channeltermination does not (yet) refer
    // to a channelpair
  }


  identity location-base {
    description
      "This identity is used as the possible locations of an
       object.";
  }
  identity inside-olt {
    base location-base;
    description
      "This identity is used to denote a location physically inside
       the OLT shelf.";
  }
  identity outside-olt {
    base location-base;
    description
      "This identity is used to denote a location physically outside
       the OLT shelf.";
  }


  identity channelpair-type-base {
    description
      "This identity is used to qualify the possible types of a
       channelpair.";
  }
  identity ngpon2-twdm {
    base channelpair-type-base;
    description
      "This identity is used to denote a TWDM NG-PON2 channelpair,
       per G.989.3.";
  }
  identity ngpon2-ptp {
    base channelpair-type-base;
    description
      "This identity is used to denote a PtP NG-PON2 channelpair, per
       G.989.3.";
  }
  identity xgs {
    base channelpair-type-base;
    description
      "This identity is used to denote an XGS-PON channelpair,
       per G.9807.1.";
  }
  identity xgpon {
    base channelpair-type-base;
    description
      "This identity is used to denote an XG-PON channelpair,
       per G.987.3.";
  }
  identity gpon {
    base channelpair-type-base;
    description
      "This identity is used to denote an G-PON channelpair,
       per G.984.3.";
  }


  identity channelpair-linerate-profile-base {
    description
      "This identity is used to define the possible combinations
       of DS and US line-rates for an NG-PON2 channelpair.";
  }
  identity unplanned-cp-linerate {
    base channelpair-linerate-profile-base;
    description
      "This identity is used to denote an NG-PON2 channelpair with
       yet undefined DS and US linerates.";
  }
  identity down-10-up-10 {
    base channelpair-linerate-profile-base;
    description
      "This identity is used to denote an NG-PON2 channelpair with
       DS:10Gbps and US:10Gbps linerates.";
  }
  identity down-10-up-2.5 {
    base channelpair-linerate-profile-base;
    description
      "This identity is used to denote an NG-PON2 channelpair with
       DS:10Gbps and US:2.5Gbps linerates.";
  }
  identity down-2.5-up-2.5 {
    base channelpair-linerate-profile-base;
    description
      "This identity is used to denote an NG-PON2 channelpair with
       DS:2.5Gbps and US:2.5Gbps linerates.";
  }


  typedef string7only {
    type string {
      length "7";
    }
    description
      "Used for a string of exactly 7 octets, with each octets having
       any value in [0..255].";
  }

  typedef ponid-display-type {
    type union {
      type uint32;
      type string7only;
    }
    description
      "A type meant for the different formats of the PON-ID for the
       various channelpair types. The 'unint' is meant for NG-PON2,
       XGS-PON and XG-PON and the 'string7only' is meant for G-PON.";
  }

  typedef composite-channelid-type {
    type union {
      type uint8 {
        range "0..7";
      }
      type enumeration {
        enum "xgs" {
          description
            "To be used in case of XGS-PON, rather than 0.";
        }
      }
    }
    description
      "A composite type strictly meant for leaves reflecting the
       already allocated DS or US channel-id on a channelgroup.
       Such leaves are used to prevent conflicts when allocating
       a channelpair to a channelgroup. For NG-PON2, the applicable
       values are in [0..7], for XGS-PON a dedicated value 'xgs'
       is applicable rather than value '0': this is not to a priori
       forbid in yang model the coexistence of XGS-PON with NG-PON2
       using Channelid=0.";
  }

  typedef composite-downstream-wavelength-type {
    type union {
      type uint32 {
        range "0 | 156000..161000";
      }
      type enumeration {
        enum "xgs" {
          description
            "To be used in case of XGS-PON.";
        }
        enum "xgpon" {
          description
            "To be used in case of XG-PON.";
        }
        enum "gpon" {
          description
            "To be used in case of G-PON.";
        }
      }
    }
    description
      "A composite type strictly meant for leaves reflecting the
       already allocated DS or US channel-id on a channelgroup.
       Such leaves are used to prevent conflicts when allocating a
       channelpair to a channelgroup. For NG-PON2, the applicable
       values are in [0..8], for XGS-PON a dedicated value 'xgs'
       is applicable rather than value '0': this is not to a priori
       forbid in yang model the coexistence of XGS-PON with NG-PON2
       using Channelid=0.";
  }


  typedef auth-method-type {
    // [Temporary comment by Robert Peschi 17 Feb 2017]
    // tbc: probably a better idea to make it an identity rather than
    // an enumeration
    type enumeration {
      enum "serial-number" {

        description
          ".";
      }
      enum "loid" {

        description
          ".";
      }
      enum "registration-id" {

        description
          ".";
      }
      enum "omci" {

        description
          ".";
      }
      enum "dot1x" {

        description
          ".";
      }
    }
    description
      ".";
  }

  typedef raman-mitigation-type {
    // [Temporary comment by Robert Peschi 17 Feb 2017]
    // tbc: probably a better idea to make it an identity rather than
    // an enumeration
    type enumeration {
      enum "raman_none" {

        description
          ".";
      }
      enum "raman_miller" {

        description
          ".";
      }
      enum "raman_8b10b" {

        description
          ".";
      }
    }
    description
      ".";
  }

  typedef ponid-odn-class-type {
    // [Temporary comment by Robert Peschi 17 Feb 2017]
    // tbc: probably a better idea to make it an identity rather than
    // an enumeration
    type enumeration {
      enum "class-a" {
        value 0;
        description
          ".";
      }
      enum "class-b" {
        value 1;
        description
          ".";
      }
      enum "class-b-plus" {
        value 2;
        description
          ".";
      }
      enum "class-c" {
        value 3;
        description
          ".";
      }
      enum "class-c-plus" {
        value 4;
        description
          ".";
      }
      enum "class-auto" {
        value 255;
        description
          "Means to auto-detect from the optical transceive2.";
      }
    }
    description
      ".";
  }


  // [Temporary comment by Robert Peschi 17 Feb 2017]
  // the "URI" type defined in 'ietf-inet-types' per RFC 6991, will be
  // used for leaves being a "URL", rather than defining a home-made
  // 'url-type' as below:
  //
  // typedef url-type {
  // have reused instead uri type definition from ietf-inet-types
  //  type string;
  //    description
  //       "The url type characterizes a Uniform Resource Locator";
  // }
}
