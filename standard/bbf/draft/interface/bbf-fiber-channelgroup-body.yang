submodule bbf-fiber-channelgroup-body {
  yang-version 1.1;
  belongs-to bbf-fiber {
    prefix fiber;
  }

  import bbf-fiber-types {
    prefix fiber-types;
  }

  include bbf-fiber-channelpartition-body;

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "This module contains channelgroup data.

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  grouping channelgroup-config-data {
    description
      "All config data for a channelgroup.";
    leaf polling-period {
      type uint32 {
        range "1..864000";
      }
      units "0.1 second";
      default "100";
      description
        "The period between two consecutive times the
         autodetection procedure on each pair in the
         group is executed.
         Used in NG-PON2 for quiet window control.
         Value represents tenths of seconds.
         (e.g. 1 = 0.1 second, 864000 = 24 hours).";
    }
    leaf raman-mitigation {
      type fiber-types:raman-mitigation-type;
      default "raman_none";
      description
        "This indicates raman mitigation code.";
    }
    leaf system-id {
      type string {
        pattern '[0-9a-fA-F]{6}';
      }
      description
        "Each octet is represented by two hex values.
         This is a 20-bit number that identifies
         a specific NG2 system among multiple NG2
         system.  NG2 system here is a channel-group.
         It maybe coded to include data to support
         administration, such as name, geographical
         location, service profile, and
         the system is for protection.  only the
         low-order 20 bits are relevant.
         This is defined in
         G989-3 standard document which says in table
         VIII-2: 3bits (operator),
         5 bits (region), 5 bits (town), 3 bits
         (service area), and 4 bits (service profile).";
    }
  }

  grouping channelgroup-oper-data {
    description
      "All oper data for a channelgroup.";

    list upstream-channelid-already-allocated {
      key "upstream-channelid";
      leaf upstream-channelid {
        type fiber-types:composite-channelid-type;
        description
          "An upstream channel-id in use on the channelgroup.
           For NG-PON2, value must be in [0..7].
           For XGS-PON, value must be 'xgs'.";
      }
      description
        "The list maintained by the system of all the upstream
         channel-id's which are already allocated to the
         channelgroup. For NG-PON2, the applicable values are
         in [0..7], for XGS-PON a dedicated value 'xgs' is
         applicable rather than value '0': this is not to a
         priori forbid in yang model the coexistence of XGS-PON
         with NG-PON2 using Channelid=0. This list is a helper
         to avoid upstream channel-id conflicts when allocating
         channelpairs to a channelgroup.";
    }
    // this list is intended to enforce upstream channel-id
    // compatibility when channelpairs are allocated to the
    // channelgroup
    // [Temporary comment by Robert Peschi 10 March 2017: TBP]

    list downstream-channelid-already-allocated {
      key "downstream-channelid";
      leaf downstream-channelid {
        type fiber-types:composite-channelid-type;
        description
          "A downstreamchannel-id in use on the channelgroup.
           For NG-PON2, value must be in [0..7].
           For XGS-PON, value must be 'xgs'.";
      }
      description
        "The list maintained by the system of all the downstream
         channel-id's which are already allocated to the
         channelgroup. For NG-PON2, the applicable values are
         in [0..7], for XGS-PON a dedicated value 'xgs' is
         applicable rather than value '0': this is not to a
         priori forbid in yang model the coexistence of XGS-PON
         with NG-PON2 using Channelid=0. This list is a helper
         to avoid downstream channel-id conflicts when allocating
         channelpairs to a channelgroup.";
    }
    // This list is intended to enforce downstream channel-id
    // compatibility when channelpairs are allocated to the
    // channelgroup
    // [Temporary comment by Robert Peschi 10 March 2017: TBP]

    list downstream-wavelength-already-allocated {
      key "downstream-wavelength";
      leaf downstream-wavelength {
        type fiber-types:composite-downstream-wavelength-type;
        description
          "A downstream wavelength already allocated to the
           channelgroup. For NG-PON2 it must be a value in
           [156000..161000] expressed in hundredths of nm to fit
           ITU-T precision requirements. For the XGS-PON, XG-PON
           and G-PON cases, it must have resp. the value 'xgs',
           'xgpon' or 'gpon'.";
      }
      description
        "The list maintained by the system of all the downstream
         wavelengths already allocated to the channelgroup
         including all of the NG-PON2, XGS-PON, XG-PON and G-PON
         cases.
         This list is a helper to avoid wavelength conflicts
         when allocating channelpairs to a channelgroup.";
    }
    // this list is intended to enforce wavelength compatibility when
    // channelpairs are allocated to the channelgroup
    // [Temporary comment by Robert Peschi 10 March 2017: TBP]
  }
}
