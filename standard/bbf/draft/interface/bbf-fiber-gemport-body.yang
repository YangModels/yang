submodule bbf-fiber-gemport-body {
  yang-version 1.1;
  belongs-to bbf-fiber {
    prefix fiber;
  }


  import ietf-interfaces {
    prefix if;
  }

  include bbf-fiber-tcont-body;

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "This module contains the data of point-to-point gemports

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  container fiber-gemports-config {
    description
      "Gemports configuration data.";
    uses gemports-config-data;
  }

  container fiber-gemports-oper {
    config false;
    description
      "Gemports operational data.";
    uses gemports-oper-data;
  }


  grouping gemports-config-data {
    description
      "The config data for all gemports.";
    list gemport {
      key "name";
      description
        "List of gemports.";
      leaf name {
        type string;
        description
          "Name of gemport.";
      }
      leaf itf-ref {
        type if:interface-ref;
        description
          "Points to an interface.";
      }
      leaf traffic-class {
        type uint8 {
          range "0..7";
        }
        description
          "Traffic class value.";
      }
      leaf aes-indicator {
        type boolean;
        default "false";
        description
          "Used to designate whether AES should be
           enabled/disabled for all bi-directional
           GEM ports associated with this ONT.";
      }

      leaf tcont-ref {
        type leafref {
          path '/fiber:fiber-tconts-config/fiber:tcont/fiber:name';
        }
        description
          "For the purpose of upstream scheduling in the ONU, a
           gemport needs to refer to the tcont into which it feeds
           upstream traffic.";
      }
    }
  }

  grouping gemports-oper-data {
    description
      "The oper data for all gemports.";
    list gemport {
      key "name";
      description
        "List of gemports.";
      leaf name {
        type string;
        description
          "Name of gemport.";
      }
      leaf gemport-id {
        type uint32;
        mandatory true;
        description
          "Id of gemport.";
      }
    }
  }
}
