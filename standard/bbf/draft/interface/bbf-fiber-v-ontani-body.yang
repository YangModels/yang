submodule bbf-fiber-v-ontani-body {
  yang-version 1.1;
  belongs-to bbf-fiber {
    prefix fiber;
  }

  import ietf-interfaces {
    prefix if;
  }

  import bbf-fiber-if-type {
    prefix bbffiberift;
  }

  import ietf-yang-types {
    prefix yang;
  }

  include bbf-fiber-tcont-body;
  include bbf-fiber-gemport-body;

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "This module contains the data of the images of the ONUs seen by
     the OLT. The image of the ONU is 1-1 associated to the ONU unique
     v-ontani interface.
     This module should not be confused with the bbf-fiber-ontani-body
     which contains the data of the actual ONU

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  grouping v-ontani-config-data {
    description
      ".";
    container v-ontani-config-data {
      leaf parent-ref {
        type if:interface-ref;
        must
          "/if:interfaces/if:interface[if:name=current()]
           /if:type='bbffiberift:channelpartition'" {
          error-message
            "must reference a channelpartition";
        }
        description
          "Reference to a channelpartition itf.";
      }
      leaf expected-serial-number {
        type string {
          pattern '[a-zA-Z]{4}[0-9a-fA-F]{8}';
        }
        description
          "The serial number of the ONT which the OLT expects to
           show up. The serial number is unique for each ONU.
           It contains the vendor ID and vendor specific serial
           number. The first four bytes are an ASCII-encoded
           vendor ID four letter mnemonic. The second four bytes
           are a binary encoded serial number, under the control
           of the ONT vendor.";
        reference
          "ITU-T G.984.3, section 9.2.4.1.";
      }
      leaf expected-registration-id {
        type string {
          length "0..36";
        }
        default "";
        description
          "A string of 36 octets that has been assigned
           to the subscriber on the management level,
           entered into and stored in non-volatile storage
           at the ONU.  registration id may be useful in
           identifying a particular ONU installed at
           a particular location.";
        reference
          "ITU-T G.987.3 section 11.3.4.2";
      }


      leaf preferred-chanpair {
        type if:interface-ref;
        must
          "/if:interfaces/if:interface[if:name=current()]
           /if:type='bbffiberift:channelpair' and
           /if:interfaces/if:interface[if:name=current()]
           /channelpair/channelpartition-ref=../parent-ref
           and current() != ../protection-chanpair" {
          error-message
            "must reference a channelpair and the cp
             should belong to same channelpartition.
             The preferred channelpair can't be the
             same as the protection channelpair";
        }
        description
          "Points to a channelpair interface. Configuring an ONU
           with both a preferred and protection channelpair
           provides wavelength protection to this ONU.";
      }

      leaf protection-chanpair {
        type if:interface-ref;
        must
          "/if:interfaces/if:interface[if:name=current()]
           /if:type='bbffiberift:channelpair' and
           /if:interfaces/if:interface[if:name=current()]
           /channelpair/channelpartition-ref=../parent-ref and
           current() != ../preferred-chanpair" {
          error-message
            "must reference a channelpair and the cp
             should belong to same channelpartition.
             The protection channelpair can't be the
             same as the preferred channelpair";
        }
        description
          "Points to a channelpair interface. Configuring an ONU
           with both a preferred and protection channelpair
           provides wavelength protection to this ONU.";
      }

      leaf upstream-channel-speed {
        type yang:gauge64;
        units "bits/second";
        description
          "Upstream channel speed for this interface in
           bits per second.";
      }
      description
        ".";
    }
  }

  grouping v-ontani-oper-data {
    description
      ".";
    container v-ontani-oper-data {
      config false;
      leaf onu-id {
        type uint32 {
          range "0..1020";
        }
        description
          "Identifies an ONU on a channelgroup, unique
           on a channelgroup.";
      }
      description
        ".";
    }
  }
}
