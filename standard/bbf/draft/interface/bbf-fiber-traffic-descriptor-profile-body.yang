submodule bbf-fiber-traffic-descriptor-profile-body {
  yang-version 1.1;
  belongs-to bbf-fiber {
    prefix fiber;
  }

  organization
    "Broadband Forum <https://www.broadband-forum.org>
     PON Management Project Stream";

  contact
    "Comments or questions about this Broadband Forum YANG module
     should be directed to <mailto:help@broadband-forum.org>.

     Editor:      Joey Boyd, ADTRAN
                  <mailto:joey.boyd@adtran.com>

     Editor:      Samuel Chen, Broadcom
                  <mailto:samuel.chen@broadcom.com>

     WA Director: Greg Bathrick, Calix
                  <mailto:gregory.bathrick@calix.com>

     WA Director: Lin Wei, Huawei
                  <mailto:wei.linwei@huawei.com>";

  description
    "This module contains traffic descriptor profile data.

     Copyright (c) 2017, Broadband Forum

     This is draft software, is subject to change, and has not been
     approved by members of the Broadband Forum. It is made available
     to non-members for internal study purposes only. For such study
     purposes, you have the right to make copies and modifications
     only for distributing this software internally within your
     organization among those who are working on it (redistribution
     outside of your organization for other than study purposes of
     the original or modified works is not permitted). For the
     avoidance of doubt, no patent rights are conferred by this
     license.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF
     USE, DATA, OR PROFITS; OR BUSINESS INTERRUPTION) HOWEVER CAUSED
     AND ON ANY THEORY OF LIABILITY, WHETHER IN CONTRACT, STRICT
     LIABILITY, OR TORT (INCLUDING NEGLIGENCE OR OTHERWISE) ARISING
     IN ANY WAY OUT OF THE USE OF THIS SOFTWARE, EVEN IF ADVISED OF
     THE POSSIBILITY OF SUCH DAMAGE.

     Unless a different date is specified upon issuance of a draft
     software release, all member and non-member license rights under
     the draft software release will expire on the earliest to occur
     of (i) nine months from the date of issuance, (ii) the issuance
     of another version of the same software release, or (iii) the
     adoption of the draft software release as final.

     This version of this source file is part of the Broadband Forum
     WT-385 ITU-T PON YANG Modules project.

     Please see the revision information (given below) for further
     details of this release, e.g. documentation, license validity
     dates and availability of more recent draft or final releases.";

  revision 2017-05-09 {
    description
      "WT-385_draft1";
    reference
      "https://www.broadband-forum.org/software#WT-385_draft1";
  }

  container fiber-traffic-descriptor-profiles {
    description
      "Traffic descriptor profile configuration.";
    uses traffic-descriptor-profile-data;
  }

  grouping traffic-descriptor-profile-data {
    description
      "All config data for traffic descriptor profile.";
    reference
      "ITU-T G.989.3";

    list traffic-descriptor-profile {
      key "name";
      leaf name {
        type string;
        description
          "Traffic descriptor profile name.";
      }
      leaf fixed-bandwidth {
        type uint64;
        units "bits/second";
        description
          "Represents the reserved portion of the link
           capacity that is allocated
           to the given traffic flow, regardless
           of its traffic demand and the overall
           traffic load conditions.";
      }
      leaf assured-bandwidth {
        type uint64;
        units "bits/second";
        description
          "Represents a portion of the link capacity
           that is allocated to the
           given traffic flow as long as the
           flow has unsatisfied traffic demand,
           regardless of the overall traffic conditions.";
      }
      leaf maximum-bandwidth {
        type uint64;
        units "bits/second";
        description
          "Represents the upper limit on the total
           bandwidth that can be
           allocated to the traffic flow under any
           traffic conditions.";
      }
      leaf priority {
        type uint8 {
          range "1..8";
        }
        description
          "Used for scheduling traffic on a T-CONT.";
      }
      leaf weight {
        type uint8;
        description
          "Used for scheduling traffic on a T-CONT.";
      }
      leaf additional-bw-eligibility-indicator {
        type enumeration {
          enum "non-assured-sharing" {
            description
              "The T-CONT is eligible for non-assured bandwidth
               in addition to the bandwidth described by this
               traffic descriptor.";
          }
          enum "best-effort-sharing" {
            description
              "The T-CONT is eligible for best effort bandwidth
               in addition to the bandwidth described by this
               traffic descriptor.";
          }
          enum "none" {
            description
              "The T-CONT is not eligible for any additional
               bandwidth beyond the bandwidth described by
               this traffic descriptor.";
          }
        }
        description
          "In case of rate-proportional assignment of
           additional bandwidth, additional bandwidth
           eligibility can be provisioned to either value
           (non-assured-sharing, best-effort-sharing,
           or none).";
        reference
          "ITU-T G.989.3, section 7.3.5";
      }
      description
        "List of traffic descriptor profiles.";
    }
  }
}
