module bbf-yang-types {
  yang-version 1.1;
  namespace "urn:bbf:yang:bbf-yang-types";
  prefix bbf-yang;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This module contains a collection of YANG definitions for
     common types used throughout BBF defined models.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef performance-counter32 {
    type uint32;
    description
      "A performance-counter32 type represents a non-negative
       integer which may increase but shall never exceed a maximum
       value.  The maximum value can not be greater than 2^32-1
       (4294967295 decimal).
       The value of a performance-counter32 has its maximum value
       whenever the information being modeled is greater than or
       equal to its maximum value.";
  }

  typedef performance-counter32-or-inactive {
    type union {
      type uint32;
      type enumeration {
        enum "inactive" {
          description
            "Indicates that this counter is not active on the
             line.";
        }
      }
    }
    description
      "A performance-counter32-or-inactive type represents a 
       non-negative integer which may increase but shall never
       exceed a maximum value.  The maximum value can not be 
       greater than 2^32-1 (4294967295 decimal).
       The value of a performance-counter32-or-inactive has its
       maximum value whenever the information being modeled is
       greater than or equal to its maximum value.
       A special value (enum inactive) indicates that this counter
       is not active on the line.";
  }

  typedef string-ascii64 {
    type string {
      length "1..64";
      pattern '[ -~]*';
    }
    description
      "Used where a string is represented using at least 1 and no more
       than 64 ASCII characters.";
  }

  typedef undetermined {
    type enumeration {
      enum "undetermined" {
        description
          "Indicates the value is not determined.";
      }
    }
    description
      "A type which defines an enumeration respresenting when
       the value for an object is not determined. Often, this is
       combined with other data via a union acting as a special value
       to indicate the undetermined state.";
  }

  typedef data-rate32 {
    type uint32;
    units "kbits/second";
    description
      "A type which represents the rate at which data is being 
       transferred.";
  }

  typedef data-rate32-or-undetermined {
    type union {
      type undetermined;
      type data-rate32;
    }
    units "kbits/second";
    description
      "A type which represents the rate at which data is being 
       transferred. A special value, 'undetermined', is used to
       indicate the data rate is undetermined.";
  }
}
