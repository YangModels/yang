submodule bbf-fast-test-mode-body {
  yang-version 1.1;
  belongs-to bbf-fast {
    prefix bbf-fast;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for
     managing test modes.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping test-mode-enable-parameters {
    description
      "A set of parameters used to enable various test modes
       specified by ITU-T G.997.2 and G.9701";

    leaf rtx-tc-test-mode {
      type boolean;
      default "false";
      description
        "Defines whether the retransmission test-mode defined in
         clause 9.8.3.1.2/G.9701 is enabled or disabled. The
         RTX_TESTMODE setting may be changed during showtime. When
         changed, it shall take effect within 2 seconds without 
         re-initialization";
      reference
        "ITU-T G.997.2 clause 7.2.2.7 (RTX_TESTMODE); ITU-T G.9701
         clause 9.8.3.1.2.";
    }

    leaf tps-tc-test-mode {
      type boolean;
      default "false";
      description
        "Defines whether the TPS-TC test-mode defined in
         clause 8.3.1/G.9701 is enabled or disabled.The
         TPS_TESTMODE setting may be changed during showtime. When
         changed, it shall take effect within 2 seconds without 
         re-initialization";
      reference
        "ITU-T G.997.2 clause 7.3.1 (TPS_TESTMODE); ITU-T G.9701
         clause 8.3.1.";
    }

    leaf dra-test-mode {
      type boolean;
      default "false";
      description
        "Defines whether the DRA test-mode defined in clause
         9.8.3.1.2/G.9701 is enabled or disabled. The DRA_TESTMODE
         setting may be changed during showtime. When changed, it
         shall take effect on the line within 2 seconds without
         re-initialization.";
      reference
        "ITU-T G.997.2 clause 7.3.2 (DRA_TESTMODE); ITU-T G.9701
         clause 9.8.3.1.2.";
    }
  }

  grouping line-test-modes {
    description
      "Test modes associated with a line";

    uses test-mode-enable-parameters;
  }
}
