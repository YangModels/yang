submodule bbf-vdsl-xtu-line-threshold-profile-body {
  yang-version 1.1;
  belongs-to bbf-vdsl {
    prefix bbf-vdsl;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 8.1 xDSL Line Threshold
     Template.

     Copyright (c) 2016, 2017 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping line-threshold-profile {

    description
      "The xDSL Line Threshold Template object represents a complete
       set of performance monitoring thresholds for an xDSL Line,
       this grouping is for the XTU - Central office.";

    leaf forward-error-correction-seconds-threshold {
      type uint32;
      units "1 second";
      default "0";
      description
        "This parameter is the performance monitoring threshold
         for threshold reports of Forward Error Correction
         Seconds (FECS). A special value (0) indicates the
         threshold is disabled";
      reference
        "ITU-T G.997.1 clause 7.2.7";
    }

    leaf errored-seconds-threshold {
      type uint32;
      units "1 second";
      default "0";
      description
        "This parameter is the performance monitoring
         threshold for threshold reports of Errored Seconds (ES).
         A special value (0) indicates the threshold is disabled.";
      reference
        "ITU-T G.997.1 clause 7.2.7.";
    }

    leaf severely-errored-seconds-threshold {
      type uint32;
      units "1 second";
      default "0";
      description
        "This parameter is the performance monitoring threshold
         for threshold reports of Severely Errored Seconds (SES).
         A special value (0) indicates the threshold is disabled.";
      reference
        "ITU-T G.997.1 clause 7.2.7.";
    }

    leaf loss-of-signal-seconds-threshold {
      type uint32;
      units "1 second";
      default "0";
      description
        "This parameter is the performance monitoring threshold
         for threshold reports of Loss of Signal Seconds Line 
         (LOSS). A special value (0) indicates the threshold is
         disabled.";
      reference
        "ITU-T G.997.1 clause 7.2.7.";
    }

    leaf unavailable-seconds-threshold {
      type uint32;
      units "1 second";
      default "0";
      description
        "This parameter is the performance monitoring threshold
         for threshold reports of Unavailable Seconds (UAS).
         A special value (0) indicates the threshold is disabled.";
      reference
        "ITU-T G.997.1 clause 7.2.7.";
    }

    leaf leftr-defects-seconds-threshold {
      // only defined in upstream
      type uint32;
      units "1 second";
      default "0";
      description
        "This parameter is the performance monitoring threshold
         for threshold reports of near-end line leftr defects
         seconds. The near-end line leftr defects seconds counter
         is only defined in upstream.
         A special value (0) indicates the threshold is disabled.";
      reference
        "ITU-T G.997.1 clause 7.2.7.";
    }

    leaf leftr-defect-threshold {
      type union {
        type uint8 {
          range "0..99";
        }
        type enumeration {
          enum "etr-default-threshold" {
            description
              "Indicates that the ETR shall be used as the default
               threshold for declaring a leftr defect.";
          }
        }
      }
      units "0.01";
      default "etr-default-threshold";
      description
        "If retransmission is used in a given transmit direction,
         LEFTR_THRESH specifies the threshold for declaring a 
         leftr defect (see clause 11.1.12 of ITU-T G.998.4)
         for the definition of this threshold). 
         The value is coded as a fraction of the NDR with valid
         range from 0.01 to 0.99 in increments of 0.01. 
         A special value of (enum etr-default-threshold) means the
         ETR shall be used as the default threshold for declaring a
         leftr defect.";
      reference
        "ITU-T G.997.1 clause 7.3.1.12.";
    }

    // The below four objects were in 
    // bbf-vdsl-xtu-c-line-threshold-profile.yang
    leaf full-initializations-threshold {
      type uint32;
      default "0";
      description
        "This parameter is the performance monitoring threshold
         for threshold reports of the full initializations
         attempted on the line (successful and failed) during the
         accumulation period.
         A special value (0) indicates the threshold is disabled.";
      reference
        "ITU-T G.997.1 clause 7.2.7.";
    }

    leaf failed-full-initializations-threshold {
      type uint32;
      default "0";
      description
        "This performance parameter is the performance monitoring
         threshold for threshold reports of the total number of
         failed full initializations during the accumulation
         period. A special value (0) indicates the threshold is
         disabled.";
      reference
        "ITU-T G.997.1 clause 7.2.7.";
    }

    leaf short-initializations-threshold {
      type uint32;
      default "0";
      description
        "This parameter is is the performance monitoring
         threshold for threshold reports of the total number of
         fast retrains or short initializations attempted on the
         line (successful and failed) during the accumulation
         period. A special value (0) indicates the threshold is
         disabled.";
      reference
        "ITU-T G.997.1 clause 7.2.7.";
    }

    leaf failed-short-initializations-threshold {
      type uint32;
      default "0";
      description
        "This performance parameter is the performance monitoring
         threshold for threshold reports of the total number of
         failed fast retrains or short initializations during the
         accumulation period. A special value (0) indicates the
         threshold is disabled.";
      reference
        "ITU-T G.997.1 clause 7.2.7.";
    }

    leaf spontaneous-interruptions-threshold {
      type uint32;
      default "0";
      description
        "This parameter is a count is the performance monitoring
         threshold for threshold reports of the spont_intrpt
         anomalies occurring during the accumulation period. Only
         the counters on the current and previous 24-hours
         intervals are supported. Threshold reports are specified
         for the 24-hour interval counter only. A special value (0)
         indicates the threshold is disabled.";
      reference
        "ITU-T G.997.1 clause 7.2.7.";
    }
  } // end grouping line-threshold-profile
} // end submodule line-threshold-profile-body
