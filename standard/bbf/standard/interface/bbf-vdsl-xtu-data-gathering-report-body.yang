submodule bbf-vdsl-xtu-data-gathering-report-body {
  yang-version 1.1;
  belongs-to bbf-vdsl {
    prefix bbf-vdsl;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 9.2 xTU Data Gathering
     Report.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping xtu-data-gathering-report {

    description
      "These parameters are obtained from the data gathering
       functionality in the xDSL modems for use in
       testing/diagnostics";

    leaf logging-depth {
      type uint32;
      units "6-byte data gathering records";
      description
        "This parameter is the maximum depth of the entire data
         gathering event buffer at the VTU, in number of 6-byte
         data gathering records.";
      reference
        "ITU-T G.997.1 clause 7.5.3.1 Logging depth VTU-O
         (LOGGING_DEPTH_O) and clause 7.5.3.2 Logging depth VTU-R
         (LOGGING_DEPTH_R)";
    }

    leaf actual-logging-depth-reporting {
      type uint32;
      units "6-byte data gathering records";
      description
        "This parameter is actual logging depth that is used for
         reporting the VTU-O event trace buffer in the CO-MIB, or
         for reporting the VTU-R event trace buffer over the eoc
         channel, in number of 6-byte data gathering records.";
      reference
        "ITU-T G.997.1 clause 7.5.3.3 Actual logging depth for
         reporting VTU-O (ACT_logging_depth_reporting_O) and
         clause 7.5.3.4 Actual logging depth for reporting VTU-R
         (ACT_logging_depth_reporting_R)";
    }

    leaf event-trace-buffer {
      type binary;
      description
        "This parameter is the event trace buffer containing the
         event records that originated at the VTU.";
      reference
        "ITU-T G.997.1 clause 7.5.3.5 Event trace buffer VTU O
         (EVENT_TRACE_BUFFER_O) and clause 7.5.3.6 Event trace
         buffer VTU R (EVENT_TRACE_BUFFER_R)";
    }
  } // end grouping xtu-data-gathering-report
} // end submodule xtu-data-gathering-report-body
