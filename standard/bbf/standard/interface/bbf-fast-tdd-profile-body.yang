submodule bbf-fast-tdd-profile-body {
  yang-version 1.1;
  belongs-to bbf-fast {
    prefix bbf-fast;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for
     managing TDD profiles.

     Copyright (c) 2016, 2017 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping time-division-duplexing-parameters {
    description
      "Time division duplexing (TDD) configuration parameters.";
    reference
      "ITU-T G.997.2 clause 7.1.1.";

    leaf total-symbol-periods {
      type uint8 {
        range "23 | 36";
      }
      default "36";
      description
        "Defines the total number of symbol periods in a TDD
         frame.";
      reference
        "ITU-T G.997.2 clause 7.1.1.1 (MF); ITU-T G.9701 clause
         10.5.";
    }

    leaf downstream-symbol-periods {
      type uint8 {
        range "6..32";
      }
      must
        "(../total-symbol-periods = 23 and .>= 6 and .<= 19) or
         (../total-symbol-periods = 36 and .>= 10 and .<= 32)" {
        description
          "If the total symbol periods is 23, the number of downstream
           symbol periods must be between 6 to 19 inclusive. If the 
           total symbol periods is 36, the number of downstream symbol
           periods must be between 10 to 32 inclusive";
      }
      default "28";
      description
        "Defines the total number of symbol positions in a TDD frame
         allocated for downstream transmission. The total number of
         symbol positions in a TDD frame allocated for upstream
         transmission is calculated as Mus = MF-1-Mds.";

      reference
        "ITU-T G.997.2 clause 7.1.1.2 (Mds); ITU-T G.9701 Clause
         10.5";
    }

    leaf cyclic-extension {
      type uint8 {
        range "4 | 8 | 10 | 12 | 14 | 16 | 20 | 24 | 30 | 33";
      }
      units "N/64 samples";
      default "10";
      description
        "Defines the cyclic extension(Lcp) to be used. The units
         are in N/64 samples, where N = index of the highest
         supported downstream data-bearing sub-carrier as defined
         for the enabled profile (see Table 6-1/G.9701) plus one.";
      reference
        "ITU-T G.997.2 clause 7.1.1.3; ITU-T G.9701 clause 10.4.4";
    }
  }

  grouping tdd-profile {
    description
      "Defines the contents of a Time Division Duplexing Profile.";

    uses time-division-duplexing-parameters;
  }
}
