submodule bbf-vdsl-downstream-power-back-off-profile-body {
  yang-version 1.1;
  belongs-to bbf-vdsl {
    prefix bbf-vdsl;
  }

  include bbf-vdsl-base-body;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 5.6 Spectrum related 
     profiles; Downstream Power Back Off Profile.

     Copyright (c) 2016, 2017 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping downstream-power-back-off-profile {

    description
      "This configures downstream power back-off (DPBO),
       generally for static spectral compatibility of VDSL
       with ADSL, ADSL2, or ADSL2plus.";

    container dpboepsd {
      uses psdmask-descriptor {
        refine "psdmask" {
          max-elements 16;
        }
      }
      description
        "Assumed exchange PSD mask (DPBOEPSD). This parameter
         defines the PSD mask that is assumed to be permitted at
         the exchange. This parameter will use the same format as
         PSDMASKds. The maximum number of breakpoints for
         DPBOEPSD is 16.
         The default is an empty list indicating no DPBO.";
      reference
        "ITU-T G.997.1 clause 7.3.1.2.13 a.1) Assumed exchange
         PSD mask (DPBOEPSD)";
    }

    leaf dpboesel {
      type uint16 {
        range "0..511";
      }
      units "0.5 dB";
      default "0";
      description
        "E-side electrical length (DPBOESEL). This configuration
         parameter defines the assumed electrical length of
         cables (E-side cables) connecting exchange based DSL
         services to a remote flexibility point (cabinet), that
         hosts the xTU-C that is subject to spectrally shaped
         downstream power back-off depending on this length. For
         this parameter the electrical length is defined as the
         loss (in dB) of an equivalent length of hypothetical
         cable at a reference frequency defined by the network
         operator or in spectrum management regulations. DPBOESEL
         will be coded as an unsigned integer representing an
         electrical length from 0 dB to 255.5 dB in steps of 0.5
         dB. All values in the range are valid.
         If DPBOESEL is set to zero, the DPBO in this clause will
         be disabled.";
      reference
        "ITU-T G.997.1 clause 7.3.1.2.13 a.2) E-side electrical
         length (DPBOESEL)";
    }

    container dpboescm {
      description
        "E-side cable model (DPBOESCM). This configuration
         parameter defines a cable model in terms of three
         scalars DPBOESCMA, DPBOESCMB and DPBOESCMC that will be
         used to describe the frequency dependent loss of E-side
         cables.
         where ESCM is expressed in dB and f is expressed in MHz.
         Parameters DPBOESCMA, DPBOESCMB, DPBOESCMC will be coded
         as unsigned integers representing a scalar value from -1
         to 1.5 in steps of 2^-8. = 1/256.
         dpboescma, dpboescmb, and dpboescmc are defined with an
         offset of -1.0 in units of 1/256, so DPBOESCMA =
         dpboescma/256 - 1.0, DPBOESCMB = dpboescmb/256 - 1.0,
         and DPBOESCMC = dpboescmc/256 - 1.0";
      reference
        "ITU-T G.997.1 clause 7.3.1.2.13 a.3) E-side cable model
         (DPBOESCM)";

      leaf dpboescma {
        type uint16 {
          range "0..640";
        }
        units "(1/256)"; // offset 1.0
        default "0";
        description
          "DPBOESCMA = dpboescma/256 - 1.0";
      }

      leaf dpboescmb {
        type uint16 {
          range "0..640";
        }
        units "(1/256)"; // offset 1.0
        default "0";
        description
          "DPBOESCMB = dpboescmb/256 - 1.0";
      }

      leaf dpboescmc {
        type uint16 {
          range "0..640";
        }
        units "(1/256)"; // offset 1.0
        default "0";
        description
          "DPBOESCMC = dpboescmc/256 - 1.0";
      }
    }

    leaf dpbomus {
      type uint8 {
        range "0..255";
      }
      units "-0.5 dBm/Hz";
      default "0";
      description
        "Minimum usable signal (DPBOMUS). DPBOMUS defines the
         assumed minimum usable receive PSD mask (in dBm/Hz) for
         exchange based services, used to modify parameter
         DPBOFMAX defined below. It will be coded as an unsigned
         integer representing a PSD mask level from 0 dBm/Hz to
         -127.5 dBm/Hz in steps of 0.5 dB.";
      reference
        "ITU-T G.997.1 clause 7.3.1.2.13 a.4) Minimum usable
         signal (DPBOMUS)";
    }

    leaf dpbofmin {
      type uint16 {
        range "0..2048";
      }
      units "4.3125 kHz";
      default "0";
      description
        "DPBO span minimum frequency (DPBOFMIN). DPBOFMIN defines
         the minimum frequency from which the DPBO will be
         applied. It ranges from 0 kHz to 8832 kHz in steps of
         4.3125 kHz.";
      reference
        "ITU-T G.997.1 clause 7.3.1.2.13 a.5) DPBO span minimum
         frequency (DPBOFMIN)";
    }

    leaf dpbofmax {
      type uint16 {
        range "32..8191";
      }
      units "4.3125 kHz";
      must ". >= ../dpbofmin" {
        description
          "The DPBO span maximum frequency must be greater than or
           equal to the DPBO span minimum frequency.";
      }
      default "8191";
      description
        "DPBO span maximum frequency (DPBOFMIN). DPBOFMAX defines
         the maximum frequency at which DPBO may be applied. It
         ranges from 138 kHz to 35323.6875 kHz in steps of 4.3125
         kHz.";
      reference
        "ITU-T G.997.1 clause 7.3.1.2.13 a.6) DPBO span maximum
         frequency (DPBOFMAX)";
    }
  } // end grouping downstream-power-back-off-profile
} // end submodule downstream-power-back-off-profile-body
