submodule bbf-vdsl-xtu-line-performance-body {
  yang-version 1.1;
  belongs-to bbf-vdsl {
    prefix bbf-vdsl;
  }

  import bbf-yang-types {
    prefix bbf-yang;
  }

  import ietf-yang-types {
    prefix yang;
  }

  include bbf-vdsl-base-body;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 7.1 xTU Line 
     Performance.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping xtu-c-line-performance {

    description
      "The xTU-C Line Performance object represents line performance
       related data for a given xTU - Central office.";

    leaf measured-time {
      type uint32;
      description
        "Reports the amount of time, measured in seconds,
         that statistics for this interval have been counted.";
      reference
        "ITU-T G.997.2 clause 7.7.1 and 7.8.1.";
    }

    leaf invalid-data-flag {
      type boolean;
      description
        "Reports the validity of the corresponding 
         performance monitoring data. true = invalid.";
      reference
        "ITU-T G.997.2 clause 7.7.2 and 7.8.2.";
    }

    leaf forward-error-correction-seconds-l {
      type bbf-yang:performance-counter32;
      description
        "This parameter is a count of 1-second intervals with one
         or more FEC anomalies summed over all received bearer
         channels.";
      reference
        "ITU-T G.997.1 clause 7.2.1.1.1 Forward error correction
         second - Line (FECS-L)";
    }

    leaf errored-seconds-l {
      type bbf-yang:performance-counter32;
      description
        "This parameter is a count of 1-second intervals with one
         or more CRC-8 anomalies summed over all received bearer
         channels, or one or more LOS defects, or one or more SEF
         defects, or one or more LPR defects.";
      reference
        "ITU-T G.997.1 clause 7.2.1.1.2 Errored second - Line
         (ES-L)";
    }

    leaf severely-errored-seconds-l {
      type bbf-yang:performance-counter32;
      description
        "This parameter is a count of severely errored seconds
         (SES). An SES is declared if, during a 1-second
         interval, there are 18 or more CRC-8 anomalies in one or
         more of the received bearer channels, or one or more LOS
         defects, or one or more SEF defects, or one or more LPR
         defects. If [ITU-T G.998.4] is supported and
         retransmission is enabled in the near-end received
         direction, a SES is also declared if, during a 1-second
         interval, there is one or more severe loss of error-free
         throughput (seftr) defect in the near-end received
         direction.";
      reference
        "ITU-T G.997.1 clause 7.2.1.1.3 Severely errored second -
         Line (SES-L)";
    }

    leaf loss-of-signal-seconds-l {
      type bbf-yang:performance-counter32;
      description
        "This parameter is a count of 1-second intervals
         containing one or more LOS defects.";
      reference
        "ITU-T G.997.1 clause 7.2.1.1.4 LOS second - Line
         (LOSS-L)";
    }

    leaf unavailable-seconds-l {
      type bbf-yang:performance-counter32;
      description
        "This parameter is a count of 1-second intervals for
         which the xDSL line is unavailable. Some parameter
         counts are inhibited during unavailability - see ITU-T
         G.997.1 clause 7.2.7.13.";
      reference
        "ITU-T G.997.1 clause 7.2.1.1.5 Unavailable second - Line
         (UAS-L)";
    }
    list inminpeq-l {
      key "inminpeq-index";
      leaf inminpeq-index {
        type uint8 {
          range "1..17";
        }
        description
          "Identifies the INMAINPEQ histogram bin";
      }
      leaf inminpeq-l {
        type bbf-yang:performance-counter32;
        description
          "count of the near-end INMAINPEQ anomalies";
      }
      description
        "This parameter is a count of the near-end INMAINPEQi
         anomalies occurring on the line during the accumulation
         period. This parameter is subject to inhibiting - see
         ITU-T G.997.1 clause 7.2.7.13.";
      reference
        "ITU-T G.997.1 clause 7.2.1.4.1 INM INPEQ histogram 1..17
         (INMINPEQ1..17-L)";
    }

    leaf inmme-l {
      type bbf-yang:performance-counter32;
      description
        "This parameter is a count of the near-end INMAME
         anomalies occurring on the line during the accumulation
         period. This parameter is subject to inhibiting - see
         ITU-T G.997.1 clause 7.2.7.13.";
      reference
        "ITU-T G.997.1 clause 7.2.1.4.2 INM total measurement
         (INMME-L)";
    }

    list inmiat-l {
      key "inminiat-index";
      leaf inminiat-index {
        type uint8 {
          range "0..7";
        }
        description
          "Identifies the INMAIAT histogram bin";
      }
      leaf inmiat-l {
        type bbf-yang:performance-counter32;
        description
          "Count of the near-end INMAIAT anomalies";
      }
      description
        "This parameter is a count of the near-end INMAIATi
         anomalies occurring on the line during the accumulation
         period. This parameter is subject to inhibiting - see
         ITU-T G.997.1 clause 7.2.7.13.";
      reference
        "ITU-T G.997.1 clause 7.2.1.4.3 INM IAT histogram 0..7
         (INMIAT0..7-L)";
    }

    leaf sos-success-ne {
      type bbf-yang:performance-counter32;
      description
        "This parameter is a count of the total number of
         successful SOS procedures initiated by the near-end xTU
         on the line during the accumulation period. Parameter
         procedures will be as defined in ITU-T G.997.1 clause
         7.2.7. Successful SOS is defined in clause 12.1.4 of
         [ITU-T G.993.2].";
      reference
        "ITU-T G.997.1 clause 7.2.1.6.1 Near-end successful SOS
         count (SOS-SUCCESS-NE)";
    }

    leaf leftr-defects-seconds-counter-ne {
      // only defined in upstream
      type bbf-yang:performance-counter32;
      description
        "Near-end line leftr defects seconds counter. If
         retransmission is used in a given transmit direction,
         this parameter is a count of the seconds with a near-end
         ''leftr'' defect present (see clause 11.4.1 of [ITU-T
         G.998.4] for the definition of this counter).
         This near-end counter is only defined in upstream.";
      reference
        "ITU-T G.997.1 clause 7.2.1.1.6 leftr defects seconds
         counter";
    }

    leaf error-free-bits-counter-ne {
      // only defined in upstream
      type bbf-yang:performance-counter32;
      description
        "Near-end line error-free bits counter. If retransmission
         is used in a given transmit direction, this parameter is
         a count of the number of error-free bits passed over the
         Beta1 reference point, divided by 65536 = 2^16 (see
         clause 11.4.2 of [ITU-T G.998.4] for the definition of
         this counter).
         This near-end counter is only defined in upstream.";
      reference
        "ITU-T G.997.1 clause 7.2.1.1.7 Error-free bits counter";
    }

    leaf minimum-error-free-throughput-ne {
      // only defined upstream
      type bbf-yang:performance-counter32;
      units "bit/s";
      description
        "Near-end minimum error-free throughput (MINEFTR). If
         retransmission is used in a given transmit direction,
         this parameter MINEFTR reports the minimum of the EFTR
         observed over the 15-min or 24-hour accumulation period
         (see clause 11.4.3 of [ITU-T G.998.4] for the definition
         of this parameter). The value is reported in bit/s.
         This near-end value is only defined in upstream.";
      reference
        "ITU-T G.997.1 clause 7.2.1.1.8 Minimum error-free
         throughput (MINEFTR)";
    }

    // below xtu-c parameters were in 
    // bbf-vdsl-xtu-c-line-performance.yang
    leaf full-initializations {
      type bbf-yang:performance-counter32;
      description
        "This parameter is a count of the total number of full
         initializations attempted on the line (successful and
         failed) during the accumulation period. Parameter
         procedures are defined in ITU-T G997.1 clause 7.2.7.";
      reference
        "ITU-T G.997.1 clause 7.2.1.3.1 Full initialization
         count";
    }

    leaf failed-full-initializations {
      type bbf-yang:performance-counter32;
      description
        "This performance parameter is a count of the total
         number of failed full initializations during the
         accumulation period. A failed full initialization is
         when showtime is not reached at the end of the full
         initialization procedure. Parameter procedures are
         defined in ITU-T G997.1 clause 7.2.7.";
      reference
        "ITU-T G.997.1 clause 7.2.1.3.2 Failed full
         initialization count";
    }

    leaf short-initializations {
      type bbf-yang:performance-counter32;
      description
        "This parameter is a count of the total number of fast
         retrains or short initializations attempted on the line
         (successful and failed) during the accumulation period.
         Parameter procedures are defined in ITU-T G997.1 clause
         7.2.7.";
      reference
        "ITU-T G.997.1 clause 7.2.1.3.3 Short initialization
         count";
    }

    leaf failed-short-initializations {
      type bbf-yang:performance-counter32;
      description
        "This performance parameter is a count of the total
         number of failed fast retrains or short initializations
         during the accumulation period. A failed fast retrain or
         short initialization is when showtime is not reached at
         the end of the fast retrain or short initialization
         procedure, e.g., when: A CRC error is detected, a
         time-out occurs, or a fast retrain profile is unknown.
         Parameter procedures are defined in ITU-T G997.1 clause
         7.2.7.";
      reference
        "ITU-T G.997.1 clause 7.2.1.3.4 Failed short
         initialization count";
    }

    leaf loss-of-power-intrpt {
      type bbf-yang:performance-counter32-or-inactive;
      description
        "This parameter is a count of the number of lpr_intrpt
         anomalies occurring during the accumulation period.
         Those anomalies are defined in clause 11.3.1.1 of [ITU-T
         G.993.2]. Only the counters on the current and previous
         24-hours intervals are supported. A special value
         (enum inactive) indicates that this counter is not active
         on the line.
         Threshold reports for this counter are not specified.";
      reference
        "ITU-T G.997.1 clause 7.2.1.8.1 Loss-of-power
         interruption count (LPR_INTRPT)";
    }

    leaf host-reinit-interruptions {
      type bbf-yang:performance-counter32-or-inactive;
      description
        "This parameter is a count of the number of hri_intrpt
         anomalies occurring during the accumulation period.
         Those anomalies are defined in clause 11.3.1.1 of [ITU-T
         G.993.2]. Only the counters on the current and previous
         24-hours intervals are supported. A special value 
         (enum inactive) indicates that this counter is not active
         on the line.
         Threshold reports for this counter are not specified.";
      reference
        "ITU-T G.997.1 clause 7.2.1.8.2 Host-Reinit interruption
         count (HRI_INTRPT)";
    }

    leaf spontaneous-intrpt {
      type bbf-yang:performance-counter32-or-inactive;
      description
        "This parameter is a count of the number of spont_intrpt
         anomalies occurring during the accumulation period.
         Those defects are defined in clause 11.3.1.1 of [ITU-T
         G.993.2]. Only the counters on the current and previous
         24-hours intervals are supported. A special value
         (enum inactive) indicates that this counter is not active
         on the line.
         Threshold reports are specified for the 24-hour interval
         counter only.";
      reference
        "ITU-T G.997.1 clause 7.2.1.8.3 Spontaneous interruption
         count (SPONT_INTRPT)";
    }

    // below three counters (los, lof, lpr) are from bbf2016.024
    leaf loss-of-signal {
      type bbf-yang:performance-counter32;
      description
        "Reports a count of the Loss-of-signal (LOS) failures.";
      reference
        "Borrowed from ITU-T G.997.2 clause 7.7.4 (LOS).
         Count of failures defined in ITU-T G.997.1 
         clause 7.1.1.1.1.";
    }

    leaf loss-of-frame {
      type bbf-yang:performance-counter32;
      description
        "Reports a count of the Loss-of-frame (LOF) failures.";
      reference
        "Count of failures defined in ITU-T G.997.1 
         clause 7.1.1.1.2.";
    }

    leaf loss-of-power {
      type bbf-yang:performance-counter32;
      description
        "reports a count of the Loss-of-power (LPR) failures.";
      reference
        "Borrowed from ITU-T G.997.2 clause 7.7.7 (LPR).
         Count of failures defined in ITU-T G.997.1 
         clause 7.1.1.1.3.";
    }
  } // end grouping xtu-c-line-performance

  grouping xtu-r-line-performance {

    description
      "The xTU-R Line Performance object represents line performance
       related data for a given xTU - Remote side.";

    leaf measured-time {
      type uint32;
      description
        "Reports the amount of time, measured in seconds,
         that statistics for this interval have been counted.";
      reference
        "ITU-T G.997.2 clause 7.7.1 and 7.8.1.";
    }

    leaf invalid-data-flag {
      type boolean;
      description
        "Reports the validity of the corresponding 
         performance monitoring data. true = invalid.";
      reference
        "ITU-T G.997.2 clause 7.7.2 and 7.8.2.";
    }

    leaf forward-error-correction-seconds-lfe {
      type bbf-yang:performance-counter32;
      description
        "This parameter is a count of 1-second intervals with one
         or more FFEC anomalies summed over all transmitted
         bearer channels.";
      reference
        "ITU-T G.997.1 clause 7.2.1.2.1 Forward error correction
         second - Line far-end (FECS-LFE)";
    }

    leaf errored-seconds-lfe {
      type bbf-yang:performance-counter32;
      description
        "This parameter is a count of one-second intervals with
         one or more FEBE anomalies summed over all transmitted
         bearer channels, or one or more LOS-FE defects, or one
         or more RDI defects, or one or more LPR-FE defects.";
      reference
        "ITU-T G.997.1 clause 7.2.1.2.2 Errored second - Line
         far-end (ES-LFE)";
    }

    leaf severely-errored-seconds-lfe {
      type bbf-yang:performance-counter32;
      description
        "This parameter is a count of severely errored seconds
         (SES). An SES is declared if, during a 1-second
         interval, there are 18 or more FEBE anomalies in one or
         more of the transmitted bearer channels, or one or more
         far-end LOS defects, or one or more RDI defects, or one
         or more LPR-FE defects. If [ITU-T G.998.4] is supported
         and retransmission is enabled in the far-end received
         direction, a SES-LFE is also declared if, during a
         1-second interval, there is one or more severe loss of
         error-free throughput (seftr) defect in the far-end
         received direction.";
      reference
        "ITU-T G.997.1 clause 7.2.1.2.3 Severely errored second -
         Line far-end (SES-LFE)";
    }

    leaf loss-of-signal-seconds-lfe {
      type bbf-yang:performance-counter32;
      description
        "This parameter is a count of 1-second intervals
         containing one or more far-end LOS defects.";
      reference
        "ITU-T G.997.1 clause 7.2.1.2.4 LOS second - Line far-end
         (LOSS-LFE)";
    }

    leaf unavailable-seconds-lfe {
      type bbf-yang:performance-counter32;
      description
        "This parameter is a count of 1-second intervals for
         which the far-end xDSL line is unavailable. Some
         parameter counts are inhibited during unavailability -
         see ITU-T G.997.1 clause 7.2.7.13.";
      reference
        "ITU-T G.997.1 clause 7.2.1.2.5 Unavailable seconds -
         Line far-end (UAS-LFE)";
    }

    list inminpeq-lfe {
      key "inminpeq-index";
      leaf inminpeq-index {
        type uint8 {
          range "1..17";
        }
        description
          "Identifies the INMAINPEQ histogram bin";
      }
      leaf inminpeq-lfe {
        type bbf-yang:performance-counter32;
        description
          "Count of the far-end INMAINPEQ anomalies";
      }
      description
        "This parameter is a count of the far-end INMAINPEQi
         anomalies occurring on the line during the accumulation
         period. This parameter is subject to inhibiting - see
         ITU-T G.997.1 clause 7.2.7.13.";
      reference
        "ITU-T G.997.1 clause 7.2.1.5.1 INM INPEQ histogram 1..17
         (INMINPEQ1..17-LFE)";
    }

    leaf inmme-lfe {
      type bbf-yang:performance-counter32;
      description
        "This parameter is a count of the far-end INMAME
         anomalies occurring on the line during the accumulation
         period. This parameter is subject to inhibiting - see
         ITU-T G.997.1 clause 7.2.7.13.";
      reference
        "ITU-T G.997.1 clause 7.2.1.5.2 INM total measurement
         (INMME-LFE)";
    }

    list inmiat-lfe {
      key "inminiat-index";
      leaf inminiat-index {
        type uint8 {
          range "0..7";
        }
        description
          "Identifies the INMAIAT histogram bin";
      }
      leaf inmiat-lfe {
        type bbf-yang:performance-counter32;
        description
          "Count of the far-end INMAIAT anomalies";
      }
      description
        "This parameter is a count of the far-end INMAIATi
         anomalies occurring on the line during the accumulation
         period. This parameter is subject to inhibiting - see
         ITU-T G.997.1 clause 7.2.7.13.";
      reference
        "ITU-T G.997.1 clause 7.2.1.5.3 INM IAT histogram 0..7
         (INMIAT0..7-LFE)";
    }

    leaf sos-success-fe {
      type bbf-yang:performance-counter32;
      description
        "This parameter is a count of the total number of
         successful SOS procedures initiated by the far-end xTU
         on the line during the accumulation period. Parameter
         procedures will be as defined in ITU-T G.997.1 clause
         7.2.7. Successful SOS is defined in clause 12.1.4 of
         [ITU-T G.993.2].";
      reference
        "ITU-T G.997.1 clause 7.2.1.7.1 Far-end successful SOS
         count (SOS-SUCCESS-FE)";
    }

    leaf leftr-defects-seconds-counter-lfe {
      // only defined in downstream
      type bbf-yang:performance-counter32;
      description
        "Far-end line leftr defects seconds counter. If
         retransmission is used in a given transmit direction,
         this parameter is a count of the seconds with a far-end
         leftr defect present (see clause 11.4.1 of [ITU-T
         G.998.4] for the definition of this counter).
         The far-end counter is only defined in downstream.";
      reference
        "ITU-T G.997.1 clause 7.2.1.2.6 leftr defects seconds
         counter";
    }

    leaf error-free-bits-counter-lfe {
      // only defined downstream
      type bbf-yang:performance-counter32;
      description
        "Far-end line error-free bits counter. If retransmission
         is used in a given transmit direction, this parameter is
         a count of the number of error-free bits passed over the
         Beta1 reference point, divided by 65536 = 2^16 (see
         clause 11.4.2 of [ITU-T G.998.4] for the definition of
         this counter).
         This far-end counter is only defined in downstream.";
      reference
        "ITU-T G.997.1 clause 7.2.1.2.7 Error-free bits counter";
    }

    // only defined downstream
    leaf minimum-error-free-throughput-lfe {
      type bbf-yang:performance-counter32;
      units "bit/s";
      description
        "Far-end minimum error-free throughput (MINEFTR). If
         retransmission is used in a given transmit direction,
         this parameter MINEFTR reports the minimum of the EFTR
         observed over the 15-min or 24-hour accumulation period
         (see clause 11.4.3 of [ITU-T G.998.4] for the definition
         of this parameter). The value is reported in bit/s.
         This far-end value is only defined in downstream.";
      reference
        "ITU-T G.997.1 clause 7.2.1.2.8 Minimum error-free
         throughput (MINEFTR)";
    }

    // below three counters (los, lof, lpr) are from bbf2016.024
    leaf loss-of-signal-fe {
      type bbf-yang:performance-counter32;
      description
        "Reports a count of the far-end Loss-of-signal (LOS)
         failures.";
      reference
        "Borrowed from ITU-T G.997.2 clause 7.7.4 (LOS).
         Count of failures defined in ITU-T G.997.1 
         clause 7.1.1.2.1.";
    }

    leaf loss-of-frame-fe {
      type bbf-yang:performance-counter32;
      description
        "Reports a count of the Loss-of-frame (LOF) failures.";
      reference
        "Count of failures defined in ITU-T G.997.1 
         clause 7.1.1.2.2.";
    }

    leaf loss-of-power-fe {
      type bbf-yang:performance-counter32;
      description
        "reports a count of the Loss-of-power (LPR) failures.";
      reference
        "Borrowed from ITU-T G.997.2 clause 7.7.7 (LPR).
         Count of failures defined in ITU-T G.997.1 
         clause 7.1.1.2.3.";
    }
  } // end grouping xtu-r-line-performance  

  grouping line-time-stamp {
    description
      "Time stamp for line performance parameters.";

    leaf time-stamp {
      type yang:date-and-time;
      description
        "This parameter is the date and time when this
         counter completed measuring.";
      reference
        "ITU-T G.997.2 clause 7.7.3 and 7.7.3.";
    }
  }
} // end submodule xtu-line-performance-body
