submodule bbf-fast-perf-types {
  yang-version 1.1;
  belongs-to bbf-fast {
    prefix bbf-fast;
  }

  import ietf-yang-types {
    prefix yang;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of general performance
     related YANG data types and grouping definitions for the
     management of FAST line.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  feature performance-24hr {
    description
      "Indicates that collection of 24 hour performance intervals
       is supported";
  }

  typedef performance-15min-interval {
    type uint8 {
      range "0..96";
    }
    description
      "Defines the range of 15 minute intervals.";
  }

  typedef performance-15min-history-interval {
    type performance-15min-interval {
      range "1..96";
    }
    description
      "Defines the range of 15 minutes intervals and defines
       the position of the interval relative to the current interval
       where 1 is the most recent interval.";
  }

  typedef performance-24hr-interval {
    type uint8 {
      range "0..7";
    }
    description
      "Defines the range of 24 hour intervals.";
  }

  typedef performance-24hr-history-interval {
    type performance-24hr-interval {
      range "1..7";
    }
    description
      "Defines the range of 24 hour intervals and defines
       the position of the interval relative to the current interval
       where 1 is the most recent interval.";
  }

  grouping performance-history-interval-parameters {
    description
      "Defines common parameters required when defining history
       interval performance counters.";

    leaf invalid-data-flag {
      type boolean;
      description
        "Reports the validity of the corresponding PM data.";
      reference
        "ITU-T G.997.2 clause 7.7.2 and 7.8.2.";
    }

    leaf time-stamp {
      type yang:date-and-time;
      description
        "Reports the start date/time for this interval.";
      reference
        "ITU-T G.997.2 clause 7.7.3 and 7.7.3.";
    }
  }

  grouping performance-history-measured-time {
    description
      "Reports the measured time for a given interval";

    leaf measured-time {
      type uint32;
      description
        "Reports the amount of time, measured in seconds,
         that statistics for this interval have been counted.";
      reference
        "ITU-T G.997.2 clause 7.7.1 and 7.8.1.";
    }
  }

  grouping performance-history-15min-interval-parameters {
    description
      "Defines common parameters required when defining 15 minute
       interval history performance counters.";

    uses performance-history-measured-time;
    uses performance-history-interval-parameters;
  }

  grouping performance-history-24hr-interval-parameters {
    description
      "Defines common parameters required when defining 24 hour
       interval history performance counters.";

    uses performance-history-measured-time;
    uses performance-history-interval-parameters;
  }

  grouping performance-15min-history-parameters {
    description
      "Defines common parameters required when defining 15 minute
       history performance counters.";

    leaf number-of-intervals {
      type performance-15min-interval;
      description
        "The total number of 15-minute PM intervals for which data 
         was collected. ";
    }

    leaf non-valid-intervals {
      type performance-15min-interval;
      description
        "The number of 15-minute PM intervals for which the data
         is considered to be invalid or incomplete.";
    }
  }

  grouping performance-24hr-history-parameters {
    description
      "Defines common parameters required when defining 24 hour
       history performance counters.";

    leaf number-of-intervals {
      type performance-24hr-interval;
      description
        "The total number of 24-hour PM intervals for which data 
         was collected. ";
    }

    leaf non-valid-intervals {
      type performance-24hr-interval;
      description
        "The number of 24-hour PM intervals for which the data
         is considered to be invalid or incomplete.";
    }
  }
}
