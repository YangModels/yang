submodule bbf-vdsl-xtu-channel-performance-body {
  yang-version 1.1;
  belongs-to bbf-vdsl {
    prefix bbf-vdsl;
  }

  import bbf-yang-types {
    prefix bbf-yang;
  }

  import ietf-yang-types {
    prefix yang;
  }

  include bbf-vdsl-base-body;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 7.2 xTU Channel 
     Performance.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping xtu-channel-performance-c {

    description
      "The xTU Channel (near-end) performance object represents 
       channel performance related data for a particular channel
       associated with a particular xTU-C.";

    leaf measured-time {
      type uint32;
      description
        "Reports the amount of time, measured in seconds,
         that statistics for this interval have been counted.";
      reference
        "ITU-T G.997.2 clause 7.7.1 and 7.8.1.";
    }

    leaf invalid-data-flag {
      type boolean;
      description
        "Reports the validity of the corresponding 
         performance monitoring data.  true = invalid.";
      reference
        "ITU-T G.997.2 clause 7.7.2 and 7.8.2.";
    }

    leaf code-violations-c {
      type bbf-yang:performance-counter32;
      description
        "This parameter is a count of CRC-8 anomalies (the number
         of incorrect CRC) occurring in the bearer channel during
         the accumulation period. This parameter is subject to
         inhibiting - see ITU-T G.997.1 clause 7.2.7.13.";
      reference
        "ITU-T G.997.1 clause 7.2.2.1.1 Code violation - Channel
         (CV-C)";
    }

    leaf forward-error-corrections-c {
      type bbf-yang:performance-counter32;
      description
        "This parameter is a count of FEC anomalies (the number
         of corrected code words) occurring in the bearer channel
         during the accumulation period. This parameter is
         subject to inhibiting - see ITU-T G.997.1 clause
         7.2.7.13.";
      reference
        "ITU-T G.997.1 clause 7.2.2.1.2 Forward error correction
         - Channel (FEC-C)";
    }

    leaf uncorrected-dtu-c {
      type bbf-yang:performance-counter32;
      description
        "This parameter is a count of rtx-uc anomalies 
         (the number of uncorrected DTUs) occurring in the bearer
         channel during the accumulation period. This parameter
         only applies to systems supporting ITU-T G.998.4.
         This parameter is subject to inhibiting - see ITU-T
         G.997.1 clause 7.2.7.13.";
      reference
        "ITU-T G.997.1 clause 7.2.2.1.3\tUncorrected DTU - Channel
         (RTXUC-C).";
    }
  }

  grouping xtu-channel-performance-cfe {

    description
      "The xTU Channel far-end performance object represents channel
       performance related data for a particular channel associated
       with a particular xTU-R.";

    leaf measured-time {
      type uint32;
      description
        "Reports the amount of time, measured in seconds,
         that statistics for this interval have been counted.";
      reference
        "ITU-T G.997.2 clause 7.7.1 and 7.8.1.";
    }

    leaf invalid-data-flag {
      type boolean;
      description
        "Reports the validity of the corresponding 
         performance monitoring data.  true = invalid.";
      reference
        "ITU-T G.997.2 clause 7.7.2 and 7.8.2.";
    }

    leaf code-violations-cfe {
      type bbf-yang:performance-counter32;
      description
        "This parameter is a count of FEBE anomalies occurring in
         the bearer channel during the accumulation period. This
         parameter is subject to inhibiting - see ITU-T G997.1
         clause 7.2.7.13.";
      reference
        "ITU-T G.997.1 clause 7.2.2.2.1 Code violation - Channel
         far-end (CV-CFE)";
    }

    leaf forward-error-corrections-cfe {
      type bbf-yang:performance-counter32;
      description
        "This parameter is a count of FFEC anomalies occurring in
         the bearer channel during the accumulation period. This
         parameter is subject to inhibiting - see ITU-T G997.1
         clause 7.2.7.13.";
      reference
        "ITU-T G.997.1 clause 7.2.2.2.2 Forward error correction
         - Channel far-end (FEC-CFE)";
    }

    leaf uncorrected-dtu-cfe {
      type bbf-yang:performance-counter32;
      description
        "This parameter is a count of far-end rtx-uc anomalies 
         (the number of uncorrected DTUs) occurring in the bearer
         channel during the accumulation period. This parameter
         only applies to systems supporting ITU-T G.998.4.
         This parameter is subject to inhibiting - see ITU-T 
         G.997.1 clause 7.2.7.13.";
      reference
        "ITU-T G.997.1 clause 7.2.2.2.3\tUncorrected DTU - Channel
         far-end (RTXUC-CFE)";
    }
  } // end grouping xtu-channel-performance-cfe

  grouping performance-history-15min-parameters {
    description
      "Defines common parameters required of historical 
       performance counters across 15 minute intervals.";

    leaf number-of-intervals {
      type performance-15min-interval;
      description
        "The total number of 15-minute PM intervals for which data
         was collected. ";
    }

    leaf non-valid-intervals {
      type performance-15min-interval;
      description
        "The number of 15-minute PM intervals for which the data
         is considered to be invalid or incomplete.";
    }
  }

  grouping performance-history-24hr-parameters {
    description
      "Defines common parameters required of historical 
       performance counters across 24 hour intervals.";

    leaf number-of-intervals {
      type performance-24hr-interval;
      description
        "The total number of 24-hour performance monitoring
         intervals for which data was collected. ";
    }

    leaf non-valid-intervals {
      type performance-24hr-interval;
      description
        "The number of 24-hour performance monitoring
         intervals for which the data is considered to be
         invalid or incomplete.";
    }
  }

  grouping xtu-channel-time-stamp {
    description
      "Time stamp of channel performance parameters.";

    leaf time-stamp {
      type yang:date-and-time;
      description
        "This parameter is the date and time when this
         counter completed measuring.";
      reference
        "ITU-T G.997.2 clause 7.7.3 and 7.7.3.";
    }
  }
} // end submodule xtu-channel-performance-body
