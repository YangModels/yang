submodule bbf-vdsl-mode-specific-psd-profile-body {
  yang-version 1.1;
  belongs-to bbf-vdsl {
    prefix bbf-vdsl;
  }

  include bbf-vdsl-base-body;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 5.6 Spectrum related 
     profiles; Mode Specific PSD Profile.

     Copyright (c) 2016, 2017 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping mode-specific-psd-profile {

    description
      "These configuration parameters depend on a transmission mode.
       Each transmission mode enabled in a Line Spectrum Profile is
       covered by one and only one of the Mode Specific PSD Profiles
       contained in that Line Spectrum Profile.";

    leaf ts {
      type xts-descriptor;
      mandatory true;
      description
        "This indicates the transmission system type this mode 
         specific profile is used with.";
      reference
        "ITU-T G.997.1 clause 7.3.1.1.1 xTU transmission system
         enabling (XTSE)";
    }

    leaf maximum-nominal-psd-ds {
      type int16 {
        range "-600..-300";
      }
      units "0.1 dBm/Hz";
      default "-400";
      description
        "This parameter represents the maximum nominal transmit
         PSD in the downstream direction during initialization
         and showtime (in dBm/Hz). A single MAXNOMPSDds parameter
         is defined per mode enabled in the XTSE line
         configuration parameter. It ranges from -60 to -30
         dBm/Hz, with 0.1 dB steps.";
      reference
        "ITU-T G.997.1 clause 7.3.1.2.1 Downstream maximum
         nominal power spectral density (MAXNOMPSDds)";
    }

    leaf maximum-nominal-psd-us {
      type int16 {
        range "-600..-300";
      }
      units "0.1 dBm/Hz";
      default "-380";
      description
        "This parameter represents the maximum nominal transmit
         PSD in the upstream direction during initialization and
         showtime (in dBm/Hz). A single MAXNOMPSDus parameter is
         defined per mode enabled in the XTSE line configuration
         parameter. It ranges from -60 to -30 dBm/Hz, with 0.1 dB
         steps.";
      reference
        "ITU-T G.997.1 clause 7.3.1.2.2 Upstream maximum nominal
         power spectral density (MAXNOMPSDus)";
    }

    leaf maximum-aggregate-transmit-power-ds {
      type uint8 {
        range "0..255";
      }
      units "0.1 dBm";
      default "255";
      description
        "This parameter represents the maximum nominal aggregate
         transmit power in the downstream direction during
         initialization and showtime (in dBm). It ranges from 0
         to 25.5 dBm, with 0.1 dB steps.";
      reference
        "ITU-T G.997.1 clause 7.3.1.2.3 Downstream maximum
         nominal aggregate transmit power (MAXNOMATPds)";
    }

    leaf maximum-aggregate-transmit-power-us {
      type uint8 {
        range "0..255";
      }
      units "0.1 dBm";
      default "255";
      description
        "This parameter represents the maximum nominal aggregate
         transmit power in the upstream direction during
         initialization and showtime (in dBm). It ranges from 0
         to 25.5 dBm, with 0.1 dB steps.";
      reference
        "ITU-T G.997.1 clause 7.3.1.2.4 Upstream maximum nominal
         aggregate transmit power (MAXNOMATPus)";
    }

    leaf maximum-aggregate-receive-power-us {
      type union {
        type int16 {
          range "-255..255";
        }
        type enumeration {
          enum "unbounded" {
            description
              "Indicates that that no upstream maximum aggregate
               receive power limit is to be applied
               (i.e., the maximum value is unbounded).";
          }
        }
      }
      units "0.1 dBm";
      default "unbounded";
      description
        "This parameter represents the maximum upstream aggregate
         receive power over a set of subcarriers (in dBm) as
         specified in the relevant Recommendation. The xTU-C will
         request an upstream power cutback such that the upstream
         aggregate receive power over that set of subcarriers is
         at or below the configured maximum value. It ranges from
         -25.5 to 25.5 dBm, with 0.1 dB steps. A special value of 
         (enum unbounded) is used to indicate that no upstream
         maximum aggregate receive power limit is to be applied
         (i.e., the maximum value is unbounded).";
      reference
        "ITU-T G.997.1 clause 7.3.1.2.5 Upstream maximum
         aggregate receive power (MAXRXPWRus)";
    }

    container psd-mask-ds {
      uses psdmask-descriptor {
        refine "psdmask" {
          max-elements 32;
        }
      }
      description
        "This configuration parameter defines the downstream PSD
         mask applicable at the U-C2 reference point as defined
         in the respective Recommendation. A modified PSD mask,
         as defined in clause 7.3.1.2.13, may apply at the U-C2
         reference point. This MIB PSD mask may impose PSD
         restrictions in addition to the Limit PSD mask defined
         in the relevant Recommendations [ITU-T G.992.5] and 
         [ITU-T G.993.2].
         NOTE - In [ITU-T G.993.2], the PSDMASKds parameter is
         referred to as MIBMASKds.
         The downstream PSD mask in the CO-MIB will be specified
         through a set of breakpoints. Each breakpoint will
         consist of a subcarrier index t, with a subcarrier
         spacing of 4.3125 kHz, and a MIB PSD mask level
         (expressed in dBm/Hz) at that subcarrier. The set of
         breakpoints can then be represented as [(t1, PSD1), (t2,
         PSD2), , (tN, PSDN)]. The subcarrier index will be coded
         as an unsigned integer. The MIB PSD mask level will be
         coded as an unsigned integer representing the MIB PSD
         mask levels 0 dBm/Hz to -127.5 dBm/Hz, in steps of 0.5
         dBm/Hz, with valid range from 0 to -95 dBm/Hz. The
         maximum number of breakpoints is 32 for [ITU-T G.992.5] and 
         [ITU-T G.993.2].
         The default is an empty list indicating no PSD mask.";
      reference
        "ITU-T G.997.1 clause 7.3.1.2.9 Downstream PSD Mask
         (PSDMASKds)";
    }

    leaf upstream_psd_mask_selection {
      type uint8 {
        range "1..9";
      }
      default "9";
      description
        "This configuration parameter defines which upstream PSD
         mask is enabled. This parameter is used only for Annexes
         J and M of [ITU-T G.992.3] and [ITU-T G.992.5]. As only
         one selection parameter is defined in the MIB, the same
         selection value applies to all relevant modes enabled in
         the XTSE line configuration parameter. It ranges from 1
         to 9 and selects the mask with the definitions of Table
         7-5 of [ITU-T G.997.1].";
      reference
        "ITU-T G.997.1 clause 7.3.1.2.11 Upstream PSD mask
         selection";
    }

    container psd-mask-us {
      uses psdmask-descriptor {
        refine "psdmask" {
          max-elements 16;
        }
      }
      description
        "This configuration parameter defines the upstream PSD
         mask applicable at the U-R2 reference point as defined
         in the respective Recommendation. This MIB PSD mask may
         impose PSD restrictions in addition to the Limit PSD
         mask defined in the relevant Recommendations [ITU-T G.992.3 
         Annex J and M], [ITU-T G.992.5 Annex J and M], and 
         [ITU-T G.993.2].
         NOTE - In [ITU-T G.993.2], the PSDMASKus parameter is
         referred to as MIBMASKus and does not include
         breakpoints to shape US0.
         The upstream PSD mask in the CO-MIB will be specified
         through a set of breakpoints. Each breakpoint will
         consist of a subcarrier index t, with a subcarrier
         spacing of 4.3125 kHz, and a MIB PSD mask level
         (expressed in dBm/Hz) at that subcarrier. The set of
         breakpoints can then be represented as [(t1, PSD1), (t2,
         PSD2), , (tN, PSDN)]. The subcarrier index will be coded
         as an unsigned integer. The MIB PSD mask level will be
         coded as an unsigned integer representing the MIB PSD
         mask levels 0 dBm/Hz to -127.5 dBm/Hz, in steps of 0.5
         dBm/Hz, with valid range from 0 to -95 dBm/Hz. The
         maximum number of breakpoints is 4 for [ITU-T G.992.3 Annex J
         and M] and [ITU-T G.992.5 Annex J and M], and 16 for [ITU-T 
         G.993.2].
         The default is an empty list indicating no PSD mask.";
      reference
        "ITU-T G.997.1 clause 7.3.1.2.12 Upstream PSD mask
         (PSDMASKus)";
    }

    leaf limitmask {
      type limitmask-descriptor;
      must
        "(../ts!='xts57' and ../ts!='xts58' and ../ts!='xts59'
          and .='') or .!=''" {
        description
          "If the transmission system is VDSL, then the limitmask must
           be populated.";
      }
      default "";
      description
        "This configuration parameter contains the G.993.2 limit
         PSD masks of the selected PSD mask class, enabled by the
         near-end xTU on this line for each class of profiles.
         One LIMITMASK parameter is defined per the G.993.2 Annex
         enabled in the XTSE.
         For each profile class, several limit PSD masks of the
         selected PSD mask class (CLASSMASK) may be enabled. The
         enabling parameter is coded in a bit-map representation
         (0 if the associated mask is not allowed, 1 if it is
         allowed). The profiles are grouped into profile classes.
         The default is an empty bit list, corresponding to no VDSL2
         limit masks enabled.";
      reference
        "ITU-T G.997.1 clause 7.3.1.2.16 VDSL2 limit PSD masks
         and band plans enabling (LIMITMASK)";
    }

    leaf us0disable {
      type limitmask-descriptor;
      default "";
      description
        "This configuration parameter indicates if the use of US0
         is disabled for each limit PSD mask enabled in the
         LIMITMASK parameter. One US0DISABLE parameter is defined
         per the G.993.2 Annex enabled in the XTSE.
         For each limit PSD mask enabled in the LIMITMASK
         parameter, a bit will indicate if US0 is disabled. The
         disabling parameter is coded as a bit-map. The bit is
         set to 1 if US0 is disabled for the associated limit
         mask. The bit-map has the same structure as the
         LIMITMASK parameter.
         The default is an empty bit list, corresponding to VDSL2 US0 
         enabled for each limit PSD mask enabled in the LIMITMASK 
         parameter.";
      reference
        "ITU-T G.997.1 clause 7.3.1.2.17 VDSL2 US0 disabling
         (US0DISABLE).";
    }

    leaf classmask {
      type classmask-descriptor;
      must
        "(../ts!='xts57' and ../ts!='xts58' and ../ts!='xts59')
          or (../ts='xts57' and (.='class1'))
          or (../ts='xts58' and ((.='class1') or (.='class2')
          or (.='class3') or (.='class5') or (.='class6')
          or (.='class8') or (.='class9')))
          or (../ts='xts59' and ((.='class1') or (.='class2')))" {
        description
          "If the transmission system is VDSL, ensure the classmask
           support aligns with Table 7-6 in ITU-T G.997.1.";
      }
      default "none";
      description
        "The parameter configures CLASSMASK. The default is 'none', 
         corresponding to no VDSL2 classmask selected.";
      reference
        "ITU-T G.997.1 clause 7.3.1.2.15 VDSL2 PSD mask class
         selection (CLASSMASK).";
    }
  } // end grouping mode-specific-psd-profile
} // end submodule mode-specific-psd-profile-body
