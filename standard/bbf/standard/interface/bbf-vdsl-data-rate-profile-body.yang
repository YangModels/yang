submodule bbf-vdsl-data-rate-profile-body {
  yang-version 1.1;
  belongs-to bbf-vdsl {
    prefix bbf-vdsl;
  }

  import bbf-yang-types {
    prefix bbf-yang;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for 
     managing Broadband Forum TR-252i3 clause 5.5 Service related 
     profiles; DS Data Rate Profile and US Data Rate Profile.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping data-rate-profile {

    description
      "Data rate profile for upstream and downstream";

    leaf minimum-net-data-rate {
      type bbf-yang:data-rate32;
      default "0";
      description
        "If retransmission is not used in a given transmit
         direction, this parameter specifies the minimum net data
         rate for the bearer channel as desired by the operator
         of the system. The rate is coded in steps of 1,000
         bit/s.";
      reference
        "ITU-T G.997.1 clause 7.3.2.1.1 Minimum data rate";
    }

    leaf minimum-reserved-data-rate {
      type bbf-yang:data-rate32;
      default "0";
      description
        "This parameter specifies the minimum reserved net data
         rate for the bearer channel as desired by the operator
         of the system. The rate is coded in steps of 1,000
         bit/s.
         This parameter is optional. It is used only if the rate
         adaptation mode is set to DYNAMIC.";
      reference
        "ITU-T G.997.1 clause 7.3.2.1.2 Minimum reserved data
         rate";
    }

    leaf maximum-net-data-rate {
      type bbf-yang:data-rate32;
      default "4294967295";
      description
        "If retransmission is not used in a given transmit
         direction, this parameter specifies the maximum net data
         rate for the bearer channel as desired by the operator
         of the system. The data rate is coded in steps of 1,000
         bit/s.";
      reference
        "ITU-T G.997.1 clause 7.3.2.1.3 Maximum data rate";
    }

    leaf rate-adaptation-ratio {
      type uint8 {
        range "0..100";
      }
      units "percent";
      default "100";
      description
        "This parameter (expressed in %) specifies the ratio that
         will be taken into account for the bearer channel when
         performing rate adaptation in the transmission direction
         of the bearer channel. The ratio is defined as a
         percentage in the 0 to 100 range. A ratio of 20% means
         that 20% of the available data rate (in excess of the
         minimum data rate summed over all bearer channels) will
         be assigned to this bearer channel and 80% to the other
         bearer channels.
         The sum of rate adaptation ratios over all bearers in
         one direction will be equal to 100%.";
      reference
        "ITU-T G.997.1 clause 7.3.2.1.4 Rate adaptation ratio";
    }

    leaf minimum-data-rate-in-low-power-state {
      type bbf-yang:data-rate32;
      default "0";
      description
        "This parameter specifies the minimum net data rate for
         the bearer channel as desired by the operator of the
         system during the low power state (L1/L2). The power
         management low power states L1 and L2 are defined in
         [ITU-T G.992.2] and [ITU-T G.992.3], respectively. The
         data rate is coded in steps of 1,000 bit/s.";
      reference
        "ITU-T G.997.1 clause 7.3.2.1.5 Minimum data rate in low
         power state";
    }

    leaf maximum-bit-error-ratio {
      type enumeration {
        enum "1e-3" {
          description
            "bit error ratio 10^-3";
        }
        enum "1e-5" {
          description
            "bit error ratio 10^-5";
        }
        enum "1e-7" {
          description
            "bit error ratio 10^-7";
        }
      }
      default "1e-7";
      description
        "If retransmission is not used in a given transmit
         direction, this parameter specifies the maximum bit
         error ratio for the bearer channel as desired by the
         operator of the system. The bit error ratio can take the
         values 10^-3, 10^-5 or 10^-7. The default is 1e-7.";
      reference
        "ITU-T G.997.1 clause 7.3.2.6 Maximum bit error ratio";
    }

    leaf data-rate-threshold-upshift {
      type bbf-yang:data-rate32;
      default "0";
      description
        "If retransmission is not used in a given transmit
         direction, this parameter is a threshold on the net data
         rate upshift achieved over one or more bearer channel
         data rate adaptations. An upshift rate change alarm
         (event) is triggered when the actual data rate exceeds
         the data rate at the last entry into showtime by more
         than the threshold. The data rate threshold is coded in
         bit/s. The default of 0 corresponds to no event on a
         threshold crossing.";
      reference
        "ITU-T G.997.1 clause 7.3.2.8.1 Data rate threshold
         upshift";
    }

    leaf data-rate-threshold-downshift {
      type bbf-yang:data-rate32;
      default "0";
      description
        "If retransmission is not used in a given transmit
         direction, this parameter is a threshold on the net data
         rate downshift achieved over one or more bearer channel
         data rate adaptations. A downshift rate change alarm
         (event) is triggered when the actual data rate is below
         the data rate at the last entry into showtime by more
         than the threshold. The data rate threshold is coded in
         bit/s. The default of 0 corresponds to no event on a
         threshold crossing.";
      reference
        "ITU-T G.997.1 clause 7.3.2.8.2 Data rate threshold
         downshift";
    }

    leaf minimum-sos-data-rate {
      type bbf-yang:data-rate32;
      default "0";
      description
        "This parameter specifies the minimum net data rate for
         the bearer channel required for a valid SOS request in
         the direction of the bearer channel. The value will be
         coded as an unsigned integer representing the data rate
         as a multiple of 8 kbit/s. ";
      reference
        "ITU-T G.997.1 clause 7.3.2.1.6 Minimum SOS Data rate
         (MIN-SOS-DR)";
    }

    leaf minimum-expected-throughput-rtx {
      type bbf-yang:data-rate32;
      default "0";
      description
        "If retransmission is used in a given transmit direction,
         this parameter specifies the minimum expected throughput
         for the bearer channel (as specified in clause 11.1.1 of
         [ITU-T G.998.4]). The rate is coded in steps of 1,000
         bit/s.";
      reference
        "ITU-T G.997.1 clause 7.3.2.1.8 Minimum expected
         throughput for retransmission (MINETR_RTX)";
    }

    leaf maximum-expected-throughput-rtx {
      type bbf-yang:data-rate32;
      default "4294967295";
      description
        "If retransmission is used in a given transmit direction,
         this parameter specifies the maximum expected throughput
         for the bearer channel (as specified in clause 11.1.2 of
         [ITU-T G.998.4]). The rate is coded in steps of 1,000
         bit/s.";
      reference
        "ITU-T G.997.1 clause 7.3.2.1.9 Maximum expected
         throughput for retransmission (MAXETR_RTX)";
    }

    leaf maximum-net-data-rate-rtx {
      type bbf-yang:data-rate32;
      default "4294967295";
      description
        "If retransmission is used in a given transmit direction,
         this parameter specifies the maximum net data rate for
         the bearer channel (as specified in clause 11.1.3 of
         [ITU-T G.998.4]). The rate is coded in steps of 1,000
         bit/s.";
      reference
        "ITU-T G.997.1 clause 7.3.2.1.10 Maximum net data rate
         for retransmission (MAXNDR_RTX)";
    }

    leaf target-net-data-rate {
      type bbf-yang:data-rate32;
      default "4294967295";
      description
        "If retransmission is not used in a given transmit
         direction, this parameter specifies the target net data
         rate as defined in [ITU-T G.993.5] of the bearer
         channel. The target expected throughput is coded in
         steps of 1,000 bit/s.";
      reference
        "ITU-T G.997.1 clause 7.3.2.19.1 Target net data rate
         (TARGET_NDR) ";
    }

    leaf target-expected-throughput {
      type bbf-yang:data-rate32;
      default "4294967295";
      description
        "If retransmission is used in a given transmit direction,
         this parameter specifies the target expected throughput
         as defined in [ITU-T G.993.5] for the bearer channel.
         The target expected throughput is coded in steps of
         1,000 bit/s.";
      reference
        "ITU-T G.997.1 clause 7.3.2.19.2 Target expected
         throughput for retransmission (TARGET_ETR)";
    }
  } // end grouping data-rate-profile
} // end submodule data-rate-profile-body
