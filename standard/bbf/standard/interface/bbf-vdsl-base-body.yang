submodule bbf-vdsl-base-body {
  yang-version 1.1;

  belongs-to bbf-vdsl {
    prefix bbf-vdsl;
  }

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     Editor:      William Lupton, Broadband Forum
                  <mailto:wlupton@broadband-forum.org>

     WA Director: Christopher Croot, BT plc
                  <mailto:chris.croot@bt.com>

     WA Director: Sven Ooghe, Nokia
                  <mailto:sven.ooghe@nokia.com>";

  description
    "This submodule contains a collection of YANG definitions for 
     managing common aspects of VDSL used among other submodules.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355; see
     the TR itself for full legal notices.";

  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef line-identifier {
    type string {
      length "1..64";
    }
    description
      "identifies a line";
  }

  // used for identifiers that aren't formally called out in TR-252
  typedef profile-identifier {
    type string {
      length "1..64";
    }
    description
      "used for identifing profiles";
  }

  typedef performance-15min-history-interval {
    type uint8 {
      range "1..96";
    }
    description
      "Defines the range of 15 minutes intervals and defines
       the position of the interval relative to the current interval
       where 1 is the most recent interval.";
  }

  typedef performance-24hr-history-interval {
    type uint8 {
      range "1..28";
    }
    description
      "Defines the range of 24 hour intervals and defines
       the position of the interval relative to the current interval
       where 1 is the most recent interval.";
  }

  typedef performance-15min-interval {
    type uint8 {
      range "0..96";
    }
    description
      "Defines the range of 15 minute intervals.";
  }

  typedef performance-24hr-interval {
    type uint8 {
      range "0..28";
    }
    description
      "Defines the range of 24 hour intervals.";
  }

  typedef xts-descriptor {
    type enumeration {
      enum "xts1" {
        description
          "Regional standards. It is recommended that
           bit1 be used for ATIS-0600413";
      }
      enum "xts2" {
        description
          "Regional standards. It is recommended that
           bit2 be used for Annex C of ETSI TS 101 388";
      }
      enum "xts3" {
        description
          "G.992.1 operation over POTS non-overlapped spectrum
           (Annex A of [ITU-T G.992.1])";
      }
      enum "xts4" {
        description
          "G.992.1 operation over POTS overlapped spectrum
           (Annex A of [ITU-T G.992.1])";
      }
      enum "xts5" {
        description
          "G.992.1 operation over ISDN non-overlapped spectrum
           (Annex B of [ITU-T G.992.1])";
      }
      enum "xts6" {
        description
          "G.992.1 operation over ISDN overlapped spectrum
           (Annex B of [ITU-T G.992.1])";
      }
      enum "xts7" {
        description
          "G.992.1 operation in conjunction with TCM ISDN
           non-overlapped spectrum (Annex C of [ITU T G.992.1])";
      }
      enum "xts8" {
        description
          "G.992.1 operation in conjunction with TCM ISDN
           overlapped spectrum (Annex C of [ITU T G.992.1])";
      }
      enum "xts9" {
        description
          "G.992.2 operation over POTS non-overlapped spectrum
           (Annex A of [ITU-T G.992.2])";
      }
      enum "xts10" {
        description
          "G.992.2 operation over POTS overlapped spectrum
           (Annex B of [ITU-T G.992.2])";
      }
      enum "xts11" {
        description
          "G.992.2 operation in conjunction with TCM ISDN
           non-overlapped spectrum (Annex C of [ITU T G.992.2])";
      }
      enum "xts12" {
        description
          "G.992.2 operation in conjunction with TCM ISDN
           overlapped spectrum (Annex C of [ITU T G.992.2])";
      }
      // enum xts13; // Reserved
      // enum xts14; // Reserved
      // enum xts15; // Reserved
      // enum xts16; // Reserved
      // enum xts17; // Reserved
      // enum xts18; // Reserved
      enum "xts19" {
        description
          "G.992.3 operation over POTS non-overlapped spectrum
           (Annex A of [ITU-T G.992.3]).";
      }
      enum "xts20" {
        description
          "G.992.3 operation over POTS overlapped spectrum
           (Annex A of [ITU-T G.992.3])";
      }
      enum "xts21" {
        description
          "G.992.3 operation over ISDN non-overlapped spectrum
           (Annex B of [ITU-T G.992.3])";
      }
      enum "xts22" {
        description
          "G.992.3 operation over ISDN overlapped spectrum
           (Annex B of [ITU-T G.992.3])";
      }
      enum "xts23" {
        description
          "G.992.3 operation in conjunction with TCM ISDN
           non-overlapped spectrum (Annex C of [ITU T G.992.3])";
      }
      enum "xts24" {
        description
          "G.992.3 operation in conjunction with TCM ISDN
           overlapped spectrum (Annex C of [ITU T G.992.3])";
      }
      enum "xts25" {
        description
          "G.992.4 operation over POTS non-overlapped spectrum
           (Annex A of [ITU-T G.992.4])";
      }
      enum "xts26" {
        description
          "G.992.4 operation over POTS overlapped spectrum
           (Annex A of [ITU-T G.992.4])";
      }
      // enum xts27; // Reserved
      // enum xts28; // Reserved
      enum "xts29" {
        description
          "G.992.3 all digital mode operation with non-overlapped
           spectrum (Annex I of [ITU T G.992.3])";
      }
      enum "xts30" {
        description
          "G.992.3 all digital mode operation with overlapped
           spectrum (Annex I of [ITU T G.992.3])";
      }
      enum "xts31" {
        description
          "G.992.3 all digital mode operation with non-overlapped
           spectrum (Annex J of [ITU T G.992.3])";
      }
      enum "xts32" {
        description
          "G.992.3 all digital mode operation with overlapped
           spectrum (Annex J of [ITU T G.992.3])";
      }
      enum "xts33" {
        description
          "G.992.4 all digital mode operation with non-overlapped
           spectrum (Annex I of [ITU T G.992.4])";
      }
      enum "xts34" {
        description
          "G.992.4 all digital mode operation with overlapped
           spectrum (Annex I of [ITU T G.992.4])";
      }
      enum "xts35" {
        description
          "G.992.3 reach extended operation over POTS, Mode 1
           (non-overlapped, wide upstream)
           (Annex L of [ITU-T G.992.3])";
      }
      enum "xts36" {
        description
          "G.992.3 reach extended operation over POTS, Mode 2
           (non-overlapped, narrow upstream)
           (Annex L of [ITU-T G.992.3])";
      }
      enum "xts37" {
        description
          "G.992.3 reach extended operation over POTS, Mode 3
           (overlapped, wide upstream)
           (Annex L of [ITU-T G.992.3])";
      }
      enum "xts38" {
        description
          "G.992.3 reach extended operation over POTS, Mode 4
           (overlapped, narrow upstream)
           (Annex L of [ITU-T G.992.3])";
      }
      enum "xts39" {
        description
          "G.992.3 extended upstream operation over POTS
           non-overlapped spectrum (Annex M of [ITU-T G.992.3])";
      }
      enum "xts40" {
        description
          "G.992.3 extended upstream operation over POTS
           overlapped spectrum (Annex M of [ITU T G.992.3])";
      }
      enum "xts41" {
        description
          "G.992.5 operation over POTS non-overlapped spectrum
           (Annex A of [ITU-T G.992.5])";
      }
      enum "xts42" {
        description
          "G.992.5 operation over POTS overlapped spectrum
           (Annex A of [ITU-T G.992.5])";
      }
      enum "xts43" {
        description
          "G.992.5 operation over ISDN non-overlapped spectrum
           (Annex B of [ITU-T G.992.5])";
      }
      enum "xts44" {
        description
          "G.992.5 operation over ISDN overlapped spectrum
           (Annex B of [ITU-T G.992.5])";
      }
      enum "xts45" {
        description
          "G.992.5 operation in conjunction with TCM ISDN
           non-overlapped spectrum (Annex C of [ITU T G.992.5])";
      }
      enum "xts46" {
        description
          "G.992.5 operation in conjunction with TCM ISDN
           overlapped spectrum (Annex C of [ITU T G.992.5])";
      }
      enum "xts47" {
        description
          "G.992.5 all digital mode operation with non-overlapped
           spectrum (Annex I of [ITU T G.992.5])";
      }
      enum "xts48" {
        description
          "G.992.5 all digital mode operation with overlapped
           spectrum (Annex I of [ITU T G.992.5])";
      }
      enum "xts49" {
        description
          "G.992.5 all digital mode operation with non-overlapped
           spectrum (Annex J of [ITU T G.992.5])";
      }
      enum "xts50" {
        description
          "G.992.5 all digital mode operation with overlapped
           spectrum (Annex J of [ITU T G.992.5])";
      }
      enum "xts51" {
        description
          "G.992.5 extended upstream operation over POTS
           non-overlapped spectrum (Annex M of [ITU-T G.992.5])";
      }
      enum "xts52" {
        description
          "G.992.5 extended upstream operation over POTS
           overlapped spectrum (Annex M of [ITU T G.992.5])";
      }
      // enum xts53; // Reserved
      // enum xts54; // Reserved
      // enum xts55; // Reserved
      // enum xts56; // Reserved
      enum "xts57" {
        description
          "G.993.2 Region A (North America)
           (Annex A of [ITU-T G.993.2])";
      }
      enum "xts58" {
        description
          "G.993.2 Region B (Europe)
           (Annex B of [ITU-T G.993.2])";
      }
      enum "xts59" {
        description
          "G.993.2 Region C (Japan)
           (Annex C of [ITU-T G.993.2])";
      }
      // enum xts60; // Reserved
      // enum xts61; // Reserved
      // enum xts62; // Reserved
      // enum xts63; // Reserved
      // enum xts64; // Reserved
    }

    description
      "This is used in *-body submodules to define transmission
       system capabilities (XTS).
       This defines the transmission system types to be
       allowed by the near-end xTU on this line.";
    reference
      "ITU-T G.997.1 clause 7.3.1.1.1 xTU transmission system
       enabling (XTSE)";
  } // end typedef xts-descriptor


  typedef us0mask-descriptor {
    type bits {
      bit bit1 {
        position 1;
        description
          "Octet 1 bit 1, EU-32";
      }
      bit bit2 {
        position 2;
        description
          "Octet 1 bit 2, EU-36";
      }
      bit bit3 {
        position 3;
        description
          "Octet 1 bit 3, EU-40";
      }
      bit bit4 {
        position 4;
        description
          "Octet 1 bit 4, EU-44";
      }
      bit bit5 {
        position 5;
        description
          "Octet 1 bit 5, EU-48";
      }
      bit bit6 {
        position 6;
        description
          "Octet 1 bit 6, EU-52";
      }
      bit bit7 {
        position 7;
        description
          "Octet 1 bit 7, EU-56";
      }
      bit bit8 {
        position 8;
        description
          "Octet 1 bit 8, EU-60";
      }
      bit bit9 {
        position 9;
        description
          "Octet 2 bit 1, EU-64";
      }
      bit bit10 {
        position 10;
        description
          "Octet 2 bit 2, EU-128";
      }
      // bit bit11; // reserved by ITU
      // bit bit12; // reserved by ITU
      // bit bit13; // reserved by ITU
      // bit bit14; // reserved by ITU
      // bit bit15; // reserved by ITU
      // bit bit16; // reserved by ITU
      bit bit17 {
        position 17;
        description
          "Octet 3 bit 1, ADLU-32";
      }
      bit bit18 {
        position 18;
        description
          "Octet 3 bit 2, ADLU-36";
      }
      bit bit19 {
        position 19;
        description
          "Octet 3 bit 3, ADLU-40";
      }
      bit bit20 {
        position 20;
        description
          "Octet 3 bit 4, ADLU-44";
      }
      bit bit21 {
        position 21;
        description
          "Octet 3 bit 5, ADLU-48";
      }
      bit bit22 {
        position 22;
        description
          "Octet 3 bit 6, ADLU-52";
      }
      bit bit23 {
        position 23;
        description
          "Octet 3 bit 7, ADLU-56";
      }
      bit bit24 {
        position 24;
        description
          "Octet 3 bit 8, ADLU-60";
      }
      bit bit25 {
        position 25;
        description
          "Octet 4 bit 1, ADLU-64";
        // Called bit 9 in ITU-T G.997.1
      }
      bit bit26 {
        position 26;
        description
          "Octet 4 bit 2, ADLU-128";
        // Called bit 10 in ITU-T G.997.1
      }
      // bit bit27;
      // bit bit28;
      // bit bit29;
      // bit bit30;
      // bit bit31;
      // bit bit32;
    }
    description
      "Defines us0mask so it can be used for both configuration in
       line-spectrum-profile and status in line-xtu-status.
       This contains the US0 PSD masks for
       the near-end xTU on the line. This parameter is only
       defined for Annex A of [ITU-T G.993.2]. It is
       represented as a bitmap (0 or false if not allowed, and
       1 or true if allowed) with the definitions of Table 7-8
       of [ITU-T G.997.1]. The default is all 1s, corresponding to
       all US0 PSD masks allowed.";
    reference
      "ITU-T G.997.1 clause 7.3.1.2.18 VDSL2 US0 PSD masks
       (US0MASK)";
  } // end typedef us0mask-descriptor

  typedef limitmask-descriptor {

    type bits {
      bit class8 {
        position 0;
        description
          "Class 8: Profiles 8a, 8b, 8c, 8d";
      }
      bit class12 {
        position 1;
        description
          "Class 12: Profiles 12a, 12b";
      }
      bit class17 {
        position 2;
        description
          "Class 17: Profile 17a";
      }
      bit class30 {
        position 3;
        description
          "Class 30: Profile 30a";
      }
    }
    description
      "This contains the G.993.2 limit PSD masks of the selected
       PSD mask class, enabled by the
       near-end xTU on this line for each class of profiles.
       One LIMITMASK parameter is defined per the G.993.2 Annex
       enabled in the XTSE.
       For each profile class, several limit PSD masks of the
       selected PSD mask class (CLASSMASK) may be enabled. The
       enabling parameter is coded in a bit-map representation
       (0 if the associated mask is not allowed, 1 if it is
       allowed). The profiles are grouped into profile classes.
       The default is all 1s, corresponding to all VDSL2 PSD 
       limit masks allowed.";
    reference
      "ITU-T G.997.1 clause 7.3.1.2.16 VDSL2 limit PSD masks
       and band plans enabling (LIMITMASK)";
  } // end typedef limitmask-descriptor

  typedef classmask-descriptor {
    type bits {
      bit class998 {
        position 0;
        description
          "Class 998 Annex A of [ITU-T G.993.2]: D-32, D-48,
           D-64, D-128.";
      }
      bit class997-M1c {
        position 1;
        description
          "Class 997-M1c Annex B of [ITU-T G.993.2]:
           997-M1c-A-7.";
      }
      bit class997-M1x {
        position 2;
        description
          "Class 997-M1x Annex B of [ITU-T G.993.2]:
           997-M1x-M.";
      }
      bit class997-M2x {
        position 3;
        description
          "Class 997-M2x Annex B of [ITU-T G.993.2]:
           997E17-M2x-NUS0, 997E30-M2x-NUS0.";
      }
      bit class998-M1x {
        position 4;
        description
          "Class 998-M1x Annex B of [ITU-T G.993.2]: 998-M1x-A,
           998-M1x-B, 998-M1x-NUS0.";
      }
      bit class998-M2x {
        position 5;
        description
          "Class 998-M2x Annex B of [ITU-T G.993.2]: 998-M2x-A,
           998-M2x-M, 998-M2x-B, 998-M2x-NUS0, 998E17-M2x-NUS0,
           998E17-M2x-NUS0-M, 998E30-M2x-NUS0,
           998E30-M2x-NUS0-M.";
      }
      bit class998ADE-M2x {
        position 6;
        description
          "Class 998ADE-M2x Annex B of [ITU-T G.993.2]:
           998-M2x-A, 998-M2x-M, 998-M2x-B, 998-M2x-NUS0,
           998ADE17-M2x-A, 998ADE17-M2x-B, 998ADE17-M2x-M,
           998ADE17-M2x-NUS0-M, 998ADE30-M2x-NUS0-A,
           998ADE30-M2x-NUS0-M.";
      }
      bit class998-B {
        position 7;
        description
          "Class 998-B Annex C: POTS-138b, POTS-276b (clause
           C.2.1.1 of [ITU-T G.993.2]), TCM-ISDN
           (C.2.1.2/G.993.2).";
      }
      bit class998-CO {
        position 8;
        description
          "Class 998-CO Annex C of [ITU-T G.993.2]: POTS-138co,
           POTS-276co (clause C.2.1.1 of [ITU-T G.993.2]).";
      }
      bit classHPE-M1 {
        position 9;
        description
          "Class HPE-M1 Annex B of [ITU-T G.993.2]:
           HPE17-M1-NUS0, HPE30-M1-NUS0, HPE1230-M1-NUS0,
           HPE1730-M1-NUS0.";
      }
    }
    description
      "In order to reduce the number of configuration
       possibilities, the limit power spectral density masks
       (limit PSD masks) are grouped in the PSD mask classes.
       Each class is designed such that the PSD levels of each
       limit PSD mask of a specific class are equal in their
       respective passband above 552 kHz.
       One CLASSMASK parameter is defined per the G.993.2 Annex
       enabled in the XTSE. It selects a single PSD mask class
       per the G.993.2 Annex that is activated at the VTU-O.
       The coding is as indicated in Table 7-6 of [ITU-T G.997.1].
       For each profile class, several limit PSD masks of the
       selected PSD mask class (CLASSMASK) may be enabled. The
       enabling parameter is coded in a bit-map representation
       (0 if the associated mask is not allowed, 1 if it is allowed).
       The parameter has the bit definitions for each PSD mask
       class as indicated in Table 7-7 of [ITU-T G.997.1].
       The default is all 1s, corresponding to all VDSL2 PSD limit 
       masks allowed.";
    reference
      "ITU-T G.997.1 clause 7.3.1.2.15 VDSL2 PSD mask class
       selection (CLASSMASK)";
  }

  typedef profiles {
    type bits {
      bit profile-8a {
        position 1;
        description
          "G.993.2 profile 8a.";
      }
      bit profile-8b {
        position 2;
        description
          "G.993.2 profile 8b.";
      }
      bit profile-8c {
        position 3;
        description
          "G.993.2 profile 8c.";
      }
      bit profile-8d {
        position 4;
        description
          "G.993.2 profile 8d.";
      }
      bit profile-12a {
        position 5;
        description
          "G.993.2 profile 12a.";
      }
      bit profile-12b {
        position 6;
        description
          "G.993.2 profile 12b.";
      }
      bit profile-17a {
        position 7;
        description
          "G.993.2 profile 17a.";
      }
      bit profile-30a {
        position 8;
        description
          "G.993.2 profile 30a.";
      }
      bit profile-35b {
        position 9;
        description
          "G.993.2 profile 35b.";
      }
    }
    description
      "Delineates the VDSL2 profiles.";
    reference
      "ITU-T G.993.2.";
  }

  grouping psdmask-descriptor {
    list psdmask {
      key "group-number";
      leaf group-number {
        type uint16;
        description
          "The subcarrier index or sub-carrier group index";
      }
      leaf sub-carrier {
        type uint16 {
          range "0..8191";
        }
        description
          "sub-carrier or sub-carrier group index";
      }
      leaf psd-level {
        type uint8 {
          range "0..255";
        }
        units "-0.5 dBm/Hz";
        description
          "PSD level. Valid values: 0..255 (0 to -127.5 dBm/Hz)";
      }
      description
        "This list defines a PSD level per subcarrier or per 
         subcarrier group. The default is an empty list indicating no 
         PSD mask.";
    }
    description
      "This grouping is used in other *-body submodules to define
       a power spectral density (PSD) or PSD mask";
  }

  typedef band {
    type enumeration {
      enum "upstream" {
        description
          "Transmission from the xTU-R to the xTU-C (refers to the 
           single upstream band for ADSL/ADSL2/ADSL2plus or to the 
           whole upstream traffic for VDSL2).";
      }
      enum "downstream" {
        description
          "Transmission from the xTU-C to the xTU-R (refers to the 
           single downstream band for ADSL/ADSL2/ADSL2plus or to the
           whole downstream traffic for VDSL2).";
      }
      enum "us0" {
        description
          "Upstream band 0";
      }
      enum "us1" {
        description
          "Upstream band 1";
      }
      enum "us2" {
        description
          "Upstream band 2";
      }
      enum "us3" {
        description
          "Upstream band 3";
      }
      enum "us4" {
        description
          "Upstream band 4";
      }
      enum "ds1" {
        description
          "Downstream band 1";
      }
      enum "ds2" {
        description
          "Downstream band 2";
      }
      enum "ds3" {
        description
          "Downstream band 3";
      }
      enum "ds4" {
        description
          "Downstream band 4";
      }
    }
    description
      "Represents the available upstream and downstream bands";
  }
}
