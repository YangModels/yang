module iana-ssh-public-key-algs {
  yang-version 1.1;
  namespace "urn:ietf:params:xml:ns:yang:iana-ssh-public-key-algs";
  prefix sshpka;

  organization
    "Internet Assigned Numbers Authority (IANA)";

  contact
    "Postal: ICANN
             12025 Waterfront Drive, Suite 300
             Los Angeles, CA  90094-2536
             United States of America
     Tel:    +1 310 301 5800
     Email:  iana@iana.org";

  description
    "This module defines enumerations for the public key algorithms
     defined in the 'Public Key Algorithm Names' registry of the
     'Secure Shell (SSH) Protocol Parameters' registry group
     maintained by IANA.

     Copyright (c) 2024 IETF Trust and the persons identified as
     authors of the code.  All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     The initial version of this YANG module is part of RFC 9644
     (https://www.rfc-editor.org/info/rfc9644); see the RFC
     itself for full legal notices.

     All versions of this module are published by IANA at
     https://www.iana.org/assignments/yang-parameters.";
	 
  revision 2026-09-08 {
    description
      "Registered ssh-mldsa-44, ssh-mldsa-65, ssh-mldsa-87, ssh-mldsa44-ed25519, and ssh-mldsa87-p384.";
    reference
      "draft-sfluhrer-ssh-mldsa-08
	  draft-ietf-sshm-composite-sigs-00";
  }

  revision 2024-10-16 {
    description
      "This initial version of the module was created using
       the script defined in RFC 9644 to reflect the contents
       of the public key algorithms registry maintained by IANA.";
    reference
      "RFC 9644: YANG Groupings for SSH Clients and SSH Servers";
  }

  typedef ssh-public-key-algorithm {
    type enumeration {

      enum ssh-dss {
        description
          "Enumeration for the 'ssh-dss' algorithm. Section 6.6";
        reference
          "RFC 4253:
             The Secure Shell (SSH) Transport Layer Protocol";
      }

      enum ssh-rsa {
        description
          "Enumeration for the 'ssh-rsa' algorithm. Section 6.6";
        reference
          "RFC 4253:
             The Secure Shell (SSH) Transport Layer Protocol";
      }

      enum rsa-sha2-256 {
        description
          "Enumeration for the 'rsa-sha2-256' algorithm. Section 3";
        reference
          "RFC 8332:
             Use of RSA Keys with SHA-256 and SHA-512 in the Secure
             Shell (SSH) Protocol";
      }

      enum rsa-sha2-512 {
        description
          "Enumeration for the 'rsa-sha2-512' algorithm. Section 3";
        reference
          "RFC 8332:
             Use of RSA Keys with SHA-256 and SHA-512 in the Secure
             Shell (SSH) Protocol";
      }

      enum spki-sign-rsa {
        description
          "Enumeration for the 'spki-sign-rsa' algorithm. Section
           6.6";
        reference
          "RFC 4253:
             The Secure Shell (SSH) Transport Layer Protocol";
      }

      enum spki-sign-dss {
        description
          "Enumeration for the 'spki-sign-dss' algorithm. Section
           6.6";
        reference
          "RFC 4253:
             The Secure Shell (SSH) Transport Layer Protocol";
      }

      enum pgp-sign-rsa {
        description
          "Enumeration for the 'pgp-sign-rsa' algorithm. Section
           6.6";
        reference
          "RFC 4253:
             The Secure Shell (SSH) Transport Layer Protocol";
      }

      enum pgp-sign-dss {
        description
          "Enumeration for the 'pgp-sign-dss' algorithm. Section
           6.6";
        reference
          "RFC 4253:
             The Secure Shell (SSH) Transport Layer Protocol";
      }

      enum null {
        description
          "Enumeration for the 'null' algorithm. Section 5";
        reference
          "RFC 4462:
             Generic Security Service Application Program Interface
             (GSS-API) Authentication and Key Exchange for the
             Secure Shell (SSH) Protocol";
      }

      enum ecdsa-sha2-nistp256 {
        description
          "Enumeration for the 'ecdsa-sha2-nistp256' algorithm.";
        reference
          "RFC 5656:
             Elliptic Curve Algorithm Integration in the Secure
             Shell Transport Layer";
      }

      enum ecdsa-sha2-nistp384 {
        description
          "Enumeration for the 'ecdsa-sha2-nistp384' algorithm.";
        reference
          "RFC 5656:
             Elliptic Curve Algorithm Integration in the Secure
             Shell Transport Layer";
      }

      enum ecdsa-sha2-nistp521 {
        description
          "Enumeration for the 'ecdsa-sha2-nistp521' algorithm.";
        reference
          "RFC 5656:
             Elliptic Curve Algorithm Integration in the Secure
             Shell Transport Layer";
      }

      enum ecdsa-sha2-1.3.132.0.1 {
        description
          "Enumeration for the 'ecdsa-sha2-1.3.132.0.1' algorithm.";
        reference
          "RFC 5656:
             Elliptic Curve Algorithm Integration in the Secure
             Shell Transport Layer";
      }

      enum ecdsa-sha2-1.2.840.10045.3.1.1 {
        description
          "Enumeration for the 'ecdsa-sha2-1.2.840.10045.3.1.1'
           algorithm.";
        reference
          "RFC 5656:
             Elliptic Curve Algorithm Integration in the Secure
             Shell Transport Layer";
      }

      enum ecdsa-sha2-1.3.132.0.33 {
        description
          "Enumeration for the 'ecdsa-sha2-1.3.132.0.33' algorithm.";
        reference
          "RFC 5656:
             Elliptic Curve Algorithm Integration in the Secure
             Shell Transport Layer";
      }

      enum ecdsa-sha2-1.3.132.0.26 {
        description
          "Enumeration for the 'ecdsa-sha2-1.3.132.0.26' algorithm.";
        reference
          "RFC 5656:
             Elliptic Curve Algorithm Integration in the Secure
             Shell Transport Layer";
      }

      enum ecdsa-sha2-1.3.132.0.27 {
        description
          "Enumeration for the 'ecdsa-sha2-1.3.132.0.27' algorithm.";
        reference
          "RFC 5656:
             Elliptic Curve Algorithm Integration in the Secure
             Shell Transport Layer";
      }

      enum ecdsa-sha2-1.3.132.0.16 {
        description
          "Enumeration for the 'ecdsa-sha2-1.3.132.0.16' algorithm.";
        reference
          "RFC 5656:
             Elliptic Curve Algorithm Integration in the Secure
             Shell Transport Layer";
      }

      enum ecdsa-sha2-1.3.132.0.36 {
        description
          "Enumeration for the 'ecdsa-sha2-1.3.132.0.36' algorithm.";
        reference
          "RFC 5656:
             Elliptic Curve Algorithm Integration in the Secure
             Shell Transport Layer";
      }

      enum ecdsa-sha2-1.3.132.0.37 {
        description
          "Enumeration for the 'ecdsa-sha2-1.3.132.0.37' algorithm.";
        reference
          "RFC 5656:
             Elliptic Curve Algorithm Integration in the Secure
             Shell Transport Layer";
      }

      enum ecdsa-sha2-1.3.132.0.38 {
        description
          "Enumeration for the 'ecdsa-sha2-1.3.132.0.38' algorithm.";
        reference
          "RFC 5656:
             Elliptic Curve Algorithm Integration in the Secure
             Shell Transport Layer";
      }

      enum x509v3-ssh-dss {
        description
          "Enumeration for the 'x509v3-ssh-dss' algorithm.";
        reference
          "RFC 6187:
             X.509v3 Certificates for Secure Shell Authentication";
      }

      enum x509v3-ssh-rsa {
        description
          "Enumeration for the 'x509v3-ssh-rsa' algorithm.";
        reference
          "RFC 6187:
             X.509v3 Certificates for Secure Shell Authentication";
      }

      enum x509v3-rsa2048-sha256 {
        description
          "Enumeration for the 'x509v3-rsa2048-sha256' algorithm.";
        reference
          "RFC 6187:
             X.509v3 Certificates for Secure Shell Authentication";
      }

      enum x509v3-ecdsa-sha2-nistp256 {
        description
          "Enumeration for the 'x509v3-ecdsa-sha2-nistp256'
           algorithm.";
        reference
          "RFC 6187:
             X.509v3 Certificates for Secure Shell Authentication";
      }

      enum x509v3-ecdsa-sha2-nistp384 {
        description
          "Enumeration for the 'x509v3-ecdsa-sha2-nistp384'
           algorithm.";
        reference
          "RFC 6187:
             X.509v3 Certificates for Secure Shell Authentication";
      }

      enum x509v3-ecdsa-sha2-nistp521 {
        description
          "Enumeration for the 'x509v3-ecdsa-sha2-nistp521'
           algorithm.";
        reference
          "RFC 6187:
             X.509v3 Certificates for Secure Shell Authentication";
      }

      enum x509v3-ecdsa-sha2-1.3.132.0.1 {
        description
          "Enumeration for the 'x509v3-ecdsa-sha2-1.3.132.0.1'
           algorithm.";
        reference
          "RFC 6187:
             X.509v3 Certificates for Secure Shell Authentication";
      }

      enum x509v3-ecdsa-sha2-1.2.840.10045.3.1.1 {
        description
          "Enumeration for the 'x509v3-ecdsa-
           sha2-1.2.840.10045.3.1.1' algorithm.";
        reference
          "RFC 6187:
             X.509v3 Certificates for Secure Shell Authentication";
      }

      enum x509v3-ecdsa-sha2-1.3.132.0.33 {
        description
          "Enumeration for the 'x509v3-ecdsa-sha2-1.3.132.0.33'
           algorithm.";
        reference
          "RFC 6187:
             X.509v3 Certificates for Secure Shell Authentication";
      }

      enum x509v3-ecdsa-sha2-1.3.132.0.26 {
        description
          "Enumeration for the 'x509v3-ecdsa-sha2-1.3.132.0.26'
           algorithm.";
        reference
          "RFC 6187:
             X.509v3 Certificates for Secure Shell Authentication";
      }

      enum x509v3-ecdsa-sha2-1.3.132.0.27 {
        description
          "Enumeration for the 'x509v3-ecdsa-sha2-1.3.132.0.27'
           algorithm.";
        reference
          "RFC 6187:
             X.509v3 Certificates for Secure Shell Authentication";
      }

      enum x509v3-ecdsa-sha2-1.3.132.0.16 {
        description
          "Enumeration for the 'x509v3-ecdsa-sha2-1.3.132.0.16'
           algorithm.";
        reference
          "RFC 6187:
             X.509v3 Certificates for Secure Shell Authentication";
      }

      enum x509v3-ecdsa-sha2-1.3.132.0.36 {
        description
          "Enumeration for the 'x509v3-ecdsa-sha2-1.3.132.0.36'
           algorithm.";
        reference
          "RFC 6187:
             X.509v3 Certificates for Secure Shell Authentication";
      }

      enum x509v3-ecdsa-sha2-1.3.132.0.37 {
        description
          "Enumeration for the 'x509v3-ecdsa-sha2-1.3.132.0.37'
           algorithm.";
        reference
          "RFC 6187:
             X.509v3 Certificates for Secure Shell Authentication";
      }

      enum x509v3-ecdsa-sha2-1.3.132.0.38 {
        description
          "Enumeration for the 'x509v3-ecdsa-sha2-1.3.132.0.38'
           algorithm.";
        reference
          "RFC 6187:
             X.509v3 Certificates for Secure Shell Authentication";
      }

      enum ssh-ed25519 {
        description
          "Enumeration for the 'ssh-ed25519' algorithm.";
        reference
          "RFC 8709:
             Ed25519 and Ed448 Public Key Algorithms for the Secure
             Shell (SSH) Protocol";
      }

      enum ssh-ed448 {
        description
          "Enumeration for the 'ssh-ed448' algorithm.";
        reference
          "RFC 8709:
             Ed25519 and Ed448 Public Key Algorithms for the Secure
             Shell (SSH) Protocol";
      }
	  
	  enum ssh-mldsa-44 {
	    description
	      "Enumeration for the 'ssh-mldsa-44' algorithm.";
	  	reference
	      "draft-sfluhrer-ssh-mldsa-08:
	  		SSH Support of ML-DSA";
	  }

	  enum ssh-mldsa-65 {
	  	description
	  	  "Enumeration for the 'ssh-mldsa-65' algorithm.";
	  	reference
	      "draft-ietf-sshm-composite-sigs-08:
	  		SSH Support of ML-DSA";
	  }

	  enum ssh-mldsa-87 {
	  	description
	      "Enumeration for the 'ssh-mldsa-87' algorithm.";
	  	reference
	  	  "draft-ietf-sshm-composite-sigs-08:
	  		SSH Support of ML-DSA";
	  }

	  enum ssh-mldsa44-ed25519 {
	  	description
	     "Enumeration for the 'ssh-mldsa44-ed25519' algorithm.";
	  	reference
	  	  "draft-ietf-sshm-composite-sigs-00:
	  		Post-Quantum Composite Signatures in SSH";
	  }

	  enum ssh-mldsa87-p384 {
	  	description
	     "Enumeration for the 'ssh-mldsa87-p384' algorithm.";
	  	reference
	  	  "draft-ietf-sshm-composite-sigs-00:
	  		Post-Quantum Composite Signatures in SSH";
	  }
    }
    description
      "An enumeration for SSH public key algorithms.";
  }

}
