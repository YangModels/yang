module iana-ospf-functional-cap-bits {
  yang-version 1.1;
  namespace "urn:ietf:params:xml:ns:yang:"
          + "iana-ospf-functional-cap-bits";
  prefix iana-ospf-fc-bits;

  organization
    "Internet Assigned Numbers Authority (IANA)";
  contact
    "Internet Assigned Numbers Authority

     ICANN
     12025 Waterfront Drive, Suite 300
     Los Angeles, CA 90094-2536
     United States of America

     Tel:    +1 310 301 5800
     <mailto:iana@iana.org>";
  description
    "This YANG module defines the identities for OSPF Router
     Functional Capabilities.

     This YANG module is maintained by IANA and reflects the 'OSPF
     Router Functional Capability Bits' registry.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This initial version of this YANG module is part of RFC 10041
     (https://www.rfc-editor.org/info/rfc10041); see the RFC itself
     for full legal notices.

     The latest version of this YANG module is available at
     https://www.iana.org/assignments/yang-parameters.";

  revision 2026-01-28 {
    description
      "Initial version";
    reference
      "RFC 10041: Advertising Unreachable Links in OSPF";
  }

  identity functional-capability {
    description
      "Base identity for OSPF Router Functional Capabilities. The
       functional capabilities are defined in IANA OSPF Router
       Functional Capability Bits registry.";
  }

  identity unreachable-link {
    base functional-capability;
    description
      "Indicates that the OSPF router is capable of advertising
       unreachable links.";
    reference
      "RFC 10041: Advertising Unreachable Links in OSPF";
  }
}
