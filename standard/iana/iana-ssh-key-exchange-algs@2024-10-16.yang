module iana-ssh-key-exchange-algs {
  yang-version 1.1;
  namespace "urn:ietf:params:xml:ns:yang:iana-ssh-key-exchange-algs";
  prefix sshkea;

  organization
    "Internet Assigned Numbers Authority (IANA)";

  contact
    "Postal: ICANN
             12025 Waterfront Drive, Suite 300
             Los Angeles, CA  90094-2536
             United States of America
     Tel:    +1 310 301 5800
     Email:  iana@iana.org";

  description
    "This module defines enumerations for the key exchange algorithms
     defined in the 'Key Exchange Method Names' registry of the
     'Secure Shell (SSH) Protocol Parameters' registry group
     maintained by IANA.

     Copyright (c) 2024 IETF Trust and the persons identified as
     authors of the code.  All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     The initial version of this YANG module is part of RFC 9644
     (https://www.rfc-editor.org/info/rfc9644); see the RFC
     itself for full legal notices.

     All versions of this module are published by IANA at
     https://www.iana.org/assignments/yang-parameters.";

  revision 2024-10-16 {
    description
      "This initial version of the module was created using
       the script defined in RFC 9644 to reflect the contents
       of the key exchange algorithms registry maintained by IANA.";
    reference
      "RFC 9644: YANG Groupings for SSH Clients and SSH Servers";
  }

  typedef ssh-key-exchange-algorithm {
    type enumeration {

      enum diffie-hellman-group-exchange-sha1 {
        status deprecated;
        description
          "Enumeration for the 'diffie-hellman-group-exchange-sha1'
           algorithm. Section 4.1";
        reference
          "RFC 4419:
             Diffie-Hellman Group Exchange for the Secure Shell
             (SSH) Transport Layer Protocol
        RFC 8270:
             Increase the Secure Shell Minimum Recommended Diffie-
             Hellman Modulus Size to 2048 Bits";
      }

      enum diffie-hellman-group-exchange-sha256 {
        description
          "Enumeration for the 'diffie-hellman-group-exchange-sha256'
           algorithm. Section 4.2";
        reference
          "RFC 4419:
             Diffie-Hellman Group Exchange for the Secure Shell
             (SSH) Transport Layer Protocol
        RFC 8270:
             Increase the Secure Shell Minimum Recommended Diffie-
             Hellman Modulus Size to 2048 Bits";
      }

      enum diffie-hellman-group1-sha1 {
        status deprecated;
        description
          "Enumeration for the 'diffie-hellman-group1-sha1'
           algorithm. Section 8.1";
        reference
          "RFC 4253:
             The Secure Shell (SSH) Transport Layer Protocol";
      }

      enum diffie-hellman-group14-sha1 {
        description
          "Enumeration for the 'diffie-hellman-group14-sha1'
           algorithm. Section 8.2";
        reference
          "RFC 4253:
             The Secure Shell (SSH) Transport Layer Protocol";
      }

      enum diffie-hellman-group14-sha256 {
        description
          "Enumeration for the 'diffie-hellman-group14-sha256'
           algorithm.";
        reference
          "RFC 8268:
             More Modular Exponentiation (MODP) Diffie-Hellman (DH)
             Key Exchange (KEX) Groups for Secure Shell (SSH)";
      }

      enum diffie-hellman-group15-sha512 {
        description
          "Enumeration for the 'diffie-hellman-group15-sha512'
           algorithm.";
        reference
          "RFC 8268:
             More Modular Exponentiation (MODP) Diffie-Hellman (DH)
             Key Exchange (KEX) Groups for Secure Shell (SSH)";
      }

      enum diffie-hellman-group16-sha512 {
        description
          "Enumeration for the 'diffie-hellman-group16-sha512'
           algorithm.";
        reference
          "RFC 8268:
             More Modular Exponentiation (MODP) Diffie-Hellman (DH)
             Key Exchange (KEX) Groups for Secure Shell (SSH)";
      }

      enum diffie-hellman-group17-sha512 {
        description
          "Enumeration for the 'diffie-hellman-group17-sha512'
           algorithm.";
        reference
          "RFC 8268:
             More Modular Exponentiation (MODP) Diffie-Hellman (DH)
             Key Exchange (KEX) Groups for Secure Shell (SSH)";
      }

      enum diffie-hellman-group18-sha512 {
        description
          "Enumeration for the 'diffie-hellman-group18-sha512'
           algorithm.";
        reference
          "RFC 8268:
             More Modular Exponentiation (MODP) Diffie-Hellman (DH)
             Key Exchange (KEX) Groups for Secure Shell (SSH)";
      }

      enum ecdh-sha2-nistp256 {
        description
          "Enumeration for the 'ecdh-sha2-nistp256' algorithm.";
        reference
          "RFC 5656:
             Elliptic Curve Algorithm Integration in the Secure
             Shell Transport Layer";
      }

      enum ecdh-sha2-nistp384 {
        description
          "Enumeration for the 'ecdh-sha2-nistp384' algorithm.";
        reference
          "RFC 5656:
             Elliptic Curve Algorithm Integration in the Secure
             Shell Transport Layer";
      }

      enum ecdh-sha2-nistp521 {
        description
          "Enumeration for the 'ecdh-sha2-nistp521' algorithm.";
        reference
          "RFC 5656:
             Elliptic Curve Algorithm Integration in the Secure
             Shell Transport Layer";
      }

      enum ecdh-sha2-1.3.132.0.1 {
        description
          "Enumeration for the 'ecdh-sha2-1.3.132.0.1' algorithm.";
        reference
          "RFC 5656:
             Elliptic Curve Algorithm Integration in the Secure
             Shell Transport Layer";
      }

      enum ecdh-sha2-1.2.840.10045.3.1.1 {
        description
          "Enumeration for the 'ecdh-sha2-1.2.840.10045.3.1.1'
           algorithm.";
        reference
          "RFC 5656:
             Elliptic Curve Algorithm Integration in the Secure
             Shell Transport Layer";
      }

      enum ecdh-sha2-1.3.132.0.33 {
        description
          "Enumeration for the 'ecdh-sha2-1.3.132.0.33' algorithm.";
        reference
          "RFC 5656:
             Elliptic Curve Algorithm Integration in the Secure
             Shell Transport Layer";
      }

      enum ecdh-sha2-1.3.132.0.26 {
        description
          "Enumeration for the 'ecdh-sha2-1.3.132.0.26' algorithm.";
        reference
          "RFC 5656:
             Elliptic Curve Algorithm Integration in the Secure
             Shell Transport Layer";
      }

      enum ecdh-sha2-1.3.132.0.27 {
        description
          "Enumeration for the 'ecdh-sha2-1.3.132.0.27' algorithm.";
        reference
          "RFC 5656:
             Elliptic Curve Algorithm Integration in the Secure
             Shell Transport Layer";
      }

      enum ecdh-sha2-1.3.132.0.16 {
        description
          "Enumeration for the 'ecdh-sha2-1.3.132.0.16' algorithm.";
        reference
          "RFC 5656:
             Elliptic Curve Algorithm Integration in the Secure
             Shell Transport Layer";
      }

      enum ecdh-sha2-1.3.132.0.36 {
        description
          "Enumeration for the 'ecdh-sha2-1.3.132.0.36' algorithm.";
        reference
          "RFC 5656:
             Elliptic Curve Algorithm Integration in the Secure
             Shell Transport Layer";
      }

      enum ecdh-sha2-1.3.132.0.37 {
        description
          "Enumeration for the 'ecdh-sha2-1.3.132.0.37' algorithm.";
        reference
          "RFC 5656:
             Elliptic Curve Algorithm Integration in the Secure
             Shell Transport Layer";
      }

      enum ecdh-sha2-1.3.132.0.38 {
        description
          "Enumeration for the 'ecdh-sha2-1.3.132.0.38' algorithm.";
        reference
          "RFC 5656:
             Elliptic Curve Algorithm Integration in the Secure
             Shell Transport Layer";
      }

      enum ecmqv-sha2 {
        description
          "Enumeration for the 'ecmqv-sha2' algorithm.";
        reference
          "RFC 5656:
             Elliptic Curve Algorithm Integration in the Secure
             Shell Transport Layer";
      }

      enum gss-group1-sha1-nistp256 {
        status deprecated;
        description
          "Enumeration for the 'gss-group1-sha1-nistp256'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-nistp384 {
        status deprecated;
        description
          "Enumeration for the 'gss-group1-sha1-nistp384'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-nistp521 {
        status deprecated;
        description
          "Enumeration for the 'gss-group1-sha1-nistp521'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.3.132.0.1 {
        status deprecated;
        description
          "Enumeration for the 'gss-group1-sha1-1.3.132.0.1'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.2.840.10045.3.1.1 {
        status deprecated;
        description
          "Enumeration for the 'gss-group1-sha1-1.2.840.10045.3.1.1'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.3.132.0.33 {
        status deprecated;
        description
          "Enumeration for the 'gss-group1-sha1-1.3.132.0.33'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.3.132.0.26 {
        status deprecated;
        description
          "Enumeration for the 'gss-group1-sha1-1.3.132.0.26'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.3.132.0.27 {
        status deprecated;
        description
          "Enumeration for the 'gss-group1-sha1-1.3.132.0.27'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.3.132.0.16 {
        status deprecated;
        description
          "Enumeration for the 'gss-group1-sha1-1.3.132.0.16'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.3.132.0.36 {
        status deprecated;
        description
          "Enumeration for the 'gss-group1-sha1-1.3.132.0.36'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.3.132.0.37 {
        status deprecated;
        description
          "Enumeration for the 'gss-group1-sha1-1.3.132.0.37'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group1-sha1-1.3.132.0.38 {
        status deprecated;
        description
          "Enumeration for the 'gss-group1-sha1-1.3.132.0.38'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-nistp256 {
        status deprecated;
        description
          "Enumeration for the 'gss-group14-sha1-nistp256'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-nistp384 {
        status deprecated;
        description
          "Enumeration for the 'gss-group14-sha1-nistp384'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-nistp521 {
        status deprecated;
        description
          "Enumeration for the 'gss-group14-sha1-nistp521'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.3.132.0.1 {
        status deprecated;
        description
          "Enumeration for the 'gss-group14-sha1-1.3.132.0.1'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.2.840.10045.3.1.1 {
        status deprecated;
        description
          "Enumeration for the 'gss-group14-sha1-1.2.840.10045.3.1.1'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.3.132.0.33 {
        status deprecated;
        description
          "Enumeration for the 'gss-group14-sha1-1.3.132.0.33'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.3.132.0.26 {
        status deprecated;
        description
          "Enumeration for the 'gss-group14-sha1-1.3.132.0.26'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.3.132.0.27 {
        status deprecated;
        description
          "Enumeration for the 'gss-group14-sha1-1.3.132.0.27'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.3.132.0.16 {
        status deprecated;
        description
          "Enumeration for the 'gss-group14-sha1-1.3.132.0.16'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.3.132.0.36 {
        status deprecated;
        description
          "Enumeration for the 'gss-group14-sha1-1.3.132.0.36'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.3.132.0.37 {
        status deprecated;
        description
          "Enumeration for the 'gss-group14-sha1-1.3.132.0.37'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-group14-sha1-1.3.132.0.38 {
        status deprecated;
        description
          "Enumeration for the 'gss-group14-sha1-1.3.132.0.38'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-nistp256 {
        status deprecated;
        description
          "Enumeration for the 'gss-gex-sha1-nistp256' algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-nistp384 {
        status deprecated;
        description
          "Enumeration for the 'gss-gex-sha1-nistp384' algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-nistp521 {
        status deprecated;
        description
          "Enumeration for the 'gss-gex-sha1-nistp521' algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.3.132.0.1 {
        status deprecated;
        description
          "Enumeration for the 'gss-gex-sha1-1.3.132.0.1'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.2.840.10045.3.1.1 {
        status deprecated;
        description
          "Enumeration for the 'gss-gex-sha1-1.2.840.10045.3.1.1'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.3.132.0.33 {
        status deprecated;
        description
          "Enumeration for the 'gss-gex-sha1-1.3.132.0.33'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.3.132.0.26 {
        status deprecated;
        description
          "Enumeration for the 'gss-gex-sha1-1.3.132.0.26'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.3.132.0.27 {
        status deprecated;
        description
          "Enumeration for the 'gss-gex-sha1-1.3.132.0.27'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.3.132.0.16 {
        status deprecated;
        description
          "Enumeration for the 'gss-gex-sha1-1.3.132.0.16'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.3.132.0.36 {
        status deprecated;
        description
          "Enumeration for the 'gss-gex-sha1-1.3.132.0.36'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.3.132.0.37 {
        status deprecated;
        description
          "Enumeration for the 'gss-gex-sha1-1.3.132.0.37'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss-gex-sha1-1.3.132.0.38 {
        status deprecated;
        description
          "Enumeration for the 'gss-gex-sha1-1.3.132.0.38'
           algorithm.";
        reference
          "RFC 4462:
             Generic Security Service Application Program Interface
             (GSS-API) Authentication and Key Exchange for the
             Secure Shell (SSH) Protocol
        RFC 8732:
             Generic Security Service Application Program Interface
             (GSS-API) Key Exchange with SHA-2";
      }

      enum gss- {
        description
          "Enumeration for the 'gss-' algorithm. Section 2.6";
        reference
          "RFC 4462:
             Generic Security Service Application Program Interface
             (GSS-API) Authentication and Key Exchange for the
             Secure Shell (SSH) Protocol";
      }

      enum rsa1024-sha1 {
        status obsolete;
        description
          "Enumeration for the 'rsa1024-sha1' algorithm.";
        reference
          "RFC 4432:
             RSA Key Exchange for the Secure Shell (SSH) Transport
             Layer Protocol";
      }

      enum rsa2048-sha256 {
        description
          "Enumeration for the 'rsa2048-sha256' algorithm.";
        reference
          "RFC 4432:
             RSA Key Exchange for the Secure Shell (SSH) Transport
             Layer Protocol";
      }

      enum ext-info-s {
        description
          "Enumeration for the 'ext-info-s' algorithm. Section 2";
        reference
          "RFC 8308:
             Extension Negotiation in the Secure Shell (SSH)
             Protocol";
      }

      enum ext-info-c {
        description
          "Enumeration for the 'ext-info-c' algorithm. Section 2";
        reference
          "RFC 8308:
             Extension Negotiation in the Secure Shell (SSH)
             Protocol";
      }

      enum gss-group14-sha256-nistp256 {
        description
          "Enumeration for the 'gss-group14-sha256-nistp256'
           algorithm.";
        reference
          "RFC 8732:
             Generic Security Service Application Program Interface
             (GSS-API) Key Exchange with SHA-2";
      }

      enum gss-group14-sha256-nistp384 {
        description
          "Enumeration for the 'gss-group14-sha256-nistp384'
           algorithm.";
        reference
          "RFC 8732:
             Generic Security Service Application Program Interface
             (GSS-API) Key Exchange with SHA-2";
      }

      enum gss-group14-sha256-nistp521 {
        description
          "Enumeration for the 'gss-group14-sha256-nistp521'
           algorithm.";
        reference
          "RFC 8732:
             Generic Security Service Application Program Interface
             (GSS-API) Key Exchange with SHA-2";
      }

      enum gss-group14-sha256-1.3.132.0.1 {
        description
          "Enumeration for the 'gss-group14-sha256-1.3.132.0.1'
           algorithm.";
        reference
          "RFC 8732:
             Generic Security Service Application Program Interface
             (GSS-API) Key Exchange with SHA-2";
      }

      enum gss-group14-sha256-1.2.840.10045.3.1.1 {
        description
          "Enumeration for the 'gss-
           group14-sha256-1.2.840.10045.3.1.1' algorithm.";
        reference
          "RFC 8732:
             Generic Security Service Application Program Interface
             (GSS-API) Key Exchange with SHA-2";
      }

      enum gss-group14-sha256-1.3.132.0.33 {
        description
          "Enumeration for the 'gss-group14-sha256-1.3.132.0.33'
           algorithm.";
        reference
          "RFC 8732:
             Generic Security Service Application Program Interface
             (GSS-API) Key Exchange with SHA-2";
      }

      enum gss-group14-sha256-1.3.132.0.26 {
        description
          "Enumeration for the 'gss-group14-sha256-1.3.132.0.26'
           algorithm.";
        reference
          "RFC 8732:
             Generic Security Service Application Program Interface
             (GSS-API) Key Exchange with SHA-2";
      }

      enum gss-group14-sha256-1.3.132.0.27 {
        description
          "Enumeration for the 'gss-group14-sha256-1.3.132.0.27'
           algorithm.";
        reference
          "RFC 8732:
             Generic Security Service Application Program Interface
             (GSS-API) Key Exchange with SHA-2";
      }

      enum gss-group14-sha256-1.3.132.0.16 {
        description
          "Enumeration for the 'gss-group14-sha256-1.3.132.0.16'
           algorithm.";
        reference
          "RFC 8732:
             Generic Security Service Application Program Interface
             (GSS-API) Key Exchange with SHA-2";
      }

      enum gss-group14-sha256-1.3.132.0.36 {
        description
          "Enumeration for the 'gss-group14-sha256-1.3.132.0.36'
           algorithm.";
        reference
          "RFC 8732:
             Generic Security Service Application Program Interface
             (GSS-API) Key Exchange with SHA-2";
      }

      enum gss-group14-sha256-1.3.132.0.37 {
        description
          "Enumeration for the 'gss-group14-sha256-1.3.132.0.37'
           algorithm.";
        reference
          "RFC 8732:
             Generic Security Service Application Program Interface
             (GSS-API) Key Exchange with SHA-2";
      }

      enum gss-group14-sha256-1.3.132.0.38 {
        description
          "Enumeration for the 'gss-group14-sha256-1.3.132.0.38'
           algorithm.";
        reference
          "RFC 8732:
             Generic Security Service Application Program Interface
             (GSS-API) Key Exchange with SHA-2";
      }

      enum gss-group15-sha512-nistp256 {
        description
          "Enumeration for the 'gss-group15-sha512-nistp256'
           algorithm.";
        reference
          "RFC 8732:
             Generic Security Service Application Program Interface
             (GSS-API) Key Exchange with SHA-2";
      }

      enum gss-group15-sha512-nistp384 {
        description
          "Enumeration for the 'gss-group15-sha512-nistp384'
           algorithm.";
        reference
          "RFC 8732:
             Generic Security Service Application Program Interface
             (GSS-API) Key Exchange with SHA-2";
      }

      enum gss-group15-sha512-nistp521 {
        description
          "Enumeration for the 'gss-group15-sha512-nistp521'
           algorithm.";
        reference
          "RFC 8732:
             Generic Security Service Application Program Interface
             (GSS-API) Key Exchange with SHA-2";
      }

      enum gss-group15-sha512-1.3.132.0.1 {
        description
          "Enumeration for the 'gss-group15-sha512-1.3.132.0.1'
           algorithm.";
        reference
          "RFC 8732:
             Generic Security Service Application Program Interface
             (GSS-API) Key Exchange with SHA-2";
      }

      enum gss-group15-sha512-1.2.840.10045.3.1.1 {
        description
          "Enumeration for the 'gss-
           group15-sha512-1.2.840.10045.3.1.1' algorithm.";
        reference
          "RFC 8732:
             Generic Security Service Application Program Interface
             (GSS-API) Key Exchange with SHA-2";
      }

      enum gss-group15-sha512-1.3.132.0.33 {
        description
          "Enumeration for the 'gss-group15-sha512-1.3.132.0.33'
           algorithm.";
        reference
          "RFC 8732:
             Generic Security Service Application Program Interface
             (GSS-API) Key Exchange with SHA-2";
      }

      enum gss-group15-sha512-1.3.132.0.26 {
        description
          "Enumeration for the 'gss-group15-sha512-1.3.132.0.26'
           algorithm.";
        reference
          "RFC 8732:
             Generic Security Service Application Program Interface
             (GSS-API) Key Exchange with SHA-2";
      }

      enum gss-group15-sha512-1.3.132.0.27 {
        description
          "Enumeration for the 'gss-group15-sha512-1.3.132.0.27'
           algorithm.";
        reference
          "RFC 8732:
             Generic Security Service Application Program Interface
             (GSS-API) Key Exchange with SHA-2";
      }

      enum gss-group15-sha512-1.3.132.0.16 {
        description
          "Enumeration for the 'gss-group15-sha512-1.3.132.0.16'
           algorithm.";
        reference
          "RFC 8732:
             Generic Security Service Application Program Interface
             (GSS-API) Key Exchange with SHA-2";
      }

      enum gss-group15-sha512-1.3.132.0.36 {
        description
          "Enumeration for the 'gss-group15-sha512-1.3.132.0.36'
           algorithm.";
        reference
          "RFC 8732:
             Generic Security Service Application Program Interface
             (GSS-API) Key Exchange with SHA-2";
      }

      enum gss-group15-sha512-1.3.132.0.37 {
        description
          "Enumeration for the 'gss-group15-sha512-1.3.132.0.37'
           algorithm.";
        reference
          "RFC 8732:
             Generic Security Service Application Program Interface
             (GSS-API) Key Exchange with SHA-2";
      }

      enum gss-group15-sha512-1.3.132.0.38 {
        description
          "Enumeration for the 'gss-group15-sha512-1.3.132.0.38'
           algorithm.";
        reference
          "RFC 8732:
             Generic Security Service Application Program Interface
             (GSS-API) Key Exchange with SHA-2";
      }

      enum gss-group16-sha512-nistp256 {
        description
          "Enumeration for the 'gss-group16-sha512-nistp256'
           algorithm.";
        reference
          "RFC 8732:
             Generic Security Service Application Program Interface
             (GSS-API) Key Exchange with SHA-2";
      }

      enum gss-group16-sha512-nistp384 {
        description
          "Enumeration for the 'gss-group16-sha512-nistp384'
           algorithm.";
        reference
          "RFC 8732:
             Generic Security Service Application Program Interface
             (GSS-API) Key Exchange with SHA-2";
      }

      enum gss-group16-sha512-nistp521 {
        description
          "Enumeration for the 'gss-group16-sha512-nistp521'
           algorithm.";
        reference
          "RFC 8732:
             Generic Security Service Application Program Interface
             (GSS-API) Key Exchange with SHA-2";
      }

      enum gss-group16-sha512-1.3.132.0.1 {
        description
          "Enumeration for the 'gss-group16-sha512-1.3.132.0.1'
           algorithm.";
        reference
          "RFC 8732:
             Generic Security Service Application Program Interface
             (GSS-API) Key Exchange with SHA-2";
      }

      enum gss-group16-sha512-1.2.840.10045.3.1.1 {
        description
          "Enumeration for the 'gss-
           group16-sha512-1.2.840.10045.3.1.1' algorithm.";
        reference
          "RFC 8732:
             Generic Security Service Application Program Interface
             (GSS-API) Key Exchange with SHA-2";
      }

      enum gss-group16-sha512-1.3.132.0.33 {
        description
          "Enumeration for the 'gss-group16-sha512-1.3.132.0.33'
           algorithm.";
        reference
          "RFC 8732:
             Generic Security Service Application Program Interface
             (GSS-API) Key Exchange with SHA-2";
      }

      enum gss-group16-sha512-1.3.132.0.26 {
        description
          "Enumeration for the 'gss-group16-sha512-1.3.132.0.26'
           algorithm.";
        reference
          "RFC 8732:
             Generic Security Service Application Program Interface
             (GSS-API) Key Exchange with SHA-2";
      }

      enum gss-group16-sha512-1.3.132.0.27 {
        description
          "Enumeration for the 'gss-group16-sha512-1.3.132.0.27'
           algorithm.";
        reference
          "RFC 8732:
             Generic Security Service Application Program Interface
             (GSS-API) Key Exchange with SHA-2";
      }

      enum gss-group16-sha512-1.3.132.0.16 {
        description
          "Enumeration for the 'gss-group16-sha512-1.3.132.0.16'
           algorithm.";
        reference
          "RFC 8732:
             Generic Security Service Application Program Interface
             (GSS-API) Key Exchange with SHA-2";
      }

      enum gss-group16-sha512-1.3.132.0.36 {
        description
          "Enumeration for the 'gss-group16-sha512-1.3.132.0.36'
           algorithm.";
        reference
          "RFC 8732:
             Generic Security Service Application Program Interface
             (GSS-API) Key Exchange with SHA-2";
      }

      enum gss-group16-sha512-1.3.132.0.37 {
        description
          "Enumeration for the 'gss-group16-sha512-1.3.132.0.37'
           algorithm.";
        reference
          "RFC 8732:
             Generic Security Service Application Program Interface
             (GSS-API) Key Exchange with SHA-2";
      }

      enum gss-group16-sha512-1.3.132.0.38 {
        description
          "Enumeration for the 'gss-group16-sha512-1.3.132.0.38'
           algorithm.";
        reference
          "RFC 8732:
             Generic Security Service Application Program Interface
             (GSS-API) Key Exchange with SHA-2";
      }

      enum gss-group17-sha512-nistp256 {
        description
          "Enumeration for the 'gss-group17-sha512-nistp256'
           algorithm.";
        reference
          "RFC 8732:
             Generic Security Service Application Program Interface
             (GSS-API) Key Exchange with SHA-2";
      }

      enum gss-group17-sha512-nistp384 {
        description
          "Enumeration for the 'gss-group17-sha512-nistp384'
           algorithm.";
        reference
          "RFC 8732:
             Generic Security Service Application Program Interface
             (GSS-API) Key Exchange with SHA-2";
      }

      enum gss-group17-sha512-nistp521 {
        description
          "Enumeration for the 'gss-group17-sha512-nistp521'
           algorithm.";
        reference
          "RFC 8732:
             Generic Security Service Application Program Interface
             (GSS-API) Key Exchange with SHA-2";
      }

      enum gss-group17-sha512-1.3.132.0.1 {
        description
          "Enumeration for the 'gss-group17-sha512-1.3.132.0.1'
           algorithm.";
        reference
          "RFC 8732:
             Generic Security Service Application Program Interface
             (GSS-API) Key Exchange with SHA-2";
      }

      enum gss-group17-sha512-1.2.840.10045.3.1.1 {
        description
          "Enumeration for the 'gss-
           group17-sha512-1.2.840.10045.3.1.1' algorithm.";
        reference
          "RFC 8732:
             Generic Security Service Application Program Interface
             (GSS-API) Key Exchange with SHA-2";
      }

      enum gss-group17-sha512-1.3.132.0.33 {
        description
          "Enumeration for the 'gss-group17-sha512-1.3.132.0.33'
           algorithm.";
        reference
          "RFC 8732:
             Generic Security Service Application Program Interface
             (GSS-API) Key Exchange with SHA-2";
      }

      enum gss-group17-sha512-1.3.132.0.26 {
        description
          "Enumeration for the 'gss-group17-sha512-1.3.132.0.26'
           algorithm.";
        reference
          "RFC 8732:
             Generic Security Service Application Program Interface
             (GSS-API) Key Exchange with SHA-2";
      }

      enum gss-group17-sha512-1.3.132.0.27 {
        description
          "Enumeration for the 'gss-group17-sha512-1.3.132.0.27'
           algorithm.";
        reference
          "RFC 8732:
             Generic Security Service Application Program Interface
             (GSS-API) Key Exchange with SHA-2";
      }

      enum gss-group17-sha512-1.3.132.0.16 {
        description
          "Enumeration for the 'gss-group17-sha512-1.3.132.0.16'
           algorithm.";
        reference
          "RFC 8732:
             Generic Security Service Application Program Interface
             (GSS-API) Key Exchange with SHA-2";
      }

      enum gss-group17-sha512-1.3.132.0.36 {
        description
          "Enumeration for the 'gss-group17-sha512-1.3.132.0.36'
           algorithm.";
        reference
          "RFC 8732:
             Generic Security Service Application Program Interface
             (GSS-API) Key Exchange with SHA-2";
      }

      enum gss-group17-sha512-1.3.132.0.37 {
        description
          "Enumeration for the 'gss-group17-sha512-1.3.132.0.37'
           algorithm.";
        reference
          "RFC 8732:
             Generic Security Service Application Program Interface
             (GSS-API) Key Exchange with SHA-2";
      }

      enum gss-group17-sha512-1.3.132.0.38 {
        description
          "Enumeration for the 'gss-group17-sha512-1.3.132.0.38'
           algorithm.";
        reference
          "RFC 8732:
             Generic Security Service Application Program Interface
             (GSS-API) Key Exchange with SHA-2";
      }

      enum gss-group18-sha512-nistp256 {
        description
          "Enumeration for the 'gss-group18-sha512-nistp256'
           algorithm.";
        reference
          "RFC 8732:
             Generic Security Service Application Program Interface
             (GSS-API) Key Exchange with SHA-2";
      }

      enum gss-group18-sha512-nistp384 {
        description
          "Enumeration for the 'gss-group18-sha512-nistp384'
           algorithm.";
        reference
          "RFC 8732:
             Generic Security Service Application Program Interface
             (GSS-API) Key Exchange with SHA-2";
      }

      enum gss-group18-sha512-nistp521 {
        description
          "Enumeration for the 'gss-group18-sha512-nistp521'
           algorithm.";
        reference
          "RFC 8732:
             Generic Security Service Application Program Interface
             (GSS-API) Key Exchange with SHA-2";
      }

      enum gss-group18-sha512-1.3.132.0.1 {
        description
          "Enumeration for the 'gss-group18-sha512-1.3.132.0.1'
           algorithm.";
        reference
          "RFC 8732:
             Generic Security Service Application Program Interface
             (GSS-API) Key Exchange with SHA-2";
      }

      enum gss-group18-sha512-1.2.840.10045.3.1.1 {
        description
          "Enumeration for the 'gss-
           group18-sha512-1.2.840.10045.3.1.1' algorithm.";
        reference
          "RFC 8732:
             Generic Security Service Application Program Interface
             (GSS-API) Key Exchange with SHA-2";
      }

      enum gss-group18-sha512-1.3.132.0.33 {
        description
          "Enumeration for the 'gss-group18-sha512-1.3.132.0.33'
           algorithm.";
        reference
          "RFC 8732:
             Generic Security Service Application Program Interface
             (GSS-API) Key Exchange with SHA-2";
      }

      enum gss-group18-sha512-1.3.132.0.26 {
        description
          "Enumeration for the 'gss-group18-sha512-1.3.132.0.26'
           algorithm.";
        reference
          "RFC 8732:
             Generic Security Service Application Program Interface
             (GSS-API) Key Exchange with SHA-2";
      }

      enum gss-group18-sha512-1.3.132.0.27 {
        description
          "Enumeration for the 'gss-group18-sha512-1.3.132.0.27'
           algorithm.";
        reference
          "RFC 8732:
             Generic Security Service Application Program Interface
             (GSS-API) Key Exchange with SHA-2";
      }

      enum gss-group18-sha512-1.3.132.0.16 {
        description
          "Enumeration for the 'gss-group18-sha512-1.3.132.0.16'
           algorithm.";
        reference
          "RFC 8732:
             Generic Security Service Application Program Interface
             (GSS-API) Key Exchange with SHA-2";
      }

      enum gss-group18-sha512-1.3.132.0.36 {
        description
          "Enumeration for the 'gss-group18-sha512-1.3.132.0.36'
           algorithm.";
        reference
          "RFC 8732:
             Generic Security Service Application Program Interface
             (GSS-API) Key Exchange with SHA-2";
      }

      enum gss-group18-sha512-1.3.132.0.37 {
        description
          "Enumeration for the 'gss-group18-sha512-1.3.132.0.37'
           algorithm.";
        reference
          "RFC 8732:
             Generic Security Service Application Program Interface
             (GSS-API) Key Exchange with SHA-2";
      }

      enum gss-group18-sha512-1.3.132.0.38 {
        description
          "Enumeration for the 'gss-group18-sha512-1.3.132.0.38'
           algorithm.";
        reference
          "RFC 8732:
             Generic Security Service Application Program Interface
             (GSS-API) Key Exchange with SHA-2";
      }

      enum gss-nistp256-sha256-nistp256 {
        description
          "Enumeration for the 'gss-nistp256-sha256-nistp256'
           algorithm.";
        reference
          "RFC 8732:
             Generic Security Service Application Program Interface
             (GSS-API) Key Exchange with SHA-2";
      }

      enum gss-nistp256-sha256-nistp384 {
        description
          "Enumeration for the 'gss-nistp256-sha256-nistp384'
           algorithm.";
        reference
          "RFC 8732:
             Generic Security Service Application Program Interface
             (GSS-API) Key Exchange with SHA-2";
      }

      enum gss-nistp256-sha256-nistp521 {
        description
          "Enumeration for the 'gss-nistp256-sha256-nistp521'
           algorithm.";
        reference
          "RFC 8732:
             Generic Security Service Application Program Interface
             (GSS-API) Key Exchange with SHA-2";
      }

      enum gss-nistp256-sha256-1.3.132.0.1 {
        description
          "Enumeration for the 'gss-nistp256-sha256-1.3.132.0.1'
           algorithm.";
        reference
          "RFC 8732:
             Generic Security Service Application Program Interface
             (GSS-API) Key Exchange with SHA-2";
      }

      enum gss-nistp256-sha256-1.2.840.10045.3.1.1 {
        description
          "Enumeration for the 'gss-
           nistp256-sha256-1.2.840.10045.3.1.1' algorithm.";
        reference
          "RFC 8732:
             Generic Security Service Application Program Interface
             (GSS-API) Key Exchange with SHA-2";
      }

      enum gss-nistp256-sha256-1.3.132.0.33 {
        description
          "Enumeration for the 'gss-nistp256-sha256-1.3.132.0.33'
           algorithm.";
        reference
          "RFC 8732:
             Generic Security Service Application Program Interface
             (GSS-API) Key Exchange with SHA-2";
      }

      enum gss-nistp256-sha256-1.3.132.0.26 {
        description
          "Enumeration for the 'gss-nistp256-sha256-1.3.132.0.26'
           algorithm.";
        reference
          "RFC 8732:
             Generic Security Service Application Program Interface
             (GSS-API) Key Exchange with SHA-2";
      }

      enum gss-nistp256-sha256-1.3.132.0.27 {
        description
          "Enumeration for the 'gss-nistp256-sha256-1.3.132.0.27'
           algorithm.";
        reference
          "RFC 8732:
             Generic Security Service Application Program Interface
             (GSS-API) Key Exchange with SHA-2";
      }

      enum gss-nistp256-sha256-1.3.132.0.16 {
        description
          "Enumeration for the 'gss-nistp256-sha256-1.3.132.0.16'
           algorithm.";
        reference
          "RFC 8732:
             Generic Security Service Application Program Interface
             (GSS-API) Key Exchange with SHA-2";
      }

      enum gss-nistp256-sha256-1.3.132.0.36 {
        description
          "Enumeration for the 'gss-nistp256-sha256-1.3.132.0.36'
           algorithm.";
        reference
          "RFC 8732:
             Generic Security Service Application Program Interface
             (GSS-API) Key Exchange with SHA-2";
      }

      enum gss-nistp256-sha256-1.3.132.0.37 {
        description
          "Enumeration for the 'gss-nistp256-sha256-1.3.132.0.37'
           algorithm.";
        reference
          "RFC 8732:
             Generic Security Service Application Program Interface
             (GSS-API) Key Exchange with SHA-2";
      }

      enum gss-nistp256-sha256-1.3.132.0.38 {
        description
          "Enumeration for the 'gss-nistp256-sha256-1.3.132.0.38'
           algorithm.";
        reference
          "RFC 8732:
             Generic Security Service Application Program Interface
             (GSS-API) Key Exchange with SHA-2";
      }

      enum gss-nistp384-sha384-nistp256 {
        description
          "Enumeration for the 'gss-nistp384-sha384-nistp256'
           algorithm.";
        reference
          "RFC 8732:
             Generic Security Service Application Program Interface
             (GSS-API) Key Exchange with SHA-2";
      }

      enum gss-nistp384-sha384-nistp384 {
        description
          "Enumeration for the 'gss-nistp384-sha384-nistp384'
           algorithm.";
        reference
          "RFC 8732:
             Generic Security Service Application Program Interface
             (GSS-API) Key Exchange with SHA-2";
      }

      enum gss-nistp384-sha384-nistp521 {
        description
          "Enumeration for the 'gss-nistp384-sha384-nistp521'
           algorithm.";
        reference
          "RFC 8732:
             Generic Security Service Application Program Interface
             (GSS-API) Key Exchange with SHA-2";
      }

      enum gss-nistp384-sha384-1.3.132.0.1 {
        description
          "Enumeration for the 'gss-nistp384-sha384-1.3.132.0.1'
           algorithm.";
        reference
          "RFC 8732:
             Generic Security Service Application Program Interface
             (GSS-API) Key Exchange with SHA-2";
      }

      enum gss-nistp384-sha384-1.2.840.10045.3.1.1 {
        description
          "Enumeration for the 'gss-
           nistp384-sha384-1.2.840.10045.3.1.1' algorithm.";
        reference
          "RFC 8732:
             Generic Security Service Application Program Interface
             (GSS-API) Key Exchange with SHA-2";
      }

      enum gss-nistp384-sha384-1.3.132.0.33 {
        description
          "Enumeration for the 'gss-nistp384-sha384-1.3.132.0.33'
           algorithm.";
        reference
          "RFC 8732:
             Generic Security Service Application Program Interface
             (GSS-API) Key Exchange with SHA-2";
      }

      enum gss-nistp384-sha384-1.3.132.0.26 {
        description
          "Enumeration for the 'gss-nistp384-sha384-1.3.132.0.26'
           algorithm.";
        reference
          "RFC 8732:
             Generic Security Service Application Program Interface
             (GSS-API) Key Exchange with SHA-2";
      }

      enum gss-nistp384-sha384-1.3.132.0.27 {
        description
          "Enumeration for the 'gss-nistp384-sha384-1.3.132.0.27'
           algorithm.";
        reference
          "RFC 8732:
             Generic Security Service Application Program Interface
             (GSS-API) Key Exchange with SHA-2";
      }

      enum gss-nistp384-sha384-1.3.132.0.16 {
        description
          "Enumeration for the 'gss-nistp384-sha384-1.3.132.0.16'
           algorithm.";
        reference
          "RFC 8732:
             Generic Security Service Application Program Interface
             (GSS-API) Key Exchange with SHA-2";
      }

      enum gss-nistp384-sha384-1.3.132.0.36 {
        description
          "Enumeration for the 'gss-nistp384-sha384-1.3.132.0.36'
           algorithm.";
        reference
          "RFC 8732:
             Generic Security Service Application Program Interface
             (GSS-API) Key Exchange with SHA-2";
      }

      enum gss-nistp384-sha384-1.3.132.0.37 {
        description
          "Enumeration for the 'gss-nistp384-sha384-1.3.132.0.37'
           algorithm.";
        reference
          "RFC 8732:
             Generic Security Service Application Program Interface
             (GSS-API) Key Exchange with SHA-2";
      }

      enum gss-nistp384-sha384-1.3.132.0.38 {
        description
          "Enumeration for the 'gss-nistp384-sha384-1.3.132.0.38'
           algorithm.";
        reference
          "RFC 8732:
             Generic Security Service Application Program Interface
             (GSS-API) Key Exchange with SHA-2";
      }

      enum gss-nistp521-sha512-nistp256 {
        description
          "Enumeration for the 'gss-nistp521-sha512-nistp256'
           algorithm.";
        reference
          "RFC 8732:
             Generic Security Service Application Program Interface
             (GSS-API) Key Exchange with SHA-2";
      }

      enum gss-nistp521-sha512-nistp384 {
        description
          "Enumeration for the 'gss-nistp521-sha512-nistp384'
           algorithm.";
        reference
          "RFC 8732:
             Generic Security Service Application Program Interface
             (GSS-API) Key Exchange with SHA-2";
      }

      enum gss-nistp521-sha512-nistp521 {
        description
          "Enumeration for the 'gss-nistp521-sha512-nistp521'
           algorithm.";
        reference
          "RFC 8732:
             Generic Security Service Application Program Interface
             (GSS-API) Key Exchange with SHA-2";
      }

      enum gss-nistp521-sha512-1.3.132.0.1 {
        description
          "Enumeration for the 'gss-nistp521-sha512-1.3.132.0.1'
           algorithm.";
        reference
          "RFC 8732:
             Generic Security Service Application Program Interface
             (GSS-API) Key Exchange with SHA-2";
      }

      enum gss-nistp521-sha512-1.2.840.10045.3.1.1 {
        description
          "Enumeration for the 'gss-
           nistp521-sha512-1.2.840.10045.3.1.1' algorithm.";
        reference
          "RFC 8732:
             Generic Security Service Application Program Interface
             (GSS-API) Key Exchange with SHA-2";
      }

      enum gss-nistp521-sha512-1.3.132.0.33 {
        description
          "Enumeration for the 'gss-nistp521-sha512-1.3.132.0.33'
           algorithm.";
        reference
          "RFC 8732:
             Generic Security Service Application Program Interface
             (GSS-API) Key Exchange with SHA-2";
      }

      enum gss-nistp521-sha512-1.3.132.0.26 {
        description
          "Enumeration for the 'gss-nistp521-sha512-1.3.132.0.26'
           algorithm.";
        reference
          "RFC 8732:
             Generic Security Service Application Program Interface
             (GSS-API) Key Exchange with SHA-2";
      }

      enum gss-nistp521-sha512-1.3.132.0.27 {
        description
          "Enumeration for the 'gss-nistp521-sha512-1.3.132.0.27'
           algorithm.";
        reference
          "RFC 8732:
             Generic Security Service Application Program Interface
             (GSS-API) Key Exchange with SHA-2";
      }

      enum gss-nistp521-sha512-1.3.132.0.16 {
        description
          "Enumeration for the 'gss-nistp521-sha512-1.3.132.0.16'
           algorithm.";
        reference
          "RFC 8732:
             Generic Security Service Application Program Interface
             (GSS-API) Key Exchange with SHA-2";
      }

      enum gss-nistp521-sha512-1.3.132.0.36 {
        description
          "Enumeration for the 'gss-nistp521-sha512-1.3.132.0.36'
           algorithm.";
        reference
          "RFC 8732:
             Generic Security Service Application Program Interface
             (GSS-API) Key Exchange with SHA-2";
      }

      enum gss-nistp521-sha512-1.3.132.0.37 {
        description
          "Enumeration for the 'gss-nistp521-sha512-1.3.132.0.37'
           algorithm.";
        reference
          "RFC 8732:
             Generic Security Service Application Program Interface
             (GSS-API) Key Exchange with SHA-2";
      }

      enum gss-nistp521-sha512-1.3.132.0.38 {
        description
          "Enumeration for the 'gss-nistp521-sha512-1.3.132.0.38'
           algorithm.";
        reference
          "RFC 8732:
             Generic Security Service Application Program Interface
             (GSS-API) Key Exchange with SHA-2";
      }

      enum gss-curve25519-sha256-nistp256 {
        description
          "Enumeration for the 'gss-curve25519-sha256-nistp256'
           algorithm.";
        reference
          "RFC 8732:
             Generic Security Service Application Program Interface
             (GSS-API) Key Exchange with SHA-2";
      }

      enum gss-curve25519-sha256-nistp384 {
        description
          "Enumeration for the 'gss-curve25519-sha256-nistp384'
           algorithm.";
        reference
          "RFC 8732:
             Generic Security Service Application Program Interface
             (GSS-API) Key Exchange with SHA-2";
      }

      enum gss-curve25519-sha256-nistp521 {
        description
          "Enumeration for the 'gss-curve25519-sha256-nistp521'
           algorithm.";
        reference
          "RFC 8732:
             Generic Security Service Application Program Interface
             (GSS-API) Key Exchange with SHA-2";
      }

      enum gss-curve25519-sha256-1.3.132.0.1 {
        description
          "Enumeration for the 'gss-curve25519-sha256-1.3.132.0.1'
           algorithm.";
        reference
          "RFC 8732:
             Generic Security Service Application Program Interface
             (GSS-API) Key Exchange with SHA-2";
      }

      enum gss-curve25519-sha256-1.2.840.10045.3.1.1 {
        description
          "Enumeration for the 'gss-
           curve25519-sha256-1.2.840.10045.3.1.1' algorithm.";
        reference
          "RFC 8732:
             Generic Security Service Application Program Interface
             (GSS-API) Key Exchange with SHA-2";
      }

      enum gss-curve25519-sha256-1.3.132.0.33 {
        description
          "Enumeration for the 'gss-curve25519-sha256-1.3.132.0.33'
           algorithm.";
        reference
          "RFC 8732:
             Generic Security Service Application Program Interface
             (GSS-API) Key Exchange with SHA-2";
      }

      enum gss-curve25519-sha256-1.3.132.0.26 {
        description
          "Enumeration for the 'gss-curve25519-sha256-1.3.132.0.26'
           algorithm.";
        reference
          "RFC 8732:
             Generic Security Service Application Program Interface
             (GSS-API) Key Exchange with SHA-2";
      }

      enum gss-curve25519-sha256-1.3.132.0.27 {
        description
          "Enumeration for the 'gss-curve25519-sha256-1.3.132.0.27'
           algorithm.";
        reference
          "RFC 8732:
             Generic Security Service Application Program Interface
             (GSS-API) Key Exchange with SHA-2";
      }

      enum gss-curve25519-sha256-1.3.132.0.16 {
        description
          "Enumeration for the 'gss-curve25519-sha256-1.3.132.0.16'
           algorithm.";
        reference
          "RFC 8732:
             Generic Security Service Application Program Interface
             (GSS-API) Key Exchange with SHA-2";
      }

      enum gss-curve25519-sha256-1.3.132.0.36 {
        description
          "Enumeration for the 'gss-curve25519-sha256-1.3.132.0.36'
           algorithm.";
        reference
          "RFC 8732:
             Generic Security Service Application Program Interface
             (GSS-API) Key Exchange with SHA-2";
      }

      enum gss-curve25519-sha256-1.3.132.0.37 {
        description
          "Enumeration for the 'gss-curve25519-sha256-1.3.132.0.37'
           algorithm.";
        reference
          "RFC 8732:
             Generic Security Service Application Program Interface
             (GSS-API) Key Exchange with SHA-2";
      }

      enum gss-curve25519-sha256-1.3.132.0.38 {
        description
          "Enumeration for the 'gss-curve25519-sha256-1.3.132.0.38'
           algorithm.";
        reference
          "RFC 8732:
             Generic Security Service Application Program Interface
             (GSS-API) Key Exchange with SHA-2";
      }

      enum gss-curve448-sha512-nistp256 {
        description
          "Enumeration for the 'gss-curve448-sha512-nistp256'
           algorithm.";
        reference
          "RFC 8732:
             Generic Security Service Application Program Interface
             (GSS-API) Key Exchange with SHA-2";
      }

      enum gss-curve448-sha512-nistp384 {
        description
          "Enumeration for the 'gss-curve448-sha512-nistp384'
           algorithm.";
        reference
          "RFC 8732:
             Generic Security Service Application Program Interface
             (GSS-API) Key Exchange with SHA-2";
      }

      enum gss-curve448-sha512-nistp521 {
        description
          "Enumeration for the 'gss-curve448-sha512-nistp521'
           algorithm.";
        reference
          "RFC 8732:
             Generic Security Service Application Program Interface
             (GSS-API) Key Exchange with SHA-2";
      }

      enum gss-curve448-sha512-1.3.132.0.1 {
        description
          "Enumeration for the 'gss-curve448-sha512-1.3.132.0.1'
           algorithm.";
        reference
          "RFC 8732:
             Generic Security Service Application Program Interface
             (GSS-API) Key Exchange with SHA-2";
      }

      enum gss-curve448-sha512-1.2.840.10045.3.1.1 {
        description
          "Enumeration for the 'gss-
           curve448-sha512-1.2.840.10045.3.1.1' algorithm.";
        reference
          "RFC 8732:
             Generic Security Service Application Program Interface
             (GSS-API) Key Exchange with SHA-2";
      }

      enum gss-curve448-sha512-1.3.132.0.33 {
        description
          "Enumeration for the 'gss-curve448-sha512-1.3.132.0.33'
           algorithm.";
        reference
          "RFC 8732:
             Generic Security Service Application Program Interface
             (GSS-API) Key Exchange with SHA-2";
      }

      enum gss-curve448-sha512-1.3.132.0.26 {
        description
          "Enumeration for the 'gss-curve448-sha512-1.3.132.0.26'
           algorithm.";
        reference
          "RFC 8732:
             Generic Security Service Application Program Interface
             (GSS-API) Key Exchange with SHA-2";
      }

      enum gss-curve448-sha512-1.3.132.0.27 {
        description
          "Enumeration for the 'gss-curve448-sha512-1.3.132.0.27'
           algorithm.";
        reference
          "RFC 8732:
             Generic Security Service Application Program Interface
             (GSS-API) Key Exchange with SHA-2";
      }

      enum gss-curve448-sha512-1.3.132.0.16 {
        description
          "Enumeration for the 'gss-curve448-sha512-1.3.132.0.16'
           algorithm.";
        reference
          "RFC 8732:
             Generic Security Service Application Program Interface
             (GSS-API) Key Exchange with SHA-2";
      }

      enum gss-curve448-sha512-1.3.132.0.36 {
        description
          "Enumeration for the 'gss-curve448-sha512-1.3.132.0.36'
           algorithm.";
        reference
          "RFC 8732:
             Generic Security Service Application Program Interface
             (GSS-API) Key Exchange with SHA-2";
      }

      enum gss-curve448-sha512-1.3.132.0.37 {
        description
          "Enumeration for the 'gss-curve448-sha512-1.3.132.0.37'
           algorithm.";
        reference
          "RFC 8732:
             Generic Security Service Application Program Interface
             (GSS-API) Key Exchange with SHA-2";
      }

      enum gss-curve448-sha512-1.3.132.0.38 {
        description
          "Enumeration for the 'gss-curve448-sha512-1.3.132.0.38'
           algorithm.";
        reference
          "RFC 8732:
             Generic Security Service Application Program Interface
             (GSS-API) Key Exchange with SHA-2";
      }

      enum curve25519-sha256 {
        description
          "Enumeration for the 'curve25519-sha256' algorithm.";
        reference
          "RFC 8731:
             Secure Shell (SSH) Key Exchange Method Using
             Curve25519 and Curve448";
      }

      enum curve448-sha512 {
        description
          "Enumeration for the 'curve448-sha512' algorithm.";
        reference
          "RFC 8731:
             Secure Shell (SSH) Key Exchange Method Using
             Curve25519 and Curve448";
      }

      enum sntrup761x25519-sha512 {
        description
          "Enumeration for the 'sntrup761x25519-sha512' algorithm.";
        reference
          "draft-josefsson-ntruprime-ssh-02:
             Secure Shell (SSH) Key Exchange Method Using Hybrid
             Streamlined NTRU Prime sntrup761 and X25519 with
             SHA-512: sntrup761x25519-sha512";
      }

      enum mlkem768nistp256-sha256 {
        description
          "Enumeration for the 'mlkem768nistp256-sha256' algorithm.";
        reference
          "draft-kampanakis-curdle-ssh-pq-ke-04:
             PQ/T Hybrid Key Exchange in SSH";
      }

      enum mlkem1024nistp384-sha384 {
        description
          "Enumeration for the 'mlkem1024nistp384-sha384'
           algorithm.";
        reference
          "draft-kampanakis-curdle-ssh-pq-ke-04:
             PQ/T Hybrid Key Exchange in SSH";
      }

      enum mlkem768x25519-sha256 {
        description
          "Enumeration for the 'mlkem768x25519-sha256' algorithm.";
        reference
          "draft-kampanakis-curdle-ssh-pq-ke-04:
             PQ/T Hybrid Key Exchange in SSH";
      }
    }
    description
      "An enumeration for SSH key exchange algorithms.";
  }

}
