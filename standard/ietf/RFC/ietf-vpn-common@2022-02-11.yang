module ietf-vpn-common {
  yang-version 1.1;
  namespace "urn:ietf:params:xml:ns:yang:ietf-vpn-common";
  prefix vpn-common;

  import ietf-netconf-acm {
    prefix nacm;
    reference
      "RFC 8341: Network Configuration Access Control Model";
  }
  import ietf-routing-types {
    prefix rt-types;
    reference
      "RFC 8294: Common YANG Data Types for the Routing Area";
  }
  import ietf-yang-types {
    prefix yang;
    reference
      "RFC 6991: Common YANG Data Types, Section 3";
  }
  import ietf-packet-fields {
    prefix packet-fields;
    reference
      "RFC 8519: YANG Data Model for Network Access
                 Control Lists (ACLs)";
  }

  organization
    "IETF OPSAWG (Operations and Management Area Working Group)";
  contact
    "WG Web:   &lt;https://datatracker.ietf.org/wg/opsawg/&gt;
     WG List:  &lt;mailto:opsawg@ietf.org&gt;

     Editor:   Mohamed Boucadair
               &lt;mailto:mohamed.boucadair@orange.com&gt;
     Author:   Samier Barguil
               &lt;mailto:samier.barguilgiraldo.ext@telefonica.com&gt;
     Editor:   Oscar Gonzalez de Dios
               &lt;mailto:oscar.gonzalezdedios@telefonica.com&gt;
     Author:   Qin Wu
               &lt;mailto:bill.wu@huawei.com&gt;";
  description
    "This YANG module defines a common module that is meant
     to be reused by various VPN-related modules (e.g., the
     Layer 3 VPN Service Model (L3SM), the Layer 2 VPN Service
     Model (L2SM), the Layer 3 VPN Network Model (L3NM), and
     the Layer 2 VPN Network Model (L2NM)).

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC 9181; see the
     RFC itself for full legal notices.";

  revision 2022-02-11 {
    description
      "Initial revision.";
    reference
      "RFC 9181: A Common YANG Data Model for Layer 2 and Layer 3
                 VPNs";
  }

  /******** Collection of VPN-related features ********/
  /*
   * Features related to encapsulation schemes
   */

  feature dot1q {
    description
      "Indicates support for dot1Q encapsulation.";
    reference
      "IEEE Std 802.1Q: IEEE Standard for Local and Metropolitan
                        Area Networks--Bridges and Bridged
                        Networks";
  }

  feature qinq {
    description
      "Indicates support for QinQ encapsulation.";
    reference
      "IEEE Std 802.1ad: IEEE Standard for Local and Metropolitan
                         Area Networks---Virtual Bridged Local
                         Area Networks---Amendment 4: Provider
                         Bridges";
  }

  feature vxlan {
    description
      "Indicates support for Virtual eXtensible Local Area
       Network (VXLAN) encapsulation.";
    reference
      "RFC 7348: Virtual eXtensible Local Area Network (VXLAN):
                 A Framework for Overlaying Virtualized Layer 2
                 Networks over Layer 3 Networks";
  }

  feature qinany {
    description
      "Indicates support for QinAny encapsulation.
       The outer VLAN tag is set to a specific value, but
       the inner VLAN tag is set to any.";
  }

  feature lag-interface {
    description
      "Indicates support for Link Aggregation Groups (LAGs)
       between VPN network accesses.";
    reference
      "IEEE Std 802.1AX: IEEE Standard for Local and Metropolitan
                         Area Networks--Link Aggregation";
  }

  /*
   * Features related to multicast
   */

  feature multicast {
    description
      "Indicates support for multicast capabilities in a VPN.";
    reference
      "RFC 6513: Multicast in MPLS/BGP IP VPNs";
  }

  feature igmp {
    description
      "Indicates support for the Internet Group Management
       Protocol (IGMP).";
    reference
      "RFC 1112: Host Extensions for IP Multicasting
       RFC 2236: Internet Group Management Protocol, Version 2
       RFC 3376: Internet Group Management Protocol, Version 3";
  }

  feature mld {
    description
      "Indicates support for Multicast Listener Discovery (MLD).";
    reference
      "RFC 2710: Multicast Listener Discovery (MLD) for IPv6
       RFC 3810: Multicast Listener Discovery Version 2 (MLDv2)
                 for IPv6";
  }

  feature pim {
    description
      "Indicates support for Protocol Independent Multicast
       (PIM).";
    reference
      "RFC 7761: Protocol Independent Multicast - Sparse Mode
                 (PIM-SM): Protocol Specification (Revised)";
  }

  /*
   * Features related to address family types
   */

  feature ipv4 {
    description
      "Indicates IPv4 support in a VPN.  That is, IPv4 traffic
       can be carried in the VPN, IPv4 addresses/prefixes can
       be assigned to a VPN network access, IPv4 routes can be
       installed for the Customer Edge to Provider Edge (CE-PE)
       link, etc.";
    reference
      "RFC 791: Internet Protocol";
  }

  feature ipv6 {
    description
      "Indicates IPv6 support in a VPN.  That is, IPv6 traffic
       can be carried in the VPN, IPv6 addresses/prefixes can
       be assigned to a VPN network access, IPv6 routes can be
       installed for the CE-PE link, etc.";
    reference
      "RFC 8200: Internet Protocol, Version 6 (IPv6)
                 Specification";
  }

  /*
   * Features related to routing protocols
   */

  feature rtg-ospf {
    description
      "Indicates support for OSPF as the Provider Edge to
       Customer Edge (PE-CE) routing protocol.";
    reference
      "RFC 4577: OSPF as the Provider/Customer Edge Protocol
                 for BGP/MPLS IP Virtual Private Networks (VPNs)
       RFC 6565: OSPFv3 as a Provider Edge to Customer Edge
                 (PE-CE) Routing Protocol";
  }

  feature rtg-ospf-sham-link {
    description
      "Indicates support for OSPF sham links.";
    reference
      "RFC 4577: OSPF as the Provider/Customer Edge Protocol
                 for BGP/MPLS IP Virtual Private Networks (VPNs),
                 Section 4.2.7
       RFC 6565: OSPFv3 as a Provider Edge to Customer Edge
                 (PE-CE) Routing Protocol, Section 5";
  }

  feature rtg-bgp {
    description
      "Indicates support for BGP as the PE-CE routing protocol.";
    reference
      "RFC 4271: A Border Gateway Protocol 4 (BGP-4)";
  }

  feature rtg-rip {
    description
      "Indicates support for RIP as the PE-CE routing protocol.";
    reference
      "RFC 2453: RIP Version 2
       RFC 2080: RIPng for IPv6";
  }

  feature rtg-isis {
    description
      "Indicates support for IS-IS as the PE-CE routing
       protocol.";
    reference
      "ISO10589: Information technology - Telecommunications and
                 information exchange between systems -
                 Intermediate System to Intermediate System
                 intra-domain routeing information exchange
                 protocol for use in conjunction with the protocol
                 for providing the connectionless-mode network
                 service (ISO 8473)";
  }

  feature rtg-vrrp {
    description
      "Indicates support for the Virtual Router Redundancy
       Protocol (VRRP) in the CE-PE link.";
    reference
      "RFC 5798: Virtual Router Redundancy Protocol (VRRP)
                 Version 3 for IPv4 and IPv6";
  }

  feature bfd {
    description
      "Indicates support for Bidirectional Forwarding Detection
       (BFD) between the CE and the PE.";
    reference
      "RFC 5880: Bidirectional Forwarding Detection (BFD)";
  }

  /*
   * Features related to VPN service constraints
   */

  feature bearer-reference {
    description
      "A bearer refers to properties of the CE-PE attachment that
       are below Layer 3.
       This feature indicates support for the bearer reference
       access constraint, i.e., the reuse of a network connection
       that was already ordered to the service provider apart from
       the IP VPN site.";
  }

  feature placement-diversity {
    description
      "Indicates support for placement diversity constraints in
       the customer premises.  An example of these constraints
       may be to avoid connecting a site network access to the
       same PE as a target site network access.";
  }

  /*
   * Features related to bandwidth and Quality of Service (QoS)
   */

  feature qos {
    description
      "Indicates support for Classes of Service (CoSes) in
       the VPN.";
  }

  feature inbound-bw {
    description
      "Indicates support for the inbound bandwidth in a VPN,
       i.e., support for specifying the download bandwidth from
       the service provider network to the VPN site.  Note that
       the L3SM uses 'input' to identify the same feature.
       That terminology should be deprecated in favor of
       the terminology defined in this module.";
  }

  feature outbound-bw {
    description
      "Indicates support for the outbound bandwidth in a VPN,
       i.e., support for specifying the upload bandwidth from
       the VPN site to the service provider network.  Note that
       the L3SM uses 'output' to identify the same feature.
       That terminology should be deprecated in favor of the
       terminology defined in this module.";
  }

  /*
   * Features related to security and resilience
   */

  feature encryption {
    description
      "Indicates support for encryption in the VPN.";
  }

  feature fast-reroute {
    description
      "Indicates support for Fast Reroute (FRR) capabilities for
       a VPN site.";
  }

  /*
   * Features related to advanced VPN options
   */

  feature external-connectivity {
    description
      "Indicates support for the VPN to provide external
       connectivity (e.g., Internet, private or public cloud).";
    reference
      "RFC 4364: BGP/MPLS IP Virtual Private Networks
                 (VPNs), Section 11";
  }

  feature extranet-vpn {
    description
      "Indicates support for extranet VPNs, i.e., the capability
       of a VPN to access a list of other VPNs.";
    reference
      "RFC 4364: BGP/MPLS IP Virtual Private Networks
                 (VPNs), Section 1.1";
  }

  feature carriers-carrier {
    description
      "Indicates support for Carriers' Carriers in VPNs.";
    reference
      "RFC 4364: BGP/MPLS IP Virtual Private Networks
                 (VPNs), Section 9";
  }

  /*
   * Identities related to address families
   */

  identity address-family {
    description
      "Defines a type for the address family.";
  }

  identity ipv4 {
    base address-family;
    description
      "Identity for an IPv4 address family.";
  }

  identity ipv6 {
    base address-family;
    description
      "Identity for an IPv6 address family.";
  }

  identity dual-stack {
    base address-family;
    description
      "Identity for IPv4 and IPv6 address families.";
  }

  /*
   * Identities related to VPN topology
   */

  identity vpn-topology {
    description
      "Base identity of the VPN topology.";
  }

  identity any-to-any {
    base vpn-topology;
    description
      "Identity for any-to-any VPN topology.  All VPN sites
       can communicate with each other without any restrictions.";
  }

  identity hub-spoke {
    base vpn-topology;
    description
      "Identity for Hub-and-Spoke VPN topology.  All Spokes can
       communicate with Hubs only and not with each other.  Hubs
       can communicate with each other.";
  }

  identity hub-spoke-disjoint {
    base vpn-topology;
    description
      "Identity for Hub-and-Spoke VPN topology where Hubs cannot
       communicate with each other.";
  }

  identity custom {
    base vpn-topology;
    description
      "Identity for custom VPN topologies where the role of the
       nodes is not strictly Hub or Spoke.  The VPN topology is
       controlled by the import/export policies.  The custom
       topology reflects more complex VPN nodes, such as a
       VPN node that acts as a Hub for certain nodes and a Spoke
       for others.";
  }

  /*
   * Identities related to network access types
   */

  identity site-network-access-type {
    description
      "Base identity for site network access types.";
  }

  identity point-to-point {
    base site-network-access-type;
    description
      "Point-to-point access type.";
  }

  identity multipoint {
    base site-network-access-type;
    description
      "Multipoint access type.";
  }

  identity irb {
    base site-network-access-type;
    description
      "Integrated Routing and Bridging (IRB).
       Identity for pseudowire connections.";
  }

  identity loopback {
    base site-network-access-type;
    description
      "Loopback access type.";
  }

  /*
   * Identities related to operational and administrative status
   */

  identity operational-status {
    description
      "Base identity for operational status.";
  }

  identity op-up {
    base operational-status;
    description
      "Operational status is Up/Enabled.";
  }

  identity op-down {
    base operational-status;
    description
      "Operational status is Down/Disabled.";
  }

  identity op-unknown {
    base operational-status;
    description
      "Operational status is Unknown.";
  }

  identity administrative-status {
    description
      "Base identity for administrative status.";
  }

  identity admin-up {
    base administrative-status;
    description
      "Administrative status is Up/Enabled.";
  }

  identity admin-down {
    base administrative-status;
    description
      "Administrative status is Down/Disabled.";
  }

  identity admin-testing {
    base administrative-status;
    description
      "Administrative status is Up for testing purposes.";
  }

  identity admin-pre-deployment {
    base administrative-status;
    description
      "Administrative status reflects a pre-deployment phase,
       i.e., prior to the actual deployment of a service.";
  }

  /*
   * Identities related to site or node roles
   */

  identity role {
    description
      "Base identity of a site or node role.";
  }

  identity any-to-any-role {
    base role;
    description
      "Any-to-any role.";
  }

  identity spoke-role {
    base role;
    description
      "A node or a site is acting as a Spoke.";
  }

  identity hub-role {
    base role;
    description
      "A node or a site is acting as a Hub.";
  }

  identity custom-role {
    base role;
    description
      "VPN node with a custom or complex role in the VPN.  For
       some sources/destinations, it can behave as a Hub, but for
       others, it can act as a Spoke, depending on the configured
       policy.";
  }

  /*
   * Identities related to VPN service constraints
   */

  identity placement-diversity {
    description
      "Base identity for access placement constraints.";
  }

  identity bearer-diverse {
    base placement-diversity;
    description
      "Bearer diversity.

       The bearers should not use common elements.";
  }

  identity pe-diverse {
    base placement-diversity;
    description
      "PE diversity.";
  }

  identity pop-diverse {
    base placement-diversity;
    description
      "Point of Presence (POP) diversity.";
  }

  identity linecard-diverse {
    base placement-diversity;
    description
      "Linecard diversity.";
  }

  identity same-pe {
    base placement-diversity;
    description
      "Having sites connected on the same PE.";
  }

  identity same-bearer {
    base placement-diversity;
    description
      "Having sites connected using the same bearer.";
  }

  /*
   * Identities related to service types
   */

  identity service-type {
    description
      "Base identity for service types.";
  }

  identity l3vpn {
    base service-type;
    description
      "L3VPN service.";
    reference
      "RFC 4364: BGP/MPLS IP Virtual Private Networks (VPNs)";
  }

  identity vpls {
    base service-type;
    description
      "Virtual Private LAN Service (VPLS).";
    reference
      "RFC 4761: Virtual Private LAN Service (VPLS) Using BGP for
                 Auto-Discovery and Signaling
       RFC 4762: Virtual Private LAN Service (VPLS) Using Label
                 Distribution Protocol (LDP) Signaling";
  }

  identity vpws {
    base service-type;
    description
      "Virtual Private Wire Service (VPWS).";
    reference
      "RFC 4664: Framework for Layer 2 Virtual Private Networks
                 (L2VPNs), Section 3.1.1";
  }

  identity vpws-evpn {
    base service-type;
    description
      "Ethernet VPN (EVPN) used to support VPWS.";
    reference
      "RFC 8214: Virtual Private Wire Service Support in
                 Ethernet VPN";
  }

  identity pbb-evpn {
    base service-type;
    description
      "Provider Backbone Bridging (PBB) EVPN service.";
    reference
      "RFC 7623: Provider Backbone Bridging Combined with
                 Ethernet VPN (PBB-EVPN)";
  }

  identity mpls-evpn {
    base service-type;
    description
      "MPLS-based EVPN service.";
    reference
      "RFC 7432: BGP MPLS-Based Ethernet VPN";
  }

  identity vxlan-evpn {
    base service-type;
    description
      "VXLAN-based EVPN service.";
    reference
      "RFC 8365: A Network Virtualization Overlay Solution Using
                 Ethernet VPN (EVPN)";
  }

  /*
   * Identities related to VPN signaling types
   */

  identity vpn-signaling-type {
    description
      "Base identity for VPN signaling types.";
  }

  identity bgp-signaling {
    base vpn-signaling-type;
    description
      "Layer 2 VPNs using BGP signaling.";
    reference
      "RFC 6624: Layer 2 Virtual Private Networks Using BGP for
                 Auto-Discovery and Signaling
       RFC 7432: BGP MPLS-Based Ethernet VPN";
  }

  identity ldp-signaling {
    base vpn-signaling-type;
    description
      "Targeted Label Distribution Protocol (LDP) signaling.";
    reference
      "RFC 5036: LDP Specification";
  }

  identity l2tp-signaling {
    base vpn-signaling-type;
    description
      "Layer Two Tunneling Protocol (L2TP) signaling.";
    reference
      "RFC 3931: Layer Two Tunneling Protocol - Version 3 (L2TPv3)";
  }

  /*
   * Identities related to routing protocols
   */

  identity routing-protocol-type {
    description
      "Base identity for routing protocol types.";
  }

  identity static-routing {
    base routing-protocol-type;
    description
      "Static routing protocol.";
  }

  identity bgp-routing {
    if-feature "rtg-bgp";
    base routing-protocol-type;
    description
      "BGP routing protocol.";
    reference
      "RFC 4271: A Border Gateway Protocol 4 (BGP-4)";
  }

  identity ospf-routing {
    if-feature "rtg-ospf";
    base routing-protocol-type;
    description
      "OSPF routing protocol.";
    reference
      "RFC 4577: OSPF as the Provider/Customer Edge Protocol
                 for BGP/MPLS IP Virtual Private Networks (VPNs)
       RFC 6565: OSPFv3 as a Provider Edge to Customer Edge
                 (PE-CE) Routing Protocol";
  }

  identity rip-routing {
    if-feature "rtg-rip";
    base routing-protocol-type;
    description
      "RIP routing protocol.";
    reference
      "RFC 2453: RIP Version 2
       RFC 2080: RIPng for IPv6";
  }

  identity isis-routing {
    if-feature "rtg-isis";
    base routing-protocol-type;
    description
      "IS-IS routing protocol.";
    reference
      "ISO10589: Information technology - Telecommunications and
                 information exchange between systems -
                 Intermediate System to Intermediate System
                 intra-domain routeing information exchange
                 protocol for use in conjunction with the protocol
                 for providing the connectionless-mode network
                 service (ISO 8473)";
  }

  identity vrrp-routing {
    if-feature "rtg-vrrp";
    base routing-protocol-type;
    description
      "VRRP protocol.

       This is to be used when LANs are directly connected to
       PEs.";
    reference
      "RFC 5798: Virtual Router Redundancy Protocol (VRRP)
                 Version 3 for IPv4 and IPv6";
  }

  identity direct-routing {
    base routing-protocol-type;
    description
      "Direct routing.

       This is to be used when LANs are directly connected to PEs
       and must be advertised in the VPN.";
  }

  identity any-routing {
    base routing-protocol-type;
    description
      "Any routing protocol.

       For example, this can be used to set policies that apply
       to any routing protocol in place.";
  }

  identity isis-level {
    if-feature "rtg-isis";
    description
      "Base identity for the IS-IS level.";
    reference
      "ISO10589: Information technology - Telecommunications and
                 information exchange between systems -
                 Intermediate System to Intermediate System
                 intra-domain routeing information exchange
                 protocol for use in conjunction with the protocol
                 for providing the connectionless-mode network
                 service (ISO 8473)";
  }

  identity level-1 {
    base isis-level;
    description
      "IS-IS Level 1.";
  }

  identity level-2 {
    base isis-level;
    description
      "IS-IS Level 2.";
  }

  identity level-1-2 {
    base isis-level;
    description
      "IS-IS Levels 1 and 2.";
  }

  identity bfd-session-type {
    if-feature "bfd";
    description
      "Base identity for the BFD session type.";
  }

  identity classic-bfd {
    base bfd-session-type;
    description
      "Classic BFD.";
    reference
      "RFC 5880: Bidirectional Forwarding Detection (BFD)";
  }

  identity s-bfd {
    base bfd-session-type;
    description
      "Seamless BFD.";
    reference
      "RFC 7880: Seamless Bidirectional Forwarding Detection
                 (S-BFD)";
  }

  /*
   * Identities related to route import and export policies
   */

  identity ie-type {
    description
      "Base identity for import/export routing profiles.
       These profiles can be reused between VPN nodes.";
  }

  identity import {
    base ie-type;
    description
      "Import routing profile.";
    reference
      "RFC 4364: BGP/MPLS IP Virtual Private Networks
                 (VPNs), Section 4.3.1";
  }

  identity export {
    base ie-type;
    description
      "Export routing profile.";
    reference
      "RFC 4364: BGP/MPLS IP Virtual Private Networks
                 (VPNs), Section 4.3.1";
  }

  identity import-export {
    base ie-type;
    description
      "Import/export routing profile.";
  }

  /*
   * Identities related to bandwidth and QoS
   */

  identity bw-direction {
    description
      "Base identity for the bandwidth direction.";
  }

  identity inbound-bw {
    if-feature "inbound-bw";
    base bw-direction;
    description
      "Inbound bandwidth.";
  }

  identity outbound-bw {
    if-feature "outbound-bw";
    base bw-direction;
    description
      "Outbound bandwidth.";
  }

  identity bw-type {
    description
      "Base identity for the bandwidth type.";
  }

  identity bw-per-cos {
    if-feature "qos";
    base bw-type;
    description
      "The bandwidth is per CoS.";
  }

  identity bw-per-port {
    base bw-type;
    description
      "The bandwidth is per a given site network access.";
  }

  identity bw-per-site {
    base bw-type;
    description
      "The bandwidth is per site.  It is applicable to all the
       site network accesses within a site.";
  }

  identity bw-per-service {
    base bw-type;
    description
      "The bandwidth is per VPN service.";
  }

  identity qos-profile-direction {
    if-feature "qos";
    description
      "Base identity for the QoS profile direction.";
  }

  identity site-to-wan {
    base qos-profile-direction;
    description
      "From the customer site to the provider's network.
       This is typically the CE-to-PE direction.";
  }

  identity wan-to-site {
    base qos-profile-direction;
    description
      "From the provider's network to the customer site.
       This is typically the PE-to-CE direction.";
  }

  identity both {
    base qos-profile-direction;
    description
      "Both the WAN-to-site direction and the site-to-WAN
       direction.";
  }

  /*
   * Identities related to underlay transport instances
   */

  identity transport-instance-type {
    description
      "Base identity for underlay transport instance types.";
  }

  identity virtual-network {
    base transport-instance-type;
    description
      "Virtual network.";
    reference
      "RFC 8453: Framework for Abstraction and Control of TE
                 Networks (ACTN)";
  }

  identity enhanced-vpn {
    base transport-instance-type;
    description
      "Enhanced VPN (VPN+).  VPN+ is an approach that is
       based on existing VPN and Traffic Engineering (TE)
       technologies but adds characteristics that specific
       services require over and above classical VPNs.";
    reference
      "draft-ietf-teas-enhanced-vpn-09:
         A Framework for Enhanced Virtual Private Network
         (VPN+) Services";
  }

  identity ietf-network-slice {
    base transport-instance-type;
    description
      "IETF network slice.  An IETF network slice
       is a logical network topology connecting a number of
       endpoints using a set of shared or dedicated network
       resources that are used to satisfy specific service
       objectives.";
    reference
      "draft-ietf-teas-ietf-network-slices-05:
         Framework for IETF Network Slices";
  }

  /*
   * Identities related to protocol types.  These types are
   * typically used to identify the underlay transport.
   */

  identity protocol-type {
    description
      "Base identity for protocol types.";
  }

  identity ip-in-ip {
    base protocol-type;
    description
      "Transport is based on IP in IP.";
    reference
      "RFC 2003: IP Encapsulation within IP
       RFC 2473: Generic Packet Tunneling in IPv6 Specification";
  }

  identity ip-in-ipv4 {
    base ip-in-ip;
    description
      "Transport is based on IP over IPv4.";
    reference
      "RFC 2003: IP Encapsulation within IP";
  }

  identity ip-in-ipv6 {
    base ip-in-ip;
    description
      "Transport is based on IP over IPv6.";
    reference
      "RFC 2473: Generic Packet Tunneling in IPv6 Specification";
  }

  identity gre {
    base protocol-type;
    description
      "Transport is based on Generic Routing Encapsulation
       (GRE).";
    reference
      "RFC 1701: Generic Routing Encapsulation (GRE)
       RFC 1702: Generic Routing Encapsulation over IPv4 networks
       RFC 7676: IPv6 Support for Generic Routing Encapsulation
                 (GRE)";
  }

  identity gre-v4 {
    base gre;
    description
      "Transport is based on GRE over IPv4.";
    reference
      "RFC 1702: Generic Routing Encapsulation over IPv4
                 networks";
  }

  identity gre-v6 {
    base gre;
    description
      "Transport is based on GRE over IPv6.";
    reference
      "RFC 7676: IPv6 Support for Generic Routing Encapsulation
                 (GRE)";
  }

  identity vxlan-trans {
    base protocol-type;
    description
      "Transport is based on VXLANs.";
    reference
      "RFC 7348: Virtual eXtensible Local Area Network (VXLAN):
                 A Framework for Overlaying Virtualized Layer 2
                 Networks over Layer 3 Networks";
  }

  identity geneve {
    base protocol-type;
    description
      "Transport is based on Generic Network Virtualization
       Encapsulation (Geneve).";
    reference
      "RFC 8926: Geneve: Generic Network Virtualization
                 Encapsulation";
  }

  identity ldp {
    base protocol-type;
    description
      "Transport is based on LDP.";
    reference
      "RFC 5036: LDP Specification";
  }

  identity mpls-in-udp {
    base protocol-type;
    description
      "Transport is based on MPLS in UDP.";
    reference
      "RFC 7510: Encapsulating MPLS in UDP";
  }

  identity sr {
    base protocol-type;
    description
      "Transport is based on Segment Routing (SR).";
    reference
      "RFC 8660: Segment Routing with the MPLS Data Plane
       RFC 8663: MPLS Segment Routing over IP
       RFC 8754: IPv6 Segment Routing Header (SRH)";
  }

  identity sr-mpls {
    base sr;
    description
      "Transport is based on SR with the MPLS data plane.";
    reference
      "RFC 8660: Segment Routing with the MPLS Data Plane";
  }

  identity srv6 {
    base sr;
    description
      "Transport is based on SR over IPv6.";
    reference
      "RFC 8754: IPv6 Segment Routing Header (SRH)";
  }

  identity sr-mpls-over-ip {
    base sr;
    description
      "Transport is based on SR over MPLS over IP.";
    reference
      "RFC 8663: MPLS Segment Routing over IP";
  }

  identity rsvp-te {
    base protocol-type;
    description
      "Transport setup relies upon RSVP-TE.";
    reference
      "RFC 3209: RSVP-TE: Extensions to RSVP for LSP Tunnels";
  }

  identity bgp-lu {
    base protocol-type;
    description
      "Transport setup relies upon BGP-based labeled prefixes.";
    reference
      "RFC 8277: Using BGP to Bind MPLS Labels to Address Prefixes";
  }

  identity unknown {
    base protocol-type;
    description
      "Unknown protocol type.";
  }

  /*
   * Identities related to encapsulation types
   */

  identity encapsulation-type {
    description
      "Base identity for encapsulation types.";
  }

  identity priority-tagged {
    base encapsulation-type;
    description
      "Priority-tagged interface.";
  }

  identity dot1q {
    if-feature "dot1q";
    base encapsulation-type;
    description
      "dot1Q encapsulation.";
  }

  identity qinq {
    if-feature "qinq";
    base encapsulation-type;
    description
      "QinQ encapsulation.";
  }

  identity qinany {
    if-feature "qinany";
    base encapsulation-type;
    description
      "QinAny encapsulation.";
  }

  identity vxlan {
    if-feature "vxlan";
    base encapsulation-type;
    description
      "VXLAN encapsulation.";
  }

  identity ethernet-type {
    base encapsulation-type;
    description
      "Ethernet encapsulation type.";
  }

  identity vlan-type {
    base encapsulation-type;
    description
      "VLAN encapsulation type.";
  }

  identity untagged-int {
    base encapsulation-type;
    description
      "Untagged interface type.";
  }

  identity tagged-int {
    base encapsulation-type;
    description
      "Tagged interface type.";
  }

  identity lag-int {
    if-feature "lag-interface";
    base encapsulation-type;
    description
      "LAG interface type.";
  }

  /*
   * Identities related to VLAN tags
   */

  identity tag-type {
    description
      "Base identity for VLAN tag types.";
  }

  identity c-vlan {
    base tag-type;
    description
      "Indicates a Customer VLAN (C-VLAN) tag, normally using
       the 0x8100 Ethertype.";
  }

  identity s-vlan {
    base tag-type;
    description
      "Indicates a Service VLAN (S-VLAN) tag.";
  }

  identity s-c-vlan {
    base tag-type;
    description
      "Uses both an S-VLAN tag and a C-VLAN tag.";
  }

  /*
   * Identities related to VXLANs
   */

  identity vxlan-peer-mode {
    if-feature "vxlan";
    description
      "Base identity for VXLAN peer modes.";
  }

  identity static-mode {
    base vxlan-peer-mode;
    description
      "VXLAN access in the static mode.";
  }

  identity bgp-mode {
    base vxlan-peer-mode;
    description
      "VXLAN access by BGP EVPN learning.";
  }

  /*
   * Identities related to multicast
   */

  identity multicast-gp-address-mapping {
    if-feature "multicast";
    description
      "Base identity for multicast group mapping types.";
  }

  identity static-mapping {
    base multicast-gp-address-mapping;
    description
      "Static mapping, i.e., an interface is attached to the
       multicast group as a static member.";
  }

  identity dynamic-mapping {
    base multicast-gp-address-mapping;
    description
      "Dynamic mapping, i.e., an interface is added to the
       multicast group as a result of snooping.";
  }

  identity multicast-tree-type {
    if-feature "multicast";
    description
      "Base identity for multicast tree types.";
  }

  identity ssm-tree-type {
    base multicast-tree-type;
    description
      "Source-Specific Multicast (SSM) tree type.";
  }

  identity asm-tree-type {
    base multicast-tree-type;
    description
      "Any-Source Multicast (ASM) tree type.";
  }

  identity bidir-tree-type {
    base multicast-tree-type;
    description
      "Bidirectional tree type.";
  }

  identity multicast-rp-discovery-type {
    if-feature "multicast";
    description
      "Base identity for Rendezvous Point (RP) discovery types.";
  }

  identity auto-rp {
    base multicast-rp-discovery-type;
    description
      "Auto-RP discovery type.";
  }

  identity static-rp {
    base multicast-rp-discovery-type;
    description
      "Static type.";
  }

  identity bsr-rp {
    base multicast-rp-discovery-type;
    description
      "Bootstrap Router (BSR) discovery type.";
  }

  identity group-management-protocol {
    if-feature "multicast";
    description
      "Base identity for multicast group management protocols.";
  }

  identity igmp-proto {
    base group-management-protocol;
    description
      "IGMP.";
    reference
      "RFC 1112: Host Extensions for IP Multicasting
       RFC 2236: Internet Group Management Protocol, Version 2
       RFC 3376: Internet Group Management Protocol, Version 3";
  }

  identity mld-proto {
    base group-management-protocol;
    description
      "MLD.";
    reference
      "RFC 2710: Multicast Listener Discovery (MLD) for IPv6
       RFC 3810: Multicast Listener Discovery Version 2 (MLDv2)
                 for IPv6";
  }

  identity pim-proto {
    if-feature "pim";
    base routing-protocol-type;
    description
      "PIM.";
    reference
      "RFC 7761: Protocol Independent Multicast - Sparse Mode
                 (PIM-SM): Protocol Specification (Revised)";
  }

  identity igmp-version {
    if-feature "igmp";
    description
      "Base identity for indicating the IGMP version.";
  }

  identity igmpv1 {
    base igmp-version;
    description
      "IGMPv1.";
    reference
      "RFC 1112: Host Extensions for IP Multicasting";
  }

  identity igmpv2 {
    base igmp-version;
    description
      "IGMPv2.";
    reference
      "RFC 2236: Internet Group Management Protocol, Version 2";
  }

  identity igmpv3 {
    base igmp-version;
    description
      "IGMPv3.";
    reference
      "RFC 3376: Internet Group Management Protocol, Version 3";
  }

  identity mld-version {
    if-feature "mld";
    description
      "Base identity for indicating the MLD version.";
  }

  identity mldv1 {
    base mld-version;
    description
      "MLDv1.";
    reference
      "RFC 2710: Multicast Listener Discovery (MLD) for IPv6";
  }

  identity mldv2 {
    base mld-version;
    description
      "MLDv2.";
    reference
      "RFC 3810: Multicast Listener Discovery Version 2 (MLDv2)
                 for IPv6";
  }

  /*
   * Identities related to traffic types
   */

  identity tf-type {
    description
      "Base identity for traffic types.";
  }

  identity multicast-traffic {
    base tf-type;
    description
      "Multicast traffic.";
  }

  identity broadcast-traffic {
    base tf-type;
    description
      "Broadcast traffic.";
  }

  identity unknown-unicast-traffic {
    base tf-type;
    description
      "Unknown unicast traffic.";
  }

  /*
   * Identities related to customer applications
   */

  identity customer-application {
    description
      "Base identity for customer applications.";
  }

  identity web {
    base customer-application;
    description
      "Web applications (e.g., HTTP, HTTPS).";
  }

  identity mail {
    base customer-application;
    description
      "Mail application.";
  }

  identity file-transfer {
    base customer-application;
    description
      "File transfer application (e.g., FTP, Secure FTP (SFTP)).";
  }

  identity database {
    base customer-application;
    description
      "Database application.";
  }

  identity social {
    base customer-application;
    description
      "Social-network application.";
  }

  identity games {
    base customer-application;
    description
      "Gaming application.";
  }

  identity p2p {
    base customer-application;
    description
      "Peer-to-peer application.";
  }

  identity network-management {
    base customer-application;
    description
      "Management application (e.g., Telnet, syslog, SNMP).";
  }

  identity voice {
    base customer-application;
    description
      "Voice application.";
  }

  identity video {
    base customer-application;
    description
      "Video-conference application.";
  }

  identity embb {
    base customer-application;
    description
      "Enhanced Mobile Broadband (eMBB) application.
       Note that eMBB applications demand network performance
       with a wide variety of such characteristics as data rate,
       latency, loss rate, reliability, and many other
       parameters.";
  }

  identity urllc {
    base customer-application;
    description
      "Ultra-Reliable and Low Latency Communications (URLLC)
       application.  Note that URLLC applications demand
       network performance with a wide variety of such
       characteristics as latency, reliability, and many other
       parameters.";
  }

  identity mmtc {
    base customer-application;
    description
      "Massive Machine Type Communications (mMTC) application.
       Note that mMTC applications demand network performance
       with a wide variety of such characteristics as data rate,
       latency, loss rate, reliability, and many other
       parameters.";
  }

  /*
   * Identities related to service bundling
   */

  identity bundling-type {
    description
      "The base identity for the bundling type.  It supports a
       subset or all Customer Edge VLAN IDs (CE-VLAN IDs)
       associated with an L2VPN service.";
  }

  identity multi-svc-bundling {
    base bundling-type;
    description
      "Multi-service bundling, i.e., multiple CE-VLAN IDs
       can be associated with an L2VPN service at a site.";
  }

  identity one2one-bundling {
    base bundling-type;
    description
      "One-to-one service bundling, i.e., each L2VPN can
       be associated with only one CE-VLAN ID at a site.";
  }

  identity all2one-bundling {
    base bundling-type;
    description
      "All-to-one bundling, i.e., all CE-VLAN IDs are mapped
       to one L2VPN service.";
  }

  /*
   * Identities related to Ethernet services
   */

  identity control-mode {
    description
      "Base identity for the type of control mode used with the
       Layer 2 Control Protocol (L2CP).";
  }

  identity peer {
    base control-mode;
    description
      "'peer' mode, i.e., participate in the protocol towards
       the CE.  Peering is common for the Link Aggregation Control
       Protocol (LACP) and the Ethernet Local Management Interface
       (E-LMI) and, occasionally, for the Link Layer Discovery
       Protocol (LLDP).  For VPLSs and VPWSs, the subscriber can
       also request that the peer service provider enable
       spanning tree.";
  }

  identity tunnel {
    base control-mode;
    description
      "'tunnel' mode, i.e., pass to the egress or destination
       site.  For Ethernet Private Lines (EPLs), the expectation
       is that L2CP frames are tunneled.";
  }

  identity discard {
    base control-mode;
    description
      "'Discard' mode, i.e., discard the frame.";
  }

  identity neg-mode {
    description
      "Base identity for the type of negotiation mode.";
  }

  identity full-duplex {
    base neg-mode;
    description
      "Full-duplex negotiation mode.";
  }

  identity auto-neg {
    base neg-mode;
    description
      "Auto-negotiation mode.";
  }

  /******** VPN-related type ********/

  typedef vpn-id {
    type string;
    description
      "Defines an identifier that is used with a VPN module.
       For example, this can be a service identifier, a node
       identifier, etc.";
  }

  /******* VPN-related reusable groupings *******/

  grouping vpn-description {
    description
      "Provides common VPN information.";
    leaf vpn-id {
      type vpn-common:vpn-id;
      description
        "A VPN identifier that uniquely identifies a VPN.
         This identifier has a local meaning, e.g., within
         a service provider network.";
    }
    leaf vpn-name {
      type string;
      description
        "Used to associate a name with the service
         in order to facilitate the identification of
         the service.";
    }
    leaf vpn-description {
      type string;
      description
        "Textual description of a VPN.";
    }
    leaf customer-name {
      type string;
      description
        "Name of the customer that actually uses the VPN.";
    }
  }

  grouping vpn-profile-cfg {
    description
      "Grouping for VPN profile configuration.";
    container valid-provider-identifiers {
      description
        "Container for valid provider profile identifiers.";
      list external-connectivity-identifier {
        if-feature "external-connectivity";
        key "id";
        description
          "List of profile identifiers that uniquely identify
           profiles governing how external connectivity is
           provided to a VPN.  A profile indicates the type of
           external connectivity (Internet, cloud, etc.), the
           sites/nodes that are associated with a connectivity
           profile, etc.  A profile can also indicate filtering
           rules and/or address translation rules.  Such features
           may involve PE, P, or dedicated nodes as a function
           of the deployment.";
        leaf id {
          type string;
          description
            "Identification of an external connectivity profile.
             The profile only has significance within the service
             provider's administrative domain.";
        }
      }
      list encryption-profile-identifier {
        key "id";
        description
          "List of encryption profile identifiers.";
        leaf id {
          type string;
          description
            "Identification of the encryption profile to be used.
             The profile only has significance within the service
             provider's administrative domain.";
        }
      }
      list qos-profile-identifier {
        key "id";
        description
          "List of QoS profile identifiers.";
        leaf id {
          type string;
          description
            "Identification of the QoS profile to be used.  The
             profile only has significance within the service
             provider's administrative domain.";
        }
      }
      list bfd-profile-identifier {
        key "id";
        description
          "List of BFD profile identifiers.";
        leaf id {
          type string;
          description
            "Identification of the BFD profile to be used.  The
             profile only has significance within the service
             provider's administrative domain.";
        }
      }
      list forwarding-profile-identifier {
        key "id";
        description
          "List of forwarding profile identifiers.";
        leaf id {
          type string;
          description
            "Identification of the forwarding profile to be used.
             The profile only has significance within the service
             provider's administrative domain.";
        }
      }
      list routing-profile-identifier {
        key "id";
        description
          "List of routing profile identifiers.";
        leaf id {
          type string;
          description
            "Identification of the routing profile to be used by
             the routing protocols within sites, VPN network
             accesses, or VPN nodes for referring to VRF's
             import/export policies.

             The profile only has significance within the service
             provider's administrative domain.";
        }
      }
      nacm:default-deny-write;
    }
  }

  grouping oper-status-timestamp {
    description
      "This grouping defines some operational parameters for the
       service.";
    leaf status {
      type identityref {
        base operational-status;
      }
      config false;
      description
        "Operational status.";
    }
    leaf last-change {
      type yang:date-and-time;
      config false;
      description
        "Indicates the actual date and time of the service status
         change.";
    }
  }

  grouping service-status {
    description
      "Service status grouping.";
    container status {
      description
        "Service status.";
      container admin-status {
        description
          "Administrative service status.";
        leaf status {
          type identityref {
            base administrative-status;
          }
          description
            "Administrative service status.";
        }
        leaf last-change {
          type yang:date-and-time;
          description
            "Indicates the actual date and time of the service
             status change.";
        }
      }
      container oper-status {
        config false;
        description
          "Operational service status.";
        uses oper-status-timestamp;
      }
    }
  }

  grouping underlay-transport {
    description
      "This grouping defines the type of underlay transport for
       the VPN service or how that underlay is set.  It can
       include an identifier for an abstract transport instance to
       which the VPN is grafted or indicate a technical
       implementation that is expressed as an ordered list of
       protocols.";
    choice type {
      description
        "A choice based on the type of underlay transport
         constraints.";
      case abstract {
        description
          "Indicates that the transport constraint is an abstract
           concept.";
        leaf transport-instance-id {
          type string;
          description
            "An optional identifier of the abstract transport
             instance.";
        }
        leaf instance-type {
          type identityref {
            base transport-instance-type;
          }
          description
            "Indicates a transport instance type.  For example,
             it can be a VPN+, an IETF network slice, a virtual
             network, etc.";
        }
      }
      case protocol {
        description
          "Indicates a list of protocols.";
        leaf-list protocol {
          type identityref {
            base protocol-type;
          }
          ordered-by user;
          description
            "A client-ordered list of transport protocols.";
        }
      }
    }
  }

  grouping vpn-route-targets {
    description
      "A grouping that specifies Route Target (RT) import/export
       rules used in a BGP-enabled VPN.";
    reference
      "RFC 4364: BGP/MPLS IP Virtual Private Networks (VPNs)
       RFC 4664: Framework for Layer 2 Virtual Private Networks
                 (L2VPNs)";
    list vpn-target {
      key "id";
      description
        "RTs.  AND/OR operations may be defined based on the
         assigned RTs.";
      leaf id {
        type uint8;
        description
          "Identifies each VPN target.";
      }
      list route-targets {
        key "route-target";
        description
          "List of RTs.";
        leaf route-target {
          type rt-types:route-target;
          description
            "Conveys an RT value.";
        }
      }
      leaf route-target-type {
        type rt-types:route-target-type;
        mandatory true;
        description
          "Import/export type of the RT.";
      }
    }
    container vpn-policies {
      description
        "VPN service policies.  'vpn-policies' contains references
         to the import and export policies to be associated with
         the VPN service.";
      leaf import-policy {
        type string;
        description
          "Identifies the import policy.";
      }
      leaf export-policy {
        type string;
        description
          "Identifies the export policy.";
      }
    }
  }

  grouping route-distinguisher {
    description
      "Grouping for Route Distinguishers (RDs).";
    choice rd-choice {
      description
        "RD choice between several options for providing the RD
         value.";
      case directly-assigned {
        description
          "Explicitly assigns an RD value.";
        leaf rd {
          type rt-types:route-distinguisher;
          description
            "Indicates an RD value that is explicitly assigned.";
        }
      }
      case directly-assigned-suffix {
        description
          "The value of the Assigned Number subfield of the RD.
           The Administrator subfield of the RD will be
           based on other configuration information such as the
           Router ID or Autonomous System Number (ASN).";
        leaf rd-suffix {
          type uint16;
          description
            "Indicates the value of the Assigned Number
             subfield that is explicitly assigned.";
        }
      }
      case auto-assigned {
        description
          "The RD is auto-assigned.";
        container rd-auto {
          description
            "The RD is auto-assigned.";
          choice auto-mode {
            description
              "Indicates the auto-assignment mode.  The RD can be
               automatically assigned with or without
               indicating a pool from which the RD should be
               taken.

               For both cases, the server will auto-assign an RD
               value 'auto-assigned-rd' and use that value
               operationally.";
            case from-pool {
              leaf rd-pool-name {
                type string;
                description
                  "The auto-assignment will be made from the pool
                   identified by 'rd-pool-name'.";
              }
            }
            case full-auto {
              leaf auto {
                type empty;
                description
                  "Indicates that an RD is fully auto-assigned.";
              }
            }
          }
          leaf auto-assigned-rd {
            type rt-types:route-distinguisher;
            config false;
            description
              "The value of the auto-assigned RD.";
          }
        }
      }
      case auto-assigned-suffix {
        description
          "The value of the Assigned Number subfield will be
           auto-assigned.  The Administrator subfield will be
           based on other configuration information such as the
           Router ID or ASN.";
        container rd-auto-suffix {
          description
            "The Assigned Number subfield is auto-assigned.";
          choice auto-mode {
            description
              "Indicates the auto-assignment mode of the
               Assigned Number subfield.  This number can be
               automatically assigned with or without indicating a
               pool from which the value should be taken.

               For both cases, the server will auto-assign
               'auto-assigned-rd-suffix' and use that value to
               build the RD that will be used operationally.";
            case from-pool {
              leaf rd-pool-name {
                type string;
                description
                  "The assignment will be made from the pool
                   identified by 'rd-pool-name'.";
              }
            }
            case full-auto {
              leaf auto {
                type empty;
                description
                  "Indicates that the Assigned Number subfield is
                   fully auto-assigned.";
              }
            }
          }
          leaf auto-assigned-rd-suffix {
            type uint16;
            config false;
            description
              "Includes the value of the Assigned Number subfield
               that is auto-assigned.";
          }
        }
      }
      case no-rd {
        description
          "Uses the 'empty' type to indicate that the RD has no
           value and is not to be auto-assigned.";
        leaf no-rd {
          type empty;
          description
            "No RD is assigned.";
        }
      }
    }
  }

  grouping vpn-components-group {
    description
      "Grouping definition to assign group IDs to associate
       VPN nodes, sites, or network accesses.";
    container groups {
      description
        "Lists the groups to which a VPN node, a site, or a
         network access belongs.";
      list group {
        key "group-id";
        description
          "List of group IDs.";
        leaf group-id {
          type string;
          description
            "The group ID to which a VPN node, a site, or a
             network access belongs.";
        }
      }
    }
  }

  grouping placement-constraints {
    description
      "Constraints related to placement of a network access.";
    list constraint {
      key "constraint-type";
      description
        "List of constraints.";
      leaf constraint-type {
        type identityref {
          base placement-diversity;
        }
        description
          "Diversity constraint type.";
      }
      container target {
        description
          "The constraint will apply against this list of
           groups.";
        choice target-flavor {
          description
            "Choice for the group definition.";
          case id {
            list group {
              key "group-id";
              description
                "List of groups.";
              leaf group-id {
                type string;
                description
                  "The constraint will apply against this
                   particular group ID.";
              }
            }
          }
          case all-accesses {
            leaf all-other-accesses {
              type empty;
              description
                "The constraint will apply against all other
                 network accesses of a site.";
            }
          }
          case all-groups {
            leaf all-other-groups {
              type empty;
              description
                "The constraint will apply against all other
                 groups managed by the customer.";
            }
          }
        }
      }
    }
  }

  grouping ports {
    description
      "Choice of specifying source or destination port numbers.";
    choice source-port {
      description
        "Choice of specifying the source port or referring to a
         group of source port numbers.";
      container source-port-range-or-operator {
        description
          "Source port definition.";
        uses packet-fields:port-range-or-operator;
      }
    }
    choice destination-port {
      description
        "Choice of specifying a destination port or referring to a
         group of destination port numbers.";
      container destination-port-range-or-operator {
        description
          "Destination port definition.";
        uses packet-fields:port-range-or-operator;
      }
    }
  }

  grouping qos-classification-policy {
    description
      "Configuration of the traffic classification policy.";
    list rule {
      key "id";
      ordered-by user;
      description
        "List of marking rules.";
      leaf id {
        type string;
        description
          "An identifier of the QoS classification policy rule.";
      }
      choice match-type {
        default "match-flow";
        description
          "Choice for classification.";
        case match-flow {
          choice l3 {
            description
              "Either IPv4 or IPv6.";
            container ipv4 {
              description
                "Rule set that matches the IPv4 header.";
              uses packet-fields:acl-ip-header-fields;
              uses packet-fields:acl-ipv4-header-fields;
            }
            container ipv6 {
              description
                "Rule set that matches the IPv6 header.";
              uses packet-fields:acl-ip-header-fields;
              uses packet-fields:acl-ipv6-header-fields;
            }
          }
          choice l4 {
            description
              "Includes Layer-4-specific information.
               This version focuses on TCP and UDP.";
            container tcp {
              description
                "Rule set that matches the TCP header.";
              uses packet-fields:acl-tcp-header-fields;
              uses ports;
            }
            container udp {
              description
                "Rule set that matches the UDP header.";
              uses packet-fields:acl-udp-header-fields;
              uses ports;
            }
          }
        }
        case match-application {
          leaf match-application {
            type identityref {
              base customer-application;
            }
            description
              "Defines the application to match.";
          }
        }
      }
      leaf target-class-id {
        type string;
        description
          "Identification of the class of service.  This
           identifier is internal to the administration.";
      }
    }
  }
}
