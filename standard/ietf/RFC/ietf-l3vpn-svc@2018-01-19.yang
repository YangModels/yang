module ietf-l3vpn-svc {
 namespace &quot;urn:ietf:params:xml:ns:yang:ietf-l3vpn-svc&quot;;

 prefix l3vpn-svc;

 import ietf-inet-types {
  prefix inet;
 }

 import ietf-yang-types {
  prefix yang;
 }

 organization
  &quot;IETF L3SM Working Group&quot;;

 contact
  &quot;WG List: &lt;mailto:<a href="mailto:l3sm@ietf.org">l3sm@ietf.org</a>&gt;

  Editor:
   L3SM WG

  Chairs:
   Adrian Farrel, Qin Wu
  &quot;;

 description
  &quot;This YANG module defines a generic service configuration
  model for Layer 3 VPNs.  This model is common across all
  vendor implementations.&quot;;

 revision 2017-01-27 {
  description
   &quot;Initial document.&quot;;
  reference
    &quot;<a href="/doc/html/rfc8049">RFC 8049</a>.&quot;;
 }

<span class="grey"><a href="/doc/html/rfc8049">RFC 8049</a>       YANG Data Model for L3VPN Service Delivery  February 2017</span>

    /* Features */

    feature cloud-access {
     description
      &quot;Allows the VPN to connect to a CSP.&quot;;
    }
    feature multicast {
     description
      &quot;Enables multicast capabilities in a VPN.&quot;;
    }
    feature ipv4 {
     description
      &quot;Enables IPv4 support in a VPN.&quot;;
    }
    feature ipv6 {
     description
      &quot;Enables IPv6 support in a VPN.&quot;;
    }
    feature carrierscarrier {
     description
      &quot;Enables support of CsC.&quot;;
    }
    feature extranet-vpn {
     description
      &quot;Enables support of extranet VPNs.&quot;;
    }
    feature site-diversity {
     description
      &quot;Enables support of site diversity constraints.&quot;;
    }
    feature encryption {
     description
      &quot;Enables support of encryption.&quot;;
    }
    feature qos {
     description
      &quot;Enables support of classes of services.&quot;;
    }
    feature qos-custom {
     description
      &quot;Enables support of the custom QoS profile.&quot;;
    }
    feature rtg-bgp {
     description
      &quot;Enables support of the BGP routing protocol.&quot;;
    }

<span class="grey"><a href="/doc/html/rfc8049">RFC 8049</a>       YANG Data Model for L3VPN Service Delivery  February 2017</span>

    feature rtg-rip {
     description
      &quot;Enables support of the RIP routing protocol.&quot;;
    }
    feature rtg-ospf {
     description
      &quot;Enables support of the OSPF routing protocol.&quot;;
    }
    feature rtg-ospf-sham-link {
     description
      &quot;Enables support of OSPF sham links.&quot;;
    }
    feature rtg-vrrp {
     description
      &quot;Enables support of the VRRP routing protocol.&quot;;
    }
    feature fast-reroute {
     description
      &quot;Enables support of Fast Reroute.&quot;;
    }
    feature bfd {
     description
      &quot;Enables support of BFD.&quot;;
    }
    feature always-on {
     description
      &quot;Enables support of the &#x27;always-on&#x27; access constraint.&quot;;
    }
    feature requested-type {
     description
      &quot;Enables support of the &#x27;requested-type&#x27; access constraint.&quot;;
    }
    feature bearer-reference {
     description
      &quot;Enables support of the &#x27;bearer-reference&#x27; access constraint.&quot;;
    }

    /* Typedefs */

    typedef svc-id {
     type string;
     description
      &quot;Defines a type of service component identifier.&quot;;
    }

<span class="grey"><a href="/doc/html/rfc8049">RFC 8049</a>       YANG Data Model for L3VPN Service Delivery  February 2017</span>

    typedef template-id {
     type string;
     description
      &quot;Defines a type of service template identifier.&quot;;
    }

    typedef address-family {
     type enumeration {
      enum ipv4 {
       description
        &quot;IPv4 address family.&quot;;
      }
      enum ipv6 {
       description
        &quot;IPv6 address family.&quot;;
      }
     }
     description
      &quot;Defines a type for the address family.&quot;;
    }

    /* Identities */

    identity site-network-access-type {
     description
      &quot;Base identity for site-network-access type.&quot;;
    }
    identity point-to-point {
     base site-network-access-type;
     description
      &quot;Identity for point-to-point connection.&quot;;
    }
    identity multipoint {
     base site-network-access-type;
     description
      &quot;Identity for multipoint connection.
      Example: Ethernet broadcast segment.&quot;;
    }
    identity placement-diversity {
     description
      &quot;Base identity for site placement constraints.&quot;;
    }
    identity bearer-diverse {
     base placement-diversity;
     description
      &quot;Identity for bearer diversity.
      The bearers should not use common elements.&quot;;
    }
<span class="grey"><a href="/doc/html/rfc8049">RFC 8049</a>       YANG Data Model for L3VPN Service Delivery  February 2017</span>

    identity pe-diverse {
     base placement-diversity;
     description
      &quot;Identity for PE diversity.&quot;;
    }
    identity pop-diverse {
     base placement-diversity;
     description
      &quot;Identity for POP diversity.&quot;;
    }
    identity linecard-diverse {
     base placement-diversity;
     description
      &quot;Identity for linecard diversity.&quot;;
    }
    identity same-pe {
     base placement-diversity;
     description
      &quot;Identity for having sites connected on the same PE.&quot;;
    }
    identity same-bearer {
     base placement-diversity;
     description
      &quot;Identity for having sites connected using the same bearer.&quot;;
    }
    identity customer-application {
     description
      &quot;Base identity for customer application.&quot;;
    }
    identity web {
     base customer-application;
     description
      &quot;Identity for Web application (e.g., HTTP, HTTPS).&quot;;
    }
    identity mail {
     base customer-application;
     description
      &quot;Identity for mail application.&quot;;
    }
    identity file-transfer {
     base customer-application;
     description
      &quot;Identity for file transfer application (e.g., FTP, SFTP).&quot;;
    }

<span class="grey"><a href="/doc/html/rfc8049">RFC 8049</a>       YANG Data Model for L3VPN Service Delivery  February 2017</span>

    identity database {
     base customer-application;
     description
      &quot;Identity for database application.&quot;;
    }
    identity social {
     base customer-application;
     description
      &quot;Identity for social-network application.&quot;;
    }
    identity games {
     base customer-application;
     description
      &quot;Identity for gaming application.&quot;;
    }
    identity p2p {
     base customer-application;
     description
      &quot;Identity for peer-to-peer application.&quot;;
    }
    identity network-management {
     base customer-application;
     description
      &quot;Identity for management application
      (e.g., Telnet, syslog, SNMP).&quot;;
    }
    identity voice {
     base customer-application;
     description
      &quot;Identity for voice application.&quot;;
    }
    identity video {
     base customer-application;
     description
      &quot;Identity for video conference application.&quot;;
    }
    identity site-vpn-flavor {
     description
      &quot;Base identity for the site VPN service flavor.&quot;;
    }
    identity site-vpn-flavor-single {
     base site-vpn-flavor;
     description
      &quot;Base identity for the site VPN service flavor.
      Used when the site belongs to only one VPN.&quot;;
    }

<span class="grey"><a href="/doc/html/rfc8049">RFC 8049</a>       YANG Data Model for L3VPN Service Delivery  February 2017</span>

    identity site-vpn-flavor-multi {
     base site-vpn-flavor;
     description
      &quot;Base identity for the site VPN service flavor.
      Used when a logical connection of a site
      belongs to multiple VPNs.&quot;;
    }
    identity site-vpn-flavor-sub {
     base site-vpn-flavor;
     description
      &quot;Base identity for the site VPN service flavor.
      Used when a site has multiple logical connections.
      Each connection may belong to different multiple VPNs.&quot;;
    }
    identity site-vpn-flavor-nni {
     base site-vpn-flavor;
     description
      &quot;Base identity for the site VPN service flavor.
      Used to describe an NNI option A connection.&quot;;
    }
    identity management {
     description
      &quot;Base identity for site management scheme.&quot;;
    }
    identity co-managed {
     base management;
     description
      &quot;Base identity for co-managed site.&quot;;
    }
    identity customer-managed {
     base management;
     description
      &quot;Base identity for customer-managed site.&quot;;
    }
    identity provider-managed {
     base management;
     description
      &quot;Base identity for provider-managed site.&quot;;
    }
    identity address-allocation-type {
     description
      &quot;Base identity for address-allocation-type for PE-CE link.&quot;;
    }
    identity provider-dhcp {
     base address-allocation-type;
     description
      &quot;Provider network provides DHCP service to customer.&quot;;
    }
<span class="grey"><a href="/doc/html/rfc8049">RFC 8049</a>       YANG Data Model for L3VPN Service Delivery  February 2017</span>

    identity provider-dhcp-relay {
     base address-allocation-type;
     description
      &quot;Provider network provides DHCP relay service to customer.&quot;;
    }
    identity provider-dhcp-slaac {
     base address-allocation-type;
     description
      &quot;Provider network provides DHCP service to customer,
      as well as SLAAC.&quot;;
    }
    identity static-address {
     base address-allocation-type;
     description
      &quot;Provider-to-customer addressing is static.&quot;;
    }
    identity slaac {
     base address-allocation-type;
     description
      &quot;Use IPv6 SLAAC.&quot;;
    }

    identity site-role {
     description
      &quot;Base identity for site type.&quot;;
    }
    identity any-to-any-role {
     base site-role;
     description
      &quot;Site in an any-to-any IP VPN.&quot;;
    }
    identity spoke-role {
     base site-role;
     description
      &quot;Spoke site in a Hub-and-Spoke IP VPN.&quot;;
    }
    identity hub-role {
     base site-role;
     description
      &quot;Hub site in a Hub-and-Spoke IP VPN.&quot;;
    }

<span class="grey"><a href="/doc/html/rfc8049">RFC 8049</a>       YANG Data Model for L3VPN Service Delivery  February 2017</span>

    identity vpn-topology {
     description
      &quot;Base identity for VPN topology.&quot;;
    }
    identity any-to-any {
     base vpn-topology;
     description
      &quot;Identity for any-to-any VPN topology.&quot;;
    }
    identity hub-spoke {
     base vpn-topology;
     description
      &quot;Identity for Hub-and-Spoke VPN topology.&quot;;
    }
    identity hub-spoke-disjoint {
     base vpn-topology;
     description
      &quot;Identity for Hub-and-Spoke VPN topology
      where Hubs cannot communicate with each other.&quot;;
    }

    identity multicast-tree-type {
     description
      &quot;Base identity for multicast tree type.&quot;;
    }
    identity ssm-tree-type {
     base multicast-tree-type;
     description
      &quot;Identity for SSM tree type.&quot;;
    }
    identity asm-tree-type {
     base multicast-tree-type;
     description
      &quot;Identity for ASM tree type.&quot;;
    }
    identity bidir-tree-type {
     base multicast-tree-type;
     description
      &quot;Identity for bidirectional tree type.&quot;;
    }

    identity multicast-rp-discovery-type {
     description
      &quot;Base identity for RP discovery type.&quot;;
    }

<span class="grey"><a href="/doc/html/rfc8049">RFC 8049</a>       YANG Data Model for L3VPN Service Delivery  February 2017</span>

    identity auto-rp {
     base multicast-rp-discovery-type;
     description
      &quot;Base identity for Auto-RP discovery type.&quot;;
    }
    identity static-rp {
     base multicast-rp-discovery-type;
     description
      &quot;Base identity for static type.&quot;;
    }
    identity bsr-rp {
     base multicast-rp-discovery-type;
     description
      &quot;Base identity for BSR discovery type.&quot;;
    }

    identity routing-protocol-type {
     description
      &quot;Base identity for routing protocol type.&quot;;
    }
    identity ospf {
     base routing-protocol-type;
     description
      &quot;Identity for OSPF protocol type.&quot;;
    }
    identity bgp {
     base routing-protocol-type;
     description
      &quot;Identity for BGP protocol type.&quot;;
    }
    identity static {
     base routing-protocol-type;
     description
      &quot;Identity for static routing protocol type.&quot;;
    }
    identity rip {
     base routing-protocol-type;
     description
      &quot;Identity for RIP protocol type.&quot;;
    }
    identity vrrp {
     base routing-protocol-type;
     description
      &quot;Identity for VRRP protocol type.
      This is to be used when LANs are directly connected
      to PE routers.&quot;;
    }

<span class="grey"><a href="/doc/html/rfc8049">RFC 8049</a>       YANG Data Model for L3VPN Service Delivery  February 2017</span>

    identity direct {
     base routing-protocol-type;
     description
      &quot;Identity for direct protocol type.&quot;;
    }

    identity protocol-type {
     description
      &quot;Base identity for protocol field type.&quot;;
    }
    identity tcp {
     base protocol-type;
     description
      &quot;TCP protocol type.&quot;;
    }
    identity udp {
     base protocol-type;
     description
      &quot;UDP protocol type.&quot;;
    }
    identity icmp {
     base protocol-type;
     description
      &quot;ICMP protocol type.&quot;;
    }
    identity icmp6 {
     base protocol-type;
     description
      &quot;ICMPv6 protocol type.&quot;;
    }
    identity gre {
     base protocol-type;
     description
      &quot;GRE protocol type.&quot;;
    }
    identity ipip {
     base protocol-type;
     description
      &quot;IP-in-IP protocol type.&quot;;
    }
    identity hop-by-hop {
     base protocol-type;
     description
      &quot;Hop-by-Hop IPv6 header type.&quot;;
    }

<span class="grey"><a href="/doc/html/rfc8049">RFC 8049</a>       YANG Data Model for L3VPN Service Delivery  February 2017</span>

    identity routing {
     base protocol-type;
     description
      &quot;Routing IPv6 header type.&quot;;
    }
    identity esp {
     base protocol-type;
     description
      &quot;ESP header type.&quot;;
    }
    identity ah {
     base protocol-type;
     description
      &quot;AH header type.&quot;;
    }

    /* Groupings */

    grouping vpn-service-cloud-access {
     container cloud-accesses {
     if-feature cloud-access;
     list cloud-access {

      key cloud-identifier;

      leaf cloud-identifier {
       type string;
       description
        &quot;Identification of cloud service.
        Local administration meaning.&quot;;
      }
      choice list-flavor {
       case permit-any {
        leaf permit-any {
         type empty;
         description
          &quot;Allows all sites.&quot;;
        }
       }
       case deny-any-except {
        leaf-list permit-site {
         type leafref {
          path &quot;/l3vpn-svc/sites/site/site-id&quot;;
         }
         description
          &quot;Site ID to be authorized.&quot;;
        }
       }
<span class="grey"><a href="/doc/html/rfc8049">RFC 8049</a>       YANG Data Model for L3VPN Service Delivery  February 2017</span>

       case permit-any-except {
        leaf-list deny-site {
         type leafref {
          path &quot;/l3vpn-svc/sites/site/site-id&quot;;
         }
         description
          &quot;Site ID to be denied.&quot;;
        }
       }
       description
        &quot;Choice for cloud access policy.&quot;;
      }
      container authorized-sites {
       list authorized-site {
        key site-id;

        leaf site-id {
         type leafref {
          path &quot;/l3vpn-svc/sites/site/site-id&quot;;
         }
         description
          &quot;Site ID.&quot;;
        }
        description
         &quot;List of authorized sites.&quot;;
       }
       description
        &quot;Configuration of authorized sites.&quot;;
      }
      container denied-sites {
       list denied-site {
        key site-id;

        leaf site-id {
         type leafref {
          path &quot;/l3vpn-svc/sites/site/site-id&quot;;
         }
         description
          &quot;Site ID.&quot;;
        }
        description
         &quot;List of denied sites.&quot;;
       }
       description
        &quot;Configuration of denied sites.&quot;;
      }

<span class="grey"><a href="/doc/html/rfc8049">RFC 8049</a>       YANG Data Model for L3VPN Service Delivery  February 2017</span>

      container address-translation {
       container nat44 {
        leaf enabled {
         type boolean;
         default false;
         description
          &quot;Controls whether or not address translation is required.&quot;;
        }
        leaf nat44-customer-address {
         type inet:ipv4-address;
         must &quot;../enabled = &#x27;true&#x27;&quot; {
          description
           &quot;Applicable only if address translation is enabled.&quot;;
         }
         description
          &quot;Address to be used for translation.
          This is to be used if the customer is
          providing the address.&quot;;
        }
        description
         &quot;IPv4-to-IPv4 translation.&quot;;
       }
       description
        &quot;Container for NAT.&quot;;
      }
      description
       &quot;Cloud access configuration.&quot;;
     }
      description
       &quot;Container for cloud access configurations.&quot;;
     }
     description
      &quot;Grouping for VPN cloud definition.&quot;;
    }

<span class="grey"><a href="/doc/html/rfc8049">RFC 8049</a>       YANG Data Model for L3VPN Service Delivery  February 2017</span>

    grouping multicast-rp-group-cfg {
     choice group-format {
      case startend {
       leaf group-start {
        type inet:ip-address;
        description
         &quot;First group address.&quot;;
       }
       leaf group-end {
        type inet:ip-address;
        description
         &quot;Last group address.&quot;;
       }
      }
      case singleaddress {
       leaf group-address {
        type inet:ip-address;
        description
         &quot;Group address.&quot;;
       }
      }
      description
       &quot;Choice for group format.&quot;;
     }
     description
      &quot;Definition of groups for RP-to-group mapping.&quot;;
    }

    grouping vpn-service-multicast {
     container multicast {
      if-feature multicast;
      leaf enabled {
       type boolean;
       default false;
       description
        &quot;Enables multicast.&quot;;
      }
      container customer-tree-flavors {
       leaf-list tree-flavor {
         type identityref {
          base multicast-tree-type;
         }
         description
          &quot;Type of tree to be used.&quot;;
       }
       description
        &quot;Type of trees used by customer.&quot;;
      }
<span class="grey"><a href="/doc/html/rfc8049">RFC 8049</a>       YANG Data Model for L3VPN Service Delivery  February 2017</span>

      container rp {
       container rp-group-mappings {
        list rp-group-mapping {
         key id;

         leaf id {
          type uint16;
          description
           &quot;Unique identifier for the mapping.&quot;;
         }
         container provider-managed {
          leaf enabled {
           type boolean;
           default false;
           description
            &quot;Set to true if the RP must be a provider-managed node.
            Set to false if it is a customer-managed node.&quot;;
          }
          leaf rp-redundancy {
           when &quot;../enabled = &#x27;true&#x27;&quot; {
            description
             &quot;Relevant when the RP is provider-managed.&quot;;
           }
           type boolean;
           default false;
           description
            &quot;If true, a redundancy mechanism for the RP is required.&quot;;
          }
          leaf optimal-traffic-delivery {
           when &quot;../enabled = &#x27;true&#x27;&quot; {
            description
             &quot;Relevant when the RP is provider-managed.&quot;;
           }
           type boolean;
           default false;
           description
            &quot;If true, the SP must ensure that
            traffic uses an optimal path.&quot;;
          }
          description
           &quot;Parameters for a provider-managed RP.&quot;;
         }

<span class="grey"><a href="/doc/html/rfc8049">RFC 8049</a>       YANG Data Model for L3VPN Service Delivery  February 2017</span>

         leaf rp-address {
          when &quot;../provider-managed/enabled = &#x27;false&#x27;&quot; {
           description
            &quot;Relevant when the RP is provider-managed.&quot;;
          }
          type inet:ip-address;
          description
           &quot;Defines the address of the RP.
           Used if the RP is customer-managed.&quot;;
         }

         container groups {
          list group {
           key id;

           leaf id {
            type uint16;
            description
             &quot;Identifier for the group.&quot;;
           }
           uses multicast-rp-group-cfg;
           description
            &quot;List of groups.&quot;;
          }

          description
           &quot;Multicast groups associated with the RP.&quot;;
         }

         description
          &quot;List of RP-to-group mappings.&quot;;
        }
        description
         &quot;RP-to-group mappings.&quot;;
       }
       container rp-discovery {
        leaf rp-discovery-type {
         type identityref {
          base multicast-rp-discovery-type;
         }
         default static-rp;
         description
          &quot;Type of RP discovery used.&quot;;
        }

<span class="grey"><a href="/doc/html/rfc8049">RFC 8049</a>       YANG Data Model for L3VPN Service Delivery  February 2017</span>

        container bsr-candidates {
         when &quot;../rp-discovery-type = &#x27;bsr-rp&#x27;&quot; {
          description
           &quot;Only applicable if discovery type is BSR-RP.&quot;;
         }
         leaf-list bsr-candidate-address {
          type inet:ip-address;
          description
           &quot;Address of BSR candidate.&quot;;
         }
         description
          &quot;Customer BSR candidate&#x27;s address.&quot;;
        }
        description
         &quot;RP discovery parameters.&quot;;
       }

       description
        &quot;RP parameters.&quot;;
      }
      description
       &quot;Multicast global parameters for the VPN service.&quot;;
     }
     description
      &quot;Grouping for multicast VPN definition.&quot;;
    }

    grouping vpn-service-mpls {
     leaf carrierscarrier {
      if-feature carrierscarrier;
      type boolean;
      default false;
      description
       &quot;The VPN is using CsC, and so MPLS is required.&quot;;
     }
     description
      &quot;Grouping for MPLS CsC definition.&quot;;
    }

<span class="grey"><a href="/doc/html/rfc8049">RFC 8049</a>       YANG Data Model for L3VPN Service Delivery  February 2017</span>

    grouping customer-location-info {
     container locations {
      list location {
       key location-id;

       leaf location-id {
        type svc-id;
        description
         &quot;Identifier for a particular location.&quot;;
       }
       leaf address {
        type string;
        description
         &quot;Address (number and street) of the site.&quot;;
       }
       leaf postal-code {
        type string;
        description
         &quot;Postal code of the site.&quot;;
       }
       leaf state {
        type string;
        description
         &quot;State of the site.  This leaf can also be used to describe
         a region for a country that does not have states.&quot;;
       }
       leaf city {
        type string;
        description
         &quot;City of the site.&quot;;
       }
       leaf country-code {
        type string {
         pattern &#x27;[A-Z]{2}&#x27;;
        }
        description
         &quot;Country of the site.
         Expressed as ISO ALPHA-2 code.&quot;;
       }
       description
        &quot;Location of the site.&quot;;
       }
       description
        &quot;List of locations for the site.&quot;;
     }
     description
      &quot;This grouping defines customer location parameters.&quot;;
    }
<span class="grey"><a href="/doc/html/rfc8049">RFC 8049</a>       YANG Data Model for L3VPN Service Delivery  February 2017</span>

    grouping site-group {
     container groups {
      list group {
       key group-id;

       leaf group-id {
        type string;
        description
         &quot;Group-id the site belongs to.&quot;;
       }
       description
        &quot;List of group-ids.&quot;;
      }
      description
       &quot;Groups the site or site-network-access belongs to.&quot;;
     }
     description
      &quot;Grouping definition to assign
      group-ids to site or site-network-access.&quot;;
    }
    grouping site-diversity {
     container site-diversity {
       if-feature site-diversity;

       uses site-group;

       description
        &quot;Diversity constraint type.
        All site-network-accesses will inherit the group values
        defined here.&quot;;
      }
     description
      &quot;This grouping defines site diversity parameters.&quot;;
    }
    grouping access-diversity {
     container access-diversity {
       if-feature site-diversity;

       uses site-group;

<span class="grey"><a href="/doc/html/rfc8049">RFC 8049</a>       YANG Data Model for L3VPN Service Delivery  February 2017</span>

       container constraints {
        list constraint {
         key constraint-type;

         leaf constraint-type {
          type identityref {
           base placement-diversity;
          }
          description
           &quot;Diversity constraint type.&quot;;
         }
         container target {
          choice target-flavor {
           case id {
            list group {
             key group-id;

             leaf group-id {
              type string;
              description
               &quot;The constraint will be applied against
               this particular group-id.&quot;;
             }
             description
              &quot;List of groups.&quot;;
            }
           }
           case all-accesses {
            leaf all-other-accesses {
             type empty;
             description
              &quot;The constraint will be applied against
              all other site network accesses of this site.&quot;;
            }
           }
           case all-groups {
            leaf all-other-groups {
             type empty;
             description
              &quot;The constraint will be applied against
              all other groups managed by the customer.&quot;;
            }
           }
           description
            &quot;Choice for the group definition.&quot;;
          }

<span class="grey"><a href="/doc/html/rfc8049">RFC 8049</a>       YANG Data Model for L3VPN Service Delivery  February 2017</span>

          description
           &quot;The constraint will be applied against
           this list of groups.&quot;;
         }
         description
          &quot;List of constraints.&quot;;
        }
        description
         &quot;Placement constraints for this site network access.&quot;;
       }

       description
        &quot;Diversity parameters.&quot;;
      }
     description
      &quot;This grouping defines access diversity parameters.&quot;;
    }

    grouping operational-requirements {
       leaf requested-site-start {
         type yang:date-and-time;
         description
          &quot;Optional leaf indicating requested date and time when the
          service at a particular site is expected to start.&quot;;
        }

        leaf requested-site-stop {
         type yang:date-and-time;
         description
          &quot;Optional leaf indicating requested date and time when the
          service at a particular site is expected to stop.&quot;;
        }
     description
      &quot;This grouping defines some operational parameters.&quot;;
    }

<span class="grey"><a href="/doc/html/rfc8049">RFC 8049</a>       YANG Data Model for L3VPN Service Delivery  February 2017</span>

    grouping operational-requirements-ops {
        leaf actual-site-start {
         type yang:date-and-time;
         config false;
         description
          &quot;Optional leaf indicating actual date and time when the
          service at a particular site actually started.&quot;;
        }
        leaf actual-site-stop {
         type yang:date-and-time;
         config false;
         description
          &quot;Optional leaf indicating actual date and time when the
          service at a particular site actually stopped.&quot;;
        }
     description
      &quot;This grouping defines some operational parameters.&quot;;
    }

    grouping flow-definition {
     container match-flow {
      leaf dscp {
       type inet:dscp;
       description
        &quot;DSCP value.&quot;;
      }
      leaf dot1p {
       type uint8 {
        range &quot;0..7&quot;;
       }
       description
        &quot;802.1p matching.&quot;;
      }
      leaf ipv4-src-prefix {
       type inet:ipv4-prefix;
       description
        &quot;Match on IPv4 src address.&quot;;
      }
      leaf ipv6-src-prefix {
       type inet:ipv6-prefix;
       description
        &quot;Match on IPv6 src address.&quot;;
      }
      leaf ipv4-dst-prefix {
       type inet:ipv4-prefix;
       description
        &quot;Match on IPv4 dst address.&quot;;
      }
<span class="grey"><a href="/doc/html/rfc8049">RFC 8049</a>       YANG Data Model for L3VPN Service Delivery  February 2017</span>

      leaf ipv6-dst-prefix {
       type inet:ipv6-prefix;
       description
        &quot;Match on IPv6 dst address.&quot;;
      }
      leaf l4-src-port {
       type inet:port-number;
       description
        &quot;Match on Layer 4 src port.&quot;;
      }
      leaf-list target-sites {
       type svc-id;
       description
        &quot;Identify a site as traffic destination.&quot;;
      }
      container l4-src-port-range {
       leaf lower-port {
        type inet:port-number;
        description
         &quot;Lower boundary for port.&quot;;
       }
       leaf upper-port {
        type inet:port-number;
        must &quot;. &gt;= ../lower-port&quot; {
         description
          &quot;Upper boundary must be higher than lower boundary.&quot;;
        }
        description
         &quot;Upper boundary for port.&quot;;
       }
       description
        &quot;Match on Layer 4 src port range.&quot;;
      }
      leaf l4-dst-port {
       type inet:port-number;
       description
        &quot;Match on Layer 4 dst port.&quot;;
      }
      container l4-dst-port-range {
       leaf lower-port {
        type inet:port-number;
        description
         &quot;Lower boundary for port.&quot;;
       }

<span class="grey"><a href="/doc/html/rfc8049">RFC 8049</a>       YANG Data Model for L3VPN Service Delivery  February 2017</span>

       leaf upper-port {
        type inet:port-number;
        must &quot;. &gt;= ../lower-port&quot; {
         description
          &quot;Upper boundary must be higher than lower boundary.&quot;;
        }
        description
         &quot;Upper boundary for port.&quot;;
       }
       description
        &quot;Match on Layer 4 dst port range.&quot;;
      }
      leaf protocol-field {
       type union {
        type uint8;
        type identityref {
         base protocol-type;
        }
       }
       description
        &quot;Match on IPv4 protocol or IPv6 Next Header field.&quot;;
      }

      description
       &quot;Describes flow-matching criteria.&quot;;
     }
     description
      &quot;Flow definition based on criteria.&quot;;
    }
    grouping site-service-basic {
     leaf svc-input-bandwidth {
         type uint32;
         units bps;
         description
          &quot;From the PE&#x27;s perspective, the service input
          bandwidth of the connection.&quot;;
     }
     leaf svc-output-bandwidth {
        type uint32;
        units bps;
        description
         &quot;From the PE&#x27;s perspective, the service output
         bandwidth of the connection.&quot;;
     }

<span class="grey"><a href="/doc/html/rfc8049">RFC 8049</a>       YANG Data Model for L3VPN Service Delivery  February 2017</span>

     leaf svc-mtu {
      type uint16;
      units bytes;
      description
       &quot;MTU at service level.  If the service is IP,
       it refers to the IP MTU.&quot;;
     }
     description
      &quot;Defines basic service parameters for a site.&quot;;
    }
    grouping site-protection {
     container traffic-protection {
      if-feature fast-reroute;
      leaf enabled {
       type boolean;
       default false;
       description
        &quot;Enables traffic protection of access link.&quot;;
      }
      description
       &quot;Fast Reroute service parameters for the site.&quot;;
     }
     description
      &quot;Defines protection service parameters for a site.&quot;;
    }
    grouping site-service-mpls {
     container carrierscarrier {
      if-feature carrierscarrier;
      leaf signalling-type {
       type enumeration {
        enum &quot;ldp&quot; {
         description
          &quot;Use LDP as the signalling protocol
          between the PE and the CE.&quot;;
        }
        enum &quot;bgp&quot; {
         description
          &quot;Use BGP (as per <a href="/doc/html/rfc3107">RFC 3107</a>) as the signalling protocol
          between the PE and the CE.
          In this case, BGP must also be configured as
          the routing protocol.&quot;;
        }
       }
       description
        &quot;MPLS signalling type.&quot;;
      }

<span class="grey"><a href="/doc/html/rfc8049">RFC 8049</a>       YANG Data Model for L3VPN Service Delivery  February 2017</span>

      description
       &quot;This container is used when the customer provides
       MPLS-based services.  This is used in the case of CsC.&quot;;
     }
     description
      &quot;Defines MPLS service parameters for a site.&quot;;
    }
    grouping site-service-qos-profile {
     container qos {
      if-feature qos;
      container qos-classification-policy {
       list rule {
        key id;
        ordered-by user;

        leaf id {
         type uint16;
         description
          &quot;ID of the rule.&quot;;
        }

        choice match-type {
         case match-flow {
          uses flow-definition;
         }
         case match-application {
          leaf match-application {
           type identityref {
            base customer-application;
           }
           description
            &quot;Defines the application to match.&quot;;
          }
         }
         description
          &quot;Choice for classification.&quot;;
        }

        leaf target-class-id {
         type string;
         description
          &quot;Identification of the class of service.
          This identifier is internal to the administration.&quot;;
        }

        description
         &quot;List of marking rules.&quot;;
       }
<span class="grey"><a href="/doc/html/rfc8049">RFC 8049</a>       YANG Data Model for L3VPN Service Delivery  February 2017</span>

       description
        &quot;Configuration of the traffic classification policy.&quot;;
      }
      container qos-profile {

       choice qos-profile {
        description
         &quot;Choice for QoS profile.
         Can be standard profile or custom.&quot;;
        case standard {
         leaf profile {
          type string;
          description
           &quot;QoS profile to be used.&quot;;
         }
        }
        case custom {
         container classes {
          if-feature qos-custom;
          list class {
           key class-id;

           leaf class-id {
            type string;
            description
             &quot;Identification of the class of service.
             This identifier is internal to the administration.&quot;;
           }
           leaf rate-limit {
            type uint8;
            units percent;
            description
             &quot;To be used if the class must be rate-limited.
             Expressed as percentage of the service bandwidth.&quot;;
           }
           container latency {
            choice flavor {
             case lowest {
              leaf use-lowest-latency {
               type empty;
               description
                &quot;The traffic class should use the path with the
                lowest latency.&quot;;
              }
             }

<span class="grey"><a href="/doc/html/rfc8049">RFC 8049</a>       YANG Data Model for L3VPN Service Delivery  February 2017</span>

             case boundary {
              leaf latency-boundary {
               type uint16;
               units msec;
               description
                &quot;The traffic class should use a path with a
                defined maximum latency.&quot;;
              }
             }
             description
              &quot;Latency constraint on the traffic class.&quot;;
            }
            description
             &quot;Latency constraint on the traffic class.&quot;;
           }
           container jitter {
            choice flavor {
             case lowest {
              leaf use-lowest-jitter {
               type empty;
               description
                &quot;The traffic class should use the path with the
                lowest jitter.&quot;;
              }
             }
             case boundary {
              leaf latency-boundary {
               type uint32;
               units usec;
               description
                &quot;The traffic class should use a path with a
                defined maximum jitter.&quot;;
              }
             }
             description
              &quot;Jitter constraint on the traffic class.&quot;;
            }
            description
             &quot;Jitter constraint on the traffic class.&quot;;
           }
           container bandwidth {
            leaf guaranteed-bw-percent {
             type uint8;
             units percent;
             description
              &quot;To be used to define the guaranteed bandwidth
              as a percentage of the available service bandwidth.&quot;;
            }
<span class="grey"><a href="/doc/html/rfc8049">RFC 8049</a>       YANG Data Model for L3VPN Service Delivery  February 2017</span>

            leaf end-to-end {
             type empty;
             description
              &quot;Used if the bandwidth reservation
              must be done on the MPLS network too.&quot;;
            }
            description
             &quot;Bandwidth constraint on the traffic class.&quot;;
           }
           description
            &quot;List of classes of services.&quot;;
          }
          description
           &quot;Container for list of classes of services.&quot;;
         }

        }

       }
       description
        &quot;QoS profile configuration.&quot;;
      }
      description
       &quot;QoS configuration.&quot;;
     }
     description
      &quot;This grouping defines QoS parameters for a site.&quot;;
    }

    grouping site-security-authentication {
     container authentication {
      description
       &quot;Authentication parameters.&quot;;
     }
     description
      &quot;This grouping defines authentication parameters for a site.&quot;;

    }
    grouping site-security-encryption {
     container encryption {
      if-feature encryption;
      leaf enabled {
       type boolean;
       default false;
       description
        &quot;If true, access encryption is required.&quot;;
      }

<span class="grey"><a href="/doc/html/rfc8049">RFC 8049</a>       YANG Data Model for L3VPN Service Delivery  February 2017</span>

      leaf layer {
       type enumeration {
        enum layer2 {
         description
          &quot;Encryption will occur at Layer 2.&quot;;
        }
        enum layer3 {
         description
          &quot;Encryption will occur at Layer 3.
          For example, IPsec may be used.&quot;;
        }
       }
       mandatory true;
       description
        &quot;Layer on which encryption is applied.&quot;;
      }
      container encryption-profile {
       choice profile {
        case provider-profile {
         leaf profile-name {
          type string;
          description
           &quot;Name of the SP profile to be applied.&quot;;
         }
        }
        case customer-profile {
         leaf algorithm {
          type string;
          description
           &quot;Encryption algorithm to be used.&quot;;
         }
         choice key-type {
          case psk {
           leaf preshared-key {
            type string;
            description
             &quot;Key coming from customer.&quot;;
           }
          }
          case pki {

          }
          description
           &quot;Type of keys to be used.&quot;;
         }
        }

<span class="grey"><a href="/doc/html/rfc8049">RFC 8049</a>       YANG Data Model for L3VPN Service Delivery  February 2017</span>

        description
         &quot;Choice of profile.&quot;;
       }
       description
        &quot;Profile of encryption to be applied.&quot;;
      }
      description
       &quot;Encryption parameters.&quot;;
     }
     description
      &quot;This grouping defines encryption parameters for a site.&quot;;
    }

    grouping site-attachment-bearer {
     container bearer {
      container requested-type {
       if-feature requested-type;
       leaf requested-type {
        type string;
        description
         &quot;Type of requested bearer: Ethernet, DSL,
         Wireless, etc.  Operator specific.&quot;;
       }
       leaf strict {
        type boolean;
        default false;
        description
         &quot;Defines whether requested-type is a preference
         or a strict requirement.&quot;;
       }
       description
        &quot;Container for requested-type.&quot;;
      }
      leaf always-on {
       if-feature always-on;
       type boolean;
       default true;
       description
        &quot;Request for an always-on access type.
        For example, this could mean no dial access type.&quot;;
      }
      leaf bearer-reference {
       if-feature bearer-reference;
       type string;
       description
        &quot;This is an internal reference for the SP.&quot;;
      }

<span class="grey"><a href="/doc/html/rfc8049">RFC 8049</a>       YANG Data Model for L3VPN Service Delivery  February 2017</span>

      description
       &quot;Bearer-specific parameters.
       To be augmented.&quot;;
     }
     description
      &quot;Defines physical properties of a site attachment.&quot;;
    }

    grouping site-routing {
     container routing-protocols {
      list routing-protocol {
       key type;

       leaf type {
        type identityref {
         base routing-protocol-type;
        }
        description
         &quot;Type of routing protocol.&quot;;
       }

       container ospf {
        when &quot;../type = &#x27;ospf&#x27;&quot; {
         description
          &quot;Only applies when protocol is OSPF.&quot;;
        }
        if-feature rtg-ospf;
        leaf-list address-family {
         type address-family;

         description
          &quot;Address family to be activated.&quot;;
        }
        leaf area-address {
         type yang:dotted-quad;
         description
          &quot;Area address.&quot;;
        }
        leaf metric {
         type uint16;
         description
          &quot;Metric of the PE-CE link.&quot;;
        }

<span class="grey"><a href="/doc/html/rfc8049">RFC 8049</a>       YANG Data Model for L3VPN Service Delivery  February 2017</span>

        container sham-links {
         if-feature rtg-ospf-sham-link;
         list sham-link {
          key target-site;

          leaf target-site {
           type svc-id;
           description
            &quot;Target site for the sham link connection.
            The site is referred to by its ID.&quot;;
          }
          leaf metric {
           type uint16;
           description
            &quot;Metric of the sham link.&quot;;
          }
          description
           &quot;Creates a sham link with another site.&quot;;
         }
         description
          &quot;List of sham links.&quot;;
        }
        description
         &quot;OSPF-specific configuration.&quot;;
       }

       container bgp {

        when &quot;../type = &#x27;bgp&#x27;&quot; {
         description
          &quot;Only applies when protocol is BGP.&quot;;
        }
        if-feature rtg-bgp;
        leaf autonomous-system {
         type uint32;
         description
          &quot;AS number.&quot;;
        }
        leaf-list address-family {
         type address-family;

         description
          &quot;Address family to be activated.&quot;;
        }
        description
         &quot;BGP-specific configuration.&quot;;
       }

<span class="grey"><a href="/doc/html/rfc8049">RFC 8049</a>       YANG Data Model for L3VPN Service Delivery  February 2017</span>

       container static {
        when &quot;../type = &#x27;static&#x27;&quot; {
         description
          &quot;Only applies when protocol is static.&quot;;
        }

        container cascaded-lan-prefixes {
         list ipv4-lan-prefixes {
          if-feature ipv4;
          key &quot;lan next-hop&quot;;

          leaf lan {
           type inet:ipv4-prefix;
           description
            &quot;LAN prefixes.&quot;;
          }
          leaf lan-tag {
           type string;
           description
            &quot;Internal tag to be used in VPN policies.&quot;;
          }
          leaf next-hop {
           type inet:ipv4-address;
           description
            &quot;Next-hop address to use on the customer side.&quot;;
          }
          description
           &quot;List of LAN prefixes for the site.&quot;;
         }
         list ipv6-lan-prefixes {
          if-feature ipv6;
          key &quot;lan next-hop&quot;;

          leaf lan {
           type inet:ipv6-prefix;
           description
            &quot;LAN prefixes.&quot;;
          }
          leaf lan-tag {
           type string;
           description
            &quot;Internal tag to be used in VPN policies.&quot;;
          }
          leaf next-hop {
           type inet:ipv6-address;
           description
            &quot;Next-hop address to use on the customer side.&quot;;
          }
<span class="grey"><a href="/doc/html/rfc8049">RFC 8049</a>       YANG Data Model for L3VPN Service Delivery  February 2017</span>

          description
           &quot;List of LAN prefixes for the site.&quot;;
         }
         description
          &quot;LAN prefixes from the customer.&quot;;
        }
        description
         &quot;Configuration specific to static routing.&quot;;
       }
       container rip {

        when &quot;../type = &#x27;rip&#x27;&quot; {
         description
          &quot;Only applies when protocol is RIP.&quot;;
        }
        if-feature rtg-rip;
        leaf-list address-family {
         type address-family;

         description
          &quot;Address family to be activated.&quot;;
        }

        description
         &quot;Configuration specific to RIP routing.&quot;;
       }

       container vrrp {

        when &quot;../type = &#x27;vrrp&#x27;&quot; {
         description
          &quot;Only applies when protocol is VRRP.&quot;;
        }
        if-feature rtg-vrrp;
        leaf-list address-family {
         type address-family;

         description
          &quot;Address family to be activated.&quot;;
        }
        description
         &quot;Configuration specific to VRRP routing.&quot;;
       }

       description
        &quot;List of routing protocols used on
        the site.  This list can be augmented.&quot;;
      }
<span class="grey"><a href="/doc/html/rfc8049">RFC 8049</a>       YANG Data Model for L3VPN Service Delivery  February 2017</span>

      description
       &quot;Defines routing protocols.&quot;;
     }
     description
      &quot;Grouping for routing protocols.&quot;;
    }

    grouping site-attachment-ip-connection {
     container ip-connection {
      container ipv4 {
       if-feature ipv4;
       leaf address-allocation-type {
        type identityref {
         base address-allocation-type;
        }
        default &quot;static-address&quot;;
        description
         &quot;Defines how addresses are allocated.&quot;;
       }

       leaf number-of-dynamic-address {
        when &quot;../address-allocation-type = &#x27;provider-dhcp&#x27;&quot; {
         description
          &quot;Only applies when addresses are allocated by DHCP.&quot;;
        }
        type uint8;
        default 1;
        description
         &quot;Describes the number of IP addresses the customer requires.&quot;;
       }
       container dhcp-relay {
        when &quot;../address-allocation-type = &#x27;provider-dhcp-relay&#x27;&quot; {
         description
          &quot;Only applies when provider is required to implement
          DHCP relay function.&quot;;
        }
        container customer-dhcp-servers {
         leaf-list server-ip-address {
          type inet:ipv4-address;
          description
           &quot;IP address of customer DHCP server.&quot;;
         }
         description
          &quot;Container for list of customer DHCP servers.&quot;;
        }
        description
         &quot;DHCP relay provided by operator.&quot;;
       }
<span class="grey"><a href="/doc/html/rfc8049">RFC 8049</a>       YANG Data Model for L3VPN Service Delivery  February 2017</span>

       container addresses {
        when &quot;../address-allocation-type = &#x27;static-address&#x27;&quot; {
         description
          &quot;Only applies when protocol allocation type is static.&quot;;
        }
        leaf provider-address {
         type inet:ipv4-address;
         description
          &quot;Address of provider side.&quot;;
        }
        leaf customer-address {
         type inet:ipv4-address;
         description
          &quot;Address of customer side.&quot;;
        }
        leaf mask {
         type uint8 {
          range &quot;0..31&quot;;
         }
         description
          &quot;Subnet mask expressed in bits.&quot;;
        }
        description
         &quot;Describes IP addresses used.&quot;;
       }

       description
        &quot;IPv4-specific parameters.&quot;;

      }
      container ipv6 {
       if-feature ipv6;
       leaf address-allocation-type {
        type identityref {
         base address-allocation-type;
        }
        default &quot;static-address&quot;;
        description
         &quot;Defines how addresses are allocated.&quot;;
       }
       leaf number-of-dynamic-address {
        when
        &quot;../address-allocation-type = &#x27;provider-dhcp&#x27; &quot;+
        &quot;or ../address-allocation-type &quot;+
        &quot;= &#x27;provider-dhcp-slaac&#x27;&quot; {
         description
          &quot;Only applies when addresses are allocated by DHCP.&quot;;
        }
<span class="grey"><a href="/doc/html/rfc8049">RFC 8049</a>       YANG Data Model for L3VPN Service Delivery  February 2017</span>

        type uint8;
        default 1;
        description
         &quot;Describes the number of IP addresses the customer requires.&quot;;
       }
       container dhcp-relay {
        when &quot;../address-allocation-type = &#x27;provider-dhcp-relay&#x27;&quot; {
         description
          &quot;Only applies when provider is required to implement
          DHCP relay function.&quot;;
        }
        container customer-dhcp-servers {
         leaf-list server-ip-address {
          type inet:ipv6-address;
          description
           &quot;IP address of customer DHCP server.&quot;;
         }
         description
          &quot;Container for list of customer DHCP servers.&quot;;
        }
        description
         &quot;DHCP relay provided by operator.&quot;;
       }
       container addresses {
        when &quot;../address-allocation-type = &#x27;static-address&#x27;&quot; {
         description
          &quot;Only applies when protocol allocation type is static.&quot;;
        }
        leaf provider-address {
         type inet:ipv6-address;
         description
          &quot;Address of provider side.&quot;;
        }
        leaf customer-address {
         type inet:ipv6-address;
         description
          &quot;Address of customer side.&quot;;
        }
        leaf mask {
         type uint8 {
          range &quot;0..127&quot;;
         }
         description
          &quot;Subnet mask expressed in bits.&quot;;
        }
        description
         &quot;Describes IP addresses used.&quot;;
       }
<span class="grey"><a href="/doc/html/rfc8049">RFC 8049</a>       YANG Data Model for L3VPN Service Delivery  February 2017</span>

       description
        &quot;IPv6-specific parameters.&quot;;

      }
      container oam {
       container bfd {
        if-feature bfd;
        leaf enabled {
         type boolean;
         default false;
         description
          &quot;BFD activation.&quot;;
        }

        choice holdtime {
         case profile {
          leaf profile-name {
           type string;
           description
            &quot;Well-known SP profile.&quot;;
          }
          description
           &quot;Well-known SP profile.&quot;;
         }
         case fixed {
          leaf fixed-value {
           type uint32;
           units msec;
           description
            &quot;Expected holdtime expressed in msec.&quot;;
          }
         }
         description
          &quot;Choice for holdtime flavor.&quot;;
        }
        description
         &quot;Container for BFD.&quot;;
       }
       description
        &quot;Defines the OAM mechanisms used on the connection.&quot;;
      }
      description
       &quot;Defines connection parameters.&quot;;
     }
     description
      &quot;This grouping defines IP connection parameters.&quot;;
    }

<span class="grey"><a href="/doc/html/rfc8049">RFC 8049</a>       YANG Data Model for L3VPN Service Delivery  February 2017</span>

    grouping site-service-multicast {
     container multicast {
      if-feature multicast;
      leaf multicast-site-type {
       type enumeration {
        enum receiver-only {
         description
          &quot;The site only has receivers.&quot;;
        }
        enum source-only {
         description
          &quot;The site only has sources.&quot;;
        }
        enum source-receiver {
         description
          &quot;The site has both sources and receivers.&quot;;
        }
       }
       default &quot;source-receiver&quot;;
       description
        &quot;Type of multicast site.&quot;;
      }
      container multicast-address-family {
       leaf ipv4 {
        if-feature ipv4;
        type boolean;
        default true;
        description
         &quot;Enables IPv4 multicast.&quot;;
       }
       leaf ipv6 {
        if-feature ipv6;
        type boolean;
        default false;
        description
         &quot;Enables IPv6 multicast.&quot;;
       }
       description
        &quot;Defines protocol to carry multicast.&quot;;
      }
      leaf protocol-type {
       type enumeration {
        enum host {
         description
          &quot;Hosts are directly connected to the provider network.
          Host protocols such as IGMP or MLD are required.&quot;;
        }

<span class="grey"><a href="/doc/html/rfc8049">RFC 8049</a>       YANG Data Model for L3VPN Service Delivery  February 2017</span>

        enum router {
         description
          &quot;Hosts are behind a customer router.
          PIM will be implemented.&quot;;
        }
        enum both {
         description
          &quot;Some hosts are behind a customer router, and some others
          are directly connected to the provider network.
          Both host and routing protocols must be used.
          Typically, IGMP and PIM will be implemented.&quot;;
        }
       }
       default &quot;both&quot;;
       description
        &quot;Multicast protocol type to be used with the customer site.&quot;;
      }

      description
       &quot;Multicast parameters for the site.&quot;;
     }
     description
      &quot;Multicast parameters for the site.&quot;;
    }

    grouping site-management {
     container management {
      leaf type {
       type identityref {
        base management;
       }
       description
        &quot;Management type of the connection.&quot;;
      }
      description
       &quot;Management configuration.&quot;;
     }
     description
      &quot;Management parameters for the site.&quot;;
    }

<span class="grey"><a href="/doc/html/rfc8049">RFC 8049</a>       YANG Data Model for L3VPN Service Delivery  February 2017</span>

    grouping site-devices {
     container devices {
      must &quot;/l3vpn-svc/sites/site/management/type = &quot;+
       &quot;&#x27;provider-managed&#x27; or &quot;+
       &quot;/l3vpn-svc/sites/site/management/type = &quot;+
       &quot;&#x27;co-managed&#x27;&quot; {
        description
         &quot;Applicable only for provider-managed or co-managed device.&quot;;
       }
      list device {
       key device-id;

       leaf device-id {
        type svc-id;
        description
         &quot;Identifier for the device.&quot;;
       }
       leaf location {
        type leafref {
         path &quot;/l3vpn-svc/sites/site/locations/&quot;+
          &quot;location/location-id&quot;;
        }
        description
         &quot;Location of the device.&quot;;
       }
       container management {
        must &quot;/l3vpn-svc/sites/site/management/type&quot;+
         &quot;= &#x27;co-managed&#x27;&quot; {
          description
           &quot;Applicable only for co-managed device.&quot;;
         }
        leaf address-family {
         type address-family;

         description
          &quot;Address family used for management.&quot;;
        }
        leaf address {
         type inet:ip-address;
         description
          &quot;Management address.&quot;;
        }
        description
         &quot;Management configuration.  Applicable only for
         co-managed device.&quot;;
       }

<span class="grey"><a href="/doc/html/rfc8049">RFC 8049</a>       YANG Data Model for L3VPN Service Delivery  February 2017</span>

       description
        &quot;Device configuration.&quot;;
      }
      description
       &quot;List of devices requested by customer.&quot;;
     }
     description
      &quot;Grouping for device allocation.&quot;;
    }
    grouping site-vpn-flavor {
     leaf site-vpn-flavor {
      type identityref {
       base site-vpn-flavor;
      }
      default site-vpn-flavor-single;
      description
       &quot;Defines whether the site is, for example,
       a single VPN site or a multiVPN.&quot;;
     }
     description
      &quot;Grouping for site VPN flavor.&quot;;
    }

    grouping site-vpn-policy {
     container vpn-policies {
      list vpn-policy {
       key vpn-policy-id;

       leaf vpn-policy-id {
        type svc-id;
        description
         &quot;Unique identifier for the VPN policy.&quot;;
       }

       list entries {
        key id;

        leaf id {
          type svc-id;
          description
           &quot;Unique identifier for the policy entry.&quot;;
        }

<span class="grey"><a href="/doc/html/rfc8049">RFC 8049</a>       YANG Data Model for L3VPN Service Delivery  February 2017</span>

        container filter {
         choice lan {
          case prefixes {
           leaf-list ipv4-lan-prefix {
            if-feature ipv4;
            type inet:ipv4-prefix;
            description
             &quot;List of IPv4 prefixes to be matched.&quot;;
           }
           leaf-list ipv6-lan-prefix {
            if-feature ipv6;
            type inet:ipv6-prefix;
            description
             &quot;List of IPv6 prefixes to be matched.&quot;;
           }
          }
          case lan-tag {
           leaf-list lan-tag {
            type string;
            description
             &quot;List of &#x27;lan-tag&#x27; items to be matched.&quot;;
           }
          }
          description
           &quot;Choice of ways to do LAN matching.&quot;;
         }
         description
          &quot;If used, it permits the splitting of
          site LANs among multiple VPNs.
          If no filter is used, all the LANs will be
          part of the same VPNs with the same role.&quot;;
        }
        container vpn {
         leaf vpn-id {
          type leafref {
           path &quot;/l3vpn-svc/vpn-services/&quot;+
           &quot;vpn-service/vpn-id&quot;;
          }
          mandatory true;
          description
           &quot;Reference to an IP VPN.&quot;;
         }

<span class="grey"><a href="/doc/html/rfc8049">RFC 8049</a>       YANG Data Model for L3VPN Service Delivery  February 2017</span>

         leaf site-role {
          type identityref {
           base site-role;
          }
          default any-to-any-role;
          description
           &quot;Role of the site in the IP VPN.&quot;;
         }
         description
          &quot;List of VPNs the LAN is associated with.&quot;;
        }
        description
         &quot;List of entries for export policy.&quot;;
       }
       description
        &quot;List of VPN policies.&quot;;
      }
      description
       &quot;VPN policy.&quot;;
     }
     description
      &quot;VPN policy parameters for the site.&quot;;
    }

    grouping site-maximum-routes {
     container maximum-routes {
      list address-family {
       key af;

       leaf af {
        type address-family;

        description
         &quot;Address family.&quot;;
       }
       leaf maximum-routes {
        type uint32;
        description
         &quot;Maximum prefixes the VRF can accept for this address family.&quot;;
       }
       description
        &quot;List of address families.&quot;;
      }

      description
       &quot;Defines &#x27;maximum-routes&#x27; for the VRF.&quot;;
     }

<span class="grey"><a href="/doc/html/rfc8049">RFC 8049</a>       YANG Data Model for L3VPN Service Delivery  February 2017</span>

     description
      &quot;Defines &#x27;maximum-routes&#x27; for the site.&quot;;
    }

    grouping site-security {
     container security {
      uses site-security-authentication;
      uses site-security-encryption;

      description
       &quot;Site-specific security parameters.&quot;;
     }
     description
      &quot;Grouping for security parameters.&quot;;
    }

    grouping site-service {
     container service {
      uses site-service-qos-profile;
      uses site-service-mpls;
      uses site-service-multicast;

      description
       &quot;Service parameters on the attachment.&quot;;
     }
     description
      &quot;Grouping for service parameters.&quot;;
    }

    grouping site-network-access-service {
     container service {
      uses site-service-basic;
      uses site-service-qos-profile;
      uses site-service-mpls;
      uses site-service-multicast;

      description
       &quot;Service parameters on the attachment.&quot;;
     }
     description
      &quot;Grouping for service parameters.&quot;;
    }

<span class="grey"><a href="/doc/html/rfc8049">RFC 8049</a>       YANG Data Model for L3VPN Service Delivery  February 2017</span>

    grouping vpn-extranet {
     container extranet-vpns {
      if-feature extranet-vpn;
      list extranet-vpn {
       key vpn-id;

       leaf vpn-id {
        type svc-id;
        description
         &quot;Identifies the target VPN.&quot;;
       }
       leaf local-sites-role {
        type identityref {
         base site-role;

        }
        default any-to-any-role;
        description
         &quot;This describes the role of the
         local sites in the target VPN topology.&quot;;
       }
       description
        &quot;List of extranet VPNs the local VPN is attached to.&quot;;
      }
      description
       &quot;Container for extranet VPN configuration.&quot;;
     }
     description
      &quot;Grouping for extranet VPN configuration.
      This provides an easy way to interconnect
      all sites from two VPNs.&quot;;
    }

    grouping site-attachment-availability {
     container availability {
      leaf access-priority {
       type uint32;
       default 1;
       description
        &quot;Defines the priority for the access.
        The higher the access-priority value,
        the higher the preference of the access will be.&quot;;
      }
      description
       &quot;Availability parameters (used for multihoming).&quot;;
     }

<span class="grey"><a href="/doc/html/rfc8049">RFC 8049</a>       YANG Data Model for L3VPN Service Delivery  February 2017</span>

     description
      &quot;Defines availability parameters for a site.&quot;;
    }

    grouping access-vpn-policy {
     container vpn-attachment {

      choice attachment-flavor {
       case vpn-policy-id {
        leaf vpn-policy-id {
         type leafref {
          path &quot;/l3vpn-svc/sites/site/&quot;+
          &quot;vpn-policies/vpn-policy/&quot;+
          &quot;vpn-policy-id&quot;;
         }
         description
          &quot;Reference to a VPN policy.&quot;;
        }
       }
       case vpn-id {
        leaf vpn-id {
         type leafref {
          path &quot;/l3vpn-svc/vpn-services&quot;+
          &quot;/vpn-service/vpn-id&quot;;
         }
         description
          &quot;Reference to a VPN.&quot;;
        }
        leaf site-role {
         type identityref {
           base site-role;
          }
         default any-to-any-role;
         description
          &quot;Role of the site in the IP VPN.&quot;;
        }
       }
       mandatory true;
       description
        &quot;Choice for VPN attachment flavor.&quot;;
      }
      description
       &quot;Defines VPN attachment of a site.&quot;;
     }
     description
      &quot;Defines the VPN attachment rules for a site&#x27;s logical access.&quot;;
    }

<span class="grey"><a href="/doc/html/rfc8049">RFC 8049</a>       YANG Data Model for L3VPN Service Delivery  February 2017</span>

    grouping vpn-svc-cfg {
     leaf vpn-id {
       type svc-id;
       description
        &quot;VPN identifier.  Local administration meaning.&quot;;
      }
      leaf customer-name {
       type string;
       description
        &quot;Name of the customer.&quot;;
      }
     leaf vpn-service-topology {
      type identityref {
       base vpn-topology;
      }
      default &quot;any-to-any&quot;;
      description
       &quot;VPN service topology.&quot;;
     }

     uses vpn-service-cloud-access;
     uses vpn-service-multicast;
     uses vpn-service-mpls;
     uses vpn-extranet;

     description
      &quot;Grouping for VPN service configuration.&quot;;
    }

    grouping site-top-level-cfg {
     uses operational-requirements;
     uses customer-location-info;
     uses site-devices;
     uses site-diversity;
     uses site-management;
     uses site-vpn-policy;
     uses site-vpn-flavor;
     uses site-maximum-routes;
     uses site-security;
     uses site-service;
     uses site-protection;
     uses site-routing;

     description
      &quot;Grouping for site top-level configuration.&quot;;
    }

<span class="grey"><a href="/doc/html/rfc8049">RFC 8049</a>       YANG Data Model for L3VPN Service Delivery  February 2017</span>

    grouping site-network-access-top-level-cfg {
     leaf site-network-access-type {
      type identityref {
       base site-network-access-type;
      }
      default &quot;point-to-point&quot;;
      description
       &quot;Describes the type of connection, e.g.,
       point-to-point or multipoint.&quot;;
     }

     choice location-flavor {
      case location {
       when &quot;/l3vpn-svc/sites/site/management/type = &quot;+
         &quot;&#x27;customer-managed&#x27;&quot; {
          description
           &quot;Applicable only for customer-managed device.&quot;;
        }
       leaf location-reference {
        type leafref {
         path &quot;/l3vpn-svc/sites/site/locations/&quot;+
            &quot;location/location-id&quot;;
        }
        description
         &quot;Location of the site-network-access.&quot;;
       }
      }
      case device {
       when &quot;/l3vpn-svc/sites/site/management/type = &quot;+
         &quot;&#x27;provider-managed&#x27; or &quot;+
         &quot;/l3vpn-svc/sites/site/management/type = &quot;+
         &quot;&#x27;co-managed&#x27;&quot; {
          description
           &quot;Applicable only for provider-managed or co-managed device.&quot;;
        }
       leaf device-reference {
        type leafref {
         path &quot;/l3vpn-svc/sites/site/devices/&quot;+
            &quot;device/device-id&quot;;
        }
        description
         &quot;Identifier of CE to use.&quot;;
       }
      }
      mandatory true;
      description
       &quot;Choice of how to describe the site&#x27;s location.&quot;;
     }
<span class="grey"><a href="/doc/html/rfc8049">RFC 8049</a>       YANG Data Model for L3VPN Service Delivery  February 2017</span>

     uses access-diversity;
     uses site-attachment-bearer;
     uses site-attachment-ip-connection;
     uses site-security;
     uses site-network-access-service;
     uses site-routing;
     uses site-attachment-availability;
     uses access-vpn-policy;

     description
      &quot;Grouping for site network access top-level configuration.&quot;;
    }

    /* Main blocks */

    container l3vpn-svc {
     container vpn-services {
      list vpn-service {
       key vpn-id;

       uses vpn-svc-cfg;

       description
        &quot;List of VPN services.&quot;;
      }
      description
       &quot;Top-level container for the VPN services.&quot;;
     }

     container sites {
      list site {
       key site-id;

       leaf site-id {
        type svc-id;
        description
         &quot;Identifier of the site.&quot;;
       }

       uses site-top-level-cfg;
       uses operational-requirements-ops;

<span class="grey"><a href="/doc/html/rfc8049">RFC 8049</a>       YANG Data Model for L3VPN Service Delivery  February 2017</span>

       container site-network-accesses {
        list site-network-access {
         key site-network-access-id;

         leaf site-network-access-id {
          type svc-id;
          description
           &quot;Identifier for the access.&quot;;
         }
         uses site-network-access-top-level-cfg;

         description
          &quot;List of accesses for a site.&quot;;
        }
        description
         &quot;List of accesses for a site.&quot;;
       }

       description
        &quot;List of sites.&quot;;
      }
      description
       &quot;Container for sites.&quot;;
     }

     description
      &quot;Main container for L3VPN service configuration.&quot;;
    }

   }
