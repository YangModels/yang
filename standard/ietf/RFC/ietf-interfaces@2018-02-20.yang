module ietf-interfaces {

  namespace &quot;urn:ietf:params:xml:ns:yang:ietf-interfaces&quot;;
  prefix if;

  import ietf-yang-types {
    prefix yang;
  }

  organization
    &quot;IETF NETMOD (NETCONF Data Modeling Language) Working Group&quot;;

  contact
    &quot;WG Web:   &lt;<a href="https://tools.ietf.org/wg/netmod/">http://tools.ietf.org/wg/netmod/</a>&gt;
     WG List:  &lt;mailto:<a href="mailto:netmod@ietf.org">netmod@ietf.org</a>&gt;

     WG Chair: Thomas Nadeau
               &lt;mailto:<a href="mailto:tnadeau@lucidvision.com">tnadeau@lucidvision.com</a>&gt;

     WG Chair: Juergen Schoenwaelder
               &lt;mailto:<a href="mailto:j.schoenwaelder@jacobs-university.de">j.schoenwaelder@jacobs-university.de</a>&gt;

     Editor:   Martin Bjorklund
               &lt;mailto:<a href="mailto:mbj@tail-f.com">mbj@tail-f.com</a>&gt;&quot;;

  description
    &quot;This module contains a collection of YANG definitions for
     managing network interfaces.

     Copyright (c) 2014 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).

     This version of this YANG module is part of <a href="/doc/html/rfc7223">RFC 7223</a>; see
     the RFC itself for full legal notices.&quot;;

<span class="grey"><a href="/doc/html/rfc7223">RFC 7223</a>                YANG Interface Management               May 2014</span>

     revision 2014-05-08 {
       description
         &quot;Initial revision.&quot;;
       reference
         &quot;<a href="/doc/html/rfc7223">RFC 7223</a>: A YANG Data Model for Interface Management&quot;;
     }

     /*
      * Typedefs
      */

     typedef interface-ref {
       type leafref {
         path &quot;/if:interfaces/if:interface/if:name&quot;;
       }
       description
         &quot;This type is used by data models that need to reference
          configured interfaces.&quot;;
     }

     typedef interface-state-ref {
       type leafref {
         path &quot;/if:interfaces-state/if:interface/if:name&quot;;
       }
       description
         &quot;This type is used by data models that need to reference
          the operationally present interfaces.&quot;;
     }

     /*
      * Identities
      */

     identity interface-type {
       description
         &quot;Base identity from which specific interface types are
          derived.&quot;;
     }

     /*
      * Features
      */

     feature arbitrary-names {
       description
         &quot;This feature indicates that the device allows user-controlled
          interfaces to be named arbitrarily.&quot;;
     }
<span class="grey"><a href="/doc/html/rfc7223">RFC 7223</a>                YANG Interface Management               May 2014</span>

     feature pre-provisioning {
       description
         &quot;This feature indicates that the device supports
          pre-provisioning of interface configuration, i.e., it is
          possible to configure an interface whose physical interface
          hardware is not present on the device.&quot;;
     }

     feature if-mib {
       description
         &quot;This feature indicates that the device implements
          the IF-MIB.&quot;;
       reference
         &quot;<a href="/doc/html/rfc2863">RFC 2863</a>: The Interfaces Group MIB&quot;;
     }

     /*
      * Configuration data nodes
      */

     container interfaces {
       description
         &quot;Interface configuration parameters.&quot;;

       list interface {
         key &quot;name&quot;;

         description
           &quot;The list of configured interfaces on the device.

            The operational state of an interface is available in the
            /interfaces-state/interface list.  If the configuration of a
            system-controlled interface cannot be used by the system
            (e.g., the interface hardware present does not match the
            interface type), then the configuration is not applied to
            the system-controlled interface shown in the
            /interfaces-state/interface list.  If the configuration
            of a user-controlled interface cannot be used by the system,
            the configured interface is not instantiated in the
            /interfaces-state/interface list.&quot;;

        leaf name {
           type string;
           description
             &quot;The name of the interface.

              A device MAY restrict the allowed values for this leaf,
              possibly depending on the type of the interface.
<span class="grey"><a href="/doc/html/rfc7223">RFC 7223</a>                YANG Interface Management               May 2014</span>

              For system-controlled interfaces, this leaf is the
              device-specific name of the interface.  The &#x27;config false&#x27;
              list /interfaces-state/interface contains the currently
              existing interfaces on the device.

              If a client tries to create configuration for a
              system-controlled interface that is not present in the
              /interfaces-state/interface list, the server MAY reject
              the request if the implementation does not support
              pre-provisioning of interfaces or if the name refers to
              an interface that can never exist in the system.  A
              NETCONF server MUST reply with an rpc-error with the
              error-tag &#x27;invalid-value&#x27; in this case.

              If the device supports pre-provisioning of interface
              configuration, the &#x27;pre-provisioning&#x27; feature is
              advertised.

              If the device allows arbitrarily named user-controlled
              interfaces, the &#x27;arbitrary-names&#x27; feature is advertised.

              When a configured user-controlled interface is created by
              the system, it is instantiated with the same name in the
              /interface-state/interface list.&quot;;
         }

         leaf description {
           type string;
           description
             &quot;A textual description of the interface.

              A server implementation MAY map this leaf to the ifAlias
              MIB object.  Such an implementation needs to use some
              mechanism to handle the differences in size and characters
              allowed between this leaf and ifAlias.  The definition of
              such a mechanism is outside the scope of this document.

              Since ifAlias is defined to be stored in non-volatile
              storage, the MIB implementation MUST map ifAlias to the
              value of &#x27;description&#x27; in the persistently stored
              datastore.

              Specifically, if the device supports &#x27;:startup&#x27;, when
              ifAlias is read the device MUST return the value of
              &#x27;description&#x27; in the &#x27;startup&#x27; datastore, and when it is
              written, it MUST be written to the &#x27;running&#x27; and &#x27;startup&#x27;
              datastores.  Note that it is up to the implementation to

<span class="grey"><a href="/doc/html/rfc7223">RFC 7223</a>                YANG Interface Management               May 2014</span>

              decide whether to modify this single leaf in &#x27;startup&#x27; or
              perform an implicit copy-config from &#x27;running&#x27; to
              &#x27;startup&#x27;.

              If the device does not support &#x27;:startup&#x27;, ifAlias MUST
              be mapped to the &#x27;description&#x27; leaf in the &#x27;running&#x27;
              datastore.&quot;;
           reference
             &quot;<a href="/doc/html/rfc2863">RFC 2863</a>: The Interfaces Group MIB - ifAlias&quot;;
         }

         leaf type {
           type identityref {
             base interface-type;
           }
           mandatory true;
           description
             &quot;The type of the interface.

              When an interface entry is created, a server MAY
              initialize the type leaf with a valid value, e.g., if it
              is possible to derive the type from the name of the
              interface.

              If a client tries to set the type of an interface to a
              value that can never be used by the system, e.g., if the
              type is not supported or if the type does not match the
              name of the interface, the server MUST reject the request.
              A NETCONF server MUST reply with an rpc-error with the
              error-tag &#x27;invalid-value&#x27; in this case.&quot;;
           reference
             &quot;<a href="/doc/html/rfc2863">RFC 2863</a>: The Interfaces Group MIB - ifType&quot;;
         }

         leaf enabled {
           type boolean;
           default &quot;true&quot;;
           description
             &quot;This leaf contains the configured, desired state of the
              interface.

              Systems that implement the IF-MIB use the value of this
              leaf in the &#x27;running&#x27; datastore to set
              IF-MIB.ifAdminStatus to &#x27;up&#x27; or &#x27;down&#x27; after an ifEntry
              has been initialized, as described in <a href="/doc/html/rfc2863">RFC 2863</a>.

<span class="grey"><a href="/doc/html/rfc7223">RFC 7223</a>                YANG Interface Management               May 2014</span>

              Changes in this leaf in the &#x27;running&#x27; datastore are
              reflected in ifAdminStatus, but if ifAdminStatus is
              changed over SNMP, this leaf is not affected.&quot;;
           reference
             &quot;<a href="/doc/html/rfc2863">RFC 2863</a>: The Interfaces Group MIB - ifAdminStatus&quot;;
         }

         leaf link-up-down-trap-enable {
           if-feature if-mib;
           type enumeration {
             enum enabled {
               value 1;
             }
             enum disabled {
               value 2;
             }
           }
           description
             &quot;Controls whether linkUp/linkDown SNMP notifications
              should be generated for this interface.

              If this node is not configured, the value &#x27;enabled&#x27; is
              operationally used by the server for interfaces that do
              not operate on top of any other interface (i.e., there are
              no &#x27;lower-layer-if&#x27; entries), and &#x27;disabled&#x27; otherwise.&quot;;
           reference
             &quot;<a href="/doc/html/rfc2863">RFC 2863</a>: The Interfaces Group MIB -
                        ifLinkUpDownTrapEnable&quot;;
         }
       }
     }

     /*
      * Operational state data nodes
      */

     container interfaces-state {
       config false;
       description
         &quot;Data nodes for the operational state of interfaces.&quot;;

       list interface {
         key &quot;name&quot;;

<span class="grey"><a href="/doc/html/rfc7223">RFC 7223</a>                YANG Interface Management               May 2014</span>

         description
           &quot;The list of interfaces on the device.

            System-controlled interfaces created by the system are
            always present in this list, whether they are configured or
            not.&quot;;

         leaf name {
           type string;
           description
             &quot;The name of the interface.

              A server implementation MAY map this leaf to the ifName
              MIB object.  Such an implementation needs to use some
              mechanism to handle the differences in size and characters
              allowed between this leaf and ifName.  The definition of
              such a mechanism is outside the scope of this document.&quot;;
           reference
             &quot;<a href="/doc/html/rfc2863">RFC 2863</a>: The Interfaces Group MIB - ifName&quot;;
         }

         leaf type {
           type identityref {
             base interface-type;
           }
           mandatory true;
           description
             &quot;The type of the interface.&quot;;
           reference
             &quot;<a href="/doc/html/rfc2863">RFC 2863</a>: The Interfaces Group MIB - ifType&quot;;
         }

         leaf admin-status {
           if-feature if-mib;
           type enumeration {
             enum up {
               value 1;
               description
                 &quot;Ready to pass packets.&quot;;
             }
             enum down {
               value 2;
               description
                 &quot;Not ready to pass packets and not in some test mode.&quot;;
             }

<span class="grey"><a href="/doc/html/rfc7223">RFC 7223</a>                YANG Interface Management               May 2014</span>

             enum testing {
               value 3;
               description
                 &quot;In some test mode.&quot;;
             }
           }
           mandatory true;
           description
             &quot;The desired state of the interface.

              This leaf has the same read semantics as ifAdminStatus.&quot;;
           reference
             &quot;<a href="/doc/html/rfc2863">RFC 2863</a>: The Interfaces Group MIB - ifAdminStatus&quot;;
         }

         leaf oper-status {
           type enumeration {
             enum up {
               value 1;
               description
                 &quot;Ready to pass packets.&quot;;
             }
             enum down {
               value 2;
               description
                 &quot;The interface does not pass any packets.&quot;;
             }
             enum testing {
               value 3;
               description
                 &quot;In some test mode.  No operational packets can
                  be passed.&quot;;
             }
             enum unknown {
               value 4;
               description
                 &quot;Status cannot be determined for some reason.&quot;;
             }
             enum dormant {
               value 5;
               description
                 &quot;Waiting for some external event.&quot;;
             }
             enum not-present {
               value 6;
               description
                 &quot;Some component (typically hardware) is missing.&quot;;
             }
<span class="grey"><a href="/doc/html/rfc7223">RFC 7223</a>                YANG Interface Management               May 2014</span>

             enum lower-layer-down {
               value 7;
               description
                 &quot;Down due to state of lower-layer interface(s).&quot;;
             }
           }
           mandatory true;
           description
             &quot;The current operational state of the interface.

              This leaf has the same semantics as ifOperStatus.&quot;;
           reference
             &quot;<a href="/doc/html/rfc2863">RFC 2863</a>: The Interfaces Group MIB - ifOperStatus&quot;;
         }

         leaf last-change {
           type yang:date-and-time;
           description
             &quot;The time the interface entered its current operational
              state.  If the current state was entered prior to the
              last re-initialization of the local network management
              subsystem, then this node is not present.&quot;;
           reference
             &quot;<a href="/doc/html/rfc2863">RFC 2863</a>: The Interfaces Group MIB - ifLastChange&quot;;
         }

         leaf if-index {
           if-feature if-mib;
           type int32 {
             range &quot;1..2147483647&quot;;
           }
           mandatory true;
           description
             &quot;The ifIndex value for the ifEntry represented by this
              interface.&quot;;
           reference
             &quot;<a href="/doc/html/rfc2863">RFC 2863</a>: The Interfaces Group MIB - ifIndex&quot;;
         }

         leaf phys-address {
           type yang:phys-address;
           description
             &quot;The interface&#x27;s address at its protocol sub-layer.  For
              example, for an 802.x interface, this object normally
              contains a Media Access Control (MAC) address.  The
              interface&#x27;s media-specific modules must define the bit

<span class="grey"><a href="/doc/html/rfc7223">RFC 7223</a>                YANG Interface Management               May 2014</span>

              and byte ordering and the format of the value of this
              object.  For interfaces that do not have such an address
              (e.g., a serial line), this node is not present.&quot;;
           reference
             &quot;<a href="/doc/html/rfc2863">RFC 2863</a>: The Interfaces Group MIB - ifPhysAddress&quot;;
         }

         leaf-list higher-layer-if {
           type interface-state-ref;
           description
             &quot;A list of references to interfaces layered on top of this
              interface.&quot;;
           reference
             &quot;<a href="/doc/html/rfc2863">RFC 2863</a>: The Interfaces Group MIB - ifStackTable&quot;;
         }

         leaf-list lower-layer-if {
           type interface-state-ref;
           description
             &quot;A list of references to interfaces layered underneath this
              interface.&quot;;
           reference
             &quot;<a href="/doc/html/rfc2863">RFC 2863</a>: The Interfaces Group MIB - ifStackTable&quot;;
         }

         leaf speed {
           type yang:gauge64;
           units &quot;bits/second&quot;;
           description
               &quot;An estimate of the interface&#x27;s current bandwidth in bits
                per second.  For interfaces that do not vary in
                bandwidth or for those where no accurate estimation can
                be made, this node should contain the nominal bandwidth.
                For interfaces that have no concept of bandwidth, this
                node is not present.&quot;;
           reference
             &quot;<a href="/doc/html/rfc2863">RFC 2863</a>: The Interfaces Group MIB -
                        ifSpeed, ifHighSpeed&quot;;
         }

<span class="grey"><a href="/doc/html/rfc7223">RFC 7223</a>                YANG Interface Management               May 2014</span>

         container statistics {
           description
             &quot;A collection of interface-related statistics objects.&quot;;

           leaf discontinuity-time {
             type yang:date-and-time;
             mandatory true;
             description
               &quot;The time on the most recent occasion at which any one or
                more of this interface&#x27;s counters suffered a
                discontinuity.  If no such discontinuities have occurred
                since the last re-initialization of the local management
                subsystem, then this node contains the time the local
                management subsystem re-initialized itself.&quot;;
           }

           leaf in-octets {
             type yang:counter64;
             description
               &quot;The total number of octets received on the interface,
                including framing characters.

                Discontinuities in the value of this counter can occur
                at re-initialization of the management system, and at
                other times as indicated by the value of
                &#x27;discontinuity-time&#x27;.&quot;;
             reference
               &quot;<a href="/doc/html/rfc2863">RFC 2863</a>: The Interfaces Group MIB - ifHCInOctets&quot;;
           }

           leaf in-unicast-pkts {
             type yang:counter64;
             description
               &quot;The number of packets, delivered by this sub-layer to a
                higher (sub-)layer, that were not addressed to a
                multicast or broadcast address at this sub-layer.

                Discontinuities in the value of this counter can occur
                at re-initialization of the management system, and at
                other times as indicated by the value of
                &#x27;discontinuity-time&#x27;.&quot;;
             reference
               &quot;<a href="/doc/html/rfc2863">RFC 2863</a>: The Interfaces Group MIB - ifHCInUcastPkts&quot;;
           }

<span class="grey"><a href="/doc/html/rfc7223">RFC 7223</a>                YANG Interface Management               May 2014</span>

           leaf in-broadcast-pkts {
             type yang:counter64;
             description
               &quot;The number of packets, delivered by this sub-layer to a
                higher (sub-)layer, that were addressed to a broadcast
                address at this sub-layer.

                Discontinuities in the value of this counter can occur
                at re-initialization of the management system, and at
                other times as indicated by the value of
                &#x27;discontinuity-time&#x27;.&quot;;
             reference
               &quot;<a href="/doc/html/rfc2863">RFC 2863</a>: The Interfaces Group MIB -
                          ifHCInBroadcastPkts&quot;;
           }

           leaf in-multicast-pkts {
             type yang:counter64;
             description
               &quot;The number of packets, delivered by this sub-layer to a
                higher (sub-)layer, that were addressed to a multicast
                address at this sub-layer.  For a MAC-layer protocol,
                this includes both Group and Functional addresses.

                Discontinuities in the value of this counter can occur
                at re-initialization of the management system, and at
                other times as indicated by the value of
                &#x27;discontinuity-time&#x27;.&quot;;
             reference
               &quot;<a href="/doc/html/rfc2863">RFC 2863</a>: The Interfaces Group MIB -
                          ifHCInMulticastPkts&quot;;
           }

           leaf in-discards {
             type yang:counter32;
             description
               &quot;The number of inbound packets that were chosen to be
                discarded even though no errors had been detected to
                prevent their being deliverable to a higher-layer
                protocol.  One possible reason for discarding such a
                packet could be to free up buffer space.

                Discontinuities in the value of this counter can occur
                at re-initialization of the management system, and at
                other times as indicated by the value of
                &#x27;discontinuity-time&#x27;.&quot;;

<span class="grey"><a href="/doc/html/rfc7223">RFC 7223</a>                YANG Interface Management               May 2014</span>

             reference
               &quot;<a href="/doc/html/rfc2863">RFC 2863</a>: The Interfaces Group MIB - ifInDiscards&quot;;
           }

           leaf in-errors {
             type yang:counter32;
             description
               &quot;For packet-oriented interfaces, the number of inbound
                packets that contained errors preventing them from being
                deliverable to a higher-layer protocol.  For character-
                oriented or fixed-length interfaces, the number of
                inbound transmission units that contained errors
                preventing them from being deliverable to a higher-layer
                protocol.

                Discontinuities in the value of this counter can occur
                at re-initialization of the management system, and at
                other times as indicated by the value of
                &#x27;discontinuity-time&#x27;.&quot;;
             reference
               &quot;<a href="/doc/html/rfc2863">RFC 2863</a>: The Interfaces Group MIB - ifInErrors&quot;;
           }

           leaf in-unknown-protos {
             type yang:counter32;
             description
               &quot;For packet-oriented interfaces, the number of packets
                received via the interface that were discarded because
                of an unknown or unsupported protocol.  For
                character-oriented or fixed-length interfaces that
                support protocol multiplexing, the number of
                transmission units received via the interface that were
                discarded because of an unknown or unsupported protocol.
                For any interface that does not support protocol
                multiplexing, this counter is not present.

                Discontinuities in the value of this counter can occur
                at re-initialization of the management system, and at
                other times as indicated by the value of
                &#x27;discontinuity-time&#x27;.&quot;;
             reference
               &quot;<a href="/doc/html/rfc2863">RFC 2863</a>: The Interfaces Group MIB - ifInUnknownProtos&quot;;
           }

<span class="grey"><a href="/doc/html/rfc7223">RFC 7223</a>                YANG Interface Management               May 2014</span>

           leaf out-octets {
             type yang:counter64;
             description
               &quot;The total number of octets transmitted out of the
                interface, including framing characters.

                Discontinuities in the value of this counter can occur
                at re-initialization of the management system, and at
                other times as indicated by the value of
                &#x27;discontinuity-time&#x27;.&quot;;
             reference
               &quot;<a href="/doc/html/rfc2863">RFC 2863</a>: The Interfaces Group MIB - ifHCOutOctets&quot;;
           }

           leaf out-unicast-pkts {
             type yang:counter64;
             description
               &quot;The total number of packets that higher-level protocols
                requested be transmitted, and that were not addressed
                to a multicast or broadcast address at this sub-layer,
                including those that were discarded or not sent.

                Discontinuities in the value of this counter can occur
                at re-initialization of the management system, and at
                other times as indicated by the value of
                &#x27;discontinuity-time&#x27;.&quot;;
             reference
               &quot;<a href="/doc/html/rfc2863">RFC 2863</a>: The Interfaces Group MIB - ifHCOutUcastPkts&quot;;
           }

           leaf out-broadcast-pkts {
             type yang:counter64;
             description
               &quot;The total number of packets that higher-level protocols
                requested be transmitted, and that were addressed to a
                broadcast address at this sub-layer, including those
                that were discarded or not sent.

                Discontinuities in the value of this counter can occur
                at re-initialization of the management system, and at
                other times as indicated by the value of
                &#x27;discontinuity-time&#x27;.&quot;;
             reference
               &quot;<a href="/doc/html/rfc2863">RFC 2863</a>: The Interfaces Group MIB -
                          ifHCOutBroadcastPkts&quot;;
           }

<span class="grey"><a href="/doc/html/rfc7223">RFC 7223</a>                YANG Interface Management               May 2014</span>

           leaf out-multicast-pkts {
             type yang:counter64;
             description
               &quot;The total number of packets that higher-level protocols
                requested be transmitted, and that were addressed to a
                multicast address at this sub-layer, including those
                that were discarded or not sent.  For a MAC-layer
                protocol, this includes both Group and Functional
                addresses.

                Discontinuities in the value of this counter can occur
                at re-initialization of the management system, and at
                other times as indicated by the value of
                &#x27;discontinuity-time&#x27;.&quot;;
             reference
               &quot;<a href="/doc/html/rfc2863">RFC 2863</a>: The Interfaces Group MIB -
                          ifHCOutMulticastPkts&quot;;
           }

           leaf out-discards {
             type yang:counter32;
             description
               &quot;The number of outbound packets that were chosen to be
                discarded even though no errors had been detected to
                prevent their being transmitted.  One possible reason
                for discarding such a packet could be to free up buffer
                space.

                Discontinuities in the value of this counter can occur
                at re-initialization of the management system, and at
                other times as indicated by the value of
                &#x27;discontinuity-time&#x27;.&quot;;
             reference
               &quot;<a href="/doc/html/rfc2863">RFC 2863</a>: The Interfaces Group MIB - ifOutDiscards&quot;;
           }

           leaf out-errors {
             type yang:counter32;
             description
               &quot;For packet-oriented interfaces, the number of outbound
                packets that could not be transmitted because of errors.
                For character-oriented or fixed-length interfaces, the
                number of outbound transmission units that could not be
                transmitted because of errors.

<span class="grey"><a href="/doc/html/rfc7223">RFC 7223</a>                YANG Interface Management               May 2014</span>

                Discontinuities in the value of this counter can occur
                at re-initialization of the management system, and at
                other times as indicated by the value of
                &#x27;discontinuity-time&#x27;.&quot;;
             reference
               &quot;<a href="/doc/html/rfc2863">RFC 2863</a>: The Interfaces Group MIB - ifOutErrors&quot;;
           }
         }
       }
     }
   }
