module ietf-ospf-unreachable-links {
  yang-version 1.1;
  namespace "urn:ietf:params:xml:ns:yang:"
          + "ietf-ospf-unreachable-links";
  prefix ospf-unreach-link;

  import ietf-routing {
    prefix rt;
    reference
      "RFC 8349: A YANG Data Model for Routing Management
                 (NMDA Version)";
  }
  import ietf-ospf {
    prefix ospf;
    reference
      "RFC 9129: YANG Data Model for the OSPF Protocol";
  }

  organization
    "IETF Link State Routing (LSR) Working Group";
  contact
    "WG Web:   <https://datatracker.ietf.org/wg/lsr/>
     WG List:  <mailto:lsr@ietf.org>

     Author:   Yingzhen Qu
               <mailto:yqu@futurewei.com>
     Author:   Acee Lindem
               <mailto:acee.ietf@gmail.com>
     Author:   Liyan Gong
               <mailto:gongliyan@chinamobile.com>
     Author:   Weiqiang Cheng
               <mailto:chengweiqiang@chinamobile.com>
     Author:   Changwang Lin
               <mailto:linchangwang.04414@h3c.com>
     Author:   Ran Chen
               <mailto:chen.ran@zte.com.cn>";
  description
    "This YANG module defines the configuration and operational
     state for Advertising Unreachable Links in OSPF as defined
     in RFC 10041.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the 'YANG Parameters' registry group
     (https://www.iana.org/assignments/yang-parameters).

     This version of this YANG module is part of RFC 10041; see
     the RFC itself for full legal notices.";

  revision 2026-09-16 {
    description
      "Initial revision.";
    reference
      "RFC 10041: Advertising Unreachable Links in OSPF";
  }

  augment "/rt:routing/rt:control-plane-protocols/"
        + "rt:control-plane-protocol/ospf:ospf/"
        + "ospf:areas/ospf:area" {
    when
      "derived-from-or-self(../../../rt:type, 'ospf:ospfv2') or "
    + "derived-from-or-self(../../../rt:type, 'ospf:ospfv3')" {
      description
        "This augments the OSPF routing protocol when used.";
    }
    description
      "This augments the OSPF protocol with Unreachable Link
       advertisement.";
    container unreachable-link-advertisement {
      leaf enabled {
        type boolean;
        default "false";
        description
          "Controls the interpretation of MaxLinkMetric as
           unreachable and the advertisement of the Unreachable
           Link capability for the area.  It is enabled when set
           to true and disabled when set to false.";
      }
      description
        "OSPF Unreachable Link advertisement parameters.";
    }
  }

  augment "/rt:routing/rt:control-plane-protocols/"
        + "rt:control-plane-protocol/ospf:ospf/"
        + "ospf:areas/ospf:area/ospf:interfaces/ospf:interface" {
    when "derived-from(/rt:routing/rt:control-plane-protocols/"
       + "rt:control-plane-protocol/rt:type, 'ospf:ospfv2') or "
       + "derived-from(/rt:routing/rt:control-plane-protocols/"
       + "rt:control-plane-protocol/rt:type, 'ospf:ospfv3')" {
      description
        "This augments the OSPF interfaces.";
    }
    leaf advertise-unreachable-link {
      type boolean;
      must "not(../advertise-unreachable-link = 'true' and "
         + "/rt:routing/rt:control-plane-protocols/"
         + "rt:control-plane-protocol/ospf:ospf/ospf:areas/"
         + "ospf:area/"
         + "ospf-unreach-link:unreachable-link-advertisement/"
         + "ospf-unreach-link:enabled = 'false')" {
        error-message
          "The interface cannot be advertised "
        + "as unreachable (true) unless the "
        + "unreachable-link-advertisement capability is "
        + "enabled (true).";
        description
          "Ensures an interface isn't explicitly advertised as
           unreachable unless the OSPF area level capability is
           enabled.";
      }
      default "false";
      description
        "Specifies that the link should be advertised with a metric
         of MaxLinkMetric (0xffff) in the default topology.";
    }
    description
      "Augment OSPF interfaces with an option to advertise the link
       as unreachable.";
  }
}
