module example-service-assurance-is-is {
  yang-version 1.1;
  namespace "urn:example:example-service-assurance-is-is";
  prefix example-is-is;

  import ietf-service-assurance {
    prefix sain;
    reference
      "RFC 9418: YANG Modules for Service Assurance";
  }

  organization
    "IETF OPSAWG Working Group";
  contact
    "WG Web:   <https://datatracker.ietf.org/wg/opsawg/>
     WG List:  <mailto:opsawg@ietf.org>
     Author:   Benoit Claise  <mailto:benoit.claise@huawei.com>
     Author:   Jean Quilbeuf  <mailto:jean.quilbeuf@huawei.com>";
  description
    "This example module augments the ietf-service-assurance module
     to add support for the subservice is-is.

     It checks whether an IS-IS instance is healthy.";

  revision 2023-07-11 {
    description
      "Initial version.";
    reference
      "RFC 9418: YANG Modules for Service Assurance";
  }

  identity is-is-type {
    base sain:subservice-base;
    description
      "Health of IS-IS routing protocol.";
  }

  augment "/sain:subservices/sain:subservice/sain:parameter" {
    when "derived-from-or-self(sain:type, 'is-is-type')";
    description
      "Augments the parameter choice from the ietf-service-assurance
       module with a case specific to the is-is subservice.";
    container parameters {
      description
        "Parameters for the is-is subservice type.";
      leaf instance-name {
        type string;
        mandatory true;
        description
          "The instance to monitor.";
      }
    }
  }
}
