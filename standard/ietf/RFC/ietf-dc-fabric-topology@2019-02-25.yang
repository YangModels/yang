module ietf-dc-fabric-topology {
  yang-version 1.1;
  namespace &quot;urn:ietf:params:xml:ns:yang:ietf-dc-fabric-topology&quot;;
  prefix fabric;

  import ietf-network {
    prefix nw;
    reference
      &quot;<a href="/doc/html/rfc8345">RFC 8345</a>: A YANG Data Model for Network Topologies&quot;;
  }
  import ietf-network-topology {
    prefix nt;
    reference
      &quot;<a href="/doc/html/rfc8345">RFC 8345</a>: A YANG Data Model for Network Topologies&quot;;
  }
  import ietf-dc-fabric-types {
    prefix fabrictypes;
    reference
      &quot;<a href="/doc/html/rfc8542">RFC 8542</a>: A YANG Data Model for Fabric Topology in
       Data-Center Networks&quot;;
  }
<span class="grey"><a href="/doc/html/rfc8542">RFC 8542</a>            Data Model for DC Fabric Topology         March 2019</span>

     organization
       &quot;IETF I2RS (Interface to the Routing System) Working Group&quot;;
     contact
       &quot;WG Web:    &lt;<a href="https://datatracker.ietf.org/wg/i2rs/">https://datatracker.ietf.org/wg/i2rs/</a>&gt;
        WG List:   &lt;mailto:<a href="mailto:i2rs@ietf.org">i2rs@ietf.org</a>&gt;

        Editor:    Yan Zhuang
                   &lt;mailto:<a href="mailto:zhuangyan.zhuang@huawei.com">zhuangyan.zhuang@huawei.com</a>&gt;

        Editor:    Danian Shi
                   &lt;mailto:<a href="mailto:shidanian@huawei.com">shidanian@huawei.com</a>&gt;&quot;;
     description
       &quot;This module contains a collection of YANG definitions for
        fabric.

        Copyright (c) 2019 IETF Trust and the persons identified
        as authors of the code.  All rights reserved.

        Redistribution and use in source and binary forms, with
        or without modification, is permitted pursuant to, and
        subject to the license terms contained in, the Simplified
        BSD License set forth in <a href="#section-4">Section 4</a>.c of the IETF Trust&#x27;s
        Legal Provisions Relating to IETF Documents
        (<a href="https://trustee.ietf.org/license-info">https://trustee.ietf.org/license-info</a>).

        This version of this YANG module is part of <a href="/doc/html/rfc8542">RFC 8542</a>;
        see the RFC itself for full legal notices.&quot;;

     revision 2019-02-25 {
       description
         &quot;Initial revision.&quot;;
       reference
         &quot;<a href="/doc/html/rfc8542">RFC 8542</a>: A YANG Data Model for Fabric Topology
          in Data-Center Networks&quot;;
     }

     //grouping statements

     grouping fabric-network-type {
       description
         &quot;Identify the topology type to be fabric.&quot;;
       container fabric-network {
         presence &quot;indicates fabric Network&quot;;
         description
           &quot;The presence of the container node indicates
            fabric topology&quot;;
       }
     }
<span class="grey"><a href="/doc/html/rfc8542">RFC 8542</a>            Data Model for DC Fabric Topology         March 2019</span>

     grouping fabric-options {
       description
         &quot;Options for a fabric&quot;;
       leaf gateway-mode {
         type enumeration {
           enum centralized {
             description
               &quot;The Fabric uses centralized
                gateway, in which gateway is deployed on SPINE
                node.&quot;;
           }
           enum distributed {
             description
               &quot;The Fabric uses distributed
                gateway, in which gateway is deployed on LEAF
                node.&quot;;
           }
         }
         default &quot;distributed&quot;;
         description
           &quot;Gateway mode of the fabric&quot;;
       }
       leaf traffic-behavior {
         type enumeration {
           enum normal {
             description
               &quot;Normal means no policy is needed
                for all traffic&quot;;
           }
           enum policy-driven {
             description
               &quot;Policy driven means policy is
                needed for the traffic; otherwise, the traffic
                will be discarded.&quot;;
           }
         }
         default &quot;normal&quot;;
         description
           &quot;Traffic behavior of the fabric&quot;;
       }
       leaf-list capability-supported {
         type fabrictypes:service-capabilities;
         description
           &quot;It provides a list of supported services of the
            fabric.  The service-capabilities is defined as
            identity-ref.  Users can define more services
            by defining new identities.&quot;;
       }
<span class="grey"><a href="/doc/html/rfc8542">RFC 8542</a>            Data Model for DC Fabric Topology         March 2019</span>

     }

     grouping device-attributes {
       description
         &quot;device attributes&quot;;
       leaf device-ref {
         type fabrictypes:node-ref;
         description
           &quot;The device that the fabric includes that refers
            to a node in another topology.&quot;;
       }
       leaf-list role {
         type fabrictypes:device-role;
         default &quot;fabrictypes:leaf&quot;;
         description
           &quot;It is a list of device roles to represent the roles
            that a device plays within a POD, such as SPINE,
            LEAF, Border, or Border-Leaf.
            The device role is defined as identity-ref.  If more
            than 2 stages are used for a POD, users can
            define new identities for the device role.&quot;;
       }
     }

     grouping link-attributes {
       description
         &quot;Link attributes&quot;;
       leaf link-ref {
         type fabrictypes:link-ref;
         description
           &quot;The link that the fabric includes that refers to
            a link in another topology.&quot;;
       }
     }

     grouping port-attributes {
       description
         &quot;Port attributes&quot;;
       leaf port-ref {
         type fabrictypes:tp-ref;
         description
           &quot;The port that the fabric includes that refers to
            a termination-point in another topology.&quot;;
       }
       leaf port-type {
         type fabrictypes:port-type;
         description
           &quot;Port type is defined as identity-ref.  The current
<span class="grey"><a href="/doc/html/rfc8542">RFC 8542</a>            Data Model for DC Fabric Topology         March 2019</span>

            types include ethernet or serial.  If more types
            are needed, developers can define new identities.&quot;;
       }
       leaf bandwidth {
         type fabrictypes:bandwidth;
         description
           &quot;Bandwidth of the port.  It is defined as identity-ref.
            If more speeds are introduced, developers can define
            new identities for them.  Current speeds include 1M, 10M,
            100M, 1G, 10G, 25G, 40G, 100G, and 400G.&quot;;
       }
     }

     grouping fabric-attributes {
       description
         &quot;Attributes of a fabric&quot;;
       leaf fabric-id {
         type fabrictypes:fabric-id;
         description
           &quot;An identifier for a fabric in a topology.
            This identifier can be generated when composing a fabric.
            The composition of a fabric can be achieved by defining an
            RPC, which is left for vendor-specific implementation and
            not provided in this model.&quot;;
       }
       leaf name {
         type string;
         description
           &quot;Name of the fabric&quot;;
       }
       leaf type {
         type fabrictypes:underlay-network-type;
         description
           &quot;The type of physical network that implements this
            fabric.  Examples are VLAN and TRILL.&quot;;
       }
       container vni-capacity {
         description
           &quot;The range of the VXLAN Network Identifier
            (VNI) defined in <a href="/doc/html/rfc7348">RFC 7348</a> that the POD uses.&quot;;
         leaf min {
           type int32;
           description
             &quot;The lower-limit VNI.&quot;;
         }
         leaf max {
           type int32;
           description
<span class="grey"><a href="/doc/html/rfc8542">RFC 8542</a>            Data Model for DC Fabric Topology         March 2019</span>

             &quot;The upper-limit VNI.&quot;;
         }
       }
       leaf description {
         type string;
         description
           &quot;Description of the fabric&quot;;
       }
       container options {
         description
           &quot;Options of the fabric&quot;;
         uses fabric-options;
       }
       list device-nodes {
         key &quot;device-ref&quot;;
         description
           &quot;Device nodes that are included in a fabric.&quot;;
         uses device-attributes;
       }
       list device-links {
         key &quot;link-ref&quot;;
         description
           &quot;Links that are included within a fabric.&quot;;
         uses link-attributes;
       }
       list device-ports {
         key &quot;port-ref&quot;;
         description
           &quot;Ports that are included in the fabric.&quot;;
         uses port-attributes;
       }
     }

     // augment statements

     augment &quot;/nw:networks/nw:network/nw:network-types&quot; {
       description
         &quot;Introduce a new network type for fabric-based topology&quot;;
       uses fabric-network-type;
     }

     augment &quot;/nw:networks/nw:network/nw:node&quot; {
       when &#x27;/nw:networks/nw:network/nw:network-types/&#x27;
          + &#x27;fabric:fabric-network&#x27; {
         description
           &quot;Augmentation parameters apply only for networks
            with fabric topology&quot;;
       }
<span class="grey"><a href="/doc/html/rfc8542">RFC 8542</a>            Data Model for DC Fabric Topology         March 2019</span>

       description
         &quot;Augmentation for fabric nodes created by
          fabric topology.&quot;;
       container fabric-attributes {
         description
           &quot;Attributes for a fabric network&quot;;
         uses fabric-attributes;
       }
     }

     augment &quot;/nw:networks/nw:network/nw:node/nt:termination-point&quot; {
       when &#x27;/nw:networks/nw:network/nw:network-types/&#x27;
          + &#x27;fabric:fabric-network&#x27; {
         description
           &quot;Augmentation parameters apply only for networks
            with fabric topology&quot;;
       }
       description
         &quot;Augmentation for port on fabric.&quot;;
       container fport-attributes {
         config false;
         description
           &quot;Attributes for fabric ports&quot;;
         uses fabrictypes:fabric-port;
       }
     }
   }
