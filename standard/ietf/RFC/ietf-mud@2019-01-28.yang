module ietf-mud {
  yang-version 1.1;
  namespace &quot;urn:ietf:params:xml:ns:yang:ietf-mud&quot;;
  prefix ietf-mud;

  import ietf-access-control-list {
    prefix acl;
  }
  import ietf-yang-types {
    prefix yang;
  }
  import ietf-inet-types {
    prefix inet;
  }

  organization
    &quot;IETF OPSAWG (Operations and Management Area Working Group)&quot;;
  contact
    &quot;WG Web: &lt;<a href="https://datatracker.ietf.org/wg/opsawg/">https://datatracker.ietf.org/wg/opsawg/</a>&gt;
     WG List: <a href="mailto:opsawg@ietf.org">opsawg@ietf.org</a>

     Author: Eliot Lear
             <a href="mailto:lear@cisco.com">lear@cisco.com</a>

     Author: Ralph Droms
             <a href="mailto:rdroms@gmail.com">rdroms@gmail.com</a>

     Author: Dan Romascanu
             <a href="mailto:dromasca@gmail.com">dromasca@gmail.com</a>
    &quot;;
  description
    &quot;This YANG module defines a component that augments the
     IETF description of an access list.  This specific module
     focuses on additional filters that include local, model,
     and same-manufacturer.

<span class="grey"><a href="/doc/html/rfc8520">RFC 8520</a>             Manufacturer Usage Descriptions          March 2019</span>

        This module is intended to be serialized via JSON and stored
        as a file, as described in <a href="/doc/html/rfc8520">RFC 8520</a>.

        The key words &#x27;MUST&#x27;, &#x27;MUST NOT&#x27;, &#x27;REQUIRED&#x27;, &#x27;SHALL&#x27;, &#x27;SHALL
        NOT&#x27;, &#x27;SHOULD&#x27;, &#x27;SHOULD NOT&#x27;, &#x27;RECOMMENDED&#x27;, &#x27;NOT RECOMMENDED&#x27;,
        &#x27;MAY&#x27;, and &#x27;OPTIONAL&#x27; in this document are to be interpreted as
        described in <a href="/doc/html/bcp14">BCP 14</a> (<a href="/doc/html/rfc2119">RFC 2119</a>) (<a href="/doc/html/rfc8174">RFC 8174</a>) when, and only when,
        they appear in all capitals, as shown here.

        Copyright (c) 2019 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc8520">RFC 8520</a>; see
        the RFC itself for full legal notices.&quot;;

     revision 2019-01-28 {
       description
         &quot;Initial proposed standard.&quot;;
       reference
         &quot;<a href="/doc/html/rfc8520">RFC 8520</a>: Manufacturer Usage Description
          Specification&quot;;
     }

     typedef direction {
       type enumeration {
         enum to-device {
           description
             &quot;packets or flows destined to the target
              Thing.&quot;;
         }
         enum from-device {
           description
             &quot;packets or flows destined from
              the target Thing.&quot;;
         }
       }
       description
         &quot;Which way are we talking about?&quot;;
     }

     container mud {
<span class="grey"><a href="/doc/html/rfc8520">RFC 8520</a>             Manufacturer Usage Descriptions          March 2019</span>

       presence &quot;Enabled for this particular MUD URL&quot;;
       description
         &quot;MUD-related information, as specified
          by <a href="/doc/html/rfc8520">RFC 8520</a>.&quot;;
       uses mud-grouping;
     }

     grouping mud-grouping {
       description
         &quot;Information about when support ends (or ended)
          and when to refresh.&quot;;
       leaf mud-version {
         type uint8;
         mandatory true;
         description
           &quot;This is the version of the MUD
            specification.  This memo specifies version 1.&quot;;
       }
       leaf mud-url {
         type inet:uri;
         mandatory true;
         description
           &quot;This is the MUD URL associated with the entry found
            in a MUD file.&quot;;
       }
       leaf last-update {
         type yang:date-and-time;
         mandatory true;
         description
           &quot;This is intended to be when the current MUD file
            was generated.  MUD managers SHOULD NOT check
            for updates between this time plus cache validity.&quot;;
       }
       leaf mud-signature {
         type inet:uri;
         description
           &quot;A URI that resolves to a signature as
            described in this specification.&quot;;
       }
       leaf cache-validity {
         type uint8 {
           range &quot;1..168&quot;;
         }
         units &quot;hours&quot;;
         default &quot;48&quot;;
         description
           &quot;The information retrieved from the MUD server is
            valid for these many hours, after which it should
<span class="grey"><a href="/doc/html/rfc8520">RFC 8520</a>             Manufacturer Usage Descriptions          March 2019</span>

            be refreshed.  N.B., MUD manager implementations
            need not discard MUD files beyond this period.&quot;;
       }
       leaf is-supported {
         type boolean;
         mandatory true;
         description
           &quot;This boolean indicates whether or not the Thing is
            currently supported by the manufacturer.&quot;;
       }
       leaf systeminfo {
         type string;
         description
           &quot;A UTF-8 description of this Thing.  This
            should be a brief description that may be
            displayed to the user to determine whether
            to allow the Thing on the
            network.&quot;;
       }
       leaf mfg-name {
         type string;
         description
           &quot;Manufacturer name, as described in
            the ietf-hardware YANG module.&quot;;
       }
       leaf model-name {
         type string;
         description
           &quot;Model name, as described in the
            ietf-hardware YANG module.&quot;;
       }
       leaf firmware-rev {
         type string;
         description
           &quot;firmware-rev, as described in the
            ietf-hardware YANG module.  Note that this field
            MUST NOT be included when the device can be
            updated but the MUD URL cannot.&quot;;
       }
       leaf software-rev {
         type string;
         description
           &quot;software-rev, as described in the
            ietf-hardware YANG module.  Note that this field
            MUST NOT be included when the device can be
            updated but the MUD URL cannot.&quot;;
       }
       leaf documentation {
<span class="grey"><a href="/doc/html/rfc8520">RFC 8520</a>             Manufacturer Usage Descriptions          March 2019</span>

         type inet:uri;
         description
           &quot;This URL points to documentation that
            relates to this device and any classes that it uses
            in its MUD file.  A caution: MUD managers need
            not resolve this URL on their own but rather simply
            provide it to the administrator.  Parsing HTML is
            not an intended function of a MUD manager.&quot;;
       }
       leaf-list extensions {
         type string {
           length &quot;1..40&quot;;
         }
         description
           &quot;A list of extension names that are used in this MUD
            file.  Each name is registered with the IANA and
            described in an RFC.&quot;;
       }
       container from-device-policy {
         description
           &quot;The policies that should be enforced on traffic
            coming from the device.  These policies are not
            necessarily intended to be enforced at a single
            point but may be rendered by the controller to any
            relevant enforcement points in the network or
            elsewhere.&quot;;
         uses access-lists;
       }
       container to-device-policy {
         description
           &quot;The policies that should be enforced on traffic
            going to the device.  These policies are not
            necessarily intended to be enforced at a single
            point but may be rendered by the controller to any
            relevant enforcement points in the network or
            elsewhere.&quot;;
         uses access-lists;
       }
     }

     grouping access-lists {
       description
         &quot;A grouping for access lists in the context of device
          policy.&quot;;
       container access-lists {
         description
           &quot;The access lists that should be applied to traffic
            to or from the device.&quot;;
<span class="grey"><a href="/doc/html/rfc8520">RFC 8520</a>             Manufacturer Usage Descriptions          March 2019</span>

         list access-list {
           key &quot;name&quot;;
           description
             &quot;Each entry on this list refers to an ACL that
              should be present in the overall access list
              data model.  Each ACL is identified by name and
              type.&quot;;
           leaf name {
             type leafref {
               path &quot;/acl:acls/acl:acl/acl:name&quot;;
             }
             description
               &quot;The name of the ACL for this entry.&quot;;
           }
         }
       }
     }

     augment &quot;/acl:acls/acl:acl/acl:aces/acl:ace/acl:matches&quot; {
       description
         &quot;adding abstractions to avoid the need of IP addresses.&quot;;
       container mud {
         description
           &quot;MUD-specific matches.&quot;;
         leaf manufacturer {
           type inet:host;
           description
             &quot;A domain that is intended to match the authority
              section of the MUD URL.  This node is used to specify
              one or more manufacturers a device should
              be authorized to access.&quot;;
         }
         leaf same-manufacturer {
           type empty;
           description
             &quot;This node matches the authority section of the MUD URL
              of a Thing.  It is intended to grant access to all
              devices with the same authority section.&quot;;
         }
         leaf model {
           type inet:uri;
           description
             &quot;Devices of the specified model type will match if
              they have an identical MUD URL.&quot;;
         }
         leaf local-networks {
           type empty;
           description
<span class="grey"><a href="/doc/html/rfc8520">RFC 8520</a>             Manufacturer Usage Descriptions          March 2019</span>

             &quot;IP addresses will match this node if they are
              considered local addresses.  A local address may be
              a list of locally defined prefixes and masks
              that indicate a particular administrative scope.&quot;;
         }
         leaf controller {
           type inet:uri;
           description
             &quot;This node names a class that has associated with it
              zero or more IP addresses to match against.  These
              may be scoped to a manufacturer or via a standard
              URN.&quot;;
         }
         leaf my-controller {
           type empty;
           description
             &quot;This node matches one or more network elements that
              have been configured to be the controller for this
              Thing, based on its MUD URL.&quot;;
         }
       }
     }
     augment &quot;/acl:acls/acl:acl/acl:aces/acl:ace/acl:matches&quot;
           + &quot;/acl:l4/acl:tcp/acl:tcp&quot; {
       description
         &quot;add direction-initiated&quot;;
       leaf direction-initiated {
         type direction;
         description
           &quot;This node matches based on which direction a
            connection was initiated.  The means by which that
            is determined is discussed in this document.&quot;;
       }
     }
   }
