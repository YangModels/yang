module ietf-ptp {
  yang-version 1.1;
  namespace &quot;urn:ietf:params:xml:ns:yang:ietf-ptp&quot;;
  prefix ptp;

  import ietf-interfaces {
    prefix if;
    reference
      &quot;<a href="/doc/html/rfc8343">RFC 8343</a>: A YANG Data Model for Interface Management&quot;;
  }

  organization
    &quot;IETF TICTOC Working Group&quot;;
  contact
    &quot;WG Web:   <a href="https://datatracker.ietf.org/wg/tictoc/WG">https://datatracker.ietf.org/wg/tictoc/</a>
     <a href="https://datatracker.ietf.org/wg/tictoc/WG">WG</a> List:  &lt;mailto:<a href="mailto:tictoc@ietf.org">tictoc@ietf.org</a>&gt;
     Editor:   Yuanlong Jiang
               &lt;mailto:<a href="mailto:jiangyuanlong@huawei.com">jiangyuanlong@huawei.com</a>&gt;
     Editor:   Rodney Cummings
               &lt;mailto:<a href="mailto:rodney.cummings@ni.com">rodney.cummings@ni.com</a>&gt;&quot;;
  description
    &quot;This YANG module defines a data model for the configuration
     of IEEE Std 1588-2008 clocks, and also for retrieval of the state
     data of IEEE Std 1588-2008 clocks.&quot;;

  revision 2019-05-07 {
    description
      &quot;Initial version&quot;;
    reference
      &quot;<a href="/doc/html/rfc8575">RFC 8575</a>: YANG Data Model for the Precision Time Protocol&quot;;
  }

  typedef delay-mechanism-enumeration {
    type enumeration {
      enum e2e {
        value 1;
        description
          &quot;The port uses the delay request-response mechanism.&quot;;
      }
      enum p2p {
        value 2;
<span class="grey"><a href="/doc/html/rfc8575">RFC 8575</a>                 YANG Data Model for PTP                May 2019</span>

          description
            &quot;The port uses the peer delay mechanism.&quot;;
        }
        enum disabled {
          value 254;
          description
            &quot;The port does not implement any delay mechanism.&quot;;
        }
      }
      description
        &quot;The propagation-delay measuring option used by the
         port.  Values for this enumeration are specified
         by the IEEE Std 1588 standard exclusively.&quot;;
      reference
        &quot;IEEE Std 1588-2008: 8.2.5.4.4&quot;;
    }

    typedef port-state-enumeration {
      type enumeration {
        enum initializing {
          value 1;
          description
            &quot;The port is initializing its data sets, hardware, and
             communication facilities.&quot;;
        }
        enum faulty {
          value 2;
          description
            &quot;The port is in the fault state.&quot;;
        }
        enum disabled {
          value 3;
          description
            &quot;The port is disabled and is not communicating PTP
             messages (other than possibly PTP management
             messages).&quot;;
        }
        enum listening {
          value 4;
          description
            &quot;The port is listening for an Announce message.&quot;;
        }
        enum pre-master {
          value 5;
          description
            &quot;The port is in the pre-master state.&quot;;
        }
        enum master {
<span class="grey"><a href="/doc/html/rfc8575">RFC 8575</a>                 YANG Data Model for PTP                May 2019</span>

          value 6;
          description
            &quot;The port is behaving as a master port.&quot;;
        }
        enum passive {
          value 7;
          description
            &quot;The port is in the passive state.&quot;;
        }
        enum uncalibrated {
          value 8;
          description
            &quot;A master port has been selected, but the port is still
             in the uncalibrated state.&quot;;
        }
        enum slave {
          value 9;
          description
            &quot;The port is synchronizing to the selected master port.&quot;;
        }
      }
      description
        &quot;The current state of the protocol engine associated
         with the port.  Values for this enumeration are specified
         by the IEEE Std 1588 standard exclusively.&quot;;
      reference
        &quot;IEEE Std 1588-2008: 8.2.5.3.1, 9.2.5&quot;;
    }

    typedef time-interval-type {
      type int64;
      description
        &quot;Derived data type for time interval, represented in units of
          nanoseconds and multiplied by 2^16&quot;;
      reference
        &quot;IEEE Std 1588-2008: 5.3.2&quot;;
    }

    typedef clock-identity-type {
      type binary {
        length &quot;8&quot;;
      }
      description
        &quot;Derived data type to identify a clock&quot;;
      reference
        &quot;IEEE Std 1588-2008: 5.3.4&quot;;
    }

<span class="grey"><a href="/doc/html/rfc8575">RFC 8575</a>                 YANG Data Model for PTP                May 2019</span>

    grouping clock-quality-grouping {
      description
        &quot;Derived data type for quality of a clock, which contains
         clockClass, clockAccuracy, and offsetScaledLogVariance.&quot;;
      reference
        &quot;IEEE Std 1588-2008: 5.3.7&quot;;
      leaf clock-class {
        type uint8;
        default &quot;248&quot;;
        description
          &quot;The clockClass denotes the traceability of the time
           or frequency distributed by the clock.&quot;;
      }
      leaf clock-accuracy {
        type uint8;
        description
          &quot;The clockAccuracy indicates the expected accuracy
           of the clock.&quot;;
      }
      leaf offset-scaled-log-variance {
        type uint16;
        description
          &quot;The offsetScaledLogVariance provides an estimate of
           the variations of the clock from a linear timescale
           when it is not synchronized to another clock
           using the protocol.&quot;;
      }
    }

    container ptp {
      description
        &quot;The PTP struct containing all attributes of PTP data set,
          other optional PTP attributes can be augmented as well.&quot;;
      list instance-list {
        key &quot;instance-number&quot;;
        description
          &quot;List of one or more PTP data sets in the device (see IEEE
           Std 1588-2008 subclause 6.3).
           Each PTP data set represents a distinct instance of
           PTP implementation in the device (i.e., distinct
           Ordinary Clock or Boundary Clock).&quot;;
        leaf instance-number {
          type uint32;
          description
            &quot;The instance number of the current PTP instance.
             This instance number is used for management purposes
             only.  This instance number does not represent the PTP
             domain number and is not used in PTP messages.&quot;;
<span class="grey"><a href="/doc/html/rfc8575">RFC 8575</a>                 YANG Data Model for PTP                May 2019</span>

        }
        container default-ds {
          description
            &quot;The default data set of the clock (see IEEE Std
             1588-2008 subclause 8.2.1).  This data set represents
             the configuration/state required for operation
             of Precision Time Protocol (PTP) state machines.&quot;;
          reference
            &quot;IEEE Std 1588-2008: 8.2.1&quot;;
          leaf two-step-flag {
            type boolean;
            description
              &quot;When set to true, the clock is a two-step clock;
               otherwise,the clock is a one-step clock.&quot;;
          }
          leaf clock-identity {
            type clock-identity-type;
            config false;
            description
              &quot;The clockIdentity of the local clock.&quot;;
          }
          leaf number-ports {
            type uint16;
            description
              &quot;The number of PTP ports on the instance.&quot;;
          }
          container clock-quality {
            description
              &quot;The clockQuality of the local clock.&quot;;
            uses clock-quality-grouping;
          }
          leaf priority1 {
            type uint8;
            description
              &quot;The priority1 attribute of the local clock.&quot;;
          }
          leaf priority2 {
            type uint8;
            description
              &quot;The priority2 attribute of the local clock.&quot;;
          }
          leaf domain-number {
            type uint8;
            description
              &quot;The domain number of the current syntonization
               domain.&quot;;
          }
          leaf slave-only {
<span class="grey"><a href="/doc/html/rfc8575">RFC 8575</a>                 YANG Data Model for PTP                May 2019</span>

            type boolean;
            description
              &quot;When set to true, the clock is a slave-only clock.&quot;;
          }
        }
        container current-ds {
          description
            &quot;The current data set of the clock (see IEEE Std
             1588-2008 subclause 8.2.2).  This data set represents
             local states learned from the exchange of
             Precision Time Protocol (PTP) messages.&quot;;
          reference
            &quot;IEEE Std 1588-2008: 8.2.2&quot;;
          leaf steps-removed {
            type uint16;
            default &quot;0&quot;;
            description
              &quot;The number of communication paths traversed
               between the local clock and the grandmaster clock.&quot;;
          }
          leaf offset-from-master {
            type time-interval-type;
            description
              &quot;The current value of the time difference between
               a master and a slave clock as computed by the slave.&quot;;
          }
          leaf mean-path-delay {
            type time-interval-type;
            description
              &quot;The current value of the mean propagation time between
               a master and a slave clock as computed by the slave.&quot;;
          }
        }
        container parent-ds {
          description
            &quot;The parent data set of the clock (see IEEE Std 1588-2008
             subclause 8.2.3).&quot;;
          reference
            &quot;IEEE Std 1588-2008: 8.2.3&quot;;
          container parent-port-identity {
            description
              &quot;The portIdentity of the port on the master, it
               contains two members: clockIdentity and portNumber.&quot;;
            reference
              &quot;IEEE Std 1588-2008: 5.3.5&quot;;
            leaf clock-identity {
              type clock-identity-type;

<span class="grey"><a href="/doc/html/rfc8575">RFC 8575</a>                 YANG Data Model for PTP                May 2019</span>

              description
                &quot;Identity of the clock.&quot;;
            }
            leaf port-number {
              type uint16;
              description
                &quot;Port number.&quot;;
            }
          }
          leaf parent-stats {
            type boolean;
            default &quot;false&quot;;
            description
              &quot;When set to true, the values of
               observedParentOffsetScaledLogVariance and
               observedParentClockPhaseChangeRate of parentDS
               have been measured and are valid.&quot;;
          }
          leaf observed-parent-offset-scaled-log-variance {
            type uint16;
            default &quot;65535&quot;;
            description
              &quot;An estimate of the parent clock&#x27;s PTP variance
               as observed by the slave clock.&quot;;
          }
          leaf observed-parent-clock-phase-change-rate {
            type int32;
            description
              &quot;An estimate of the parent clock&#x27;s phase change rate
               as observed by the slave clock.&quot;;
          }
          leaf grandmaster-identity {
            type clock-identity-type;
            description
              &quot;The clockIdentity attribute of the grandmaster clock.&quot;;
          }
          container grandmaster-clock-quality {
            description
              &quot;The clockQuality of the grandmaster clock.&quot;;
            uses clock-quality-grouping;
          }
          leaf grandmaster-priority1 {
            type uint8;
            description
              &quot;The priority1 attribute of the grandmaster clock.&quot;;
          }
          leaf grandmaster-priority2 {
            type uint8;
<span class="grey"><a href="/doc/html/rfc8575">RFC 8575</a>                 YANG Data Model for PTP                May 2019</span>

            description
              &quot;The priority2 attribute of the grandmaster clock.&quot;;
          }
        }
        container time-properties-ds {
          description
            &quot;The timeProperties data set of the clock (see
             IEEE Std 1588-2008 subclause 8.2.4).&quot;;
          reference
            &quot;IEEE Std 1588-2008: 8.2.4&quot;;
          leaf current-utc-offset-valid {
            type boolean;
            description
              &quot;When set to true, the current UTC offset is valid.&quot;;
          }
          leaf current-utc-offset {
            when &quot;../current-utc-offset-valid=&#x27;true&#x27;&quot;;
            type int16;
            description
              &quot;The offset between TAI and UTC when the epoch of the
               PTP system is the PTP epoch in units of seconds, i.e.,
               when ptp-timescale is TRUE; otherwise, the value has
               no meaning.&quot;;
          }
          leaf leap59 {
            type boolean;
            description
              &quot;When set to true, the last minute of the current UTC
               day contains 59 seconds.&quot;;
          }
          leaf leap61 {
            type boolean;
            description
              &quot;When set to true, the last minute of the current UTC
               day contains 61 seconds.&quot;;
          }
          leaf time-traceable {
            type boolean;
            description
              &quot;When set to true, the timescale and the
               currentUtcOffset are traceable to a primary
               reference.&quot;;
          }
          leaf frequency-traceable {
            type boolean;
            description
              &quot;When set to true, the frequency determining the
               timescale is traceable to a primary reference.&quot;;
<span class="grey"><a href="/doc/html/rfc8575">RFC 8575</a>                 YANG Data Model for PTP                May 2019</span>

          }
          leaf ptp-timescale {
            type boolean;
            description
              &quot;When set to true, the clock timescale of the
               grandmaster clock is PTP; otherwise, the timescale is
               ARB (arbitrary).&quot;;
          }
          leaf time-source {
            type uint8;
            description
              &quot;The source of time used by the grandmaster clock.&quot;;
          }
        }
        list port-ds-list {
          key &quot;port-number&quot;;
          description
            &quot;List of port data sets of the clock (see IEEE Std
             1588-2008 subclause 8.2.5).&quot;;
          reference
            &quot;IEEE Std 1588-2008: 8.2.5&quot;;
          leaf port-number {
            type uint16;
            description
              &quot;Port number.
               The data sets (i.e., information model) of IEEE Std
               1588-2008 specify a member portDS.portIdentity, which
               uses a typed struct with members clockIdentity and
               portNumber.

               In this YANG data model, portIdentity is not modeled
               in the port-ds-list.  However, its members are provided
               as follows:
               portIdentity.portNumber is provided as this
               port-number leaf in port-ds-list, and
               portIdentity.clockIdentity is provided as the
               clock-identity leaf in default-ds of the instance
               (i.e., ../../default-ds/clock-identity).&quot;;
          }
          leaf port-state {
            type port-state-enumeration;
            default &quot;initializing&quot;;
            description
              &quot;Current state associated with the port.&quot;;
          }
          leaf underlying-interface {
            type if:interface-ref;

<span class="grey"><a href="/doc/html/rfc8575">RFC 8575</a>                 YANG Data Model for PTP                May 2019</span>

            description
              &quot;Reference to the configured underlying interface that
               is used by this PTP port (see <a href="/doc/html/rfc8343">RFC 8343</a>).&quot;;
            reference
              &quot;<a href="/doc/html/rfc8343">RFC 8343</a>: A YANG Data Model for Interface Management&quot;;
          }
          leaf log-min-delay-req-interval {
            type int8;
            description
              &quot;The base-2 logarithm of the minDelayReqInterval
               (the minimum permitted mean time interval between
               successive Delay_Req messages).&quot;;
          }
          leaf peer-mean-path-delay {
            type time-interval-type;
            default &quot;0&quot;;
            description
              &quot;An estimate of the current one-way propagation delay
               on the link when the delayMechanism is P2P; otherwise,
               it is zero.&quot;;
          }
          leaf log-announce-interval {
            type int8;
            description
              &quot;The base-2 logarithm of the mean
               announceInterval (mean time interval between
               successive Announce messages).&quot;;
          }
          leaf announce-receipt-timeout {
            type uint8;
            description
              &quot;The number of announceIntervals that have to pass
               without receipt of an Announce message before the
               occurrence of the event ANNOUNCE_RECEIPT_TIMEOUT_
               EXPIRES.&quot;;
          }
          leaf log-sync-interval {
            type int8;
            description
              &quot;The base-2 logarithm of the mean SyncInterval
               for multicast messages.  The rates for unicast
               transmissions are negotiated separately on a per-port
               basis and are not constrained by this attribute.&quot;;
          }
          leaf delay-mechanism {
            type delay-mechanism-enumeration;

<span class="grey"><a href="/doc/html/rfc8575">RFC 8575</a>                 YANG Data Model for PTP                May 2019</span>

            description
              &quot;The propagation delay measuring option used by the
               port in computing meanPathDelay.&quot;;
          }
          leaf log-min-pdelay-req-interval {
            type int8;
            description
              &quot;The base-2 logarithm of the
               minPdelayReqInterval (minimum permitted mean time
               interval between successive Pdelay_Req messages).&quot;;
          }
          leaf version-number {
            type uint8;
            description
              &quot;The PTP version in use on the port.&quot;;
          }
        }
      }
      container transparent-clock-default-ds {
        description
          &quot;The members of the transparentClockDefault data set (see
           IEEE Std 1588-2008 subclause 8.3.2).&quot;;
        reference
          &quot;IEEE Std 1588-2008: 8.3.2&quot;;
        leaf clock-identity {
          type clock-identity-type;
          config false;
          description
            &quot;The clockIdentity of the transparent clock.&quot;;
        }
        leaf number-ports {
          type uint16;
          description
            &quot;The number of PTP ports on the transparent clock.&quot;;
        }
        leaf delay-mechanism {
          type delay-mechanism-enumeration;
          description
            &quot;The propagation delay measuring option
             used by the transparent clock.&quot;;
        }
        leaf primary-domain {
          type uint8;
          default &quot;0&quot;;
          description
            &quot;The domainNumber of the primary syntonization domain (see
             IEEE Std 1588-2008 subclause 10.1).&quot;;

<span class="grey"><a href="/doc/html/rfc8575">RFC 8575</a>                 YANG Data Model for PTP                May 2019</span>

          reference
            &quot;IEEE Std 1588-2008: 10.1&quot;;
        }
      }
      list transparent-clock-port-ds-list {
        key &quot;port-number&quot;;
        description
          &quot;List of transparentClockPort data sets of the transparent
           clock (see IEEE Std 1588-2008 subclause 8.3.3).&quot;;
        reference
          &quot;IEEE Std 1588-2008: 8.3.3&quot;;
        leaf port-number {
          type uint16;
          description
            &quot;Port number.
             The data sets (i.e., information model) of IEEE Std
             1588-2008 specify a member
             transparentClockPortDS.portIdentity, which uses a typed
             struct with members clockIdentity and portNumber.

             In this YANG data model, portIdentity is not modeled in
             the transparent-clock-port-ds-list.  However, its
             members are provided as follows:
             portIdentity.portNumber is provided as this leaf member
             in transparent-clock-port-ds-list and
             portIdentity.clockIdentity is provided as the
             clock-identity leaf in transparent-clock-default-ds
             (i.e., ../../transparent-clock-default-ds/clock-
             identity).&quot;;
        }
        leaf log-min-pdelay-req-interval {
          type int8;
          description
            &quot;The logarithm to the base 2 of the
             minPdelayReqInterval (minimum permitted mean time
             interval between successive Pdelay_Req messages).&quot;;
        }
        leaf faulty-flag {
          type boolean;
          default &quot;false&quot;;
          description
            &quot;When set to true, the port is faulty.&quot;;
        }
        leaf peer-mean-path-delay {
          type time-interval-type;
          default &quot;0&quot;;

<span class="grey"><a href="/doc/html/rfc8575">RFC 8575</a>                 YANG Data Model for PTP                May 2019</span>

          description
            &quot;An estimate of the current one-way propagation delay
             on the link when the delayMechanism is P2P; otherwise,
             it is zero.&quot;;
        }
      }
    }
  }
