module ietf-mud-tls {
  yang-version 1.1;
  namespace "urn:ietf:params:xml:ns:yang:ietf-mud-tls";
  prefix ietf-mud-tls;

  import ietf-mud {
    prefix ietf-mud;
    reference
      "RFC 8520: Manufacturer Usage Description Specification";
  }

  organization
    "IETF OPSAWG (Operations and Management Area Working Group)";
  contact
    "WG Web: <https://datatracker.ietf.org/wg/opsawg/>
     WG List: opsawg@ietf.org

     Author: Tirumaleswar Reddy.K
             kondtir@gmail.com

     Author: Dan Wing
             danwing@gmail.com

     Author: Blake Anderson
             blake.anderson@cisco.com

    ";
  description
    "Extension to a MUD module to indicate (D)TLS
     profile support.

     Copyright (c) 2025 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC 9761; see
     the RFC itself for full legal notices.";

  revision 2025-04-18 {
    description
      "Initial revision.";
    reference
      "RFC 9761: Manufacturer Usage Description (MUD) for TLS and
                 DTLS Profiles for Internet of Things (IoT)
                 Devices";
  }

  augment "/ietf-mud:mud" {
    description
      "This adds an extension for a manufacturer
       to indicate whether the (D)TLS profile is
       supported by a device.";
    leaf is-tls-dtls-profile-supported {
      type boolean;
      default "false";
      description
        "This value will equal 'true' if a device supports
         (D)TLS profile.";
    }
  }
}
