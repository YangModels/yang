module ietf-complex-types {

   namespace &quot;urn:ietf:params:xml:ns:yang:ietf-complex-types&quot;;
   prefix &quot;ct&quot;;

   organization
<span class="grey"><a href="/doc/html/rfc6095">RFC 6095</a>               YANG Language Abstractions             March 2011</span>

      &quot;NETMOD WG&quot;;

    contact
      &quot;Editor:  Bernd Linowski
                &lt;<a href="mailto:bernd.linowski.ext@nsn.com">bernd.linowski.ext@nsn.com</a>&gt;
       Editor:  Mehmet Ersue
                &lt;<a href="mailto:mehmet.ersue@nsn.com">mehmet.ersue@nsn.com</a>&gt;
       Editor:  Siarhei Kuryla
                &lt;<a href="mailto:s.kuryla@gmail.com">s.kuryla@gmail.com</a>&gt;&quot;;

    description
       &quot;YANG extensions for complex types and typed instance
       identifiers.

       Copyright (c) 2011 IETF Trust and the persons identified as
       authors of the code.  All rights reserved.

       Redistribution and use in source and binary forms, with or
       without modification, is permitted pursuant to, and subject
       to the license terms contained in, the Simplified BSD License
       set forth in <a href="#section-4">Section 4</a>.c of the IETF Trust&#x27;s Legal Provisions
       Relating to IETF Documents
       (<a href="https://trustee.ietf.org/license-info">http://trustee.ietf.org/license-info</a>).

       This version of this YANG module is part of <a href="/doc/html/rfc6095">RFC 6095</a>; see
       the RFC itself for full legal notices.&quot;;

        revision 2011-03-15 {
            description &quot;Initial revision.&quot;;
        }

         extension complex-type {
             description &quot;Defines a complex-type.&quot;;
             reference &quot;<a href="#section-2.2">Section 2.2</a>, complex-type Extension Statement&quot;;
             argument type-identifier {
                 yin-element true;
             }
         }

         extension extends {
             description &quot;Defines the base type of a complex-type.&quot;;
             reference &quot;<a href="#section-2.5">Section 2.5</a>, extends Extension Statement&quot;;
             argument base-type-identifier {
                 yin-element true;
             }
         }
<span class="grey"><a href="/doc/html/rfc6095">RFC 6095</a>               YANG Language Abstractions             March 2011</span>

         extension abstract {
             description &quot;Makes the complex-type abstract.&quot;;
             reference &quot;<a href="#section-2.6">Section 2.6</a>, abstract Extension Statement&quot;;
             argument status;
         }

         extension instance {
             description &quot;Declares an instance of the given
                  complex type.&quot;;
             reference &quot;<a href="#section-2.3">Section 2.3</a>, instance Extension Statement&quot;;
             argument ct-instance-identifier {
                 yin-element true;
             }
         }

         extension instance-list {
             description &quot;Declares a list of instances of the given
                  complex type&quot;;
             reference &quot;<a href="#section-2.4">Section 2.4</a>, instance-list Extension Statement&quot;;
             argument ct-instance-identifier {
                 yin-element true;
             }
         }

         extension instance-type {
             description &quot;Tells to which type instance the instance
                          identifier refers.&quot;;
             reference &quot;<a href="#section-3.2">Section 3.2</a>, instance-type Extension Statement&quot;;
             argument target-type-identifier {
                 yin-element true;
             }
         }

         feature complex-types {
             description &quot;Indicates that the server supports
                          complex types and instance identifiers.&quot;;
         }

    }
