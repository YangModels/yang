module example-service-assurance-ip-connectivity {
  yang-version 1.1;
  namespace "urn:example:example-service-assurance-ip-connectivity";
  prefix example-ip-connectivity;

  import ietf-inet-types {
    prefix inet;
    reference
      "RFC 6991: Common YANG Data Types";
  }
  import ietf-service-assurance {
    prefix sain;
    reference
      "RFC 9418: YANG Modules for Service Assurance";
  }

  organization
    "IETF OPSAWG Working Group";
  contact
    "WG Web:   <https://datatracker.ietf.org/wg/opsawg/>
     WG List:  <mailto:opsawg@ietf.org>
     Author:   Benoit Claise  <mailto:benoit.claise@huawei.com>
     Author:   Jean Quilbeuf   <mailto:jean.quilbeuf@huawei.com>";
  description
    "This example module augments the ietf-service-assurance module
     to add support for the subservice ip-connectivity.

     It checks whether the IP connectivity between two IP addresses
     belonging to two network devices is healthy.";

  revision 2023-07-11 {
    description
      "Initial version.";
    reference
      "RFC 9418: YANG Modules for Service Assurance";
  }

  identity ip-connectivity-type {
    base sain:subservice-base;
    description
      "Checks connectivity between two IP addresses.";
  }

  augment "/sain:subservices/sain:subservice/sain:parameter" {
    when "derived-from-or-self(sain:type, 'ip-connectivity-type')";
    description
      "Augments the parameter choice from the ietf-service-assurance
       module with a case specific to the ip-connectivity
       subservice.";
    container parameters {
      description
        "Parameters for the ip-connectivity subservice type.";
      leaf device1 {
        type string;
        mandatory true;
        description
          "Device at the first end of the connection.";
      }
      leaf address1 {
        type inet:ip-address;
        mandatory true;
        description
          "Address at the first end of the connection.";
      }
      leaf device2 {
        type string;
        mandatory true;
        description
          "Device at the second end of the connection.";
      }
      leaf address2 {
        type inet:ip-address;
        mandatory true;
        description
          "Address at the second end of the connection.";
      }
    }
  }
}
