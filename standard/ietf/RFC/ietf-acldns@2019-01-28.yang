module ietf-acldns {
  yang-version 1.1;
  namespace &quot;urn:ietf:params:xml:ns:yang:ietf-acldns&quot;;
  prefix ietf-acldns;

  import ietf-access-control-list {
    prefix acl;
  }
  import ietf-inet-types {
    prefix inet;
  }

  organization
    &quot;IETF OPSAWG (Operations and Management Area Working Group)&quot;;
  contact
    &quot;WG Web: &lt;<a href="https://datatracker.ietf.org/wg/opsawg/">https://datatracker.ietf.org/wg/opsawg/</a>&gt;
     WG List: <a href="mailto:opsawg@ietf.org">opsawg@ietf.org</a>

     Author: Eliot Lear
             <a href="mailto:lear@cisco.com">lear@cisco.com</a>

     Author: Ralph Droms
             <a href="mailto:rdroms@gmail.com">rdroms@gmail.com</a>

     Author: Dan Romascanu
             <a href="mailto:dromasca@gmail.com">dromasca@gmail.com</a>
    &quot;;
  description
    &quot;This YANG module defines a component that augments the
     IETF description of an access list to allow DNS names
     as matching criteria.

     Copyright (c) 2019 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).&quot;;

  revision 2019-01-28 {
    description
      &quot;Base version of dnsname extension of the ACL model.&quot;;
<span class="grey"><a href="/doc/html/rfc8520">RFC 8520</a>             Manufacturer Usage Descriptions          March 2019</span>

       reference
         &quot;<a href="/doc/html/rfc8520">RFC 8520</a>: Manufacturer Usage Description
          Specification&quot;;
     }

     grouping dns-matches {
       description
         &quot;Domain names for matching.&quot;;
       leaf src-dnsname {
         type inet:host;
         description
           &quot;domain name to be matched against.&quot;;
       }
       leaf dst-dnsname {
         type inet:host;
         description
           &quot;domain name to be matched against.&quot;;
       }
     }

     augment &quot;/acl:acls/acl:acl/acl:aces/acl:ace/acl:matches&quot;
           + &quot;/acl:l3/acl:ipv4/acl:ipv4&quot; {
       description
         &quot;Adding domain names to matching.&quot;;
       uses dns-matches;
     }
     augment &quot;/acl:acls/acl:acl/acl:aces/acl:ace/acl:matches&quot;
           + &quot;/acl:l3/acl:ipv6/acl:ipv6&quot; {
       description
         &quot;Adding domain names to matching.&quot;;
       uses dns-matches;
     }
   }
