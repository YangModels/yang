module ietf-sztp-conveyed-info {
  yang-version 1.1;
  namespace &quot;urn:ietf:params:xml:ns:yang:ietf-sztp-conveyed-info&quot;;
  prefix sztp-info;

  import ietf-yang-types {
    prefix yang;
    reference
      &quot;<a href="/doc/html/rfc6991">RFC 6991</a>: Common YANG Data Types&quot;;
  }
  import ietf-inet-types {
    prefix inet;
    reference
      &quot;<a href="/doc/html/rfc6991">RFC 6991</a>: Common YANG Data Types&quot;;
  }
  import ietf-restconf {
    prefix rc;
    reference
      &quot;<a href="/doc/html/rfc8040">RFC 8040</a>: RESTCONF Protocol&quot;;
  }

  organization
    &quot;IETF NETCONF (Network Configuration) Working Group&quot;;
  contact
    &quot;WG Web:   &lt;<a href="https://datatracker.ietf.org/wg/netconf/">https://datatracker.ietf.org/wg/netconf/</a>&gt;
     WG List:  &lt;mailto:<a href="mailto:netconf@ietf.org">netconf@ietf.org</a>&gt;
     Author:   Kent Watsen &lt;mailto:<a href="mailto:kent%2Bietf@watsen.net">kent+ietf@watsen.net</a>&gt;&quot;;
  description
    &quot;This module defines the data model for the conveyed
     information artifact defined in <a href="/doc/html/rfc8572">RFC 8572</a> (&#x27;Secure Zero Touch
     Provisioning (SZTP)&#x27;).

     The key words &#x27;MUST&#x27;, &#x27;MUST NOT&#x27;, &#x27;REQUIRED&#x27;, &#x27;SHALL&#x27;,
     &#x27;SHALL NOT&#x27;, &#x27;SHOULD&#x27;, &#x27;SHOULD NOT&#x27;, &#x27;RECOMMENDED&#x27;,
     &#x27;NOT RECOMMENDED&#x27;, &#x27;MAY&#x27;, and &#x27;OPTIONAL&#x27; in this document
     are to be interpreted as described in <a href="/doc/html/bcp14">BCP 14</a> (<a href="/doc/html/rfc2119">RFC 2119</a>)
     (<a href="/doc/html/rfc8174">RFC 8174</a>) when, and only when, they appear in all
     capitals, as shown here.
<span class="grey"><a href="/doc/html/rfc8572">RFC 8572</a>          Secure Zero Touch Provisioning (SZTP)       April 2019</span>

       Copyright (c) 2019 IETF Trust and the persons identified as
       authors of the code.  All rights reserved.

       Redistribution and use in source and binary forms, with or
       without modification, is permitted pursuant to, and subject
       to the license terms contained in, the Simplified BSD License
       set forth in <a href="#section-4">Section 4</a>.c of the IETF Trust&#x27;s Legal Provisions
       Relating to IETF Documents
       (<a href="https://trustee.ietf.org/license-info">https://trustee.ietf.org/license-info</a>).

       This version of this YANG module is part of <a href="/doc/html/rfc8572">RFC 8572</a>; see the
       RFC itself for full legal notices.&quot;;

    revision 2019-04-30 {
      description
        &quot;Initial version&quot;;
      reference
        &quot;<a href="/doc/html/rfc8572">RFC 8572</a>: Secure Zero Touch Provisioning (SZTP)&quot;;
    }

    // identities

    identity hash-algorithm {
      description
        &quot;A base identity for hash algorithm verification.&quot;;
    }

    identity sha-256 {
      base hash-algorithm;
      description
        &quot;The SHA-256 algorithm.&quot;;
      reference
        &quot;<a href="/doc/html/rfc6234">RFC 6234</a>: US Secure Hash Algorithms&quot;;
    }

    // typedefs

    typedef cms {
      type binary;
      description
        &quot;A ContentInfo structure, as specified in <a href="/doc/html/rfc5652">RFC 5652</a>,
         encoded using ASN.1 distinguished encoding rules (DER),
         as specified in ITU-T X.690.&quot;;
      reference
        &quot;<a href="/doc/html/rfc5652">RFC 5652</a>:
           Cryptographic Message Syntax (CMS)

<span class="grey"><a href="/doc/html/rfc8572">RFC 8572</a>          Secure Zero Touch Provisioning (SZTP)       April 2019</span>

         ITU-T X.690:
           Information technology - ASN.1 encoding rules:
           Specification of Basic Encoding Rules (BER),
           Canonical Encoding Rules (CER) and Distinguished
           Encoding Rules (DER)&quot;;
    }

    // yang-data
    rc:yang-data conveyed-information {
      choice information-type {
        mandatory true;
        description
          &quot;This choice statement ensures the response contains
           redirect-information or onboarding-information.&quot;;
        container redirect-information {
          description
            &quot;Redirect information is described in <a href="/doc/html/rfc8572#section-2.1">Section&amp;nbsp;2.1 of
             RFC 8572</a>.  Its purpose is to redirect a device to
             another bootstrap server.&quot;;
          reference
            &quot;<a href="/doc/html/rfc8572">RFC 8572</a>: Secure Zero Touch Provisioning (SZTP)&quot;;
          list bootstrap-server {
            key &quot;address&quot;;
            min-elements 1;
            description
              &quot;A bootstrap server entry.&quot;;
            leaf address {
              type inet:host;
              mandatory true;
              description
                &quot;The IP address or hostname of the bootstrap server the
                 device should redirect to.&quot;;
            }
            leaf port {
              type inet:port-number;
              default &quot;443&quot;;
              description
                &quot;The port number the bootstrap server listens on.  If no
                 port is specified, the IANA-assigned port for &#x27;https&#x27;
                 (443) is used.&quot;;
            }
            leaf trust-anchor {
              type cms;
              description
                &quot;A CMS structure that MUST contain the chain of
                 X.509 certificates needed to authenticate the TLS
                 certificate presented by this bootstrap server.

<span class="grey"><a href="/doc/html/rfc8572">RFC 8572</a>          Secure Zero Touch Provisioning (SZTP)       April 2019</span>

                 The CMS MUST only contain a single chain of
                 certificates.  The bootstrap server MUST only
                 authenticate to last intermediate CA certificate
                 listed in the chain.

                 In all cases, the chain MUST include a self-signed
                 root certificate.  In the case where the root
                 certificate is itself the issuer of the bootstrap
                 server&#x27;s TLS certificate, only one certificate
                 is present.

                 If needed by the device, this CMS structure MAY
                 also contain suitably fresh revocation objects
                 with which the device can verify the revocation
                 status of the certificates.

                 This CMS encodes the degenerate form of the SignedData
                 structure that is commonly used to disseminate X.509
                 certificates and revocation objects (<a href="/doc/html/rfc5280">RFC 5280</a>).&quot;;
              reference
                &quot;<a href="/doc/html/rfc5280">RFC 5280</a>:
                   Internet X.509 Public Key Infrastructure Certificate
                   and Certificate Revocation List (CRL) Profile&quot;;
            }
          }
        }
        container onboarding-information {
          description
            &quot;Onboarding information is described in <a href="/doc/html/rfc8572#section-2.2">Section&amp;nbsp;2.2 of
             RFC 8572</a>.  Its purpose is to provide the device everything
             it needs to bootstrap itself.&quot;;
          reference
            &quot;<a href="/doc/html/rfc8572">RFC 8572</a>: Secure Zero Touch Provisioning (SZTP)&quot;;
          container boot-image {
            description
              &quot;Specifies criteria for the boot image the device MUST
               be running, as well as information enabling the device
               to install the required boot image.&quot;;
            leaf os-name {
              type string;
              description
                &quot;The name of the operating system software the device
                 MUST be running in order to not require a software
                 image upgrade (e.g., VendorOS).&quot;;
            }
            leaf os-version {
              type string;

<span class="grey"><a href="/doc/html/rfc8572">RFC 8572</a>          Secure Zero Touch Provisioning (SZTP)       April 2019</span>

              description
                &quot;The version of the operating system software the
                 device MUST be running in order to not require a
                 software image upgrade (e.g., 17.3R2.1).&quot;;
            }
            leaf-list download-uri {
              type inet:uri;
              ordered-by user;
              description
                &quot;An ordered list of URIs to where the same boot image
                 file may be obtained.  How the URI schemes (http, ftp,
                 etc.) a device supports are known is vendor specific.
                 If a secure scheme (e.g., https) is provided, a device
                 MAY establish an untrusted connection to the remote
                 server, by blindly accepting the server&#x27;s end-entity
                 certificate, to obtain the boot image.&quot;;
            }
            list image-verification {
              must &#x27;../download-uri&#x27; {
                description
                  &quot;Download URIs must be provided if an image is to
                   be verified.&quot;;
              }
              key &quot;hash-algorithm&quot;;
              description
                &quot;A list of hash values that a device can use to verify
                 boot image files with.&quot;;
              leaf hash-algorithm {
                type identityref {
                  base hash-algorithm;
                }
                description
                  &quot;Identifies the hash algorithm used.&quot;;
              }
              leaf hash-value {
                type yang:hex-string;
                mandatory true;
                description
                  &quot;The hex-encoded value of the specified hash
                   algorithm over the contents of the boot image
                   file.&quot;;
              }
            }
          }
          leaf configuration-handling {
            type enumeration {
              enum merge {

<span class="grey"><a href="/doc/html/rfc8572">RFC 8572</a>          Secure Zero Touch Provisioning (SZTP)       April 2019</span>

                description
                  &quot;Merge configuration into the running datastore.&quot;;
              }
              enum replace {
                description
                  &quot;Replace the existing running datastore with the
                   passed configuration.&quot;;
              }
            }
            must &#x27;../configuration&#x27;;
            description
              &quot;This enumeration indicates how the server should process
               the provided configuration.&quot;;
          }
          leaf pre-configuration-script {
            type script;
            description
              &quot;A script that, when present, is executed before the
               configuration has been processed.&quot;;
          }
          leaf configuration {
            type binary;
            must &#x27;../configuration-handling&#x27;;
            description
              &quot;Any configuration known to the device.  The use of
               the &#x27;binary&#x27; type enables content (e.g., XML) to be
               embedded into a JSON document.  The exact encoding
               of the content, as with the scripts, is vendor
               specific.&quot;;
          }
          leaf post-configuration-script {
            type script;
            description
              &quot;A script that, when present, is executed after the
               configuration has been processed.&quot;;
          }
        }
      }
    }

    typedef script {
      type binary;
      description
        &quot;A device-specific script that enables the execution of
         commands to perform actions not possible thru configuration
         alone.

<span class="grey"><a href="/doc/html/rfc8572">RFC 8572</a>          Secure Zero Touch Provisioning (SZTP)       April 2019</span>

         No attempt is made to standardize the contents, running
         context, or programming language of the script, other than
         that it can indicate if any warnings or errors occurred and
         can emit output.  The contents of the script are considered
         specific to the vendor, product line, and/or model of the
         device.

         If the script execution indicates that a warning occurred,
         then the device MUST assume that the script had a soft error
         that the script believes will not affect manageability.

         If the script execution indicates that an error occurred,
         the device MUST assume the script had a hard error that the
         script believes will affect manageability.  In this case,
         the script is required to gracefully exit, removing any
         state that might hinder the device&#x27;s ability to continue
         the bootstrapping sequence (e.g., process onboarding
         information obtained from another bootstrap server).&quot;;
    }
  }
