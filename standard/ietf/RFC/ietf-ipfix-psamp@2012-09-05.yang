module ietf-ipfix-psamp {
  namespace &quot;urn:ietf:params:xml:ns:yang:ietf-ipfix-psamp&quot;;
  prefix ipfix;

  import ietf-yang-types { prefix yang; }
  import ietf-inet-types { prefix inet; }

  organization
    &quot;IETF IPFIX Working Group&quot;;

  contact
    &quot;WG Web:  &lt;<a href="https://tools.ietf.org/wg/ipfix/">http://tools.ietf.org/wg/ipfix/</a>&gt;
    WG List:  &lt;<a href="mailto:ipfix@ietf.org">ipfix@ietf.org</a>&gt;

    WG Chair: Nevil Brownlee
              &lt;<a href="mailto:n.brownlee@auckland.ac.nz">n.brownlee@auckland.ac.nz</a>&gt;

<span class="grey"><a href="/doc/html/rfc6728">RFC 6728</a>          IPFIX/PSAMP Configuration Data Model      October 2012</span>

      WG Chair: Juergen Quittek
                &lt;<a href="mailto:quittek@neclab.eu">quittek@neclab.eu</a>&gt;

      Editor:   Gerhard Muenz
                &lt;<a href="mailto:muenz@net.in.tum.de">muenz@net.in.tum.de</a>&gt;&quot;;

    description
      &quot;IPFIX/PSAMP Configuration Data Model

      Copyright (c) 2012 IETF Trust and the persons identified as
      the document authors.  All rights reserved.
      Redistribution and use in source and binary forms, with or
      without modification, is permitted pursuant to, and subject
      to the license terms contained in, the Simplified BSD License
      set forth in <a href="#section-4">Section 4</a>.c of the IETF Trust&#x27;s Legal Provisions
      Relating to IETF Documents
      (<a href="https://trustee.ietf.org/license-info">http://trustee.ietf.org/license-info</a>).&quot;;

    revision 2012-09-05 {
      description &quot;Initial version&quot;;
      reference &quot;<a href="/doc/html/rfc6728">RFC 6728</a>: Configuration Data Model for the IP Flow
        Information Export (IPFIX) and Packet Sampling (PSAMP)
        Protocols&quot;;
    }

    /*****************************************************************
    * Features
    *****************************************************************/

    feature exporter {
      description &quot;If supported, the Monitoring Device can be used as
        an Exporter.  Exporting Processes can be configured.&quot;;
    }

    feature collector {
      description &quot;If supported, the Monitoring Device can be used as
        a Collector.  Collecting Processes can be configured.&quot;;
    }

    feature meter {
      description &quot;If supported, Observation Points, Selection
        Processes, and Caches can be configured.&quot;;
    }

    feature psampSampCountBased {
      description &quot;If supported, the Monitoring Device supports
        count-based Sampling.  The Selector method sampCountBased can
        be configured.&quot;;
<span class="grey"><a href="/doc/html/rfc6728">RFC 6728</a>          IPFIX/PSAMP Configuration Data Model      October 2012</span>

    }

    feature psampSampTimeBased {
      description &quot;If supported, the Monitoring Device supports
        time-based Sampling.  The Selector method sampTimeBased can
        be configured.&quot;;
    }

    feature psampSampRandOutOfN {
      description &quot;If supported, the Monitoring Device supports
        random n-out-of-N Sampling.  The Selector method
        sampRandOutOfN can be configured.&quot;;
    }

    feature psampSampUniProb {
      description &quot;If supported, the Monitoring Device supports
        uniform probabilistic Sampling.  The Selector method
        sampUniProb can be configured.&quot;;
    }

    feature psampFilterMatch {
      description &quot;If supported, the Monitoring Device supports
        property match Filtering.  The Selector method filterMatch
        can be configured.&quot;;
    }

    feature psampFilterHash {
      description &quot;If supported, the Monitoring Device supports
        hash-based Filtering.  The Selector method filterHash can be
        configured.&quot;;
    }

    feature immediateCache {
      description &quot;If supported, the Monitoring Device supports
        Caches generating PSAMP Packet Reports by configuration with
        immediateCache.&quot;;
    }

    feature timeoutCache {
      description &quot;If supported, the Monitoring Device supports
        Caches generating IPFIX Flow Records by configuration with
        timeoutCache.&quot;;
    }

    feature naturalCache {
      description &quot;If supported, the Monitoring Device supports
        Caches generating IPFIX Flow Records by configuration with
        naturalCache.&quot;;
<span class="grey"><a href="/doc/html/rfc6728">RFC 6728</a>          IPFIX/PSAMP Configuration Data Model      October 2012</span>

    }

    feature permanentCache {
      description &quot;If supported, the Monitoring Device supports
        Caches generating IPFIX Flow Records by configuration with
        permanentCache.&quot;;
    }

    feature udpTransport {
      description &quot;If supported, the Monitoring Device supports UDP
        as the transport protocol.&quot;;
    }

    feature tcpTransport {
      description &quot;If supported, the Monitoring Device supports TCP
        as the transport protocol.&quot;;
    }

    feature fileReader {
      description &quot;If supported, the Monitoring Device supports the
        configuration of Collecting Processes as File Readers.&quot;;
    }

    feature fileWriter {
      description &quot;If supported, the Monitoring Device supports the
        configuration of Exporting Processes as File Writers.&quot;;
    }

    /*****************************************************************
    * Identities
    *****************************************************************/

    /*** Hash function identities ***/
    identity hashFunction {
      description &quot;Base identity for all hash functions used for
        hash-based packet Filtering.  Identities derived from
        this base are used by the leaf
        /ipfix/selectionProcess/selector/filterHash/hashFunction.&quot;;
    }
    identity BOB {
      base &quot;hashFunction&quot;;
      description &quot;BOB hash function&quot;;
      reference &quot;<a href="/doc/html/rfc5475#section-6.2.4.1">RFC 5475, Section&amp;nbsp;6.2.4.1</a>.&quot;;
    }
    identity IPSX {
      base &quot;hashFunction&quot;;
      description &quot;IPSX hash function&quot;;
      reference &quot;<a href="/doc/html/rfc5475#section-6.2.4.1">RFC 5475, Section&amp;nbsp;6.2.4.1</a>.&quot;;
<span class="grey"><a href="/doc/html/rfc6728">RFC 6728</a>          IPFIX/PSAMP Configuration Data Model      October 2012</span>

    }
    identity CRC {
      base &quot;hashFunction&quot;;
      description &quot;CRC hash function&quot;;
      reference &quot;<a href="/doc/html/rfc5475#section-6.2.4.1">RFC 5475, Section&amp;nbsp;6.2.4.1</a>.&quot;;
    }

    /*** Export mode identities ***/
    identity exportMode {
      description &quot;Base identity for different usages of export
        destinations configured for an Exporting Process.
        Identities derived from this base are used by the leaf
        /ipfix/exportingProcess/exportMode.&quot;;
    }
    identity parallel {
      base &quot;exportMode&quot;;
      description &quot;Parallel export of Data Records to all
        destinations configured for the Exporting Process.&quot;;
    }
    identity loadBalancing {
      base &quot;exportMode&quot;;
      description &quot;Load-balancing between the different destinations
        configured for the Exporting Process.&quot;;
    }
    identity fallback {
      base &quot;exportMode&quot;;
      description &quot;Export to the primary destination (i.e., the first
        SCTP, UDP, TCP, or file destination configured for the
        Exporting Process).  If the export to the primary destination
        fails, the Exporting Process tries to export to the secondary
        destination.  If the secondary destination fails as well, it
        continues with the tertiary, etc.&quot;;
    }

    /*** Options type identities ***/
    identity optionsType {
      description &quot;Base identity for report types exported with
        options.  Identities derived from this base are used by the leaf
        /ipfix/exportingProcess/options/optionsType.&quot;;
    }
    identity meteringStatistics {
      base &quot;optionsType&quot;;
      description &quot;Metering Process Statistics.&quot;;
      reference &quot;<a href="/doc/html/rfc5101#section-4.1">RFC 5101, Section&amp;nbsp;4.1</a>.&quot;;
    }
    identity meteringReliability {
      base &quot;optionsType&quot;;
      description &quot;Metering Process Reliability Statistics.&quot;;
<span class="grey"><a href="/doc/html/rfc6728">RFC 6728</a>          IPFIX/PSAMP Configuration Data Model      October 2012</span>

      reference &quot;<a href="/doc/html/rfc5101#section-4.2">RFC 5101, Section&amp;nbsp;4.2</a>.&quot;;
    }
    identity exportingReliability {
      base &quot;optionsType&quot;;
      description &quot;Exporting Process Reliability
        Statistics.&quot;;
      reference &quot;<a href="/doc/html/rfc5101#section-4.3">RFC 5101, Section&amp;nbsp;4.3</a>.&quot;;
    }
    identity flowKeys {
      base &quot;optionsType&quot;;
      description &quot;Flow Keys.&quot;;
      reference &quot;<a href="/doc/html/rfc5101#section-4.4">RFC 5101, Section&amp;nbsp;4.4</a>.&quot;;
    }
    identity selectionSequence {
      base &quot;optionsType&quot;;
      description &quot;Selection Sequence and Selector Reports.&quot;;
      reference &quot;<a href="/doc/html/rfc5476">RFC 5476</a>, Sections <a href="#section-6.5.1">6.5.1</a> and <a href="#section-6.5.2">6.5.2</a>.&quot;;
    }
    identity selectionStatistics {
      base &quot;optionsType&quot;;
      description &quot;Selection Sequence Statistics Report.&quot;;
      reference &quot;<a href="/doc/html/rfc5476">RFC 5476</a>, Sections <a href="#section-6.5.3">6.5.3</a>.&quot;;
    }
    identity accuracy {
      base &quot;optionsType&quot;;
      description &quot;Accuracy Report.&quot;;
      reference &quot;<a href="/doc/html/rfc5476#section-6.5.4">RFC 5476, Section&amp;nbsp;6.5.4</a>.&quot;;
    }
    identity reducingRedundancy {
      base &quot;optionsType&quot;;
      description &quot;Enables the utilization of Options Templates to
        reduce redundancy in the exported Data Records.&quot;;
      reference &quot;<a href="/doc/html/rfc5473">RFC 5473</a>.&quot;;
    }
    identity extendedTypeInformation {
      base &quot;optionsType&quot;;
      description &quot;Export of extended type information for
        enterprise-specific Information Elements used in the
        exported Templates.&quot;;
      reference &quot;<a href="/doc/html/rfc5610">RFC 5610</a>.&quot;;
    }

    /*****************************************************************
    * Type definitions
    *****************************************************************/

    typedef ieNameType {
      type string {
<span class="grey"><a href="/doc/html/rfc6728">RFC 6728</a>          IPFIX/PSAMP Configuration Data Model      October 2012</span>

        length &quot;1..max&quot;;
        pattern &quot;\S+&quot;;
      }
      description &quot;Type for Information Element names.  Whitespaces
        are not allowed.&quot;;
    }

    typedef ieIdType {
      type uint16 {
        range &quot;1..32767&quot; {
          description &quot;Valid range of Information Element
              identifiers.&quot;;
          reference &quot;<a href="/doc/html/rfc5102#section-4">RFC 5102, Section&amp;nbsp;4</a>.&quot;;
        }
      }
      description &quot;Type for Information Element identifiers.&quot;;
    }

    typedef nameType {
      type string {
        length &quot;1..max&quot;;
        pattern &quot;\S(.*\S)?&quot;;
      }
      description &quot;Type for &#x27;name&#x27; leafs, which are used to identify
        specific instances within lists, etc.
        Leading and trailing whitespaces are not allowed.&quot;;
    }

    typedef ifNameType {
      type string {
        length &quot;1..255&quot;;
      }
      description &quot;This corresponds to the DisplayString textual
        convention of SNMPv2-TC, which is used for ifName in the IF
        MIB module.&quot;;
      reference &quot;<a href="/doc/html/rfc2863">RFC 2863</a> (ifName).&quot;;
    }

    typedef direction {
      type enumeration {
        enum ingress {
          description &quot;This value is used for monitoring incoming
            packets.&quot;;
        }
        enum egress {
          description &quot;This value is used for monitoring outgoing
            packets.&quot;;
        }
<span class="grey"><a href="/doc/html/rfc6728">RFC 6728</a>          IPFIX/PSAMP Configuration Data Model      October 2012</span>

        enum both {
          description &quot;This value is used for monitoring incoming and
            outgoing packets.&quot;;
        }
      }
      description &quot;Direction of packets going through an interface or
        linecard.&quot;;
    }

    typedef transportSessionStatus {
      type enumeration {
        enum inactive {
          description &quot;This value MUST be used for Transport Sessions
            that are specified in the system but currently not active.
            The value can be used for Transport Sessions that are
            backup (secondary) sessions.&quot;;
        }
        enum active {
          description &quot;This value MUST be used for Transport Sessions
            that are currently active and transmitting or receiving
            data.&quot;;
        }
        enum unknown {
          description &quot;This value MUST be used if the status of the
            Transport Sessions cannot be detected by the device.  This
            value should be avoided as far as possible.&quot;;
        }
      }
      description &quot;Status of a Transport Session.&quot;;
      reference &quot;<a href="/doc/html/rfc6615#section-8">RFC 6615, Section&amp;nbsp;8</a> (ipfixTransportSessionStatus).&quot;;
    }

    /*****************************************************************
    * Groupings
    *****************************************************************/

    grouping observationPointParameters {
      description &quot;Interface as input to Observation Point.&quot;;
      leaf observationPointId {
        type uint32;
        config false;
        description &quot;Observation Point ID (i.e., the value of the
          Information Element observationPointId) assigned by the
          Monitoring Device.&quot;;
        reference &quot;IANA registry for IPFIX Entities,
          <a href="https://www.iana.org/assignments/ipfix">http://www.iana.org/assignments/ipfix</a>.&quot;;
      }
      leaf observationDomainId {
<span class="grey"><a href="/doc/html/rfc6728">RFC 6728</a>          IPFIX/PSAMP Configuration Data Model      October 2012</span>

        type uint32;
        mandatory true;
        description &quot;The Observation Domain ID associates the
          Observation Point to an Observation Domain.  Observation
          Points with identical Observation Domain IDs belong to the
          same Observation Domain.
          Note that this parameter corresponds to
          ipfixObservationPointObservationDomainId in the IPFIX MIB
          module.&quot;;
        reference &quot;<a href="/doc/html/rfc5101">RFC 5101</a>; <a href="/doc/html/rfc6615#section-8">RFC 6615, Section&amp;nbsp;8</a>
          (ipfixObservationPointObservationDomainId).&quot;;
      }
      leaf-list ifName {
        type ifNameType;
        description &quot;List of names identifying interfaces of the
          Monitoring Device.  The Observation Point observes packets at
          the specified interfaces.&quot;;
      }
      leaf-list ifIndex {
        type uint32;
        description &quot;List of ifIndex values pointing to entries in the
          ifTable of the IF-MIB module maintained by the Monitoring
          Device.  The Observation Point observes packets at the
          specified interfaces.
          This parameter SHOULD only be used if an SNMP agent enables
          access to the ifTable.
          Note that this parameter corresponds to
          ipfixObservationPointPhysicalInterface in the IPFIX MIB
          module.&quot;;
        reference &quot;<a href="/doc/html/rfc2863">RFC 2863</a>; <a href="/doc/html/rfc6615#section-8">RFC 6615, Section&amp;nbsp;8</a>
          (ipfixObservationPointPhysicalInterface).&quot;;
      }
      leaf-list entPhysicalName {
        type string;
        description &quot;List of names identifying physical entities of the
          Monitoring Device.  The Observation Point observes packets at
          the specified entities.&quot;;
      }
      leaf-list entPhysicalIndex {
        type uint32;
        description &quot;List of entPhysicalIndex values pointing to
          entries in the entPhysicalTable of the ENTITY-MIB module
          maintained by the Monitoring Device.  The Observation Point
          observes packets at the specified entities.
          This parameter SHOULD only be used if an SNMP agent enables
          access to the entPhysicalTable.
          Note that this parameter corresponds to
          ipfixObservationPointPhysicalEntity in the IPFIX MIB
<span class="grey"><a href="/doc/html/rfc6728">RFC 6728</a>          IPFIX/PSAMP Configuration Data Model      October 2012</span>

          module.&quot;;
        reference &quot;<a href="/doc/html/rfc4133">RFC 4133</a>; <a href="/doc/html/rfc6615#section-8">RFC 6615, Section&amp;nbsp;8</a>
          (ipfixObservationPointPhysicalInterface).&quot;;
      }
      leaf direction {
        type direction;
        default both;
        description &quot;Direction of packets.  If not applicable (e.g., in
          the case of a sniffing interface in promiscuous mode), this
          parameter is ignored.&quot;;
      }
    }

    grouping sampCountBasedParameters {
      description &quot;Configuration parameters of a Selector applying
        systematic count-based packet Sampling to the packet
        stream.&quot;;
      reference &quot;<a href="/doc/html/rfc5475#section-5.1">RFC 5475, Section&amp;nbsp;5.1</a>; <a href="/doc/html/rfc5476#section-6.5.2.1">RFC 5476, Section&amp;nbsp;6.5.2.1</a>.&quot;;
      leaf packetInterval {
        type uint32;
        units packets;
        mandatory true;
        description &quot;The number of packets that are consecutively
          sampled between gaps of length packetSpace.
          This parameter corresponds to the Information Element
          samplingPacketInterval and to psampSampCountBasedInterval
          in the PSAMP MIB module.&quot;;
        reference &quot;<a href="/doc/html/rfc5477#section-8.2.2">RFC 5477, Section&amp;nbsp;8.2.2</a>; <a href="/doc/html/rfc6727#section-6">RFC 6727, Section&amp;nbsp;6</a>
          (psampSampCountBasedInterval).&quot;;
      }
      leaf packetSpace {
        type uint32;
        units packets;
        mandatory true;
        description &quot;The number of unsampled packets between two
          Sampling intervals.
          This parameter corresponds to the Information Element
          samplingPacketSpace and to psampSampCountBasedSpace
          in the PSAMP MIB module.&quot;;
        reference &quot;<a href="/doc/html/rfc5477#section-8.2.3">RFC 5477, Section&amp;nbsp;8.2.3</a>; <a href="/doc/html/rfc6727#section-6">RFC 6727, Section&amp;nbsp;6</a>
          (psampSampCountBasedSpace).&quot;;
      }
    }

    grouping sampTimeBasedParameters {
      description &quot;Configuration parameters of a Selector applying
        systematic time-based packet Sampling to the packet
        stream.&quot;;
<span class="grey"><a href="/doc/html/rfc6728">RFC 6728</a>          IPFIX/PSAMP Configuration Data Model      October 2012</span>

      reference &quot;<a href="/doc/html/rfc5475#section-5.1">RFC 5475, Section&amp;nbsp;5.1</a>; <a href="/doc/html/rfc5476#section-6.5.2.2">RFC 5476, Section&amp;nbsp;6.5.2.2</a>.&quot;;
      leaf timeInterval {
        type uint32;
        units microseconds;
        mandatory true;
        description &quot;The time interval in microseconds during
          which all arriving packets are sampled between gaps
          of length timeSpace.
          This parameter corresponds to the Information Element
          samplingTimeInterval and to psampSampTimeBasedInterval
          in the PSAMP MIB module.&quot;;
        reference &quot;<a href="/doc/html/rfc5477#section-8.2.4">RFC 5477, Section&amp;nbsp;8.2.4</a>; <a href="/doc/html/rfc6727#section-6">RFC 6727, Section&amp;nbsp;6</a>
          (psampSampTimeBasedInterval).&quot;;
      }
      leaf timeSpace {
        type uint32;
        units microseconds;
        mandatory true;
        description &quot;The time interval in microseconds during
          which no packets are sampled between two Sampling
          intervals specified by timeInterval.
          This parameter corresponds to the Information Element
          samplingTimeInterval and to psampSampTimeBasedSpace
          in the PSAMP MIB module.&quot;;
        reference &quot;<a href="/doc/html/rfc5477#section-8.2.5">RFC 5477, Section&amp;nbsp;8.2.5</a>; <a href="/doc/html/rfc6727#section-6">RFC 6727, Section&amp;nbsp;6</a>
          (psampSampTimeBasedSpace).&quot;;
      }
    }

    grouping sampRandOutOfNParameters {
      description &quot;Configuration parameters of a Selector applying
        n-out-of-N packet Sampling to the packet stream.&quot;;
      reference &quot;<a href="/doc/html/rfc5475#section-5.2.1">RFC 5475, Section&amp;nbsp;5.2.1</a>; <a href="/doc/html/rfc5476#section-6.5.2.3">RFC 5476, Section&amp;nbsp;6.5.2.3</a>.&quot;;
      leaf size {
        type uint32;
        units packets;
        mandatory true;
        description &quot;The number of elements taken from the parent
          population.
          This parameter corresponds to the Information Element
          samplingSize and to psampSampRandOutOfNSize in the PSAMP
          MIB module.&quot;;
        reference &quot;<a href="/doc/html/rfc5477#section-8.2.6">RFC 5477, Section&amp;nbsp;8.2.6</a>; <a href="/doc/html/rfc6727#section-6">RFC 6727, Section&amp;nbsp;6</a>
          (psampSampRandOutOfNSize).&quot;;
      }
      leaf population {
        type uint32;
        units packets;
<span class="grey"><a href="/doc/html/rfc6728">RFC 6728</a>          IPFIX/PSAMP Configuration Data Model      October 2012</span>

        mandatory true;
        description &quot;The number of elements in the parent
          population.
          This parameter corresponds to the Information Element
          samplingPopulation and to psampSampRandOutOfNPopulation
          in the PSAMP MIB module.&quot;;
        reference &quot;<a href="/doc/html/rfc5477#section-8.2.7">RFC 5477, Section&amp;nbsp;8.2.7</a>; <a href="/doc/html/rfc6727#section-6">RFC 6727, Section&amp;nbsp;6</a>
          (psampSampRandOutOfNPopulation).&quot;;
      }
    }

    grouping sampUniProbParameters {
      description &quot;Configuration parameters of a Selector applying
        uniform probabilistic packet Sampling (with equal
        probability per packet) to the packet stream.&quot;;
      reference &quot;<a href="/doc/html/rfc5475#section-5.2.2.1">RFC 5475, Section&amp;nbsp;5.2.2.1</a>;
        <a href="/doc/html/rfc5476#section-6.5.2.4">RFC 5476, Section&amp;nbsp;6.5.2.4</a>.&quot;;
      leaf probability {
        type decimal64 {
          fraction-digits 18;
          range &quot;0..1&quot;;
        }
        mandatory true;
        description &quot;Probability that a packet is sampled,
          expressed as a value between 0 and 1.  The probability
          is equal for every packet.
          This parameter corresponds to the Information Element
          samplingProbability and to psampSampUniProbProbability
          in the PSAMP MIB module.&quot;;
        reference &quot;<a href="/doc/html/rfc5477#section-8.2.8">RFC 5477, Section&amp;nbsp;8.2.8</a>; <a href="/doc/html/rfc6727#section-6">RFC 6727, Section&amp;nbsp;6</a>
          (psampSampUniProbProbability).&quot;;
      }
    }

    grouping filterMatchParameters {
      description &quot;Configuration parameters of a Selector applying
        property match Filtering to the packet stream.
        The field to be matched is specified as an Information
        Element.&quot;;
      reference &quot;<a href="/doc/html/rfc5475#section-6.1">RFC 5475, Section&amp;nbsp;6.1</a>; <a href="/doc/html/rfc5476#section-6.5.2.5">RFC 5476, Section&amp;nbsp;6.5.2.5</a>.&quot;;
      choice nameOrId {
        mandatory true;
        description &quot;The field to be matched is specified by
          either the name or the identifier of the Information
          Element.&quot;;
        leaf ieName {
          type ieNameType;
          description &quot;Name of the Information Element.&quot;;
<span class="grey"><a href="/doc/html/rfc6728">RFC 6728</a>          IPFIX/PSAMP Configuration Data Model      October 2012</span>

        }
        leaf ieId {
          type ieIdType;
          description &quot;Identifier of the Information Element.&quot;;
        }
      }
      leaf ieEnterpriseNumber {
        type uint32;
        default 0;
        description &quot;If this parameter is zero, the Information
          Element is registered in the IANA registry of IPFIX
          Information Elements.
          If this parameter is configured with a non-zero private
          enterprise number, the Information Element is
          enterprise-specific.&quot;;
        reference &quot;IANA registry for Private Enterprise Numbers,
          <a href="http://www.iana">http://www.iana</a>.org/assignments/enterprise-numbers;
          IANA registry for IPFIX Entities,
          <a href="https://www.iana.org/assignments/ipfix">http://www.iana.org/assignments/ipfix</a>.&quot;;
      }
      leaf value {
        type string;
        mandatory true;
        description &quot;Matching value of the Information Element.&quot;;
      }
    }

    grouping filterHashParameters {
      description &quot;Configuration parameters of a Selector applying
        hash-based Filtering to the packet stream.&quot;;
      reference &quot;<a href="/doc/html/rfc5475#section-6.2">RFC 5475, Section&amp;nbsp;6.2</a>; <a href="/doc/html/rfc5476#section-6.5.2.6">RFC 5476, Section&amp;nbsp;6.5.2.6</a>.&quot;;
      leaf hashFunction {
        type identityref {
          base &quot;hashFunction&quot;;
        }
        default BOB;
        description &quot;Hash function to be applied.  According to
          <a href="/doc/html/rfc5475#section-6.2.4.1">RFC 5475, Section&amp;nbsp;6.2.4.1</a>, &#x27;BOB&#x27; must be used in order to
          be compliant with PSAMP.
          This parameter functionally corresponds to
          psampFiltHashFunction in the PSAMP MIB module.&quot;;
        reference &quot;<a href="/doc/html/rfc6727#section-6">RFC 6727, Section&amp;nbsp;6</a> (psampFiltHashFunction)&quot;;
      }
      leaf initializerValue {
        type uint64;
        description &quot;Initializer value to the hash function.
          If not configured by the user, the Monitoring Device
          arbitrarily chooses an initializer value.
<span class="grey"><a href="/doc/html/rfc6728">RFC 6728</a>          IPFIX/PSAMP Configuration Data Model      October 2012</span>

          This parameter corresponds to the Information Element
          hashInitialiserValue and to psampFiltHashInitializerValue
          in the PSAMP MIB module.&quot;;
        reference &quot;<a href="/doc/html/rfc5477#section-8.3.9">RFC 5477, Section&amp;nbsp;8.3.9</a>; <a href="/doc/html/rfc6727#section-6">RFC 6727, Section&amp;nbsp;6</a>
          (psampFiltHashInitializerValue).&quot;;
      }
      leaf ipPayloadOffset {
        type uint64;
        units octets;
        default 0;
        description &quot;IP payload offset indicating the position of
          the first payload byte considered as input to the hash
          function.
          Default value 0 corresponds to the minimum offset that
          must be configurable according to <a href="/doc/html/rfc5476#section-6.5.2.6">RFC 5476, Section&amp;nbsp;</a>
          <a href="#section-6.5.2.6">6.5.2.6</a>.
          This parameter corresponds to the Information Element
          hashIPPayloadOffset and to psampFiltHashIpPayloadOffset
          in the PSAMP MIB module.&quot;;
        reference &quot;<a href="/doc/html/rfc5477#section-8.3.2">RFC 5477, Section&amp;nbsp;8.3.2</a>; <a href="/doc/html/rfc6727#section-6">RFC 6727, Section&amp;nbsp;6</a>
          (psampFiltHashIpPayloadOffset).&quot;;
      }
      leaf ipPayloadSize {
        type uint64;
        units octets;
        default 8;
        description &quot;Number of IP payload bytes used as input to
          the hash function, counted from the payload offset.
          If the IP payload is shorter than the payload range,
          all available payload octets are used as input.
          Default value 8 corresponds to the minimum IP payload
          size that must be configurable according to <a href="/doc/html/rfc5476#section-6.5.2.6">RFC 5476,
          Section&amp;nbsp;6.5.2.6</a>.
          This parameter corresponds to the Information Element
          hashIPPayloadSize and to psampFiltHashIpPayloadSize
          in the PSAMP MIB module.&quot;;
        reference &quot;<a href="/doc/html/rfc5477#section-8.3.3">RFC 5477, Section&amp;nbsp;8.3.3</a>; <a href="/doc/html/rfc6727#section-6">RFC 6727, Section&amp;nbsp;6</a>
          (psampFiltHashIpPayloadSize).&quot;;
      }
      leaf digestOutput {
        type boolean;
        default false;
        description &quot;If true, the output from this Selector is
          included in the Packet Report as a packet digest.
          Therefore, the configured Cache Layout needs to contain
          a digestHashValue field.
          This parameter corresponds to the Information Element
          hashDigestOutput.&quot;;
<span class="grey"><a href="/doc/html/rfc6728">RFC 6728</a>          IPFIX/PSAMP Configuration Data Model      October 2012</span>

        reference &quot;<a href="/doc/html/rfc5477#section-8.3.8">RFC 5477, Section&amp;nbsp;8.3.8</a>.&quot;;
      }
      leaf outputRangeMin {
        type uint64;
        config false;
        description &quot;Beginning of the hash function&#x27;s potential
          range.
          This parameter corresponds to the Information Element
          hashOutputRangeMin and to psampFiltHashOutputRangeMin
          in the PSAMP MIB module.&quot;;
        reference &quot;<a href="/doc/html/rfc5477#section-8.3.4">RFC 5477, Section&amp;nbsp;8.3.4</a>; <a href="/doc/html/rfc6727#section-6">RFC 6727, Section&amp;nbsp;6</a>
          (psampFiltHashOutputRangeMin).&quot;;
      }
      leaf outputRangeMax {
        type uint64;
        config false;
        description &quot;End of the hash function&#x27;s potential range.
          This parameter corresponds to the Information Element
          hashOutputRangeMax and to psampFiltHashOutputRangeMax
          in the PSAMP MIB module.&quot;;
        reference &quot;<a href="/doc/html/rfc5477#section-8.3.5">RFC 5477, Section&amp;nbsp;8.3.5</a>; <a href="/doc/html/rfc6727#section-6">RFC 6727, Section&amp;nbsp;6</a>
          (psampFiltHashOutputRangeMax).&quot;;
      }
      list selectedRange {
        key name;
        min-elements 1;
        description &quot;List of hash function return ranges for
          which packets are selected.&quot;;
        leaf name {
          type nameType;
          description &quot;Key of this list.&quot;;
        }
        leaf min {
          type uint64;
          description &quot;Beginning of the hash function&#x27;s selected
            range.
            This parameter corresponds to the Information Element
            hashSelectedRangeMin and to psampFiltHashSelectedRangeMin
            in the PSAMP MIB module.&quot;;
          reference &quot;<a href="/doc/html/rfc5477#section-8.3.6">RFC 5477, Section&amp;nbsp;8.3.6</a>; <a href="/doc/html/rfc6727#section-6">RFC 6727, Section&amp;nbsp;6</a>
          (psampFiltHashSelectedRangeMin).&quot;;
        }
        leaf max {
          type uint64;
          description &quot;End of the hash function&#x27;s selected range.
            This parameter corresponds to the Information Element
            hashSelectedRangeMax and to psampFiltHashSelectedRangeMax
            in the PSAMP MIB module.&quot;;
<span class="grey"><a href="/doc/html/rfc6728">RFC 6728</a>          IPFIX/PSAMP Configuration Data Model      October 2012</span>

          reference &quot;<a href="/doc/html/rfc5477#section-8.3.7">RFC 5477, Section&amp;nbsp;8.3.7</a>; <a href="/doc/html/rfc6727#section-6">RFC 6727, Section&amp;nbsp;6</a>
          (psampFiltHashSelectedRangeMax).&quot;;
        }
      }
    }

    grouping selectorParameters {
      description &quot;Configuration and state parameters of a Selector.&quot;;
      choice Method {
        mandatory true;
        description &quot;Packet selection method applied by the Selector.&quot;;
        leaf selectAll {
          type empty;
          description &quot;Method that selects all packets.&quot;;
        }
        container sampCountBased {
          if-feature psampSampCountBased;
          description &quot;Systematic count-based packet Sampling.&quot;;
          uses sampCountBasedParameters;
        }
        container sampTimeBased {
          if-feature psampSampTimeBased;
          description &quot;Systematic time-based packet Sampling.&quot;;
          uses sampTimeBasedParameters;
        }
        container sampRandOutOfN {
          if-feature psampSampRandOutOfN;
          description &quot;n-out-of-N packet Sampling.&quot;;
          uses sampRandOutOfNParameters;
        }
        container sampUniProb {
          if-feature psampSampUniProb;
          description &quot;Uniform probabilistic packet Sampling.&quot;;
          uses sampUniProbParameters;
        }
        container filterMatch {
          if-feature psampFilterMatch;
          description &quot;Property match Filtering.&quot;;
          uses filterMatchParameters;
        }
        container filterHash {
          if-feature psampFilterHash;
          description &quot;Hash-based Filtering.&quot;;
          uses filterHashParameters;
        }
      }
      leaf packetsObserved {
        type yang:counter64;
<span class="grey"><a href="/doc/html/rfc6728">RFC 6728</a>          IPFIX/PSAMP Configuration Data Model      October 2012</span>

        config false;
        description &quot;The number of packets observed at the input of
          the Selector.
          If this is the first Selector in the Selection Process,
          this counter corresponds to the total number of packets in
          all Observed Packet Streams at the input of the Selection
          Process.  Otherwise, the counter corresponds to the total
          number of packets at the output of the preceding Selector.
          Discontinuities in the value of this counter can occur at
          re-initialization of the management system, and at other
          times as indicated by the value of
          selectorDiscontinuityTime.
          Note that this parameter corresponds to
          ipfixSelectorStatsPacketsObserved in the IPFIX MIB
          module.&quot;;
        reference &quot;<a href="/doc/html/rfc6615#section-8">RFC 6615, Section&amp;nbsp;8</a>
          (ipfixSelectorStatsPacketsObserved).&quot;;
      }
      leaf packetsDropped {
        type yang:counter64;
        config false;
        description &quot;The total number of packets discarded by the
          Selector.
          Discontinuities in the value of this counter can occur at
          re-initialization of the management system, and at other
          times as indicated by the value of
          selectorDiscontinuityTime.
          Note that this parameter corresponds to
          ipfixSelectorStatsPacketsDropped in the IPFIX MIB
          module.&quot;;
        reference &quot;<a href="/doc/html/rfc6615#section-8">RFC 6615, Section&amp;nbsp;8</a>
          (ipfixSelectorStatsPacketsDropped).&quot;;
      }
      leaf selectorDiscontinuityTime {
        type yang:date-and-time;
        config false;
        description &quot;Timestamp of the most recent occasion at which
          one or more of the Selector counters suffered a
          discontinuity.
          Note that this parameter functionally corresponds to
          ipfixSelectionProcessStatsDiscontinuityTime in the IPFIX
          MIB module.  In contrast to
          ipfixSelectionProcessStatsDiscontinuityTime, the time is
          absolute and not relative to sysUpTime.&quot;;
        reference &quot;<a href="/doc/html/rfc6615#section-8">RFC 6615, Section&amp;nbsp;8</a>
          (ipfixSelectionProcessStatsDiscontinuityTime).&quot;;
      }
    }
<span class="grey"><a href="/doc/html/rfc6728">RFC 6728</a>          IPFIX/PSAMP Configuration Data Model      October 2012</span>

    grouping cacheLayoutParameters {
      description &quot;Cache Layout parameters used by immediateCache,
        timeoutCache, naturalCache, and permanentCache.&quot;;
      container cacheLayout {
        description &quot;Cache Layout parameters.&quot;;
        list cacheField {
          key name;
          min-elements 1;
          description &quot;Superset of fields that are included in the
            Packet Reports or Flow Records generated by the Cache.&quot;;
          leaf name {
            type nameType;
            description &quot;Key of this list.&quot;;
          }
          choice nameOrId {
            mandatory true;
            description &quot;Name or identifier of the Information
              Element.&quot;;
            reference &quot;<a href="/doc/html/rfc5102#section-2">RFC 5102, Section&amp;nbsp;2</a>; IANA registry for IPFIX
              Entities, <a href="https://www.iana.org/assignments/ipfix">http://www.iana.org/assignments/ipfix</a>.&quot;;
            leaf ieName {
              type ieNameType;
              description &quot;Name of the Information Element.&quot;;
            }
            leaf ieId {
              type ieIdType;
              description &quot;Identifier of the Information Element.&quot;;
            }
          }
          leaf ieLength {
            type uint16;
            units octets;
            description &quot;Length of the field in which the Information
              Element is encoded.  A value of 65535 specifies a
              variable-length Information Element.  For Information
              Elements of integer and float type, the field length MAY
              be set to a smaller value than the standard length of
              the abstract data type if the rules of reduced size
              encoding are fulfilled.
              If not configured by the user, this parameter is set by
              the Monitoring Device.&quot;;
            reference &quot;<a href="/doc/html/rfc5101#section-6.2">RFC 5101, Section&amp;nbsp;6.2</a>.&quot;;
          }
          leaf ieEnterpriseNumber {
            type uint32;
            default 0;
            description &quot;If this parameter is zero, the Information
              Element is registered in the IANA registry of IPFIX
<span class="grey"><a href="/doc/html/rfc6728">RFC 6728</a>          IPFIX/PSAMP Configuration Data Model      October 2012</span>

              Information Elements.
              If this parameter is configured with a non-zero private
              enterprise number, the Information Element is
              enterprise-specific.
              If the enterprise number is set to 29305, this field
              contains a Reverse Information Element.  In this case,
              the Cache MUST generate Data Records in accordance to
              <a href="/doc/html/rfc5103">RFC 5103</a>.&quot;;
            reference &quot;<a href="/doc/html/rfc5101">RFC 5101</a>; <a href="/doc/html/rfc5103">RFC 5103</a>;
              IANA registry for Private Enterprise Numbers,
              <a href="http://www.iana">http://www.iana</a>.org/assignments/enterprise-numbers;
              IANA registry for IPFIX Entities,
              <a href="https://www.iana.org/assignments/ipfix">http://www.iana.org/assignments/ipfix</a>.&quot;;
          }
          leaf isFlowKey {
            when &quot;(name(../../..) != &#x27;immediateCache&#x27;)
              and
              ((count(../ieEnterpriseNumber) = 0)
              or
              (../ieEnterpriseNumber != 29305))&quot; {
              description &quot;This parameter is not available for
                Reverse Information Elements (which have enterprise
                number 29305).  It is also not available for
                immediateCache.&quot;;
            }
            type empty;
            description &quot;If present, this is a flow key.&quot;;
          }
        }
      }
    }

    grouping flowCacheParameters {
      description &quot;Configuration and state parameters of a Cache
        generating Flow Records.&quot;;
      leaf maxFlows {
        type uint32;
        units flows;
        description &quot;This parameter configures the maximum number of
          Flows in the Cache, which is the maximum number of Flows
          that can be measured simultaneously.
          The Monitoring Device MUST ensure that sufficient resources
          are available to store the configured maximum number of
          Flows.
          If the maximum number of Flows is measured, an additional
          Flow can be measured only if an existing entry is removed.
          However, traffic that pertains to existing Flows can
          continue to be measured.&quot;;
<span class="grey"><a href="/doc/html/rfc6728">RFC 6728</a>          IPFIX/PSAMP Configuration Data Model      October 2012</span>

      }
      leaf activeTimeout {
        when &quot;(name(..) = &#x27;timeoutCache&#x27;) or
          (name(..) = &#x27;naturalCache&#x27;)&quot; {
          description &quot;This parameter is only available for
            timeoutCache and naturalCache.&quot;;
        }
        type uint32;
        units seconds;
        description &quot;This parameter configures the time in
          seconds after which a Flow is expired even though packets
          matching this Flow are still received by the Cache.
          The parameter value zero indicates infinity, meaning that
          there is no active timeout.
          If not configured by the user, the Monitoring Device sets
          this parameter.
          Note that this parameter corresponds to
          ipfixMeteringProcessCacheActiveTimeout in the IPFIX
          MIB module.&quot;;
        reference &quot;<a href="/doc/html/rfc6615#section-8">RFC 6615, Section&amp;nbsp;8</a>
          (ipfixMeteringProcessCacheActiveTimeout).&quot;;
      }
      leaf idleTimeout {
        when &quot;(name(..) = &#x27;timeoutCache&#x27;) or
          (name(..) = &#x27;naturalCache&#x27;)&quot; {
          description &quot;This parameter is only available for
            timeoutCache and naturalCache.&quot;;
        }
        type uint32;
        units seconds;
        description &quot;This parameter configures the time in
          seconds after which a Flow is expired if no more packets
          matching this Flow are received by the Cache.
          The parameter value zero indicates infinity, meaning that
          there is no idle timeout.
          If not configured by the user, the Monitoring Device sets
          this parameter.
          Note that this parameter corresponds to
          ipfixMeteringProcessCacheIdleTimeout in the IPFIX
          MIB module.&quot;;
        reference &quot;<a href="/doc/html/rfc6615#section-8">RFC 6615, Section&amp;nbsp;8</a>
          (ipfixMeteringProcessCacheIdleTimeout).&quot;;
      }
      leaf exportInterval {
        when &quot;name(..) = &#x27;permanentCache&#x27;&quot; {
          description &quot;This parameter is only available for
            permanentCache.&quot;;
        }
<span class="grey"><a href="/doc/html/rfc6728">RFC 6728</a>          IPFIX/PSAMP Configuration Data Model      October 2012</span>

        type uint32;
        units seconds;
        description &quot;This parameter configures the interval (in
          seconds) for periodical export of Flow Records.
          If not configured by the user, the Monitoring Device sets
          this parameter.&quot;;
      }
      leaf activeFlows {
        type yang:gauge32;
        units flows;
        config false;
        description &quot;The number of Flows currently active in this
          Cache.
          Note that this parameter corresponds to
          ipfixMeteringProcessCacheActiveFlows in the IPFIX MIB
          module.&quot;;
        reference &quot;<a href="/doc/html/rfc6615#section-8">RFC 6615, Section&amp;nbsp;8</a>
          (ipfixMeteringProcessCacheActiveFlows).&quot;;
      }
      leaf unusedCacheEntries {
        type yang:gauge32;
        units flows;
        config false;
        description &quot;The number of unused Cache entries in this
          Cache.
          Note that this parameter corresponds to
          ipfixMeteringProcessCacheUnusedCacheEntries in the IPFIX
          MIB module.&quot;;
        reference &quot;<a href="/doc/html/rfc6615#section-8">RFC 6615, Section&amp;nbsp;8</a>
          (ipfixMeteringProcessCacheUnusedCacheEntries).&quot;;
      }
    }

    grouping exportingProcessParameters {
      description &quot;Parameters of an Exporting Process.&quot;;
      leaf exportingProcessId {
        type uint32;
        config false;
        description &quot;The identifier of the Exporting Process.
          This parameter corresponds to the Information Element
          exportingProcessId.  Its occurrence helps to associate
          Exporting Process parameters with Exporing Process
          statistics exported by the Monitoring Device using the
          Exporting Process Reliability Statistics Template as
          defined by the IPFIX protocol specification.&quot;;
        reference &quot;<a href="/doc/html/rfc5101#section-4.3">RFC 5101, Section&amp;nbsp;4.3</a>; IANA registry for IPFIX
          Entities, <a href="https://www.iana.org/assignments/ipfix">http://www.iana.org/assignments/ipfix</a>.&quot;;
      }
<span class="grey"><a href="/doc/html/rfc6728">RFC 6728</a>          IPFIX/PSAMP Configuration Data Model      October 2012</span>

      leaf exportMode {
        type identityref {
          base &quot;exportMode&quot;;
        }
        default parallel;
        description &quot;This parameter determines to which configured
          destination(s) the incoming Data Records are exported.&quot;;
      }
      list destination {
        key name;
        min-elements 1;
        description &quot;List of export destinations.&quot;;
        leaf name {
          type nameType;
          description &quot;Key of this list.&quot;;
        }
        choice DestinationParameters {
          mandatory true;
          description &quot;Configuration parameters depend on whether
            SCTP, UDP, or TCP is used as transport protocol, and
            whether the destination is a file.&quot;;
          container sctpExporter {
            description &quot;SCTP parameters.&quot;;
            uses sctpExporterParameters;
          }
          container udpExporter {
            if-feature udpTransport;
            description &quot;UDP parameters.&quot;;
            uses udpExporterParameters;
          }
          container tcpExporter {
            if-feature tcpTransport;
            description &quot;TCP parameters.&quot;;
            uses tcpExporterParameters;
          }
          container fileWriter {
            if-feature fileWriter;
            description &quot;File Writer parameters.&quot;;
            uses fileWriterParameters;
          }
        }
      }
      list options {
        key name;
        description &quot;List of options reported by the Exporting
          Process.&quot;;
        leaf name {
          type nameType;
<span class="grey"><a href="/doc/html/rfc6728">RFC 6728</a>          IPFIX/PSAMP Configuration Data Model      October 2012</span>

          description &quot;Key of this list.&quot;;
        }
        uses optionsParameters;
      }
    }

    grouping commonExporterParameters {
      description &quot;Parameters of en export destination that are
        common to all transport protocols.&quot;;
      leaf ipfixVersion {
        type uint16;
        default 10;
        description &quot;IPFIX version number.&quot;;
        reference &quot;<a href="/doc/html/rfc5101">RFC 5101</a>.&quot;;
      }
      leaf destinationPort {
        type inet:port-number;
        description &quot;If not configured by the user, the Monitoring
          Device uses the default port number for IPFIX, which is
          4739 without TLS or DTLS and 4740 if TLS or DTLS is
          activated.&quot;;
      }
      choice indexOrName {
        description &quot;Index or name of the interface as stored in the
          ifTable of IF-MIB.
          If configured, the Exporting Process MUST use the given
          interface to export IPFIX Messages to the export
          destination.
          If omitted, the Exporting Process selects the outgoing
          interface based on local routing decision and accepts
          return traffic, such as transport-layer acknowledgments,
          on all available interfaces.&quot;;
        reference &quot;<a href="/doc/html/rfc2863">RFC 2863</a>.&quot;;
        leaf ifIndex {
          type uint32;
          description &quot;Index of an interface as stored in the ifTable
            of IF-MIB.&quot;;
          reference &quot;<a href="/doc/html/rfc2863">RFC 2863</a>.&quot;;
        }
        leaf ifName {
          type string;
          description &quot;Name of an interface as stored in the ifTable
            of IF-MIB.&quot;;
          reference &quot;<a href="/doc/html/rfc2863">RFC 2863</a>.&quot;;
        }
      }
      leaf sendBufferSize {
        type uint32;
<span class="grey"><a href="/doc/html/rfc6728">RFC 6728</a>          IPFIX/PSAMP Configuration Data Model      October 2012</span>

        units bytes;
        description &quot;Size of the socket send buffer.
          If not configured by the user, this parameter is set by
          the Monitoring Device.&quot;;
      }
      leaf rateLimit {
        type uint32;
        units &quot;bytes per second&quot;;
        description &quot;Maximum number of bytes per second the Exporting
          Process may export to the given destination.  The number of
          bytes is calculated from the lengths of the IPFIX Messages
          exported.  If not configured, no rate limiting is performed.&quot;;
        reference &quot;<a href="/doc/html/rfc5476#section-6.3">RFC 5476, Section&amp;nbsp;6.3</a>.&quot;;
      }
      container transportLayerSecurity {
        presence &quot;If transportLayerSecurity is present, DTLS is
          enabled if the transport protocol is SCTP or UDP, and TLS
          is enabled if the transport protocol is TCP.&quot;;
        description &quot;TLS or DTLS configuration.&quot;;
        uses transportLayerSecurityParameters;
      }
      container transportSession {
        config false;
        description &quot;State parameters of the Transport Session
          directed to the given destination.&quot;;
        uses transportSessionParameters;
      }
    }

    grouping sctpExporterParameters {
      description &quot;SCTP-specific export destination parameters.&quot;;
      uses commonExporterParameters;
      leaf-list sourceIPAddress {
        type inet:ip-address;
        description &quot;List of source IP addresses used by the
          Exporting Process.
          If configured, the specified addresses are eligible local
          IP addresses of the multihomed SCTP endpoint.
          If not configured, all locally assigned IP addresses are
          eligible local IP addresses.&quot;;
        reference &quot;<a href="/doc/html/rfc4960#section-6.4">RFC 4960, Section&amp;nbsp;6.4</a>.&quot;;
      }
      leaf-list destinationIPAddress {
        type inet:ip-address;
        min-elements 1;
        description &quot;One or more IP addresses of the Collecting
          Process to which IPFIX Messages are sent.
          The user MUST ensure that all configured IP addresses
<span class="grey"><a href="/doc/html/rfc6728">RFC 6728</a>          IPFIX/PSAMP Configuration Data Model      October 2012</span>

          belong to the same Collecting Process.
          The Exporting Process tries to establish an SCTP
          association to any of the configured destination IP
          addresses.&quot;;
        reference &quot;<a href="/doc/html/rfc4960#section-6.4">RFC 4960, Section&amp;nbsp;6.4</a>.&quot;;
      }
      leaf timedReliability {
        type uint32;
        units milliseconds;
        default 0;
        description &quot;Lifetime in milliseconds until an IPFIX
          Message containing Data Sets only is &#x27;abandoned&#x27; due to
          the timed reliability mechanism of PR-SCTP.
          If this parameter is set to zero, reliable SCTP
          transport is used for all Data Records.
          Regardless of the value of this parameter, the Exporting
          Process MAY use reliable SCTP transport for Data Sets
          associated with Options Templates.&quot;;
        reference &quot;<a href="/doc/html/rfc3758">RFC 3758</a>; <a href="/doc/html/rfc4960">RFC 4960</a>.&quot;;
      }
    }

    grouping udpExporterParameters {
      description &quot;Parameters of a UDP export destination.&quot;;
      uses commonExporterParameters;
      leaf sourceIPAddress {
        type inet:ip-address;
        description &quot;Source IP address used by the Exporting Process.
        If not configured, the IP address assigned to the outgoing
        interface is used as source IP address.&quot;;
      }
      leaf destinationIPAddress {
        type inet:ip-address;
        mandatory true;
        description &quot;IP address of the Collection Process to which
          IPFIX Messages are sent.&quot;;
      }
      leaf maxPacketSize {
        type uint16;
        units octets;
        description &quot;This parameter specifies the maximum size of
          IP packets sent to the Collector.  If set to zero, the
          Exporting Device MUST derive the maximum packet size
          from path MTU discovery mechanisms.
          If not configured by the user, this parameter is set by
          the Monitoring Device.&quot;;
      }
      leaf templateRefreshTimeout {
<span class="grey"><a href="/doc/html/rfc6728">RFC 6728</a>          IPFIX/PSAMP Configuration Data Model      October 2012</span>

        type uint32;
        units seconds;
        default 600;
        description &quot;Sets time after which Templates are resent in the
          UDP Transport Session.
          Note that the configured lifetime MUST be adapted to the
          templateLifeTime parameter value at the receiving Collecting
          Process.
          Note that this parameter corresponds to
          ipfixTransportSessionTemplateRefreshTimeout in the IPFIX
          MIB module.&quot;;
        reference &quot;<a href="/doc/html/rfc5101#section-10.3.6">RFC 5101, Section&amp;nbsp;10.3.6</a>; <a href="/doc/html/rfc6615#section-8">RFC 6615, Section&amp;nbsp;8</a>
          (ipfixTransportSessionTemplateRefreshTimeout).&quot;;
      }
      leaf optionsTemplateRefreshTimeout {
        type uint32;
        units seconds;
        default 600;
        description &quot;Sets time after which Options Templates are
          resent in the UDP Transport Session.
          Note that the configured lifetime MUST be adapted to the
          optionsTemplateLifeTime parameter value at the receiving
          Collecting Process.
          Note that this parameter corresponds to
          ipfixTransportSessionOptionsTemplateRefreshTimeout in the
          IPFIX MIB module.&quot;;
        reference &quot;<a href="/doc/html/rfc5101#section-10.3.6">RFC 5101, Section&amp;nbsp;10.3.6</a>; <a href="/doc/html/rfc6615#section-8">RFC 6615, Section&amp;nbsp;8</a>
          (ipfixTransportSessionOptionsTemplateRefreshTimeout).&quot;;
      }
      leaf templateRefreshPacket {
        type uint32;
        units &quot;IPFIX Messages&quot;;
        description &quot;Sets number of IPFIX Messages after which
          Templates are resent in the UDP Transport Session.
          Note that this parameter corresponds to
          ipfixTransportSessionTemplateRefreshPacket in the IPFIX
          MIB module.
          If omitted, Templates are only resent after timeout.&quot;;
        reference &quot;<a href="/doc/html/rfc5101#section-10.3.6">RFC 5101, Section&amp;nbsp;10.3.6</a>; <a href="/doc/html/rfc6615#section-8">RFC 6615, Section&amp;nbsp;8</a>
          (ipfixTransportSessionTemplateRefreshPacket).&quot;;
      }
      leaf optionsTemplateRefreshPacket {
        type uint32;
        units &quot;IPFIX Messages&quot;;
        description &quot;Sets number of IPFIX Messages after which
          Options Templates are resent in the UDP Transport Session
          protocol.
          Note that this parameter corresponds to
<span class="grey"><a href="/doc/html/rfc6728">RFC 6728</a>          IPFIX/PSAMP Configuration Data Model      October 2012</span>

          ipfixTransportSessionOptionsTemplateRefreshPacket in the
          IPFIX MIB module.
          If omitted, Templates are only resent after timeout.&quot;;
        reference &quot;<a href="/doc/html/rfc5101#section-10.3.6">RFC 5101, Section&amp;nbsp;10.3.6</a>; <a href="/doc/html/rfc6615#section-8">RFC 6615, Section&amp;nbsp;8</a>
          (ipfixTransportSessionOptionsTemplateRefreshPacket).&quot;;
      }
    }

    grouping tcpExporterParameters {
      description &quot;Parameters of a TCP export destination.&quot;;
      uses commonExporterParameters;
      leaf sourceIPAddress {
        type inet:ip-address;
        description &quot;Source IP address used by the Exporting Process.
          If not configured by the user, this parameter is set by
          the Monitoring Device to an IP address assigned to the
          outgoing interface.&quot;;
      }
      leaf destinationIPAddress {
        type inet:ip-address;
        mandatory true;
        description &quot;IP address of the Collection Process to which
          IPFIX Messages are sent.&quot;;
      }
    }

    grouping fileWriterParameters {
      description &quot;File Writer parameters.&quot;;
      leaf ipfixVersion {
        type uint16;
        default 10;
        description &quot;IPFIX version number.&quot;;
        reference &quot;<a href="/doc/html/rfc5101">RFC 5101</a>.&quot;;
      }
      leaf file {
        type inet:uri;
        mandatory true;
        description &quot;URI specifying the location of the file.&quot;;
      }
      leaf bytes {
        type yang:counter64;
        units octets;
        config false;
        description &quot;The number of bytes written by the File Writer.
          Discontinuities in the value of this counter can occur at
          re-initialization of the management system, and at other
          times as indicated by the value of
          fileWriterDiscontinuityTime.&quot;;
<span class="grey"><a href="/doc/html/rfc6728">RFC 6728</a>          IPFIX/PSAMP Configuration Data Model      October 2012</span>

      }
      leaf messages {
        type yang:counter64;
        units &quot;IPFIX Messages&quot;;
        config false;
        description &quot;The number of IPFIX Messages written by the File
          Writer.
          Discontinuities in the value of this counter can occur at
          re-initialization of the management system, and at other
          times as indicated by the value of
          fileWriterDiscontinuityTime.&quot;;
      }
      leaf discardedMessages {
        type yang:counter64;
        units &quot;IPFIX Messages&quot;;
        config false;
        description &quot;The number of IPFIX Messages that could not be
          written by the File Writer due to internal buffer
          overflows, limited storage capacity, etc.
          Discontinuities in the value of this counter can occur at
          re-initialization of the management system, and at other
          times as indicated by the value of
          fileWriterDiscontinuityTime.&quot;;
      }
      leaf records {
        type yang:counter64;
        units &quot;Data Records&quot;;
        config false;
        description &quot;The number of Data Records written by the File
          Writer.
          Discontinuities in the value of this counter can occur at
          re-initialization of the management system, and at other
          times as indicated by the value of
          fileWriterDiscontinuityTime.&quot;;
      }
      leaf templates {
        type yang:counter32;
        units &quot;Templates&quot;;
        config false;
        description &quot;The number of Template Records (excluding
          Options Template Records) written by the File Writer.
          Discontinuities in the value of this counter can occur at
          re-initialization of the management system, and at other
          times as indicated by the value of
          fileWriterDiscontinuityTime.&quot;;
      }
      leaf optionsTemplates {
        type yang:counter32;
<span class="grey"><a href="/doc/html/rfc6728">RFC 6728</a>          IPFIX/PSAMP Configuration Data Model      October 2012</span>

        units &quot;Options Templates&quot;;
        config false;
        description &quot;The number of Options Template Records written
          by the File Writer.
          Discontinuities in the value of this counter can occur at
          re-initialization of the management system, and at other
          times as indicated by the value of
          fileWriterDiscontinuityTime.&quot;;
      }
      leaf fileWriterDiscontinuityTime {
        type yang:date-and-time;
        config false;
        description &quot;Timestamp of the most recent occasion at which
          one or more File Writer counters suffered a discontinuity.
          In contrast to discontinuity times in the IPFIX MIB module,
          the time is absolute and not relative to sysUpTime.&quot;;
      }
      list template {
        config false;
        description &quot;This list contains the Templates and Options
          Templates that have been written by the File Reader.
          Withdrawn or invalidated (Options) Templates MUST be removed
          from this list.&quot;;
        uses templateParameters;
      }
    }

    grouping optionsParameters {
      description &quot;Parameters specifying the data export using an
        Options Template.&quot;;
      leaf optionsType {
        type identityref {
          base &quot;optionsType&quot;;
        }
        mandatory true;
        description &quot;Type of the exported options data.&quot;;
      }
      leaf optionsTimeout {
        type uint32;
        units milliseconds;
        description &quot;Time interval for periodic export of the options
          data.  If set to zero, the export is triggered when the
          options data has changed.
          If not configured by the user, this parameter is set by the
          Monitoring Device.&quot;;
      }
    }

<span class="grey"><a href="/doc/html/rfc6728">RFC 6728</a>          IPFIX/PSAMP Configuration Data Model      October 2012</span>

    grouping collectingProcessParameters {
      description &quot;Parameters of a Collecting Process.&quot;;
      list sctpCollector {
        key name;
        description &quot;List of SCTP receivers (sockets) on which the
          Collecting Process receives IPFIX Messages.&quot;;
        leaf name {
          type nameType;
          description &quot;Key of this list.&quot;;
        }
        uses sctpCollectorParameters;
      }
      list udpCollector {
        if-feature udpTransport;
        key name;
        description &quot;List of UDP receivers (sockets) on which the
          Collecting Process receives IPFIX Messages.&quot;;
        leaf name {
          type nameType;
          description &quot;Key of this list.&quot;;
        }
        uses udpCollectorParameters;
      }
      list tcpCollector {
        if-feature tcpTransport;
        key name;
        description &quot;List of TCP receivers (sockets) on which the
          Collecting Process receives IPFIX Messages.&quot;;
        leaf name {
          type nameType;
          description &quot;Key of this list.&quot;;
        }
        uses tcpCollectorParameters;
      }
      list fileReader {
        if-feature fileReader;
        key name;
        description &quot;List of File Readers from which the Collecting
          Process reads IPFIX Messages.&quot;;
        leaf name {
          type nameType;
          description &quot;Key of this list.&quot;;
        }
        uses fileReaderParameters;
      }
    }

    grouping commonCollectorParameters {
<span class="grey"><a href="/doc/html/rfc6728">RFC 6728</a>          IPFIX/PSAMP Configuration Data Model      October 2012</span>

      description &quot;Parameters of a Collecting Process that are
        common to all transport protocols.&quot;;
      leaf localPort {
        type inet:port-number;
        description &quot;If not configured, the Monitoring Device uses the
          default port number for IPFIX, which is 4739 without
          TLS or DTLS and 4740 if TLS or DTLS is activated.&quot;;
      }
      container transportLayerSecurity {
        presence &quot;If transportLayerSecurity is present, DTLS is enabled
          if the transport protocol is SCTP or UDP, and TLS is enabled
          if the transport protocol is TCP.&quot;;
        description &quot;TLS or DTLS configuration.&quot;;
        uses transportLayerSecurityParameters;
      }
      list transportSession {
        config false;
        description &quot;This list contains the currently established
          Transport Sessions terminating at the given socket.&quot;;
        uses transportSessionParameters;
      }
    }

    grouping sctpCollectorParameters {
      description &quot;Parameters of a listening SCTP socket at a
        Collecting Process.&quot;;
      uses commonCollectorParameters;
      leaf-list localIPAddress {
        type inet:ip-address;
        description &quot;List of local IP addresses on which the
          Collecting Process listens for IPFIX Messages.  The IP
          addresses are used as eligible local IP addresses of the
          multihomed SCTP endpoint.&quot;;
        reference &quot;<a href="/doc/html/rfc4960#section-6.4">RFC 4960, Section&amp;nbsp;6.4</a>.&quot;;
      }
    }

    grouping udpCollectorParameters {
      description &quot;Parameters of a listening UDP socket at a
        Collecting Process.&quot;;
      uses commonCollectorParameters;
      leaf-list localIPAddress {
        type inet:ip-address;
        description &quot;List of local IP addresses on which the Collecting
          Process listens for IPFIX Messages.&quot;;
      }
      leaf templateLifeTime {
        type uint32;
<span class="grey"><a href="/doc/html/rfc6728">RFC 6728</a>          IPFIX/PSAMP Configuration Data Model      October 2012</span>

        units seconds;
        default 1800;
        description &quot;Sets the lifetime of Templates for all UDP
          Transport Sessions terminating at this UDP socket.
          Templates that are not received again within the configured
          lifetime become invalid at the Collecting Process.
          As specified in <a href="/doc/html/rfc5101">RFC 5101</a>, the Template lifetime MUST be at
          least three times higher than the templateRefreshTimeout
          parameter value configured on the corresponding Exporting
          Processes.
          Note that this parameter corresponds to
          ipfixTransportSessionTemplateRefreshTimeout in the IPFIX
          MIB module.&quot;;
        reference &quot;<a href="/doc/html/rfc5101#section-10.3.7">RFC 5101, Section&amp;nbsp;10.3.7</a>; <a href="/doc/html/rfc6615#section-8">RFC 6615, Section&amp;nbsp;8</a>
          (ipfixTransportSessionTemplateRefreshTimeout).&quot;;
      }
      leaf optionsTemplateLifeTime {
        type uint32;
        units seconds;
        default 1800;
        description &quot;Sets the lifetime of Options Templates for all
          UDP Transport Sessions terminating at this UDP socket.
          Options Templates that are not received again within the
          configured lifetime become invalid at the Collecting
          Process.
          As specified in <a href="/doc/html/rfc5101">RFC 5101</a>, the Options Template lifetime MUST
          be at least three times higher than the
          optionsTemplateRefreshTimeout parameter value configured on
          the corresponding Exporting Processes.
          Note that this parameter corresponds to
          ipfixTransportSessionOptionsTemplateRefreshTimeout in the
          IPFIX MIB module.&quot;;
        reference &quot;<a href="/doc/html/rfc5101#section-10.3.7">RFC 5101, Section&amp;nbsp;10.3.7</a>; <a href="/doc/html/rfc6615#section-8">RFC 6615, Section&amp;nbsp;8</a>
          (ipfixTransportSessionOptionsTemplateRefreshTimeout).&quot;;
      }
      leaf templateLifePacket {
        type uint32;
        units &quot;IPFIX Messages&quot;;
        description &quot;If this parameter is configured, Templates
          defined in a UDP Transport Session become invalid if they
          are neither included in a sequence of more than this number
          of IPFIX Messages nor received again within the period of
          time specified by templateLifeTime.
          Note that this parameter corresponds to
          ipfixTransportSessionTemplateRefreshPacket in the IPFIX
          MIB module.&quot;;
        reference &quot;<a href="/doc/html/rfc5101#section-10.3.7">RFC 5101, Section&amp;nbsp;10.3.7</a>; <a href="/doc/html/rfc6615#section-8">RFC 6615, Section&amp;nbsp;8</a>
          (ipfixTransportSessionTemplateRefreshPacket).&quot;;
<span class="grey"><a href="/doc/html/rfc6728">RFC 6728</a>          IPFIX/PSAMP Configuration Data Model      October 2012</span>

      }
      leaf optionsTemplateLifePacket {
        type uint32;
        units &quot;IPFIX Messages&quot;;
        description &quot;If this parameter is configured, Options
          Templates defined in a UDP Transport Session become
          invalid if they are neither included in a sequence of more
          than this number of IPFIX Messages nor received again
          within the period of time specified by
          optionsTemplateLifeTime.
          Note that this parameter corresponds to
          ipfixTransportSessionOptionsTemplateRefreshPacket in the
          IPFIX MIB module.&quot;;
        reference &quot;<a href="/doc/html/rfc5101#section-10.3.7">RFC 5101, Section&amp;nbsp;10.3.7</a>; <a href="/doc/html/rfc6615#section-8">RFC 6615, Section&amp;nbsp;8</a>
          (ipfixTransportSessionOptionsTemplateRefreshPacket).&quot;;
      }
    }

    grouping tcpCollectorParameters {
      description &quot;Parameters of a listening TCP socket at a
        Collecting Process.&quot;;
      uses commonCollectorParameters;
      leaf-list localIPAddress {
        type inet:ip-address;
        description &quot;List of local IP addresses on which the Collecting
          Process listens for IPFIX Messages.&quot;;
      }
    }

    grouping fileReaderParameters {
      description &quot;File Reader parameters.&quot;;
      leaf file {
        type inet:uri;
        mandatory true;
        description &quot;URI specifying the location of the file.&quot;;
      }
      leaf bytes {
        type yang:counter64;
        units octets;
        config false;
        description &quot;The number of bytes read by the File Reader.
          Discontinuities in the value of this counter can occur at
          re-initialization of the management system, and at other
          times as indicated by the value of
          fileReaderDiscontinuityTime.&quot;;
      }
      leaf messages {
        type yang:counter64;
<span class="grey"><a href="/doc/html/rfc6728">RFC 6728</a>          IPFIX/PSAMP Configuration Data Model      October 2012</span>

        units &quot;IPFIX Messages&quot;;
        config false;
        description &quot;The number of IPFIX Messages read by the File
          Reader.
          Discontinuities in the value of this counter can occur at
          re-initialization of the management system, and at other
          times as indicated by the value of
          fileReaderDiscontinuityTime.&quot;;
      }
      leaf records {
        type yang:counter64;
        units &quot;Data Records&quot;;
        config false;
        description &quot;The number of Data Records read by the File
          Reader.
          Discontinuities in the value of this counter can occur at
          re-initialization of the management system, and at other
          times as indicated by the value of
          fileReaderDiscontinuityTime.&quot;;
      }
      leaf templates {
        type yang:counter32;
        units &quot;Templates&quot;;
        config false;
        description &quot;The number of Template Records (excluding
          Options Template Records) read by the File Reader.
          Discontinuities in the value of this counter can occur at
          re-initialization of the management system, and at other
          times as indicated by the value of
          fileReaderDiscontinuityTime.&quot;;
      }
      leaf optionsTemplates {
        type yang:counter32;
        units &quot;Options Templates&quot;;
        config false;
        description &quot;The number of Options Template Records read by
          the File Reader.
          Discontinuities in the value of this counter can occur at
          re-initialization of the management system, and at other
          times as indicated by the value of
          fileReaderDiscontinuityTime.&quot;;
      }
      leaf fileReaderDiscontinuityTime {
        type yang:date-and-time;
        config false;
        description &quot;Timestamp of the most recent occasion at which
          one or more File Reader counters suffered a discontinuity.
          In contrast to discontinuity times in the IPFIX MIB module,
<span class="grey"><a href="/doc/html/rfc6728">RFC 6728</a>          IPFIX/PSAMP Configuration Data Model      October 2012</span>

          the time is absolute and not relative to sysUpTime.&quot;;
      }
      list template {
        config false;
        description &quot;This list contains the Templates and Options
          Templates that have been read by the File Reader.
          Withdrawn or invalidated (Options) Template MUST be removed
          from this list.&quot;;
        uses templateParameters;
      }
    }

    grouping transportLayerSecurityParameters {
      description &quot;TLS or DTLS parameters.&quot;;
      leaf-list localCertificationAuthorityDN {
        type string;
        description &quot;Distinguished names of certification authorities
          whose certificates may be used to identify the local
          endpoint.&quot;;
        reference &quot;<a href="/doc/html/rfc5280">RFC 5280</a>.&quot;;
      }
      leaf-list localSubjectDN {
        type string;
        description &quot;Distinguished names that may be used in the
          certificates to identify the local endpoint.&quot;;
        reference &quot;<a href="/doc/html/rfc5280">RFC 5280</a>.&quot;;
      }
      leaf-list localSubjectFQDN {
        type inet:domain-name;
        description &quot;Fully qualified domain names that may be used to
          in the certificates to identify the local endpoint.&quot;;
        reference &quot;<a href="/doc/html/rfc5280">RFC 5280</a>.&quot;;
      }
      leaf-list remoteCertificationAuthorityDN {
        type string;
        description &quot;Distinguished names of certification authorities
          whose certificates are accepted to authorize remote
          endpoints.&quot;;
        reference &quot;<a href="/doc/html/rfc5280">RFC 5280</a>.&quot;;
      }
      leaf-list remoteSubjectDN {
        type string;
        description &quot;Distinguished names which are accepted in
          certificates to authorize remote endpoints.&quot;;
        reference &quot;<a href="/doc/html/rfc5280">RFC 5280</a>.&quot;;
      }
      leaf-list remoteSubjectFQDN {
        type inet:domain-name;
<span class="grey"><a href="/doc/html/rfc6728">RFC 6728</a>          IPFIX/PSAMP Configuration Data Model      October 2012</span>

        description &quot;Fully qualified domain names that are accepted in
          certificates to authorize remote endpoints.&quot;;
        reference &quot;<a href="/doc/html/rfc5280">RFC 5280</a>.&quot;;
      }
    }

    grouping templateParameters {
      description &quot;State parameters of a Template used by an Exporting
        Process or received by a Collecting Process in a specific
        Transport Session.  Parameter names and semantics correspond to
        the managed objects in IPFIX-MIB&quot;;
      reference &quot;<a href="/doc/html/rfc5101">RFC 5101</a>; <a href="/doc/html/rfc6615#section-8">RFC 6615, Section&amp;nbsp;8</a> (ipfixTemplateEntry,
        ipfixTemplateDefinitionEntry, ipfixTemplateStatsEntry)&quot;;
      leaf observationDomainId {
        type uint32;
        description &quot;The ID of the Observation Domain for which this
          Template is defined.
          Note that this parameter corresponds to
          ipfixTemplateObservationDomainId in the IPFIX MIB module.&quot;;
        reference &quot;<a href="/doc/html/rfc6615#section-8">RFC 6615, Section&amp;nbsp;8</a>
          (ipfixTemplateObservationDomainId).&quot;;
      }
      leaf templateId {
        type uint16 {
          range &quot;256..65535&quot; {
            description &quot;Valid range of Template IDs.&quot;;
            reference &quot;<a href="/doc/html/rfc5101">RFC 5101</a>&quot;;
          }
        }
        description &quot;This number indicates the Template ID in the IPFIX
          message.
          Note that this parameter corresponds to ipfixTemplateId in
          the IPFIX MIB module.&quot;;
        reference &quot;<a href="/doc/html/rfc6615#section-8">RFC 6615, Section&amp;nbsp;8</a> (ipfixTemplateId).&quot;;
      }
      leaf setId {
        type uint16;
        description &quot;This number indicates the Set ID of the Template.
          Currently, there are two values defined.  The value 2 is used
          for Sets containing Template definitions.  The value 3 is
          used for Sets containing Options Template definitions.
          Note that this parameter corresponds to ipfixTemplateSetId
          in the IPFIX MIB module.&quot;;
        reference &quot;<a href="/doc/html/rfc6615#section-8">RFC 6615, Section&amp;nbsp;8</a> (ipfixTemplateSetId).&quot;;
      }
      leaf accessTime {
        type yang:date-and-time;
        description &quot;Used for Exporting Processes, this parameter
<span class="grey"><a href="/doc/html/rfc6728">RFC 6728</a>          IPFIX/PSAMP Configuration Data Model      October 2012</span>

          contains the time when this (Options) Template was last
          sent to the Collector(s) or written to the file.
          Used for Collecting Processes, this parameter contains the
          time when this (Options) Template was last received from the
          Exporter or read from the file.
          Note that this parameter corresponds to
          ipfixTemplateAccessTime in the IPFIX MIB module.&quot;;
        reference &quot;<a href="/doc/html/rfc6615#section-8">RFC 6615, Section&amp;nbsp;8</a> (ipfixTemplateAccessTime).&quot;;
      }
      leaf templateDataRecords {
        type yang:counter64;
        description &quot;The number of transmitted or received Data
          Records defined by this (Options) Template.
          Discontinuities in the value of this counter can occur at
          re-initialization of the management system, and at other
          times as indicated by the value of
          templateDiscontinuityTime.
          Note that this parameter corresponds to
          ipfixTemplateDataRecords in the IPFIX MIB module.&quot;;
        reference &quot;<a href="/doc/html/rfc6615#section-8">RFC 6615, Section&amp;nbsp;8</a> (ipfixTemplateDataRecords).&quot;;
      }
      leaf templateDiscontinuityTime {
        type yang:date-and-time;
        description &quot;Timestamp of the most recent occasion at which
          the counter templateDataRecords suffered a discontinuity.
          Note that this parameter functionally corresponds to
          ipfixTemplateDiscontinuityTime in the IPFIX MIB module.
          In contrast to ipfixTemplateDiscontinuityTime, the time
          is absolute and not relative to sysUpTime.&quot;;
        reference &quot;<a href="/doc/html/rfc6615#section-8">RFC 6615, Section&amp;nbsp;8</a>
          (ipfixTemplateDiscontinuityTime).&quot;;
      }
      list field {
        description &quot;This list contains the (Options) Template
          fields of which the (Options) Template is defined.
          The order of the list corresponds to the order of the fields
          in the (Option) Template Record.&quot;;
        leaf ieId {
          type ieIdType;
          description &quot;This parameter indicates the Information
            Element identifier of the field.
            Note that this parameter corresponds to
            ipfixTemplateDefinitionIeId in the IPFIX MIB module.&quot;;
          reference &quot;<a href="/doc/html/rfc5101">RFC 5101</a>; <a href="/doc/html/rfc6615#section-8">RFC 6615, Section&amp;nbsp;8</a>
            (ipfixTemplateDefinitionIeId).&quot;;
        }
        leaf ieLength {
          type uint16;
<span class="grey"><a href="/doc/html/rfc6728">RFC 6728</a>          IPFIX/PSAMP Configuration Data Model      October 2012</span>

          units octets;
          description &quot;This parameter indicates the length of the
            Information Element of the field.
            Note that this parameter corresponds to
            ipfixTemplateDefinitionIeLength in the IPFIX MIB
            module.&quot;;
          reference &quot;<a href="/doc/html/rfc5101">RFC 5101</a>; <a href="/doc/html/rfc6615#section-8">RFC 6615, Section&amp;nbsp;8</a>
            (ipfixTemplateDefinitionIeLength).&quot;;
        }
        leaf ieEnterpriseNumber {
          type uint32;
          description &quot;This parameter indicates the IANA enterprise
            number of the authority defining the Information Element
            identifier.
            If the Information Element is not enterprise-specific,
            this state parameter is zero.
            Note that this parameter corresponds to
            ipfixTemplateDefinitionIeEnterpriseNumber in the IPFIX
            MIB module.&quot;;
          reference &quot;<a href="/doc/html/rfc6615#section-8">RFC 6615, Section&amp;nbsp;8</a>
            (ipfixTemplateDefinitionIeEnterpriseNumber);
            IANA registry for Private Enterprise Numbers,
            <a href="https://www.iana.org/assignments/enterprise-numbers">http://www.iana.org/assignments/enterprise-numbers</a>.&quot;;
        }
        leaf isFlowKey {
          when &quot;../../setId = 2&quot; {
            description &quot;This parameter is available for non-Options
              Templates (Set ID is 2).&quot;;
          }
          type empty;
          description &quot;If present, this is a Flow Key field.
            Note that this corresponds to flowKey(1) being set in
            ipfixTemplateDefinitionFlags.&quot;;
          reference &quot;<a href="/doc/html/rfc6615#section-8">RFC 6615, Section&amp;nbsp;8</a>
            (ipfixTemplateDefinitionFlags).&quot;;
        }
        leaf isScope {
          when &quot;../../setId = 3&quot; {
            description &quot;This parameter is available for Options
              Templates (Set ID is 3).&quot;;
          }
          type empty;
          description &quot;If present, this is a scope field.
            Note that this corresponds to scope(0) being set in
            ipfixTemplateDefinitionFlags.&quot;;
          reference &quot;<a href="/doc/html/rfc6615#section-8">RFC 6615, Section&amp;nbsp;8</a>
            (ipfixTemplateDefinitionFlags).&quot;;
        }
<span class="grey"><a href="/doc/html/rfc6728">RFC 6728</a>          IPFIX/PSAMP Configuration Data Model      October 2012</span>

      }
    }

    grouping transportSessionParameters {
      description &quot;State parameters of a Transport Session originating
        from an Exporting Process or terminating at a Collecting
        Process.  Parameter names and semantics correspond to the
        managed objects in IPFIX-MIB.&quot;;
      reference &quot;<a href="/doc/html/rfc5101">RFC 5101</a>; <a href="/doc/html/rfc6615#section-8">RFC 6615, Section&amp;nbsp;8</a>
        (ipfixTransportSessionEntry,
         ipfixTransportSessionStatsEntry).&quot;;
      leaf ipfixVersion {
        type uint16;
        description &quot;Used for Exporting Processes, this parameter
          contains the version number of the IPFIX protocol that the
          Exporter uses to export its data in this Transport Session.
          Hence, it is identical to the value of the configuration
          parameter ipfixVersion of the outer SctpExporter,
          UdpExporter, or TcpExporter node.
          Used for Collecting Processes, this parameter contains the
          version number of the IPFIX protocol it receives for
          this Transport Session.  If IPFIX Messages of different
          IPFIX protocol versions are received, this parameter
          contains the maximum version number.
          Note that this parameter corresponds to
          ipfixTransportSessionIpfixVersion in the IPFIX MIB
          module.&quot;;
        reference &quot;<a href="/doc/html/rfc6615#section-8">RFC 6615, Section&amp;nbsp;8</a>
          (ipfixTransportSessionIpfixVersion).&quot;;
      }
      leaf sourceAddress {
        type inet:ip-address;
        description &quot;The source address of the Exporter of the
          IPFIX Transport Session.
          If the transport protocol is SCTP, this is one of the
          potentially many IP addresses of the Exporter.
          Preferably, the source IP address of the path that is
          usually selected by the Exporter to send IPFIX Messages to
          the Collector SHOULD be used.
          Note that this parameter functionally corresponds to
          ipfixTransportSessionSourceAddressType and
          ipfixTransportSessionSourceAddress in the IPFIX MIB
          module.&quot;;
        reference &quot;<a href="/doc/html/rfc6615#section-8">RFC 6615, Section&amp;nbsp;8</a>
          (ipfixTransportSessionSourceAddressType,
          ipfixTransportSessionSourceAddress);
          <a href="/doc/html/rfc4960#section-6.4">RFC 4960, Section&amp;nbsp;6.4</a>.&quot;;
      }
<span class="grey"><a href="/doc/html/rfc6728">RFC 6728</a>          IPFIX/PSAMP Configuration Data Model      October 2012</span>

      leaf destinationAddress {
        type inet:ip-address;
        description &quot;The destination address of the Collector of
          the IPFIX Transport Session.
          If the transport protocol is SCTP, this is one of the
          potentially many IP addresses of the Collector.
          Preferably, the destination IP address of the path that is
          usually selected by the Exporter to send IPFIX Messages to
          the Collector SHOULD be used.
          Note that this parameter functionally corresponds to
          ipfixTransportSessionDestinationAddressType and
          ipfixTransportSessionDestinationAddress in the IPFIX MIB
          module.&quot;;
        reference &quot;<a href="/doc/html/rfc6615#section-8">RFC 6615, Section&amp;nbsp;8</a>
          (ipfixTransportSessionDestinationAddressType,
          ipfixTransportSessionDestinationAddress);
          <a href="/doc/html/rfc4960#section-6.4">RFC 4960, Section&amp;nbsp;6.4</a>.&quot;;
      }
      leaf sourcePort {
        type inet:port-number;
        description &quot;The transport-protocol port number of the
          Exporter of the IPFIX Transport Session.
          Note that this parameter corresponds to
          ipfixTransportSessionSourcePort in the IPFIX MIB module.&quot;;
        reference &quot;<a href="/doc/html/rfc6615#section-8">RFC 6615, Section&amp;nbsp;8</a>
          (ipfixTransportSessionSourcePort).&quot;;
      }
      leaf destinationPort {
        type inet:port-number;
        description &quot;The transport-protocol port number of the
          Collector of the IPFIX Transport Session.
          Note that this parameter corresponds to
          ipfixTransportSessionDestinationPort in the IPFIX MIB
          module.&quot;;
        reference &quot;<a href="/doc/html/rfc6615#section-8">RFC 6615, Section&amp;nbsp;8</a>
          (ipfixTransportSessionDestinationPort).&quot;;
      }
      leaf sctpAssocId {
        type uint32;
        description &quot;The association ID used for the SCTP session
          between the Exporter and the Collector of the IPFIX
          Transport Session.  It is equal to the sctpAssocId entry
          in the sctpAssocTable defined in the SCTP-MIB.
          This parameter is only available if the transport protocol
          is SCTP and if an SNMP agent on the same Monitoring Device
          enables access to the corresponding MIB objects in the
          sctpAssocTable.
          Note that this parameter corresponds to
<span class="grey"><a href="/doc/html/rfc6728">RFC 6728</a>          IPFIX/PSAMP Configuration Data Model      October 2012</span>

          ipfixTransportSessionSctpAssocId in the IPFIX MIB
          module.&quot;;
        reference &quot;<a href="/doc/html/rfc6615#section-8">RFC 6615, Section&amp;nbsp;8</a>
          (ipfixTransportSessionSctpAssocId);
          <a href="/doc/html/rfc3871">RFC 3871</a>&quot;;
      }
      leaf status {
        type transportSessionStatus;
        description &quot;Status of the Transport Session.
          Note that this parameter corresponds to
          ipfixTransportSessionStatus in the IPFIX MIB module.&quot;;
        reference &quot;<a href="/doc/html/rfc6615#section-8">RFC 6615, Section&amp;nbsp;8</a> (ipfixTransportSessionStatus).&quot;;
      }
      leaf rate {
        type yang:gauge32;
        units &quot;bytes per second&quot;;
        description &quot;The number of bytes per second transmitted by the
          Exporting Process or received by the Collecting Process.
          This parameter is updated every second.
          Note that this parameter corresponds to
          ipfixTransportSessionRate in the IPFIX MIB module.&quot;;
        reference &quot;<a href="/doc/html/rfc6615#section-8">RFC 6615, Section&amp;nbsp;8</a> (ipfixTransportSessionRate).&quot;;
      }
      leaf bytes {
        type yang:counter64;
        units bytes;
        description &quot;The number of bytes transmitted by the
          Exporting Process or received by the Collecting Process.
          Discontinuities in the value of this counter can occur at
          re-initialization of the management system, and at other
          times as indicated by the value of
          transportSessionDiscontinuityTime.
          Note that this parameter corresponds to
          ipfixTransportSessionBytes in the IPFIX MIB module.&quot;;
        reference &quot;<a href="/doc/html/rfc6615#section-8">RFC 6615, Section&amp;nbsp;8</a> (ipfixTransportSessionBytes).&quot;;
      }
      leaf messages {
        type yang:counter64;
        units &quot;IPFIX Messages&quot;;
        description &quot;The number of messages transmitted by the
          Exporting Process or received by the Collecting Process.
          Discontinuities in the value of this counter can occur at
          re-initialization of the management system, and at other
          times as indicated by the value of
          transportSessionDiscontinuityTime.
          Note that this parameter corresponds to
          ipfixTransportSessionMessages in the IPFIX MIB module.&quot;;
        reference &quot;<a href="/doc/html/rfc6615#section-8">RFC 6615, Section&amp;nbsp;8</a>
<span class="grey"><a href="/doc/html/rfc6728">RFC 6728</a>          IPFIX/PSAMP Configuration Data Model      October 2012</span>

          (ipfixTransportSessionMessages).&quot;;
      }
      leaf discardedMessages {
        type yang:counter64;
        units &quot;IPFIX Messages&quot;;
        description &quot;Used for Exporting Processes, this parameter
          indicates the number of messages that could not be sent due
          to internal buffer overflows, network congestion, routing
          issues, etc.  Used for Collecting Process, this parameter
          indicates the number of received IPFIX Message that are
          malformed, cannot be decoded, are received in the wrong
          order or are missing according to the sequence number.
          Discontinuities in the value of this counter can occur at
          re-initialization of the management system, and at other
          times as indicated by the value of
          transportSessionDiscontinuityTime.
          Note that this parameter corresponds to
          ipfixTransportSessionDiscardedMessages in the IPFIX MIB
          module.&quot;;
        reference &quot;<a href="/doc/html/rfc6615#section-8">RFC 6615, Section&amp;nbsp;8</a>
          (ipfixTransportSessionDiscardedMessages).&quot;;
      }
      leaf records {
        type yang:counter64;
        units &quot;Data Records&quot;;
        description &quot;The number of Data Records transmitted by the
          Exporting Process or received by the Collecting Process.
          Discontinuities in the value of this counter can occur at
          re-initialization of the management system, and at other
          times as indicated by the value of
          transportSessionDiscontinuityTime.
          Note that this parameter corresponds to
          ipfixTransportSessionRecords in the IPFIX MIB module.&quot;;
        reference &quot;<a href="/doc/html/rfc6615#section-8">RFC 6615, Section&amp;nbsp;8</a>
          (ipfixTransportSessionRecords).&quot;;
      }
      leaf templates {
        type yang:counter32;
        units &quot;Templates&quot;;
        description &quot;The number of Templates transmitted by the
          Exporting Process or received by the Collecting Process.
          Discontinuities in the value of this counter can occur at
          re-initialization of the management system, and at other
          times as indicated by the value of
          transportSessionDiscontinuityTime.
          Note that this parameter corresponds to
          ipfixTransportSessionTemplates in the IPFIX MIB module.&quot;;
        reference &quot;<a href="/doc/html/rfc6615#section-8">RFC 6615, Section&amp;nbsp;8</a>
<span class="grey"><a href="/doc/html/rfc6728">RFC 6728</a>          IPFIX/PSAMP Configuration Data Model      October 2012</span>

          (ipfixTransportSessionTemplates).&quot;;
      }
      leaf optionsTemplates {
        type yang:counter32;
        units &quot;Options Templates&quot;;
        description &quot;The number of Option Templates transmitted by the
          Exporting Process or received by the Collecting Process.
          Discontinuities in the value of this counter can occur at
          re-initialization of the management system, and at other
          times as indicated by the value of
          transportSessionDiscontinuityTime.
          Note that this parameter corresponds to
          ipfixTransportSessionOptionsTemplates in the IPFIX MIB
          module.&quot;;
        reference &quot;<a href="/doc/html/rfc6615#section-8">RFC 6615, Section&amp;nbsp;8</a>
          (ipfixTransportSessionOptionsTemplates).&quot;;
      }
      leaf transportSessionStartTime {
        type yang:date-and-time;
        description &quot;Timestamp of the start of the given Transport
          Session.
          This state parameter does not correspond to any object in
          the IPFIX MIB module.&quot;;
      }
      leaf transportSessionDiscontinuityTime {
        type yang:date-and-time;
        description &quot;Timestamp of the most recent occasion at which
          one or more of the Transport Session counters suffered a
          discontinuity.
          Note that this parameter functionally corresponds to
          ipfixTransportSessionDiscontinuityTime in the IPFIX MIB
          module.  In contrast to
          ipfixTransportSessionDiscontinuityTime, the time is
          absolute and not relative to sysUpTime.&quot;;
        reference &quot;<a href="/doc/html/rfc6615#section-8">RFC 6615, Section&amp;nbsp;8</a>
          (ipfixTransportSessionDiscontinuityTime).&quot;;
      }
      list template {
        description &quot;This list contains the Templates and Options
          Templates that are transmitted by the Exporting Process
          or received by the Collecting Process.
          Withdrawn or invalidated (Options) Templates MUST be removed
          from this list.&quot;;
        uses templateParameters;
      }
    }

<span class="grey"><a href="/doc/html/rfc6728">RFC 6728</a>          IPFIX/PSAMP Configuration Data Model      October 2012</span>

    /*****************************************************************
    * Main container
    *****************************************************************/

    container ipfix {
      description &quot;Top-level node of the IPFIX/PSAMP configuration
        data model.&quot;;
      list collectingProcess {
        if-feature collector;
        key name;
        description &quot;Collecting Process of the Monitoring Device.&quot;;
        leaf name {
          type nameType;
          description &quot;Key of this list.&quot;;
        }
        uses collectingProcessParameters;
        leaf-list exportingProcess {
          if-feature exporter;
          type leafref { path &quot;/ipfix/exportingProcess/name&quot;; }
          description &quot;Export of received records without any
            modifications.  Records are processed by all Exporting
            Processes in the list.&quot;;
        }
      }

      list observationPoint {
        if-feature meter;
        key name;
        description &quot;Observation Point of the Monitoring Device.&quot;;
        leaf name {
          type nameType;
          description &quot;Key of this list.&quot;;
        }
        uses observationPointParameters;
        leaf-list selectionProcess {
          type leafref { path &quot;/ipfix/selectionProcess/name&quot;; }
          description &quot;Selection Processes in this list process
            packets in parallel.&quot;;
        }
      }

      list selectionProcess {
        if-feature meter;
        key name;
        description &quot;Selection Process of the Monitoring Device.&quot;;
        leaf name {
          type nameType;
          description &quot;Key of this list.&quot;;
<span class="grey"><a href="/doc/html/rfc6728">RFC 6728</a>          IPFIX/PSAMP Configuration Data Model      October 2012</span>

        }
        list selector {
          key name;
          min-elements 1;
          ordered-by user;
          description &quot;List of Selectors that define the action of the
            Selection Process on a single packet.  The Selectors are
            serially invoked in the same order as they appear in this
            list.&quot;;
          leaf name {
            type nameType;
            description &quot;Key of this list.&quot;;
          }
          uses selectorParameters;
        }
        list selectionSequence {
          config false;
          description &quot;This list contains the Selection Sequence IDs
            that are assigned by the Monitoring Device to distinguish
            different Selection Sequences passing through the
            Selection Process.
            As Selection Sequence IDs are unique per Observation
            Domain, the corresponding Observation Domain IDs are
            included as well.
            With this information, it is possible to associate
            Selection Sequence (Statistics) Report Interpretations
            exported according to the PSAMP protocol with a Selection
            Process in the configuration data.&quot;;
          reference &quot;<a href="/doc/html/rfc5476">RFC 5476</a>.&quot;;
          leaf observationDomainId {
            type uint32;
            description &quot;Observation Domain ID for which the
              Selection Sequence ID is assigned.&quot;;
          }
          leaf selectionSequenceId {
            type uint64;
            description &quot;Selection Sequence ID used in the Selection
              Sequence (Statistics) Report Interpretation.&quot;;
          }
        }
        leaf cache {
          type leafref { path &quot;/ipfix/cache/name&quot;; }
          description &quot;Cache that receives the output of the
            Selection Process.&quot;;
        }
      }

      list cache {
<span class="grey"><a href="/doc/html/rfc6728">RFC 6728</a>          IPFIX/PSAMP Configuration Data Model      October 2012</span>

        if-feature meter;
        key name;
        description &quot;Cache of the Monitoring Device.&quot;;
        leaf name {
          type nameType;
          description &quot;Key of this list.&quot;;
        }
        leaf meteringProcessId {
          type uint32;
          config false;
          description &quot;The identifier of the Metering Process this
            Cache belongs to.
            This parameter corresponds to the Information Element
            meteringProcessId.  Its occurrence helps to associate
            Cache parameters with Metering Process statistics
            exported by the Monitoring Device using the Metering
            Process (Reliability) Statistics Template as
            defined by the IPFIX protocol specification.&quot;;
          reference &quot;<a href="/doc/html/rfc5101">RFC 5101</a>, Sections <a href="#section-4.1">4.1</a> and <a href="#section-4.2">4.2</a>;
            IANA registry for IPFIX Entities,
            <a href="https://www.iana.org/assignments/ipfix">http://www.iana.org/assignments/ipfix</a>.&quot;;
        }
        leaf dataRecords {
          type yang:counter64;
          units &quot;Data Records&quot;;
          config false;
          description &quot;The number of Data Records generated by this
            Cache.
            Discontinuities in the value of this counter can occur at
            re-initialization of the management system, and at other
            times as indicated by the value of
            cacheDiscontinuityTime.
            Note that this parameter corresponds to
            ipfixMeteringProcessDataRecords in the IPFIX MIB
            module.&quot;;
          reference &quot;<a href="/doc/html/rfc6615#section-8">RFC 6615, Section&amp;nbsp;8</a>
            (ipfixMeteringProcessDataRecords).&quot;;
        }
        leaf cacheDiscontinuityTime {
          type yang:date-and-time;
          config false;
          description &quot;Timestamp of the most recent occasion at which
            the counter dataRecords suffered a discontinuity.
            Note that this parameter functionally corresponds to
            ipfixMeteringProcessDiscontinuityTime in the IPFIX MIB
            module.  In contrast to
            ipfixMeteringProcessDiscontinuityTime, the time is
            absolute and not relative to sysUpTime.&quot;;
<span class="grey"><a href="/doc/html/rfc6728">RFC 6728</a>          IPFIX/PSAMP Configuration Data Model      October 2012</span>

          reference &quot;<a href="/doc/html/rfc6615#section-8">RFC 6615, Section&amp;nbsp;8</a>
            (ipfixMeteringProcessDiscontinuityTime).&quot;;
        }
        choice CacheType {
          mandatory true;
          description &quot;Type of Cache and specific parameters.&quot;;
          container immediateCache {
            if-feature immediateCache;
            description &quot;Flow expiration after the first packet;
              generation of Packet Records.&quot;;
            uses cacheLayoutParameters;
          }
          container timeoutCache {
            if-feature timeoutCache;
            description &quot;Flow expiration after active and idle
              timeout; generation of Flow Records.&quot;;
            uses flowCacheParameters;
            uses cacheLayoutParameters;
          }
          container naturalCache {
            if-feature naturalCache;
            description &quot;Flow expiration after active and idle
              timeout, or on natural termination (e.g., TCP FIN or
              TCP RST) of the Flow; generation of Flow Records.&quot;;
            uses flowCacheParameters;
            uses cacheLayoutParameters;
          }
          container permanentCache {
            if-feature permanentCache;
            description &quot;No flow expiration, periodical export with
              time interval exportInterval; generation of Flow
              Records.&quot;;
            uses flowCacheParameters;
            uses cacheLayoutParameters;
          }
        }
        leaf-list exportingProcess {
          if-feature exporter;
          type leafref { path &quot;/ipfix/exportingProcess/name&quot;; }
          description &quot;Records are exported by all Exporting Processes
            in the list.&quot;;
        }
      }

      list exportingProcess {
        if-feature exporter;
        key name;
        description &quot;Exporting Process of the Monitoring Device.&quot;;
<span class="grey"><a href="/doc/html/rfc6728">RFC 6728</a>          IPFIX/PSAMP Configuration Data Model      October 2012</span>

        leaf name {
          type nameType;
          description &quot;Key of this list.&quot;;
        }
        uses exportingProcessParameters;
      }
    }
  }
