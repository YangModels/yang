module ietf-access-control-list {
  yang-version 1.1;
  namespace &quot;urn:ietf:params:xml:ns:yang:ietf-access-control-list&quot;;
  prefix acl;

  import ietf-yang-types {
    prefix yang;
    reference
      &quot;<a href="/doc/html/rfc6991">RFC 6991</a> - Common YANG Data Types.&quot;;
  }

  import ietf-packet-fields {
    prefix pf;
    reference
      &quot;<a href="/doc/html/rfc8519">RFC 8519</a> - YANG Data Model for Network Access Control
                  Lists (ACLs).&quot;;
  }

  import ietf-interfaces {
    prefix if;
    reference
<span class="grey"><a href="/doc/html/rfc8519">RFC 8519</a>                YANG Data Model for ACLs              March 2019</span>

      &quot;<a href="/doc/html/rfc8343">RFC 8343</a> - A YANG Data Model for Interface Management.&quot;;
  }

  organization
    &quot;IETF NETMOD (Network Modeling) Working Group.&quot;;

  contact
    &quot;WG Web:  &lt;<a href="https://datatracker.ietf.org/wg/netmod/">https://datatracker.ietf.org/wg/netmod/</a>&gt;
     WG List: <a href="mailto:netmod@ietf.org">netmod@ietf.org</a>

     Editor: Mahesh Jethanandani
             <a href="mailto:mjethanandani@gmail.com">mjethanandani@gmail.com</a>
     Editor: Lisa Huang
             <a href="mailto:huangyi_99@yahoo.com">huangyi_99@yahoo.com</a>
     Editor: Sonal Agarwal
             <a href="mailto:sagarwal12@gmail.com">sagarwal12@gmail.com</a>
     Editor: Dana Blair
             <a href="mailto:dana@blairhome.com">dana@blairhome.com</a>&quot;;

  description
    &quot;This YANG module defines a component that describes the
     configuration and monitoring of Access Control Lists (ACLs).

     The key words &#x27;MUST&#x27;, &#x27;MUST NOT&#x27;, &#x27;REQUIRED&#x27;, &#x27;SHALL&#x27;,
     &#x27;SHALL NOT&#x27;, &#x27;SHOULD&#x27;, &#x27;SHOULD NOT&#x27;, &#x27;RECOMMENDED&#x27;,
     &#x27;NOT RECOMMENDED&#x27;, &#x27;MAY&#x27;, and &#x27;OPTIONAL&#x27; in this document
     are to be interpreted as described in <a href="/doc/html/bcp14">BCP 14</a> (<a href="/doc/html/rfc2119">RFC 2119</a>)
     (<a href="/doc/html/rfc8174">RFC 8174</a>) when, and only when, they appear in all
     capitals, as shown here.

     Copyright (c) 2019 IETF Trust and the persons identified as
     the document authors.  All rights reserved.

     Redistribution and use in source and binary forms, with or
     without modification, is permitted pursuant to, and subject
     to the license terms contained in, the Simplified BSD
     License set forth in <a href="#section-4">Section 4</a>.c of the IETF Trust&#x27;s Legal
     Provisions Relating to IETF Documents
     (<a href="https://trustee.ietf.org/license-info">http://trustee.ietf.org/license-info</a>).

     This version of this YANG module is part of <a href="/doc/html/rfc8519">RFC 8519</a>; see
     the RFC itself for full legal notices.&quot;;

  revision 2019-03-04 {
    description
      &quot;Initial version.&quot;;
    reference
      &quot;<a href="/doc/html/rfc8519">RFC 8519</a>: YANG Data Model for Network Access Control
<span class="grey"><a href="/doc/html/rfc8519">RFC 8519</a>                YANG Data Model for ACLs              March 2019</span>

                 Lists (ACLs).&quot;;
  }

  /*
   * Identities
   */
  /*
   * Forwarding actions for a packet
   */

  identity forwarding-action {
    description
      &quot;Base identity for actions in the forwarding category.&quot;;
  }

  identity accept {
    base forwarding-action;
    description
      &quot;Accept the packet.&quot;;
  }

  identity drop {
    base forwarding-action;
    description
      &quot;Drop packet without sending any ICMP error message.&quot;;
  }

  identity reject {
    base forwarding-action;
    description
      &quot;Drop the packet and send an ICMP error message to the source.&quot;;
  }

  /*
   * Logging actions for a packet
   */

  identity log-action {
    description
      &quot;Base identity for defining the destination for logging
       actions.&quot;;
  }

  identity log-syslog {
    base log-action;
    description
      &quot;System log (syslog) the information for the packet.&quot;;
  }
<span class="grey"><a href="/doc/html/rfc8519">RFC 8519</a>                YANG Data Model for ACLs              March 2019</span>

  identity log-none {
    base log-action;
    description
      &quot;No logging for the packet.&quot;;
  }

  /*
   * ACL type identities
   */

  identity acl-base {
    description
      &quot;Base Access Control List type for all Access Control List type
       identifiers.&quot;;
  }

  identity ipv4-acl-type {
    base acl:acl-base;
    if-feature &quot;ipv4&quot;;
    description
      &quot;An ACL that matches on fields from the IPv4 header
       (e.g., IPv4 destination address) and Layer 4 headers (e.g., TCP
       destination port).  An ACL of type ipv4 does not contain
       matches on fields in the Ethernet header or the IPv6 header.&quot;;
  }

  identity ipv6-acl-type {
    base acl:acl-base;
    if-feature &quot;ipv6&quot;;
    description
      &quot;An ACL that matches on fields from the IPv6 header
       (e.g., IPv6 destination address) and Layer 4 headers (e.g., TCP
       destination port).  An ACL of type ipv6 does not contain
       matches on fields in the Ethernet header or the IPv4 header.&quot;;
  }

  identity eth-acl-type {
    base acl:acl-base;
    if-feature &quot;eth&quot;;
    description
      &quot;An ACL that matches on fields in the Ethernet header,
       like 10/100/1000baseT or a Wi-Fi Access Control List.  An ACL
       of type ethernet does not contain matches on fields in the
       IPv4 header, the IPv6 header, or Layer 4 headers.&quot;;
  }

  identity mixed-eth-ipv4-acl-type {
    base acl:eth-acl-type;
<span class="grey"><a href="/doc/html/rfc8519">RFC 8519</a>                YANG Data Model for ACLs              March 2019</span>

    base acl:ipv4-acl-type;
    if-feature &quot;mixed-eth-ipv4&quot;;
    description
      &quot;An ACL that contains a mix of entries that match
       on fields in Ethernet headers and in IPv4 headers.
       Matching on Layer 4 header fields may also exist in the
       list.&quot;;
  }

  identity mixed-eth-ipv6-acl-type {
    base acl:eth-acl-type;
    base acl:ipv6-acl-type;
    if-feature &quot;mixed-eth-ipv6&quot;;
    description
      &quot;An ACL that contains a mix of entries that match on fields
       in Ethernet headers and in IPv6 headers.  Matching
       on Layer 4 header fields may also exist in the list.&quot;;
  }

  identity mixed-eth-ipv4-ipv6-acl-type {
    base acl:eth-acl-type;
    base acl:ipv4-acl-type;
    base acl:ipv6-acl-type;
    if-feature &quot;mixed-eth-ipv4-ipv6&quot;;
    description
      &quot;An ACL that contains a mix of entries that
       match on fields in Ethernet headers, IPv4 headers, and IPv6
       headers.  Matching on Layer 4 header fields may also exist
       in the list.&quot;;
  }

  /*
   * Features
   */

  /*
   * Features supported by device
   */
  feature match-on-eth {
    description
      &quot;The device can support matching on Ethernet headers.&quot;;
  }

  feature match-on-ipv4 {
    description
      &quot;The device can support matching on IPv4 headers.&quot;;
  }

<span class="grey"><a href="/doc/html/rfc8519">RFC 8519</a>                YANG Data Model for ACLs              March 2019</span>

  feature match-on-ipv6 {
    description
      &quot;The device can support matching on IPv6 headers.&quot;;
  }

  feature match-on-tcp {
    description
      &quot;The device can support matching on TCP headers.&quot;;
  }

  feature match-on-udp {
    description
      &quot;The device can support matching on UDP headers.&quot;;
  }

  feature match-on-icmp {
    description
      &quot;The device can support matching on ICMP (v4 and v6) headers.&quot;;
  }

  /*
   * Header classifications combinations supported by
   * device
   */

  feature eth {
    if-feature &quot;match-on-eth&quot;;
    description
      &quot;Plain Ethernet ACL supported.&quot;;
  }

  feature ipv4 {
    if-feature &quot;match-on-ipv4&quot;;
    description
      &quot;Plain IPv4 ACL supported.&quot;;
  }

  feature ipv6 {
    if-feature &quot;match-on-ipv6&quot;;
    description
      &quot;Plain IPv6 ACL supported.&quot;;
  }

  feature mixed-eth-ipv4 {
    if-feature &quot;match-on-eth and match-on-ipv4&quot;;
    description
      &quot;Ethernet and IPv4 ACL combinations supported.&quot;;
  }
<span class="grey"><a href="/doc/html/rfc8519">RFC 8519</a>                YANG Data Model for ACLs              March 2019</span>

  feature mixed-eth-ipv6 {
    if-feature &quot;match-on-eth and match-on-ipv6&quot;;
    description
      &quot;Ethernet and IPv6 ACL combinations supported.&quot;;
  }

  feature mixed-eth-ipv4-ipv6 {
    if-feature
      &quot;match-on-eth and match-on-ipv4
       and match-on-ipv6&quot;;
    description
      &quot;Ethernet, IPv4, and IPv6 ACL combinations supported.&quot;;
  }

  /*
   * Stats Features
   */
  feature interface-stats {
    description
      &quot;ACL counters are available and reported only per interface.&quot;;
  }

  feature acl-aggregate-stats {
    description
      &quot;ACL counters are aggregated over all interfaces and reported
       only per ACL entry.&quot;;
  }

  /*
   * Attachment point features
   */
  feature interface-attachment {
    description
      &quot;ACLs are set on interfaces.&quot;;
  }

  /*
   * Typedefs
   */
  typedef acl-type {
    type identityref {
      base acl-base;
    }
    description
      &quot;This type is used to refer to an ACL type.&quot;;
  }

  /*
<span class="grey"><a href="/doc/html/rfc8519">RFC 8519</a>                YANG Data Model for ACLs              March 2019</span>

   * Groupings
   */
  grouping acl-counters {
    description
      &quot;Common grouping for ACL counters.&quot;;
    leaf matched-packets {
      type yang:counter64;
      config false;
      description
        &quot;Count of the number of packets matching the current ACL
         entry.

         An implementation should provide this counter on a
         per-interface, per-ACL-entry basis if possible.

         If an implementation only supports ACL counters on a per-
         entry basis (i.e., not broken out per interface), then the
         value should be equal to the aggregate count across all
         interfaces.

         An implementation that provides counters on a per-entry, per-
         interface basis is not required to also provide an aggregate
         count, e.g., per entry -- the user is expected to be able to
         implement the required aggregation if such a count is
         needed.&quot;;
    }

    leaf matched-octets {
      type yang:counter64;
      config false;
      description
        &quot;Count of the number of octets (bytes) matching the current
         ACL entry.

         An implementation should provide this counter on a
         per-interface, per-ACL-entry basis if possible.

         If an implementation only supports ACL counters per entry
         (i.e., not broken out per interface), then the value
         should be equal to the aggregate count across all interfaces.

         An implementation that provides counters per entry per
         interface is not required to also provide an aggregate count,
         e.g., per entry -- the user is expected to be able to
         implement the required aggregation if such a count is needed.&quot;;
    }
  }

<span class="grey"><a href="/doc/html/rfc8519">RFC 8519</a>                YANG Data Model for ACLs              March 2019</span>

  /*
   * Configuration and monitoring data nodes
   */

  container acls {
    description
      &quot;This is a top-level container for Access Control Lists.
       It can have one or more acl nodes.&quot;;
    list acl {
      key &quot;name&quot;;
      description
        &quot;An ACL is an ordered list of ACEs.  Each ACE has a
         list of match criteria and a list of actions.
         Since there are several kinds of ACLs implemented
         with different attributes for different vendors,
         this model accommodates customizing ACLs for
         each kind and for each vendor.&quot;;
      leaf name {
        type string {
          length &quot;1..64&quot;;
        }
        description
          &quot;The name of the access list.  A device MAY further
           restrict the length of this name; space and special
           characters are not allowed.&quot;;
      }
      leaf type {
        type acl-type;
        description
          &quot;Type of ACL.  Indicates the primary intended
           type of match criteria (e.g., Ethernet, IPv4, IPv6, mixed,
           etc.) used in the list instance.&quot;;
      }
      container aces {
        description
          &quot;The aces container contains one or more ACE nodes.&quot;;
        list ace {
          key &quot;name&quot;;
          ordered-by user;
          description
            &quot;List of ACEs.&quot;;
          leaf name {
            type string {
              length &quot;1..64&quot;;
            }
            description
              &quot;A unique name identifying this ACE.&quot;;
          }
<span class="grey"><a href="/doc/html/rfc8519">RFC 8519</a>                YANG Data Model for ACLs              March 2019</span>

          container matches {
            description
              &quot;The rules in this set determine what fields will be
               matched upon before any action is taken on them.
               The rules are selected based on the feature set
               defined by the server and the acl-type defined.
               If no matches are defined in a particular container,
               then any packet will match that container.  If no
               matches are specified at all in an ACE, then any
               packet will match the ACE.&quot;;

            choice l2 {
              container eth {
                when &quot;derived-from-or-self(/acls/acl/type, &quot;
                   + &quot;&#x27;acl:eth-acl-type&#x27;)&quot;;
                if-feature &quot;match-on-eth&quot;;
                uses pf:acl-eth-header-fields;
                description
                  &quot;Rule set that matches Ethernet headers.&quot;;
              }
              description
                &quot;Match Layer 2 headers, for example, Ethernet
                 header fields.&quot;;
            }

            choice l3 {
              container ipv4 {
                when &quot;derived-from-or-self(/acls/acl/type, &quot;
                   + &quot;&#x27;acl:ipv4-acl-type&#x27;)&quot;;
                if-feature &quot;match-on-ipv4&quot;;
                uses pf:acl-ip-header-fields;
                uses pf:acl-ipv4-header-fields;
                description
                  &quot;Rule set that matches IPv4 headers.&quot;;
              }

              container ipv6 {
                when &quot;derived-from-or-self(/acls/acl/type, &quot;
                   + &quot;&#x27;acl:ipv6-acl-type&#x27;)&quot;;
                if-feature &quot;match-on-ipv6&quot;;
                uses pf:acl-ip-header-fields;
                uses pf:acl-ipv6-header-fields;
                description
                  &quot;Rule set that matches IPv6 headers.&quot;;
              }
              description
                &quot;Choice of either IPv4 or IPv6 headers&quot;;
            }
<span class="grey"><a href="/doc/html/rfc8519">RFC 8519</a>                YANG Data Model for ACLs              March 2019</span>

            choice l4 {
              container tcp {
                if-feature &quot;match-on-tcp&quot;;
                uses pf:acl-tcp-header-fields;
                container source-port {
                  choice source-port {
                    case range-or-operator {
                      uses pf:port-range-or-operator;
                      description
                        &quot;Source port definition from range or
                         operator.&quot;;
                    }
                    description
                      &quot;Choice of source port definition using
                       range/operator or a choice to support future
                       &#x27;case&#x27; statements, such as one enabling a
                       group of source ports to be referenced.&quot;;
                  }
                  description
                    &quot;Source port definition.&quot;;
                }
                container destination-port {
                  choice destination-port {
                    case range-or-operator {
                      uses pf:port-range-or-operator;
                      description
                        &quot;Destination port definition from range or
                         operator.&quot;;
                    }
                    description
                      &quot;Choice of destination port definition using
                       range/operator or a choice to support future
                       &#x27;case&#x27; statements, such as one enabling a
                       group of destination ports to be referenced.&quot;;
                  }
                  description
                    &quot;Destination port definition.&quot;;
                }
                description
                  &quot;Rule set that matches TCP headers.&quot;;
              }

              container udp {
                if-feature &quot;match-on-udp&quot;;
                uses pf:acl-udp-header-fields;
                container source-port {
                  choice source-port {
                    case range-or-operator {
<span class="grey"><a href="/doc/html/rfc8519">RFC 8519</a>                YANG Data Model for ACLs              March 2019</span>

                      uses pf:port-range-or-operator;
                      description
                        &quot;Source port definition from range or
                         operator.&quot;;
                    }
                    description
                      &quot;Choice of source port definition using
                       range/operator or a choice to support future
                       &#x27;case&#x27; statements, such as one enabling a
                       group of source ports to be referenced.&quot;;
                  }
                  description
                    &quot;Source port definition.&quot;;
                }
                container destination-port {
                  choice destination-port {
                    case range-or-operator {
                      uses pf:port-range-or-operator;
                      description
                        &quot;Destination port definition from range or
                         operator.&quot;;
                    }
                    description
                      &quot;Choice of destination port definition using
                       range/operator or a choice to support future
                       &#x27;case&#x27; statements, such as one enabling a
                       group of destination ports to be referenced.&quot;;
                  }
                  description
                    &quot;Destination port definition.&quot;;
                }
                description
                  &quot;Rule set that matches UDP headers.&quot;;
              }

              container icmp {
                if-feature &quot;match-on-icmp&quot;;
                uses pf:acl-icmp-header-fields;
                description
                  &quot;Rule set that matches ICMP headers.&quot;;
              }
              description
                &quot;Choice of TCP, UDP, or ICMP headers.&quot;;
            }

            leaf egress-interface {
              type if:interface-ref;
              description
<span class="grey"><a href="/doc/html/rfc8519">RFC 8519</a>                YANG Data Model for ACLs              March 2019</span>

                &quot;Egress interface.  This should not be used if this ACL
                 is attached as an egress ACL (or the value should
                 equal the interface to which the ACL is attached).&quot;;
            }

            leaf ingress-interface {
              type if:interface-ref;
              description
                &quot;Ingress interface.  This should not be used if this ACL
                 is attached as an ingress ACL (or the value should
                 equal the interface to which the ACL is attached).&quot;;
            }
          }

          container actions {
            description
              &quot;Definition of actions for this ace entry.&quot;;
            leaf forwarding {
              type identityref {
                base forwarding-action;
              }
              mandatory true;
              description
                &quot;Specifies the forwarding action per ace entry.&quot;;
            }

            leaf logging {
              type identityref {
                base log-action;
              }
              default &quot;log-none&quot;;
              description
                &quot;Specifies the log action and destination for
                 matched packets.  Default value is not to log the
                 packet.&quot;;
            }
          }
          container statistics {
            if-feature &quot;acl-aggregate-stats&quot;;
            config false;
            description
              &quot;Statistics gathered across all attachment points for the
               given ACL.&quot;;
            uses acl-counters;
          }
        }
      }
    }
<span class="grey"><a href="/doc/html/rfc8519">RFC 8519</a>                YANG Data Model for ACLs              March 2019</span>

    container attachment-points {
      description
        &quot;Enclosing container for the list of
         attachment points on which ACLs are set.&quot;;
      /*
       * Groupings
       */
      grouping interface-acl {
        description
          &quot;Grouping for per-interface ingress ACL data.&quot;;
        container acl-sets {
          description
            &quot;Enclosing container for the list of ingress ACLs on the
             interface.&quot;;
          list acl-set {
            key &quot;name&quot;;
            ordered-by user;
            description
              &quot;List of ingress ACLs on the interface.&quot;;
            leaf name {
              type leafref {
                path &quot;/acls/acl/name&quot;;
              }
              description
                &quot;Reference to the ACL name applied on the ingress.&quot;;
            }
            list ace-statistics {
              if-feature &quot;interface-stats&quot;;
              key &quot;name&quot;;
              config false;
              description
                &quot;List of ACEs.&quot;;
              leaf name {
                type leafref {
                  path &quot;/acls/acl/aces/ace/name&quot;;
                }
                description
                  &quot;Name of the ace entry.&quot;;
              }
              uses acl-counters;
            }
          }
        }
      }

      list interface {
        if-feature &quot;interface-attachment&quot;;
        key &quot;interface-id&quot;;
<span class="grey"><a href="/doc/html/rfc8519">RFC 8519</a>                YANG Data Model for ACLs              March 2019</span>

        description
          &quot;List of interfaces on which ACLs are set.&quot;;

        leaf interface-id {
          type if:interface-ref;
          description
            &quot;Reference to the interface id list key.&quot;;
        }

        container ingress {
          uses interface-acl;
          description
            &quot;The ACLs applied to the ingress interface.&quot;;
        }
        container egress {
          uses interface-acl;
          description
            &quot;The ACLs applied to the egress interface.&quot;;
        }
      }
    }
  }
}
