submodule ietf-snmp-tls {

  belongs-to ietf-snmp {
    prefix snmp;
  }

  import ietf-inet-types {
    prefix inet;
  }
  import ietf-x509-cert-to-name {
    prefix x509c2n;
  }

  include ietf-snmp-common;
  include ietf-snmp-engine;
  include ietf-snmp-target;

  organization
    &quot;IETF NETMOD (NETCONF Data Modeling Language) Working Group&quot;;

  contact
    &quot;WG Web:   &lt;<a href="https://tools.ietf.org/wg/netmod/">http://tools.ietf.org/wg/netmod/</a>&gt;
     WG List:  &lt;mailto:<a href="mailto:netmod@ietf.org">netmod@ietf.org</a>&gt;

     WG Chair: Thomas Nadeau
               &lt;mailto:<a href="mailto:tnadeau@lucidvision.com">tnadeau@lucidvision.com</a>&gt;

     WG Chair: Juergen Schoenwaelder
               &lt;mailto:<a href="mailto:j.schoenwaelder@jacobs-university.de">j.schoenwaelder@jacobs-university.de</a>&gt;

     Editor:   Martin Bjorklund
               &lt;mailto:<a href="mailto:mbj@tail-f.com">mbj@tail-f.com</a>&gt;

     Editor:   Juergen Schoenwaelder
               &lt;mailto:<a href="mailto:j.schoenwaelder@jacobs-university.de">j.schoenwaelder@jacobs-university.de</a>&gt;&quot;;

<span class="grey"><a href="/doc/html/rfc7407">RFC 7407</a>         YANG Data Model for SNMP Configuration    December 2014</span>

     description
       &quot;This submodule contains a collection of YANG definitions for
        configuring the Transport Layer Security Transport Model (TLSTM)
        of SNMP.

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc7407">RFC 7407</a>; see
        the RFC itself for full legal notices.&quot;;

     reference
       &quot;<a href="/doc/html/rfc6353">RFC 6353</a>: Transport Layer Security (TLS) Transport Model for
          the Simple Network Management Protocol (SNMP)&quot;;

     revision 2014-12-10 {
       description
         &quot;Initial revision.&quot;;
       reference
         &quot;<a href="/doc/html/rfc7407">RFC 7407</a>: A YANG Data Model for SNMP Configuration&quot;;
     }

     feature tlstm {
       description
         &quot;A server implements this feature if it supports the
         Transport Layer Security Transport Model for SNMP.&quot;;
       reference
         &quot;<a href="/doc/html/rfc6353">RFC 6353</a>: Transport Layer Security (TLS) Transport Model for
            the Simple Network Management Protocol (SNMP)&quot;;
     }

     augment /snmp:snmp/snmp:engine/snmp:listen/snmp:transport {
       if-feature tlstm;
       case tls {
         container tls {
           description
             &quot;A list of IPv4 and IPv6 addresses and ports to which the
              engine listens for SNMP messages over TLS.&quot;;

<span class="grey"><a href="/doc/html/rfc7407">RFC 7407</a>         YANG Data Model for SNMP Configuration    December 2014</span>

           leaf ip {
             type inet:ip-address;
             mandatory true;
             description
               &quot;The IPv4 or IPv6 address on which the engine listens
                for SNMP messages over TLS.&quot;;
           }
           leaf port {
             type inet:port-number;
             description
               &quot;The TCP port on which the engine listens for SNMP
                messages over TLS.

                If the port is not configured, an engine that
                acts as a Command Responder uses port 10161, and
                an engine that acts as a Notification Receiver
                uses port 10162.&quot;;
           }
         }
       }
       case dtls {
         container dtls {
           description
             &quot;A list of IPv4 and IPv6 addresses and ports to which the
              engine listens for SNMP messages over DTLS.&quot;;

           leaf ip {
             type inet:ip-address;
             mandatory true;
             description
               &quot;The IPv4 or IPv6 address on which the engine listens
                for SNMP messages over DTLS.&quot;;
           }
           leaf port {
             type inet:port-number;
             description
               &quot;The UDP port on which the engine listens for SNMP
                messages over DTLS.

                If the port is not configured, an engine that
                acts as a Command Responder uses port 10161, and
                an engine that acts as a Notification Receiver
                uses port 10162.&quot;;
           }
         }
       }
     }

<span class="grey"><a href="/doc/html/rfc7407">RFC 7407</a>         YANG Data Model for SNMP Configuration    December 2014</span>

     augment /snmp:snmp {
       if-feature tlstm;
       container tlstm {
         uses x509c2n:cert-to-name {
           description
             &quot;Defines how certificates are mapped to names.  The
              resulting name is used as a security name.&quot;;
           refine cert-to-name/map-type {
             description
               &quot;Mappings that use the snmpTlstmCertToTSNData column
                need to augment the cert-to-name list with
                additional configuration objects corresponding
                to the snmpTlstmCertToTSNData value.  Such objects
                should use the &#x27;when&#x27; statement to make them
                conditional based on the map-type.&quot;;
           }
         }
       }
     }

     grouping tls-transport {
       leaf ip {
         type inet:host;
         mandatory true;
         reference
           &quot;<a href="/doc/html/rfc3413">RFC 3413</a>: Simple Network Management Protocol (SNMP).
              Applications.
              SNMP-TARGET-MIB.snmpTargetAddrTAddress
            <a href="/doc/html/rfc6353">RFC 6353</a>: Transport Layer Security (TLS) Transport Model
              for the Simple Network Management Protocol (SNMP).
              SNMP-TLS-TM-MIB.SnmpTLSAddress&quot;;
       }
       leaf port {
         type inet:port-number;
         default 10161;
         reference
           &quot;<a href="/doc/html/rfc3413">RFC 3413</a>: Simple Network Management Protocol (SNMP).
              Applications.
              SNMP-TARGET-MIB.snmpTargetAddrTAddress
            <a href="/doc/html/rfc6353">RFC 6353</a>: Transport Layer Security (TLS) Transport Model
              for the Simple Network Management Protocol (SNMP).
              SNMP-TLS-TM-MIB.SnmpTLSAddress&quot;;
       }
       leaf client-fingerprint {
         type x509c2n:tls-fingerprint;
         reference
           &quot;<a href="/doc/html/rfc6353">RFC 6353</a>: Transport Layer Security (TLS) Transport Model
              for the Simple Network Management Protocol (SNMP).
<span class="grey"><a href="/doc/html/rfc7407">RFC 7407</a>         YANG Data Model for SNMP Configuration    December 2014</span>

              SNMP-TLS-TM-MIB.snmpTlstmParamsClientFingerprint&quot;;
       }
       leaf server-fingerprint {
         type x509c2n:tls-fingerprint;
         reference
           &quot;<a href="/doc/html/rfc6353">RFC 6353</a>: Transport Layer Security (TLS) Transport Model
              for the Simple Network Management Protocol (SNMP).
              SNMP-TLS-TM-MIB.snmpTlstmAddrServerFingerprint&quot;;
       }
       leaf server-identity {
         type snmp:admin-string;
         reference
           &quot;<a href="/doc/html/rfc6353">RFC 6353</a>: Transport Layer Security (TLS) Transport Model
              for the Simple Network Management Protocol (SNMP).
              SNMP-TLS-TM-MIB.snmpTlstmAddrServerIdentity&quot;;
       }
     }

     augment /snmp:snmp/snmp:target/snmp:transport {
       if-feature tlstm;
       case tls {
         reference
           &quot;<a href="/doc/html/rfc6353">RFC 6353</a>: Transport Layer Security (TLS) Transport Model
              for the Simple Network Management Protocol (SNMP).
              SNMP-TLS-TM-MIB.snmpTLSTCPDomain&quot;;
         container tls {
           uses tls-transport;
         }
       }
     }

     augment /snmp:snmp/snmp:target/snmp:transport {
       if-feature tlstm;
       case dtls {
         reference
           &quot;<a href="/doc/html/rfc6353">RFC 6353</a>: Transport Layer Security (TLS) Transport Model
              for the Simple Network Management Protocol (SNMP).
              SNMP-TLS-TM-MIB.snmpDTLSUDPDomain&quot;;
         container dtls {
           uses tls-transport;
         }
       }
     }
   }
