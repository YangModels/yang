module ietf-ipv4-unicast-routing {

  yang-version &quot;1.1&quot;;

  namespace &quot;urn:ietf:params:xml:ns:yang:ietf-ipv4-unicast-routing&quot;;

  prefix &quot;v4ur&quot;;

  import ietf-routing {
    prefix &quot;rt&quot;;
  }

  import ietf-inet-types {
    prefix &quot;inet&quot;;
  }
<span class="grey"><a href="/doc/html/rfc8022">RFC 8022</a>                 YANG Routing Management           November 2016</span>

     organization
       &quot;IETF NETMOD (NETCONF Data Modeling Language) Working Group&quot;;

     contact
       &quot;WG Web:   &lt;<a href="https://datatracker.ietf.org/wg/netmod/">https://datatracker.ietf.org/wg/netmod/</a>&gt;
        WG List:  &lt;mailto:<a href="mailto:netmod@ietf.org">netmod@ietf.org</a>&gt;

        WG Chair: Lou Berger
                  &lt;mailto:<a href="mailto:lberger@labn.net">lberger@labn.net</a>&gt;

        WG Chair: Kent Watsen
                  &lt;mailto:<a href="mailto:kwatsen@juniper.net">kwatsen@juniper.net</a>&gt;

        Editor:   Ladislav Lhotka
                  &lt;mailto:<a href="mailto:lhotka@nic.cz">lhotka@nic.cz</a>&gt;

        Editor:   Acee Lindem
                  &lt;mailto:<a href="mailto:acee@cisco.com">acee@cisco.com</a>&gt;&quot;;

     description
       &quot;This YANG module augments the &#x27;ietf-routing&#x27; module with basic
        configuration and state data for IPv4 unicast routing.

        Copyright (c) 2016 IETF Trust and the persons identified as
        authors of the code.  All rights reserved.

        Redistribution and use in source and binary forms, with or
        without modification, is permitted pursuant to, and subject to
        the license terms contained in, the Simplified BSD License set
        forth in <a href="#section-4">Section 4</a>.c of the IETF Trust&#x27;s Legal Provisions
        Relating to IETF Documents
        (<a href="https://trustee.ietf.org/license-info">http://trustee.ietf.org/license-info</a>).

        The key words &#x27;MUST&#x27;, &#x27;MUST NOT&#x27;, &#x27;REQUIRED&#x27;, &#x27;SHALL&#x27;, &#x27;SHALL
        NOT&#x27;, &#x27;SHOULD&#x27;, &#x27;SHOULD NOT&#x27;, &#x27;RECOMMENDED&#x27;, &#x27;MAY&#x27;, and
        &#x27;OPTIONAL&#x27; in the module text are to be interpreted as described
        in <a href="/doc/html/rfc2119">RFC 2119</a>.

        This version of this YANG module is part of <a href="/doc/html/rfc8022">RFC 8022</a>;
        see the RFC itself for full legal notices.&quot;;

     revision 2016-11-04 {
       description
         &quot;Initial revision.&quot;;
       reference
         &quot;<a href="/doc/html/rfc8022">RFC 8022</a>: A YANG Data Model for Routing Management&quot;;
     }

<span class="grey"><a href="/doc/html/rfc8022">RFC 8022</a>                 YANG Routing Management           November 2016</span>

     /* Identities */

     identity ipv4-unicast {
       base rt:ipv4;
       description
         &quot;This identity represents the IPv4 unicast address family.&quot;;
     }

     /* State data */

     augment &quot;/rt:routing-state/rt:ribs/rt:rib/rt:routes/rt:route&quot; {
       when &quot;derived-from-or-self(../../rt:address-family, &quot;
          + &quot;&#x27;v4ur:ipv4-unicast&#x27;)&quot; {
         description
           &quot;This augment is valid only for IPv4 unicast.&quot;;
       }
       description
         &quot;This leaf augments an IPv4 unicast route.&quot;;
       leaf destination-prefix {
         type inet:ipv4-prefix;
         description
           &quot;IPv4 destination prefix.&quot;;
       }
     }

     augment &quot;/rt:routing-state/rt:ribs/rt:rib/rt:routes/rt:route/&quot;
           + &quot;rt:next-hop/rt:next-hop-options/rt:simple-next-hop&quot; {
       when &quot;derived-from-or-self(../../../rt:address-family, &quot;
          + &quot;&#x27;v4ur:ipv4-unicast&#x27;)&quot; {
         description
           &quot;This augment is valid only for IPv4 unicast.&quot;;
       }
       description
         &quot;Augment &#x27;simple-next-hop&#x27; case in IPv4 unicast routes.&quot;;
       leaf next-hop-address {
         type inet:ipv4-address;
         description
           &quot;IPv4 address of the next hop.&quot;;
       }
     }

     augment &quot;/rt:routing-state/rt:ribs/rt:rib/rt:routes/rt:route/&quot;
           + &quot;rt:next-hop/rt:next-hop-options/rt:next-hop-list/&quot;
           + &quot;rt:next-hop-list/rt:next-hop&quot; {
       when &quot;derived-from-or-self(../../../../../rt:address-family, &quot;
          + &quot;&#x27;v4ur:ipv4-unicast&#x27;)&quot; {
         description
           &quot;This augment is valid only for IPv4 unicast.&quot;;
<span class="grey"><a href="/doc/html/rfc8022">RFC 8022</a>                 YANG Routing Management           November 2016</span>

       }
       description
         &quot;This leaf augments the &#x27;next-hop-list&#x27; case of IPv4 unicast
          routes.&quot;;
       leaf address {
         type inet:ipv4-address;
         description
           &quot;IPv4 address of the next-hop.&quot;;
       }
     }

     augment
       &quot;/rt:routing-state/rt:ribs/rt:rib/rt:active-route/rt:input&quot; {
       when &quot;derived-from-or-self(../rt:address-family, &quot;
          + &quot;&#x27;v4ur:ipv4-unicast&#x27;)&quot; {
         description
           &quot;This augment is valid only for IPv4 unicast RIBs.&quot;;
       }
       description
         &quot;This augment adds the input parameter of the &#x27;active-route&#x27;
          action.&quot;;
       leaf destination-address {
         type inet:ipv4-address;
         description
           &quot;IPv4 destination address.&quot;;
       }
     }

     augment &quot;/rt:routing-state/rt:ribs/rt:rib/rt:active-route/&quot;
           + &quot;rt:output/rt:route&quot; {
       when &quot;derived-from-or-self(../../rt:address-family, &quot;
          + &quot;&#x27;v4ur:ipv4-unicast&#x27;)&quot; {
         description
           &quot;This augment is valid only for IPv4 unicast.&quot;;
       }
       description
         &quot;This augment adds the destination prefix to the reply of the
          &#x27;active-route&#x27; action.&quot;;
       leaf destination-prefix {
         type inet:ipv4-prefix;
         description
           &quot;IPv4 destination prefix.&quot;;
       }
     }

     augment &quot;/rt:routing-state/rt:ribs/rt:rib/rt:active-route/&quot;
           + &quot;rt:output/rt:route/rt:next-hop/rt:next-hop-options/&quot;
           + &quot;rt:simple-next-hop&quot; {
<span class="grey"><a href="/doc/html/rfc8022">RFC 8022</a>                 YANG Routing Management           November 2016</span>

       when &quot;derived-from-or-self(../../../rt:address-family, &quot;
          + &quot;&#x27;v4ur:ipv4-unicast&#x27;)&quot; {
         description
           &quot;This augment is valid only for IPv4 unicast.&quot;;
       }
       description
         &quot;Augment &#x27;simple-next-hop&#x27; case in the reply to the
          &#x27;active-route&#x27; action.&quot;;
       leaf next-hop-address {
         type inet:ipv4-address;
         description
           &quot;IPv4 address of the next hop.&quot;;
       }
     }

     augment &quot;/rt:routing-state/rt:ribs/rt:rib/rt:active-route/&quot;
           + &quot;rt:output/rt:route/rt:next-hop/rt:next-hop-options/&quot;
           + &quot;rt:next-hop-list/rt:next-hop-list/rt:next-hop&quot; {
       when &quot;derived-from-or-self(../../../../../rt:address-family, &quot;
          + &quot;&#x27;v4ur:ipv4-unicast&#x27;)&quot; {
         description
           &quot;This augment is valid only for IPv4 unicast.&quot;;
       }
       description
         &quot;Augment &#x27;next-hop-list&#x27; case in the reply to the
          &#x27;active-route&#x27; action.&quot;;
       leaf next-hop-address {
         type inet:ipv4-address;
         description
           &quot;IPv4 address of the next hop.&quot;;
       }
     }

     /* Configuration data */

     augment &quot;/rt:routing/rt:control-plane-protocols/&quot;
           + &quot;rt:control-plane-protocol/rt:static-routes&quot; {
       description
         &quot;This augment defines the configuration of the &#x27;static&#x27;
          pseudo-protocol with data specific to IPv4 unicast.&quot;;
       container ipv4 {
         description
           &quot;Configuration of a &#x27;static&#x27; pseudo-protocol instance
            consists of a list of routes.&quot;;
         list route {
           key &quot;destination-prefix&quot;;
           description
             &quot;A list of static routes.&quot;;
<span class="grey"><a href="/doc/html/rfc8022">RFC 8022</a>                 YANG Routing Management           November 2016</span>

           leaf destination-prefix {
             type inet:ipv4-prefix;
             mandatory &quot;true&quot;;
             description
               &quot;IPv4 destination prefix.&quot;;
           }
           leaf description {
             type string;
             description
               &quot;Textual description of the route.&quot;;
           }
           container next-hop {
             description
               &quot;Configuration of next-hop.&quot;;
             uses rt:next-hop-content {
               augment &quot;next-hop-options/simple-next-hop&quot; {
                 description
                   &quot;Augment &#x27;simple-next-hop&#x27; case in IPv4 static
                    routes.&quot;;
                 leaf next-hop-address {
                   type inet:ipv4-address;
                   description
                     &quot;IPv4 address of the next hop.&quot;;
                 }
               }
               augment &quot;next-hop-options/next-hop-list/next-hop-list/&quot;
                     + &quot;next-hop&quot; {
                 description
                   &quot;Augment &#x27;next-hop-list&#x27; case in IPv4 static
                    routes.&quot;;
                 leaf next-hop-address {
                   type inet:ipv4-address;
                   description
                     &quot;IPv4 address of the next hop.&quot;;
                 }
               }
             }
           }
         }
       }
     }
   }
