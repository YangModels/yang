module ietf-sztp-bootstrap-server {
  yang-version 1.1;
  namespace &quot;urn:ietf:params:xml:ns:yang:ietf-sztp-bootstrap-server&quot;;
  prefix sztp-svr;

  organization
    &quot;IETF NETCONF (Network Configuration) Working Group&quot;;
  contact
    &quot;WG Web:   &lt;<a href="https://datatracker.ietf.org/wg/netconf/">https://datatracker.ietf.org/wg/netconf/</a>&gt;
     WG List:  &lt;mailto:<a href="mailto:netconf@ietf.org">netconf@ietf.org</a>&gt;
     Author:   Kent Watsen &lt;mailto:<a href="mailto:kent%2Bietf@watsen.net">kent+ietf@watsen.net</a>&gt;&quot;;
  description
    &quot;This module defines an interface for bootstrap servers, as
     defined by <a href="/doc/html/rfc8572">RFC 8572</a> (&#x27;Secure Zero Touch Provisioning (SZTP)&#x27;).

     The key words &#x27;MUST&#x27;, &#x27;MUST NOT&#x27;, &#x27;REQUIRED&#x27;, &#x27;SHALL&#x27;,
     &#x27;SHALL NOT&#x27;, &#x27;SHOULD&#x27;, &#x27;SHOULD NOT&#x27;, &#x27;RECOMMENDED&#x27;,
     &#x27;NOT RECOMMENDED&#x27;, &#x27;MAY&#x27;, and &#x27;OPTIONAL&#x27; in this document
     are to be interpreted as described in <a href="/doc/html/bcp14">BCP 14</a> (<a href="/doc/html/rfc2119">RFC 2119</a>)
     (<a href="/doc/html/rfc8174">RFC 8174</a>) when, and only when, they appear in all
     capitals, as shown here.

     Copyright (c) 2019 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">https://trustee.ietf.org/license-info</a>).

     This version of this YANG module is part of <a href="/doc/html/rfc8572">RFC 8572</a>; see the
     RFC itself for full legal notices.&quot;;

  revision 2019-04-30 {
    description
<span class="grey"><a href="/doc/html/rfc8572">RFC 8572</a>          Secure Zero Touch Provisioning (SZTP)       April 2019</span>

         &quot;Initial version&quot;;
       reference
         &quot;<a href="/doc/html/rfc8572">RFC 8572</a>: Secure Zero Touch Provisioning (SZTP)&quot;;
     }

     // features

     feature redirect-server {
       description
         &quot;The server supports being a &#x27;redirect server&#x27;.&quot;;
     }

     feature onboarding-server {
       description
         &quot;The server supports being an &#x27;onboarding server&#x27;.&quot;;
     }

     // typedefs

     typedef cms {
       type binary;
       description
         &quot;A CMS structure, as specified in <a href="/doc/html/rfc5652">RFC 5652</a>, encoded using
          ASN.1 distinguished encoding rules (DER), as specified in
          ITU-T X.690.&quot;;
       reference
         &quot;<a href="/doc/html/rfc5652">RFC 5652</a>:
            Cryptographic Message Syntax (CMS)
          ITU-T X.690:
            Information technology - ASN.1 encoding rules:
            Specification of Basic Encoding Rules (BER),
            Canonical Encoding Rules (CER) and Distinguished
            Encoding Rules (DER)&quot;;
     }

     // RPCs

     rpc get-bootstrapping-data {
       description
         &quot;This RPC enables a device, as identified by the RESTCONF
          username, to obtain bootstrapping data that has been made
          available for it.&quot;;
       input {
         leaf signed-data-preferred {
           type empty;
           description
             &quot;This optional input parameter enables a device to
              communicate to the bootstrap server that it prefers
<span class="grey"><a href="/doc/html/rfc8572">RFC 8572</a>          Secure Zero Touch Provisioning (SZTP)       April 2019</span>

              to receive signed data.  Devices SHOULD always send
              this parameter when the bootstrap server is untrusted.
              Upon receiving this input parameter, the bootstrap
              server MUST return either signed data or unsigned
              redirect information; the bootstrap server MUST NOT
              return unsigned onboarding information.&quot;;
         }
         leaf hw-model {
           type string;
           description
             &quot;This optional input parameter enables a device to
              communicate to the bootstrap server its vendor-specific
              hardware model number.  This parameter may be needed,
              for instance, when a device&#x27;s IDevID certificate does
              not include the &#x27;hardwareModelName&#x27; value in its
              subjectAltName field, as is allowed by 802.1AR.&quot;;
           reference
             &quot;IEEE 802.1AR: IEEE Standard for Local and
                metropolitan area networks - Secure
                Device Identity&quot;;
         }
         leaf os-name {
           type string;
           description
             &quot;This optional input parameter enables a device to
              communicate to the bootstrap server the name of its
              operating system.  This parameter may be useful if
              the device, as identified by its serial number, can
              run more than one type of operating system (e.g.,
              on a white-box system.&quot;;
         }
         leaf os-version {
           type string;
           description
             &quot;This optional input parameter enables a device to
              communicate to the bootstrap server the version of its
              operating system.  This parameter may be used by a
              bootstrap server to return an operating-system-specific
              response to the device, thus negating the need for a
              potentially expensive boot image update.&quot;;
         }
         leaf nonce {
           type binary {
             length &quot;16..32&quot;;
           }
           description
             &quot;This optional input parameter enables a device to
              communicate to the bootstrap server a nonce value.
<span class="grey"><a href="/doc/html/rfc8572">RFC 8572</a>          Secure Zero Touch Provisioning (SZTP)       April 2019</span>

              This may be especially useful for devices lacking
              an accurate clock, as then the bootstrap server
              can dynamically obtain from the manufacturer a
              voucher with the nonce value in it, as described
              in <a href="/doc/html/rfc8366">RFC 8366</a>.&quot;;
           reference
             &quot;<a href="/doc/html/rfc8366">RFC 8366</a>:
                A Voucher Artifact for Bootstrapping Protocols&quot;;
         }
       }
       output {
         leaf reporting-level {
           if-feature &quot;onboarding-server&quot;;
           type enumeration {
             enum minimal {
               description
                 &quot;Send just the progress reports required by <a href="/doc/html/rfc8572">RFC 8572</a>.&quot;;
               reference
                 &quot;<a href="/doc/html/rfc8572">RFC 8572</a>: Secure Zero Touch Provisioning (SZTP)&quot;;
             }
             enum verbose {
               description
                 &quot;Send additional progress reports that might help
                  troubleshooting an SZTP bootstrapping issue.&quot;;
             }
           }
           default &quot;minimal&quot;;
           description
             &quot;Specifies the reporting level for progress reports the
              bootstrap server would like to receive when processing
              onboarding information.  Progress reports are not sent
              when processing redirect information or when the
              bootstrap server is untrusted (e.g., device sent the
              &#x27;&lt;signed-data-preferred&gt;&#x27; input parameter).&quot;;
         }
         leaf conveyed-information {
           type cms;
           mandatory true;
           description
             &quot;An SZTP conveyed information artifact, as described in
              <a href="/doc/html/rfc8572#section-3.1">Section&amp;nbsp;3.1 of RFC 8572</a>.&quot;;
           reference
             &quot;<a href="/doc/html/rfc8572">RFC 8572</a>: Secure Zero Touch Provisioning (SZTP)&quot;;
         }
         leaf owner-certificate {
           type cms;
           must &#x27;../ownership-voucher&#x27; {
             description
<span class="grey"><a href="/doc/html/rfc8572">RFC 8572</a>          Secure Zero Touch Provisioning (SZTP)       April 2019</span>

               &quot;An ownership voucher must be present whenever an owner
                certificate is presented.&quot;;
           }
           description
             &quot;An owner certificate artifact, as described in <a href="/doc/html/rfc8572#section-3.2">Section</a>
              <a href="/doc/html/rfc8572#section-3.2">3.2 of RFC 8572</a>.  This leaf is optional because it is
              only needed when the conveyed information artifact is
              signed.&quot;;
           reference
             &quot;<a href="/doc/html/rfc8572">RFC 8572</a>: Secure Zero Touch Provisioning (SZTP)&quot;;
         }
         leaf ownership-voucher {
           type cms;
           must &#x27;../owner-certificate&#x27; {
             description
               &quot;An owner certificate must be present whenever an
                ownership voucher is presented.&quot;;
           }
           description
             &quot;An ownership voucher artifact, as described by <a href="/doc/html/rfc8572#section-3.3">Section</a>
              <a href="/doc/html/rfc8572#section-3.3">3.3 of RFC 8572</a>.  This leaf is optional because it is
              only needed when the conveyed information artifact is
              signed.&quot;;
           reference
             &quot;<a href="/doc/html/rfc8572">RFC 8572</a>: Secure Zero Touch Provisioning (SZTP)&quot;;
         }
       }
     }

     rpc report-progress {
       if-feature &quot;onboarding-server&quot;;
       description
         &quot;This RPC enables a device, as identified by the RESTCONF
          username, to report its bootstrapping progress to the
          bootstrap server.  This RPC is expected to be used when
          the device obtains onboarding-information from a trusted
          bootstrap server.&quot;;
       input {
         leaf progress-type {
           type enumeration {
             enum bootstrap-initiated {
               description
                 &quot;Indicates that the device just used the
                  &#x27;get-bootstrapping-data&#x27; RPC.  The &#x27;message&#x27; node
                  below MAY contain any additional information that
                  the manufacturer thinks might be useful.&quot;;
             }
             enum parsing-initiated {
<span class="grey"><a href="/doc/html/rfc8572">RFC 8572</a>          Secure Zero Touch Provisioning (SZTP)       April 2019</span>

               description
                 &quot;Indicates that the device is about to start parsing
                  the onboarding information.  This progress type is
                  only for when parsing is implemented as a distinct
                  step.&quot;;
             }
             enum parsing-warning {
               description
                 &quot;Indicates that the device had a non-fatal error when
                  parsing the response from the bootstrap server.  The
                  &#x27;message&#x27; node below SHOULD indicate the specific
                  warning that occurred.&quot;;
             }
             enum parsing-error {
               description
                 &quot;Indicates that the device encountered a fatal error
                  when parsing the response from the bootstrap server.
                  For instance, this could be due to malformed encoding,
                  the device expecting signed data when only unsigned
                  data is provided, the ownership voucher not listing
                  the device&#x27;s serial number, or because the signature
                  didn&#x27;t match.  The &#x27;message&#x27; node below SHOULD
                  indicate the specific error.  This progress type
                  also indicates that the device has abandoned trying
                  to bootstrap off this bootstrap server.&quot;;
             }
             enum parsing-complete {
               description
                 &quot;Indicates that the device successfully completed
                  parsing the onboarding information.  This progress
                  type is only for when parsing is implemented as a
                  distinct step.&quot;;
             }
             enum boot-image-initiated {
               description
                 &quot;Indicates that the device is about to start
                  processing the boot image information.&quot;;
             }
             enum boot-image-warning {
               description
                 &quot;Indicates that the device encountered a non-fatal
                  error condition when trying to install a boot image.
                  A possible reason might include a need to reformat a
                  partition causing loss of data.  The &#x27;message&#x27; node
                  below SHOULD indicate any warning messages that were
                  generated.&quot;;
             }
             enum boot-image-error {
<span class="grey"><a href="/doc/html/rfc8572">RFC 8572</a>          Secure Zero Touch Provisioning (SZTP)       April 2019</span>

               description
                 &quot;Indicates that the device encountered an error when
                  trying to install a boot image, which could be for
                  reasons such as a file server being unreachable,
                  file not found, signature mismatch, etc.  The
                  &#x27;message&#x27; node SHOULD indicate the specific error
                  that occurred.  This progress type also indicates
                  that the device has abandoned trying to bootstrap
                  off this bootstrap server.&quot;;
             }
             enum boot-image-mismatch {
               description
                 &quot;Indicates that the device has determined that
                  it is not running the correct boot image.  This
                  message SHOULD precipitate trying to download
                  a boot image.&quot;;
             }
             enum boot-image-installed-rebooting {
               description
                 &quot;Indicates that the device successfully installed
                  a new boot image and is about to reboot.  After
                  sending this progress type, the device is not
                  expected to access the bootstrap server again
                  for this bootstrapping attempt.&quot;;
             }
             enum boot-image-complete {
               description
                 &quot;Indicates that the device believes that it is
                  running the correct boot image.&quot;;
             }
             enum pre-script-initiated {
               description
                 &quot;Indicates that the device is about to execute the
                  &#x27;pre-configuration-script&#x27;.&quot;;
             }
             enum pre-script-warning {
               description
                 &quot;Indicates that the device obtained a warning from the
                  &#x27;pre-configuration-script&#x27; when it was executed.  The
                  &#x27;message&#x27; node below SHOULD capture any output the
                  script produces.&quot;;
             }
             enum pre-script-error {
               description
                 &quot;Indicates that the device obtained an error from the
                  &#x27;pre-configuration-script&#x27; when it was executed.  The
                  &#x27;message&#x27; node below SHOULD capture any output the
                  script produces.  This progress type also indicates
<span class="grey"><a href="/doc/html/rfc8572">RFC 8572</a>          Secure Zero Touch Provisioning (SZTP)       April 2019</span>

                  that the device has abandoned trying to bootstrap
                  off this bootstrap server.&quot;;
             }
             enum pre-script-complete {
               description
                 &quot;Indicates that the device successfully executed the
                  &#x27;pre-configuration-script&#x27;.&quot;;
             }
             enum config-initiated {
               description
                 &quot;Indicates that the device is about to commit the
                  initial configuration.&quot;;
             }
             enum config-warning {
               description
                 &quot;Indicates that the device obtained warning messages
                  when it committed the initial configuration.  The
                  &#x27;message&#x27; node below SHOULD indicate any warning
                  messages that were generated.&quot;;
             }
             enum config-error {
               description
                 &quot;Indicates that the device obtained error messages
                  when it committed the initial configuration.  The
                  &#x27;message&#x27; node below SHOULD indicate the error
                  messages that were generated.  This progress type
                  also indicates that the device has abandoned trying
                  to bootstrap off this bootstrap server.&quot;;
             }
             enum config-complete {
               description
                 &quot;Indicates that the device successfully committed
                  the initial configuration.&quot;;
             }
             enum post-script-initiated {
               description
                 &quot;Indicates that the device is about to execute the
                  &#x27;post-configuration-script&#x27;.&quot;;
             }
             enum post-script-warning {
               description
                 &quot;Indicates that the device obtained a warning from the
                  &#x27;post-configuration-script&#x27; when it was executed.  The
                  &#x27;message&#x27; node below SHOULD capture any output the
                  script produces.&quot;;
             }
             enum post-script-error {
               description
<span class="grey"><a href="/doc/html/rfc8572">RFC 8572</a>          Secure Zero Touch Provisioning (SZTP)       April 2019</span>

                 &quot;Indicates that the device obtained an error from the
                  &#x27;post-configuration-script&#x27; when it was executed.  The
                  &#x27;message&#x27; node below SHOULD capture any output the
                  script produces.  This progress type also indicates
                  that the device has abandoned trying to bootstrap
                  off this bootstrap server.&quot;;
             }
             enum post-script-complete {
               description
                 &quot;Indicates that the device successfully executed the
                  &#x27;post-configuration-script&#x27;.&quot;;
             }
             enum bootstrap-warning {
               description
                 &quot;Indicates that a warning condition occurred for which
                  no other &#x27;progress-type&#x27; enumeration is deemed
                  suitable.  The &#x27;message&#x27; node below SHOULD describe
                  the warning.&quot;;
             }
             enum bootstrap-error {
               description
                 &quot;Indicates that an error condition occurred for which
                  no other &#x27;progress-type&#x27; enumeration is deemed
                  suitable.  The &#x27;message&#x27; node below SHOULD describe
                  the error.  This progress type also indicates that
                  the device has abandoned trying to bootstrap off
                  this bootstrap server.&quot;;
             }
             enum bootstrap-complete {
               description
                 &quot;Indicates that the device successfully processed
                  all &#x27;onboarding-information&#x27; provided and that it
                  is ready to be managed.  The &#x27;message&#x27; node below
                  MAY contain any additional information that the
                  manufacturer thinks might be useful.  After sending
                  this progress type, the device is not expected to
                  access the bootstrap server again.&quot;;
             }
             enum informational {
               description
                 &quot;Indicates any additional information not captured
                  by any of the other progress types.  For instance,
                  a message indicating that the device is about to
                  reboot after having installed a boot image could
                  be provided.  The &#x27;message&#x27; node below SHOULD
                  contain information that the manufacturer thinks
                  might be useful.&quot;;
             }
<span class="grey"><a href="/doc/html/rfc8572">RFC 8572</a>          Secure Zero Touch Provisioning (SZTP)       April 2019</span>

           }
           mandatory true;
           description
             &quot;The type of progress report provided.&quot;;
         }
         leaf message {
           type string;
           description
             &quot;An optional arbitrary value.&quot;;
         }
         container ssh-host-keys {
           when &quot;../progress-type = &#x27;bootstrap-complete&#x27;&quot; {
             description
               &quot;SSH host keys are only sent when the progress type
                is &#x27;bootstrap-complete&#x27;.&quot;;
           }
           description
             &quot;A list of SSH host keys an NMS may use to authenticate
              subsequent SSH-based connections to this device (e.g.,
              netconf-ssh, netconf-ch-ssh).&quot;;
           list ssh-host-key {
             description
               &quot;An SSH host key an NMS may use to authenticate
                subsequent SSH-based connections to this device
                (e.g., netconf-ssh and netconf-ch-ssh).&quot;;
             reference
               &quot;<a href="/doc/html/rfc4253">RFC 4253</a>: The Secure Shell (SSH) Transport Layer
                          Protocol&quot;;
             leaf algorithm {
               type string;
               mandatory true;
               description
                 &quot;The public key algorithm name for this SSH key.

                  Valid values are listed in the &#x27;Public Key Algorithm
                  Names&#x27; subregistry of the &#x27;Secure Shell (SSH) Protocol
                  Parameters&#x27; registry maintained by IANA.&quot;;
               reference
                 &quot;<a href="/doc/html/rfc4250">RFC 4250</a>: The Secure Shell (SSH) Protocol Assigned
                            Numbers
                  IANA URL: &lt;<a href="https://www.iana">https://www.iana</a>.org/assignments/ssh-para\\
                            meters&gt;
                            (&#x27;\\&#x27; added for formatting reasons)&quot;;
             }
             leaf key-data {
               type binary;
               mandatory true;
               description
<span class="grey"><a href="/doc/html/rfc8572">RFC 8572</a>          Secure Zero Touch Provisioning (SZTP)       April 2019</span>

                 &quot;The binary public key data for this SSH key, as
                  specified by <a href="/doc/html/rfc4253#section-6.6">RFC 4253, Section&amp;nbsp;6.6</a>; that is:

                    string    certificate or public key format
                              identifier
                    byte[n]   key/certificate data.&quot;;
               reference
                 &quot;<a href="/doc/html/rfc4253">RFC 4253</a>: The Secure Shell (SSH) Transport Layer
                            Protocol&quot;;
             }
           }
         }
         container trust-anchor-certs {
           when &quot;../progress-type = &#x27;bootstrap-complete&#x27;&quot; {
             description
               &quot;Trust anchors are only sent when the progress type
                is &#x27;bootstrap-complete&#x27;.&quot;;
           }
           description
             &quot;A list of trust anchor certificates an NMS may use to
              authenticate subsequent certificate-based connections
              to this device (e.g., restconf-tls, netconf-tls, or
              even netconf-ssh with X.509 support from <a href="/doc/html/rfc6187">RFC 6187</a>).
              In practice, trust anchors for IDevID certificates do
              not need to be conveyed using this mechanism.&quot;;
           reference
             &quot;<a href="/doc/html/rfc6187">RFC 6187</a>: X.509v3 Certificates for Secure Shell
                        Authentication&quot;;
           leaf-list trust-anchor-cert {
             type cms;
             description
               &quot;A CMS structure whose topmost content type MUST be the
                signed-data content type, as described by <a href="/doc/html/rfc5652#section-5">Section&amp;nbsp;5 of
                RFC 5652</a>.

                The CMS MUST contain the chain of X.509 certificates
                needed to authenticate the certificate presented by
                the device.

                The CMS MUST contain only a single chain of
                certificates.  The last certificate in the chain
                MUST be the issuer for the device&#x27;s end-entity
                certificate.

                In all cases, the chain MUST include a self-signed
                root certificate.  In the case where the root
                certificate is itself the issuer of the device&#x27;s
                end-entity certificate, only one certificate is
<span class="grey"><a href="/doc/html/rfc8572">RFC 8572</a>          Secure Zero Touch Provisioning (SZTP)       April 2019</span>

                present.

                This CMS encodes the degenerate form of the SignedData
                structure that is commonly used to disseminate X.509
                certificates and revocation objects (<a href="/doc/html/rfc5280">RFC 5280</a>).&quot;;
             reference
               &quot;<a href="/doc/html/rfc5280">RFC 5280</a>: Internet X.509 Public Key Infrastructure
                          Certificate and Certificate Revocation List
                          (CRL) Profile
                <a href="/doc/html/rfc5652">RFC 5652</a>: Cryptographic Message Syntax (CMS)&quot;;
           }
         }
       }
     }
   }
