module iana-crypt-hash {
  namespace &quot;urn:ietf:params:xml:ns:yang:iana-crypt-hash&quot;;
  prefix ianach;

  organization &quot;IANA&quot;;
  contact
    &quot;        Internet Assigned Numbers Authority

     Postal: ICANN
             12025 Waterfront Drive, Suite 300
             Los Angeles, CA  90094-2536
             United States

     Tel:    +1 310 301 5800
     E-Mail: <a href="mailto:iana@iana.org">iana@iana.org</a>&gt;&quot;;
  description
    &quot;This YANG module defines a type for storing passwords
     using a hash function and features to indicate which hash
     functions are supported by an implementation.

     The latest revision of this YANG module can be obtained from
     the IANA web site.

<span class="grey"><a href="/doc/html/rfc7317">RFC 7317</a>                 YANG System Management              August 2014</span>

        Requests for new values should be made to IANA via
        email (<a href="mailto:iana@iana.org">iana@iana.org</a>).

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        The initial version of this YANG module is part of <a href="/doc/html/rfc7317">RFC 7317</a>;
        see the RFC itself for full legal notices.&quot;;

     revision 2014-08-06 {
       description
         &quot;Initial revision.&quot;;
       reference
         &quot;<a href="/doc/html/rfc7317">RFC 7317</a>: A YANG Data Model for System Management&quot;;
     }

     typedef crypt-hash {
       type string {
         pattern
           &#x27;$0$.*&#x27;
         + &#x27;|$1$[a-zA-Z0-9./]{1,8}$[a-zA-Z0-9./]{22}&#x27;
         + &#x27;|$5$(rounds=\d+$)?[a-zA-Z0-9./]{1,16}$[a-zA-Z0-9./]{43}&#x27;
         + &#x27;|$6$(rounds=\d+$)?[a-zA-Z0-9./]{1,16}$[a-zA-Z0-9./]{86}&#x27;;
       }
       description
         &quot;The crypt-hash type is used to store passwords using
          a hash function.  The algorithms for applying the hash
          function and encoding the result are implemented in
          various UNIX systems as the function crypt(3).

          A value of this type matches one of the forms:

            $0$&lt;clear text password&gt;
            $&lt;id&gt;$&lt;salt&gt;$&lt;password hash&gt;
            $&lt;id&gt;$&lt;parameter&gt;$&lt;salt&gt;$&lt;password hash&gt;

          The &#x27;$0$&#x27; prefix signals that the value is clear text.  When
          such a value is received by the server, a hash value is
          calculated, and the string &#x27;$&lt;id&gt;$&lt;salt&gt;$&#x27; or
          $&lt;id&gt;$&lt;parameter&gt;$&lt;salt&gt;$ is prepended to the result.  This
          value is stored in the configuration data store.
<span class="grey"><a href="/doc/html/rfc7317">RFC 7317</a>                 YANG System Management              August 2014</span>

          If a value starting with &#x27;$&lt;id&gt;$&#x27;, where &lt;id&gt; is not &#x27;0&#x27;, is
          received, the server knows that the value already represents a
          hashed value and stores it &#x27;as is&#x27; in the data store.

          When a server needs to verify a password given by a user, it
          finds the stored password hash string for that user, extracts
          the salt, and calculates the hash with the salt and given
          password as input.  If the calculated hash value is the same
          as the stored value, the password given by the client is
          accepted.

          This type defines the following hash functions:

            id | hash function | feature
            ---+---------------+-------------------
             1 | MD5           | crypt-hash-md5
             5 | SHA-256       | crypt-hash-sha-256
             6 | SHA-512       | crypt-hash-sha-512

          The server indicates support for the different hash functions
          by advertising the corresponding feature.&quot;;
       reference
         &quot;IEEE Std 1003.1-2008 - crypt() function
          <a href="/doc/html/rfc1321">RFC 1321</a>: The MD5 Message-Digest Algorithm
          FIPS.180-4.2012: Secure Hash Standard (SHS)&quot;;
     }

     feature crypt-hash-md5 {
       description
         &quot;Indicates that the device supports the MD5
          hash function in &#x27;crypt-hash&#x27; values.&quot;;
       reference &quot;<a href="/doc/html/rfc1321">RFC 1321</a>: The MD5 Message-Digest Algorithm&quot;;
     }

     feature crypt-hash-sha-256 {
       description
         &quot;Indicates that the device supports the SHA-256
          hash function in &#x27;crypt-hash&#x27; values.&quot;;
       reference &quot;FIPS.180-4.2012: Secure Hash Standard (SHS)&quot;;
     }

<span class="grey"><a href="/doc/html/rfc7317">RFC 7317</a>                 YANG System Management              August 2014</span>

     feature crypt-hash-sha-512 {
       description
         &quot;Indicates that the device supports the SHA-512
          hash function in &#x27;crypt-hash&#x27; values.&quot;;
       reference &quot;FIPS.180-4.2012: Secure Hash Standard (SHS)&quot;;
     }

   }
