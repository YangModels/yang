module ietf-netconf-monitoring {

  namespace &quot;urn:ietf:params:xml:ns:yang:ietf-netconf-monitoring&quot;;
  prefix &quot;ncm&quot;;

  import ietf-yang-types { prefix yang; }
  import ietf-inet-types { prefix inet; }

  organization
    &quot;IETF NETCONF (Network Configuration) Working Group&quot;;

  contact
    &quot;WG Web:   &lt;<a href="https://tools.ietf.org/wg/netconf/">http://tools.ietf.org/wg/netconf/</a>&gt;
     WG List:  &lt;mailto:<a href="mailto:netconf@ietf.org">netconf@ietf.org</a>&gt;

     WG Chair: Mehmet Ersue
               &lt;mailto:<a href="mailto:mehmet.ersue@nsn.com">mehmet.ersue@nsn.com</a>&gt;

     WG Chair: Bert Wijnen
               &lt;mailto:<a href="mailto:bertietf@bwijnen.net">bertietf@bwijnen.net</a>&gt;

     Editor:   Mark Scott
               &lt;mailto:<a href="mailto:mark.scott@ericsson.com">mark.scott@ericsson.com</a>&gt;

     Editor:   Martin Bjorklund
               &lt;mailto:<a href="mailto:mbj@tail-f.com">mbj@tail-f.com</a>&gt;&quot;;

  description
    &quot;NETCONF Monitoring Module.
     All elements in this module are read-only.

     Copyright (c) 2010 IETF Trust and the persons identified as
     authors of the code. All rights reserved.

     Redistribution and use in source and binary forms, with or
     without modification, is permitted pursuant to, and subject
     to the license terms contained in, the Simplified BSD
<span class="grey"><a href="/doc/html/rfc6022">RFC 6022</a>           YANG Module for NETCONF Monitoring       October 2010</span>

     License set forth in <a href="#section-4">Section 4</a>.c of the IETF Trust&#x27;s
     Legal Provisions Relating to IETF Documents
     (<a href="https://trustee.ietf.org/license-info">http://trustee.ietf.org/license-info</a>).

     This version of this YANG module is part of <a href="/doc/html/rfc6022">RFC 6022</a>; see
     the RFC itself for full legal notices.&quot;;

  revision 2010-10-04 {
    description
      &quot;Initial revision.&quot;;
    reference
      &quot;<a href="/doc/html/rfc6022">RFC 6022</a>: YANG Module for NETCONF Monitoring&quot;;
  }

  typedef netconf-datastore-type {
    type enumeration {
      enum running;
      enum candidate;
      enum startup;
    }
    description
      &quot;Enumeration of possible NETCONF datastore types.&quot;;
    reference
      &quot;<a href="/doc/html/rfc4741">RFC 4741</a>: NETCONF Configuration Protocol&quot;;
  }

  identity transport {
    description
      &quot;Base identity for NETCONF transport types.&quot;;
  }

  identity netconf-ssh {
    base transport;
    description
      &quot;NETCONF over Secure Shell (SSH).&quot;;
    reference
      &quot;<a href="/doc/html/rfc4742">RFC 4742</a>: Using the NETCONF Configuration Protocol
                 over Secure SHell (SSH)&quot;;
  }

  identity netconf-soap-over-beep {
    base transport;
    description
      &quot;NETCONF over Simple Object Access Protocol (SOAP) over
       Blocks Extensible Exchange Protocol (BEEP).&quot;;

<span class="grey"><a href="/doc/html/rfc6022">RFC 6022</a>           YANG Module for NETCONF Monitoring       October 2010</span>

    reference
      &quot;<a href="/doc/html/rfc4743">RFC 4743</a>: Using NETCONF over the Simple Object
                 Access Protocol (SOAP)&quot;;
  }

  identity netconf-soap-over-https {
    base transport;
    description
      &quot;NETCONF over Simple Object Access Protocol (SOAP)
      over Hypertext Transfer Protocol Secure (HTTPS).&quot;;
    reference
      &quot;<a href="/doc/html/rfc4743">RFC 4743</a>: Using NETCONF over the Simple Object
                 Access Protocol (SOAP)&quot;;
  }

  identity netconf-beep {
    base transport;
    description
      &quot;NETCONF over Blocks Extensible Exchange Protocol (BEEP).&quot;;
    reference
      &quot;<a href="/doc/html/rfc4744">RFC 4744</a>: Using the NETCONF Protocol over the
                 Blocks Extensible Exchange Protocol (BEEP)&quot;;
  }

  identity netconf-tls {
    base transport;
    description
      &quot;NETCONF over Transport Layer Security (TLS).&quot;;
    reference
      &quot;<a href="/doc/html/rfc5539">RFC 5539</a>: NETCONF over Transport Layer Security (TLS)&quot;;
  }

  identity schema-format {
    description
      &quot;Base identity for data model schema languages.&quot;;
  }

  identity xsd {
    base schema-format;
    description
      &quot;W3C XML Schema Definition.&quot;;
    reference
      &quot;W3C REC REC-xmlschema-1-20041028:
         XML Schema Part 1: Structures&quot;;
  }

<span class="grey"><a href="/doc/html/rfc6022">RFC 6022</a>           YANG Module for NETCONF Monitoring       October 2010</span>

  identity yang {
    base schema-format;
    description
      &quot;The YANG data modeling language for NETCONF.&quot;;
    reference
      &quot;<a href="/doc/html/rfc6020">RFC 6020</a>:  YANG - A Data Modeling Language for the
                  Network Configuration Protocol (NETCONF)&quot;;
  }

  identity yin {
    base schema-format;
    description
      &quot;The YIN syntax for YANG.&quot;;
    reference
      &quot;<a href="/doc/html/rfc6020">RFC 6020</a>:  YANG - A Data Modeling Language for the
                  Network Configuration Protocol (NETCONF)&quot;;
  }

  identity rng {
    base schema-format;
    description
      &quot;Regular Language for XML Next Generation (RELAX NG).&quot;;
    reference
      &quot;ISO/IEC 19757-2:2008: RELAX NG&quot;;
  }

  identity rnc {
    base schema-format;
    description
      &quot;Relax NG Compact Syntax&quot;;
    reference
      &quot;ISO/IEC 19757-2:2008: RELAX NG&quot;;
  }

  grouping common-counters {
    description
      &quot;Counters that exist both per session, and also globally,
       accumulated from all sessions.&quot;;

    leaf in-rpcs {
      type yang:zero-based-counter32;
      description
        &quot;Number of correct &lt;rpc&gt; messages received.&quot;;
    }
    leaf in-bad-rpcs {
      type yang:zero-based-counter32;

<span class="grey"><a href="/doc/html/rfc6022">RFC 6022</a>           YANG Module for NETCONF Monitoring       October 2010</span>

      description
        &quot;Number of messages received when an &lt;rpc&gt; message was expected,
         that were not correct &lt;rpc&gt; messages.  This includes XML parse
         errors and errors on the rpc layer.&quot;;
    }
    leaf out-rpc-errors {
      type yang:zero-based-counter32;
      description
        &quot;Number of &lt;rpc-reply&gt; messages sent that contained an
         &lt;rpc-error&gt; element.&quot;;
    }
    leaf out-notifications {
      type yang:zero-based-counter32;
      description
        &quot;Number of &lt;notification&gt; messages sent.&quot;;
    }
  }

  container netconf-state {
    config false;
    description
      &quot;The netconf-state container is the root of the monitoring
       data model.&quot;;

    container capabilities {
      description
        &quot;Contains the list of NETCONF capabilities supported by the
         server.&quot;;

      leaf-list capability {
        type inet:uri;
        description
          &quot;List of NETCONF capabilities supported by the server.&quot;;
      }
    }

    container datastores {
      description
        &quot;Contains the list of NETCONF configuration datastores.&quot;;

      list datastore {
        key name;
        description
          &quot;List of NETCONF configuration datastores supported by
           the NETCONF server and related information.&quot;;

        leaf name {
          type netconf-datastore-type;
<span class="grey"><a href="/doc/html/rfc6022">RFC 6022</a>           YANG Module for NETCONF Monitoring       October 2010</span>

          description
            &quot;Name of the datastore associated with this list entry.&quot;;
        }
        container locks {
          presence
            &quot;This container is present only if the datastore
             is locked.&quot;;
          description
            &quot;The NETCONF &lt;lock&gt; and &lt;partial-lock&gt; operations allow
             a client to lock specific resources in a datastore.  The
             NETCONF server will prevent changes to the locked
             resources by all sessions except the one that acquired
             the lock(s).

             Monitoring information is provided for each datastore
             entry including details such as the session that acquired
             the lock, the type of lock (global or partial) and the
             list of locked resources.  Multiple locks per datastore
             are supported.&quot;;

          grouping lock-info {
            description
              &quot;Lock related parameters, common to both global and
               partial locks.&quot;;

            leaf locked-by-session {
              type uint32;
              mandatory true;
              description
                &quot;The session ID of the session that has locked
                 this resource.  Both a global lock and a partial
                 lock MUST contain the NETCONF session-id.

                 If the lock is held by a session that is not managed
                 by the NETCONF server (e.g., a CLI session), a session
                 id of 0 (zero) is reported.&quot;;
              reference
                &quot;<a href="/doc/html/rfc4741">RFC 4741</a>: NETCONF Configuration Protocol&quot;;
            }
            leaf locked-time {
              type yang:date-and-time;
              mandatory true;
              description
                &quot;The date and time of when the resource was
                 locked.&quot;;
            }
          }

<span class="grey"><a href="/doc/html/rfc6022">RFC 6022</a>           YANG Module for NETCONF Monitoring       October 2010</span>

          choice lock-type {
            description
              &quot;Indicates if a global lock or a set of partial locks
               are set.&quot;;

            container global-lock {
              description
                &quot;Present if the global lock is set.&quot;;
              uses lock-info;
            }

            list partial-lock {
              key lock-id;
              description
                &quot;List of partial locks.&quot;;
              reference
                &quot;<a href="/doc/html/rfc5717">RFC 5717</a>: Partial Lock Remote Procedure Call (RPC) for
                           NETCONF&quot;;

              leaf lock-id {
                type uint32;
                description
                  &quot;This is the lock id returned in the &lt;partial-lock&gt;
                   response.&quot;;
              }
              uses lock-info;
              leaf-list select {
                type yang:xpath1.0;
                min-elements 1;
                description
                  &quot;The xpath expression that was used to request
                   the lock.  The select expression indicates the
                   original intended scope of the lock.&quot;;
              }
              leaf-list locked-node {
                type instance-identifier;
                description
                  &quot;The list of instance-identifiers (i.e., the
                   locked nodes).

                   The scope of the partial lock is defined by the list
                   of locked nodes.&quot;;
              }
            }
          }
        }
      }
    }
<span class="grey"><a href="/doc/html/rfc6022">RFC 6022</a>           YANG Module for NETCONF Monitoring       October 2010</span>

    container schemas {
      description
        &quot;Contains the list of data model schemas supported by the
         server.&quot;;

      list schema {
        key &quot;identifier version format&quot;;

        description
          &quot;List of data model schemas supported by the server.&quot;;

        leaf identifier {
          type string;
          description
            &quot;Identifier to uniquely reference the schema.  The
             identifier is used in the &lt;get-schema&gt; operation and may
             be used for other purposes such as file retrieval.

             For modeling languages that support or require a data
             model name (e.g., YANG module name) the identifier MUST
             match that name.  For YANG data models, the identifier is
             the name of the module or submodule.  In other cases, an
             identifier such as a filename MAY be used instead.&quot;;
        }
        leaf version {
          type string;
          description
            &quot;Version of the schema supported.  Multiple versions MAY be
             supported simultaneously by a NETCONF server.  Each
             version MUST be reported individually in the schema list,
             i.e., with same identifier, possibly different location,
             but different version.

             For YANG data models, version is the value of the most
             recent YANG &#x27;revision&#x27; statement in the module or
             submodule, or the empty string if no &#x27;revision&#x27; statement
             is present.&quot;;
        }
        leaf format {
          type identityref {
            base schema-format;
          }
          description
            &quot;The data modeling language the schema is written
             in (currently xsd, yang, yin, rng, or rnc).

<span class="grey"><a href="/doc/html/rfc6022">RFC 6022</a>           YANG Module for NETCONF Monitoring       October 2010</span>

             For YANG data models, &#x27;yang&#x27; format MUST be supported and
             &#x27;yin&#x27; format MAY also be provided.&quot;;
        }
        leaf namespace {
          type inet:uri;
          mandatory true;
          description
            &quot;The XML namespace defined by the data model.

             For YANG data models, this is the module&#x27;s namespace.
             If the list entry describes a submodule, this field
             contains the namespace of the module to which the
             submodule belongs.&quot;;
        }
        leaf-list location {
          type union {
            type enumeration {
              enum &quot;NETCONF&quot;;
            }
            type inet:uri;
          }
          description
            &quot;One or more locations from which the schema can be
             retrieved.  This list SHOULD contain at least one
             entry per schema.

             A schema entry may be located on a remote file system
             (e.g., reference to file system for ftp retrieval) or
             retrieved directly from a server supporting the
             &lt;get-schema&gt; operation (denoted by the value &#x27;NETCONF&#x27;).&quot;;
        }
      }
    }

<span class="grey"><a href="/doc/html/rfc6022">RFC 6022</a>           YANG Module for NETCONF Monitoring       October 2010</span>

    container sessions {
      description
        &quot;The sessions container includes session-specific data for
         NETCONF management sessions.  The session list MUST include
         all currently active NETCONF sessions.&quot;;

      list session {
        key session-id;
        description
          &quot;All NETCONF sessions managed by the NETCONF server
           MUST be reported in this list.&quot;;

        leaf session-id {
          type uint32 {
            range &quot;1..max&quot;;
          }
          description
            &quot;Unique identifier for the session.  This value is the
             NETCONF session identifier, as defined in <a href="/doc/html/rfc4741">RFC 4741</a>.&quot;;
          reference
            &quot;<a href="/doc/html/rfc4741">RFC 4741</a>: NETCONF Configuration Protocol&quot;;
        }
        leaf transport {
          type identityref {
            base transport;
          }
          mandatory true;
          description
            &quot;Identifies the transport for each session, e.g.,
            &#x27;netconf-ssh&#x27;, &#x27;netconf-soap&#x27;, etc.&quot;;
        }
        leaf username  {
          type string;
          mandatory true;
          description
            &quot;The username is the client identity that was authenticated
            by the NETCONF transport protocol.  The algorithm used to
            derive the username is NETCONF transport protocol specific
            and in addition specific to the authentication mechanism
            used by the NETCONF transport protocol.&quot;;
        }
        leaf source-host {
          type inet:host;
          description
            &quot;Host identifier of the NETCONF client.  The value
             returned is implementation specific (e.g., hostname,
             IPv4 address, IPv6 address)&quot;;
        }
<span class="grey"><a href="/doc/html/rfc6022">RFC 6022</a>           YANG Module for NETCONF Monitoring       October 2010</span>

        leaf login-time {
          type yang:date-and-time;
          mandatory true;
          description
            &quot;Time at the server at which the session was established.&quot;;
        }
        uses common-counters {
          description
            &quot;Per-session counters.  Zero based with following reset
             behaviour:
               - at start of a session
               - when max value is reached&quot;;
        }
      }
    }

    container statistics {
      description
        &quot;Statistical data pertaining to the NETCONF server.&quot;;

      leaf netconf-start-time {
        type yang:date-and-time;
        description
          &quot;Date and time at which the management subsystem was
           started.&quot;;
      }
      leaf in-bad-hellos {
        type yang:zero-based-counter32;
        description
          &quot;Number of sessions silently dropped because an
          invalid &lt;hello&gt; message was received.  This includes &lt;hello&gt;
          messages with a &#x27;session-id&#x27; attribute, bad namespace, and
          bad capability declarations.&quot;;
      }
      leaf in-sessions {
        type yang:zero-based-counter32;
        description
          &quot;Number of sessions started.  This counter is incremented
           when a &lt;hello&gt; message with a &lt;session-id&gt; is sent.

          &#x27;in-sessions&#x27; - &#x27;in-bad-hellos&#x27; =
              &#x27;number of correctly started netconf sessions&#x27;&quot;;
      }
      leaf dropped-sessions {
        type yang:zero-based-counter32;

<span class="grey"><a href="/doc/html/rfc6022">RFC 6022</a>           YANG Module for NETCONF Monitoring       October 2010</span>

        description
          &quot;Number of sessions that were abnormally terminated, e.g.,
           due to idle timeout or transport close.  This counter is not
           incremented when a session is properly closed by a
           &lt;close-session&gt; operation, or killed by a &lt;kill-session&gt;
           operation.&quot;;
      }
      uses common-counters {
        description
          &quot;Global counters, accumulated from all sessions.
           Zero based with following reset behaviour:
             - re-initialization of NETCONF server
             - when max value is reached&quot;;
      }
    }
  }

  rpc get-schema {
    description
      &quot;This operation is used to retrieve a schema from the
       NETCONF server.

       Positive Response:
         The NETCONF server returns the requested schema.

       Negative Response:
         If requested schema does not exist, the &lt;error-tag&gt; is
         &#x27;invalid-value&#x27;.

         If more than one schema matches the requested parameters, the
         &lt;error-tag&gt; is &#x27;operation-failed&#x27;, and &lt;error-app-tag&gt; is
         &#x27;data-not-unique&#x27;.&quot;;

    input {
      leaf identifier {
        type string;
        mandatory true;
        description
          &quot;Identifier for the schema list entry.&quot;;
      }
      leaf version {
        type string;
        description
          &quot;Version of the schema requested.  If this parameter is not
           present, and more than one version of the schema exists on
           the server, a &#x27;data-not-unique&#x27; error is returned, as
           described above.&quot;;
      }
<span class="grey"><a href="/doc/html/rfc6022">RFC 6022</a>           YANG Module for NETCONF Monitoring       October 2010</span>

      leaf format {
        type identityref {
          base schema-format;
        }
        description
           &quot;The data modeling language of the schema.  If this
            parameter is not present, and more than one formats of
            the schema exists on the server, a &#x27;data-not-unique&#x27; error
            is returned, as described above.&quot;;
      }
    }
    output {
        anyxml data {
          description
            &quot;Contains the schema content.&quot;;
      }
    }
  }
}
