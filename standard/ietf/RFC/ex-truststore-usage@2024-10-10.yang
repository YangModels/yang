module ex-truststore-usage {
  yang-version 1.1;
  namespace "https://example.com/ns/example-truststore-usage";
  prefix etu;

  import ietf-truststore {
    prefix ts;
    reference
      "RFC 9641: A YANG Data Model for a Truststore";
  }

  organization
    "Example Corporation";

  contact
    "Author: YANG Designer <mailto:yang.designer@example.com>";

  description
    "This example module illustrates notable groupings defined
     in the 'ietf-truststore' module.";

  revision 2024-10-10 {
    description
      "Initial version.";
    reference
      "RFC 9641: A YANG Data Model for a Truststore";
  }

  container truststore-usage {
    description
      "An illustration of the various truststore groupings.";
    list cert {
      key "name";
      leaf name {
        type string;
        description
          "An arbitrary name for this cert.";
      }
      uses ts:inline-or-truststore-certs-grouping;
      description
        "A cert that may be configured locally or be
         a reference to a cert in the truststore.";
    }
    list public-key {
      key "name";
      leaf name {
        type string;
        description
          "An arbitrary name for this cert.";
      }
      uses ts:inline-or-truststore-public-keys-grouping;
      description
        "A public key that may be configured locally or be
         a reference to a public key in the truststore.";
    }
  }
}
