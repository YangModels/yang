module ietf-ethertypes {
  namespace &quot;urn:ietf:params:xml:ns:yang:ietf-ethertypes&quot;;
  prefix ethertypes;

  organization
    &quot;IETF NETMOD (Network Modeling) Working Group.&quot;;

  contact
    &quot;WG Web:   &lt;<a href="https://datatracker.ietf.org/wg/netmod/">https://datatracker.ietf.org/wg/netmod/</a>&gt;
     WG List:  &lt;mailto:<a href="mailto:netmod@ietf.org">netmod@ietf.org</a>&gt;

     Editor:   Mahesh Jethanandani
               &lt;<a href="mailto:mjethanandani@gmail.com">mjethanandani@gmail.com</a>&gt;&quot;;

  description
    &quot;This module contains common definitions for the
<span class="grey"><a href="/doc/html/rfc8519">RFC 8519</a>                YANG Data Model for ACLs              March 2019</span>

        Ethertype used by different modules.  It is a
        placeholder module, till such time that IEEE
        starts a project to define these Ethertypes
        and publishes a standard.

        At that time, this module can be deprecated.

        Copyright (c) 2019 IETF Trust and the persons identified as
        the document authors.  All rights reserved.

        Redistribution and use in source and binary forms, with or
        without modification, is permitted pursuant to, and subject
        to the license terms contained in, the Simplified BSD
        License set forth in <a href="#section-4">Section 4</a>.c of the IETF Trust&#x27;s Legal
        Provisions Relating to IETF Documents
        (<a href="https://trustee.ietf.org/license-info">http://trustee.ietf.org/license-info</a>).

        This version of this YANG module is part of <a href="/doc/html/rfc8519">RFC 8519</a>; see
        the RFC itself for full legal notices.&quot;;

     revision 2019-03-04 {
       description
         &quot;Initial revision.&quot;;
       reference
         &quot;<a href="/doc/html/rfc8519">RFC 8519</a>: YANG Data Model for Network Access Control
                    Lists (ACLs).&quot;;
     }

     typedef ethertype {
       type union {
         type uint16;
         type enumeration {
           enum ipv4 {
             value 2048;
             description
               &quot;Internet Protocol version 4 (IPv4) with a
                hex value of 0x0800.&quot;;
             reference
               &quot;<a href="/doc/html/rfc791">RFC 791</a>: Internet Protocol.&quot;;
           }
           enum arp {
             value 2054;
             description
               &quot;Address Resolution Protocol (ARP) with a
                hex value of 0x0806.&quot;;
             reference
               &quot;<a href="/doc/html/rfc826">RFC 826</a>: An Ethernet Address Resolution Protocol: Or
                         Converting Network Protocol Addresses to 48.bit
<span class="grey"><a href="/doc/html/rfc8519">RFC 8519</a>                YANG Data Model for ACLs              March 2019</span>

                         Ethernet Address for Transmission on Ethernet
                         Hardware.&quot;;
           }
           enum wlan {
             value 2114;
             description
               &quot;Wake-on-LAN.  Hex value of 0x0842.&quot;;
           }
           enum trill {
             value 8947;
             description
               &quot;Transparent Interconnection of Lots of Links.
                Hex value of 0x22F3.&quot;;
             reference
               &quot;<a href="/doc/html/rfc6325">RFC 6325</a>: Routing Bridges (RBridges): Base Protocol
                          Specification.&quot;;
           }
           enum srp {
             value 8938;
             description
               &quot;Stream Reservation Protocol.  Hex value of
                0x22EA.&quot;;
             reference
               &quot;IEEE 801.1Q-2011.&quot;;
           }
           enum decnet {
             value 24579;
             description
               &quot;DECnet Phase IV.  Hex value of 0x6003.&quot;;
           }
           enum rarp {
             value 32821;
             description
               &quot;Reverse Address Resolution Protocol.
                Hex value 0x8035.&quot;;
             reference
               &quot;<a href="/doc/html/rfc903">RFC 903</a>: A Reverse Address Resolution Protocol.&quot;;
           }
           enum appletalk {
             value 32923;
             description
               &quot;Appletalk (Ethertalk).  Hex value of 0x809B.&quot;;
           }
           enum aarp {
             value 33011;
             description
               &quot;Appletalk Address Resolution Protocol.  Hex value
                of 0x80F3.&quot;;
<span class="grey"><a href="/doc/html/rfc8519">RFC 8519</a>                YANG Data Model for ACLs              March 2019</span>

           }
           enum vlan {
             value 33024;
             description
               &quot;VLAN-tagged frame (IEEE 802.1Q) and Shortest Path
                Bridging IEEE 802.1aq with Network-Network
                Interface (NNI) compatibility.  Hex value of
                0x8100.&quot;;
             reference
               &quot;IEEE 802.1Q.&quot;;
           }
           enum ipx {
             value 33079;
             description
               &quot;Internetwork Packet Exchange (IPX).  Hex value
                of 0x8137.&quot;;
           }
           enum qnx {
             value 33284;
             description
               &quot;QNX Qnet.  Hex value of 0x8204.&quot;;
           }
           enum ipv6 {
             value 34525;
             description
               &quot;Internet Protocol Version 6 (IPv6).  Hex value
                of 0x86DD.&quot;;
             reference
               &quot;<a href="/doc/html/rfc8200">RFC 8200</a>: Internet Protocol, Version 6 (IPv6)
                          Specification
                <a href="/doc/html/rfc8201">RFC 8201</a>: Path MTU Discovery for IP version 6.&quot;;
           }
           enum efc {
             value 34824;
             description
               &quot;Ethernet flow control using pause frames.
                Hex value of 0x8808.&quot;;
             reference
               &quot;IEEE 802.1Qbb.&quot;;
           }
           enum esp {
             value 34825;
             description
               &quot;Ethernet Slow Protocol.  Hex value of 0x8809.&quot;;
             reference
               &quot;IEEE 802.3-2015.&quot;;
           }
           enum cobranet {
<span class="grey"><a href="/doc/html/rfc8519">RFC 8519</a>                YANG Data Model for ACLs              March 2019</span>

             value 34841;
             description
               &quot;CobraNet.  Hex value of 0x8819.&quot;;
           }
           enum mpls-unicast {
             value 34887;
             description
               &quot;Multiprotocol Label Switching (MPLS) unicast traffic.
                Hex value of 0x8847.&quot;;
             reference
               &quot;<a href="/doc/html/rfc3031">RFC 3031</a>: Multiprotocol Label Switching Architecture.&quot;;
           }
           enum mpls-multicast {
             value 34888;
             description
               &quot;MPLS multicast traffic.  Hex value of 0x8848.&quot;;
             reference
               &quot;<a href="/doc/html/rfc3031">RFC 3031</a>: Multiprotocol Label Switching Architecture.&quot;;
           }
           enum pppoe-discovery {
             value 34915;
             description
               &quot;Point-to-Point Protocol over Ethernet.  Used during
                the discovery process.  Hex value of 0x8863.&quot;;
             reference
               &quot;<a href="/doc/html/rfc2516">RFC 2516</a>: A Method for Transmitting PPP Over Ethernet
                          (PPPoE).&quot;;
           }
           enum pppoe-session {
             value 34916;
             description
               &quot;Point-to-Point Protocol over Ethernet.  Used during
                session stage.  Hex value of 0x8864.&quot;;
             reference
               &quot;<a href="/doc/html/rfc2516">RFC 2516</a>: A Method for Transmitting PPP Over Ethernet
                          (PPPoE).&quot;;
           }
           enum intel-ans {
             value 34925;
             description
               &quot;Intel Advanced Networking Services.  Hex value of
                0x886D.&quot;;
           }
           enum jumbo-frames {
             value 34928;
             description
               &quot;Jumbo frames or Ethernet frames with more than
                1500 bytes of payload, up to 9000 bytes.&quot;;
<span class="grey"><a href="/doc/html/rfc8519">RFC 8519</a>                YANG Data Model for ACLs              March 2019</span>

           }
           enum homeplug {
             value 34939;
             description
               &quot;Family name for the various power line
                communications.  Hex value of 0x887B.&quot;;
           }
           enum eap {
             value 34958;
             description
               &quot;Ethernet Access Protocol (EAP) over LAN.  Hex value
                of 0x888E.&quot;;
             reference
               &quot;IEEE 802.1X.&quot;;
           }
           enum profinet {
             value 34962;
             description
               &quot;PROcess FIeld Net (PROFINET).  Hex value of 0x8892.&quot;;
           }
           enum hyperscsi {
             value 34970;
             description
               &quot;Small Computer System Interface (SCSI) over Ethernet.
                Hex value of 0x889A.&quot;;
           }
           enum aoe {
             value 34978;
             description
               &quot;Advanced Technology Advancement (ATA) over Ethernet.
                Hex value of 0x88A2.&quot;;
           }
           enum ethercat {
             value 34980;
             description
               &quot;Ethernet for Control Automation Technology (EtherCAT).
                Hex value of 0x88A4.&quot;;
           }
           enum provider-bridging {
             value 34984;
             description
               &quot;Provider Bridging (802.1ad) and Shortest Path Bridging
                (801.1aq).  Hex value of 0x88A8.&quot;;
             reference
               &quot;IEEE 802.1ad and IEEE 802.1aq).&quot;;
           }
           enum ethernet-powerlink {
             value 34987;
<span class="grey"><a href="/doc/html/rfc8519">RFC 8519</a>                YANG Data Model for ACLs              March 2019</span>

             description
               &quot;Ethernet Powerlink.  Hex value of 0x88AB.&quot;;
           }
           enum goose {
             value 35000;
             description
               &quot;Generic Object Oriented Substation Event (GOOSE).
                Hex value of 0x88B8.&quot;;
             reference
               &quot;IEC/ISO 8802-2 and 8802-3.&quot;;
           }
           enum gse {
             value 35001;
             description
               &quot;Generic Substation Events.  Hex value of 88B9.&quot;;
             reference
               &quot;IEC 61850.&quot;;
           }
           enum sv {
             value 35002;
             description
               &quot;Sampled Value Transmission.  Hex value of 0x88BA.&quot;;
             reference
               &quot;IEC 61850.&quot;;
           }
           enum lldp {
             value 35020;
             description
               &quot;Link Layer Discovery Protocol (LLDP).  Hex value of
                0x88CC.&quot;;
             reference
               &quot;IEEE 802.1AB.&quot;;
           }
           enum sercos {
             value 35021;
             description
               &quot;Sercos Interface.  Hex value of 0x88CD.&quot;;
           }
           enum wsmp {
             value 35036;
             description
               &quot;WAVE Short Message Protocol (WSMP).  Hex value of
                0x88DC.&quot;;
           }
           enum homeplug-av-mme {
             value 35041;
             description
               &quot;HomePlug AV Mobile Management Entity (MME).  Hex value
<span class="grey"><a href="/doc/html/rfc8519">RFC 8519</a>                YANG Data Model for ACLs              March 2019</span>

                of 88E1.&quot;;
           }
           enum mrp {
             value 35043;
             description
               &quot;Media Redundancy Protocol (MRP).  Hex value of
                0x88E3.&quot;;
             reference
               &quot;IEC 62439-2.&quot;;
           }
           enum macsec {
             value 35045;
             description
               &quot;MAC Security.  Hex value of 0x88E5.&quot;;
             reference
               &quot;IEEE 802.1AE.&quot;;
           }
           enum pbb {
             value 35047;
             description
               &quot;Provider Backbone Bridges (PBB).  Hex value of
                0x88E7.&quot;;
             reference
               &quot;IEEE 802.1ah.&quot;;
           }
           enum cfm {
             value 35074;
             description
               &quot;Connectivity Fault Management (CFM).  Hex value of
                0x8902.&quot;;
             reference
               &quot;IEEE 802.1ag.&quot;;
           }
           enum fcoe {
             value 35078;
             description
               &quot;Fiber Channel over Ethernet (FCoE).  Hex value of
                0x8906.&quot;;
             reference
               &quot;T11 FC-BB-5.&quot;;
           }
           enum fcoe-ip {
             value 35092;
             description
               &quot;FCoE Initialization Protocol.  Hex value of 0x8914.&quot;;
           }
           enum roce {
             value 35093;
<span class="grey"><a href="/doc/html/rfc8519">RFC 8519</a>                YANG Data Model for ACLs              March 2019</span>

             description
               &quot;RDMA over Converged Ethernet (RoCE).  Hex value of
                0x8915.&quot;;
           }
           enum tte {
             value 35101;
             description
               &quot;TTEthernet Protocol Control Frame (TTE).  Hex value
                of 0x891D.&quot;;
             reference
               &quot;SAE AS6802.&quot;;
           }
           enum hsr {
             value 35119;
             description
               &quot;High-availability Seamless Redundancy (HSR).  Hex
                value of 0x892F.&quot;;
             reference
               &quot;IEC 62439-3:2016.&quot;;
           }
         }
       }
       description
         &quot;The uint16 type placeholder is defined to enable
          users to manage their own ethertypes not
          covered by the module.  Otherwise, the module contains
          enum definitions for the more commonly used ethertypes.&quot;;
     }
   }
