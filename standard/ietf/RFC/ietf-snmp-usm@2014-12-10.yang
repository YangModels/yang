submodule ietf-snmp-usm {

  belongs-to ietf-snmp {
    prefix snmp;
  }

<span class="grey"><a href="/doc/html/rfc7407">RFC 7407</a>         YANG Data Model for SNMP Configuration    December 2014</span>

     import ietf-yang-types {
       prefix yang;
     }
     import ietf-netconf-acm {
       prefix nacm;
     }

     include ietf-snmp-common;
     include ietf-snmp-target;
     include ietf-snmp-proxy;

     organization
       &quot;IETF NETMOD (NETCONF Data Modeling Language) Working Group&quot;;

     contact
       &quot;WG Web:   &lt;<a href="https://tools.ietf.org/wg/netmod/">http://tools.ietf.org/wg/netmod/</a>&gt;
        WG List:  &lt;mailto:<a href="mailto:netmod@ietf.org">netmod@ietf.org</a>&gt;

        WG Chair: Thomas Nadeau
                  &lt;mailto:<a href="mailto:tnadeau@lucidvision.com">tnadeau@lucidvision.com</a>&gt;

        WG Chair: Juergen Schoenwaelder
                  &lt;mailto:<a href="mailto:j.schoenwaelder@jacobs-university.de">j.schoenwaelder@jacobs-university.de</a>&gt;

        Editor:   Martin Bjorklund
                  &lt;mailto:<a href="mailto:mbj@tail-f.com">mbj@tail-f.com</a>&gt;

        Editor:   Juergen Schoenwaelder
                  &lt;mailto:<a href="mailto:j.schoenwaelder@jacobs-university.de">j.schoenwaelder@jacobs-university.de</a>&gt;&quot;;

     description
       &quot;This submodule contains a collection of YANG definitions for
        configuring the User-based Security Model (USM) of SNMP.

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc7407">RFC 7407</a>; see
        the RFC itself for full legal notices.&quot;;

<span class="grey"><a href="/doc/html/rfc7407">RFC 7407</a>         YANG Data Model for SNMP Configuration    December 2014</span>

     reference
       &quot;<a href="/doc/html/rfc3414">RFC 3414</a>: User-based Security Model (USM) for version 3 of the
          Simple Network Management Protocol (SNMPv3)&quot;;

     revision 2014-12-10 {
       description
         &quot;Initial revision.&quot;;
       reference
         &quot;<a href="/doc/html/rfc7407">RFC 7407</a>: A YANG Data Model for SNMP Configuration&quot;;
     }

     grouping key {
       leaf key {
         type yang:hex-string;
         mandatory true;
         nacm:default-deny-all;
         description
           &quot;Localized key specified as a list of colon-specified
            hexadecimal octets.&quot;;
       }
     }

     grouping user-list {
       list user {
         key &quot;name&quot;;

         reference
           &quot;<a href="/doc/html/rfc3414">RFC 3414</a>: User-based Security Model (USM) for version 3
              of the Simple Network Management Protocol (SNMPv3).
              SNMP-USER-BASED-SM-MIB.usmUserTable&quot;;

         leaf name {
           type snmp:identifier;
           reference
             &quot;<a href="/doc/html/rfc3414">RFC 3414</a>: User-based Security Model (USM) for version 3
                of the Simple Network Management Protocol (SNMPv3).
                SNMP-USER-BASED-SM-MIB.usmUserName&quot;;
         }
         container auth {
           presence &quot;enables authentication&quot;;
           description
             &quot;Enables authentication of the user.&quot;;
           choice protocol {
             mandatory true;
             reference
               &quot;<a href="/doc/html/rfc3414">RFC 3414</a>: User-based Security Model (USM) for version 3
                  of the Simple Network Management Protocol (SNMPv3).
                  SNMP-USER-BASED-SM-MIB.usmUserAuthProtocol&quot;;
<span class="grey"><a href="/doc/html/rfc7407">RFC 7407</a>         YANG Data Model for SNMP Configuration    December 2014</span>

             container md5 {
               uses key;
               reference
                 &quot;<a href="/doc/html/rfc3414">RFC 3414</a>: User-based Security Model (USM) for
                    version 3 of the Simple Network Management Protocol
                    (SNMPv3).
                    SNMP-USER-BASED-SM-MIB.usmHMACMD5AuthProtocol&quot;;
             }
             container sha {
               uses key;
               reference
                 &quot;<a href="/doc/html/rfc3414">RFC 3414</a>: User-based Security Model (USM) for
                    version 3 of the Simple Network Management Protocol
                    (SNMPv3).
                    SNMP-USER-BASED-SM-MIB.usmHMACSHAAuthProtocol&quot;;
             }
           }
         }
         container priv {
           must &quot;../auth&quot; {
             error-message
               &quot;when privacy (confidentiality) is used, &quot;
             + &quot;authentication must also be used&quot;;
           }
           presence &quot;enables encryption&quot;;
           description
             &quot;Enables encryption of SNMP messages.&quot;;

           choice protocol {
             mandatory true;
             reference
               &quot;<a href="/doc/html/rfc3414">RFC 3414</a>: User-based Security Model (USM) for version 3
                  of the Simple Network Management Protocol (SNMPv3).
                  SNMP-USER-BASED-SM-MIB.usmUserPrivProtocol&quot;;
             container des {
               uses key;
               reference
                 &quot;<a href="/doc/html/rfc3414">RFC 3414</a>: User-based Security Model (USM) for
                    version 3 of the Simple Network Management Protocol
                    (SNMPv3).
                    SNMP-USER-BASED-SM-MIB.usmDESPrivProtocol&quot;;
             }
             container aes {
               uses key;

<span class="grey"><a href="/doc/html/rfc7407">RFC 7407</a>         YANG Data Model for SNMP Configuration    December 2014</span>

               reference
                 &quot;<a href="/doc/html/rfc3826">RFC 3826</a>: The Advanced Encryption Standard (AES)
                    Cipher Algorithm in the SNMP User-based Security
                    Model.
                    SNMP-USM-AES-MIB.usmAesCfb128Protocol&quot;;
             }
           }
         }
       }
     }

     augment /snmp:snmp {

       container usm {
         description
           &quot;Configuration of the User-based Security Model.&quot;;
         container local {
           uses user-list;
         }

         list remote {
           key &quot;engine-id&quot;;

           leaf engine-id {
             type snmp:engine-id;
             reference
               &quot;<a href="/doc/html/rfc3414">RFC 3414</a>: User-based Security Model (USM) for version 3
                  of the Simple Network Management Protocol (SNMPv3).
                  SNMP-USER-BASED-SM-MIB.usmUserEngineID&quot;;
           }

           uses user-list;
         }
       }
     }

     grouping usm-target-params {
       container usm {
         description
           &quot;User-based SNMPv3 parameters type.

            Represents snmpTargetParamsMPModel &#x27;3&#x27; and
            snmpTargetParamsSecurityModel &#x27;3&#x27;.&quot;;
         leaf user-name {
           type snmp:security-name;
           mandatory true;

<span class="grey"><a href="/doc/html/rfc7407">RFC 7407</a>         YANG Data Model for SNMP Configuration    December 2014</span>

           reference
             &quot;<a href="/doc/html/rfc3413">RFC 3413</a>: Simple Network Management Protocol (SNMP).
                Applications.
                SNMP-TARGET-MIB.snmpTargetParamsSecurityName&quot;;
         }
         leaf security-level {
           type snmp:security-level;
           mandatory true;
           reference
             &quot;<a href="/doc/html/rfc3413">RFC 3413</a>: Simple Network Management Protocol (SNMP).
                Applications.
                SNMP-TARGET-MIB.snmpTargetParamsSecurityLevel&quot;;
         }
       }
     }

     augment /snmp:snmp/snmp:target-params/snmp:params {
       case usm {
         uses usm-target-params;
       }
     }

   }
