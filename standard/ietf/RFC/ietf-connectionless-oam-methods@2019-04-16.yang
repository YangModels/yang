module ietf-connectionless-oam-methods {
  namespace
    &quot;urn:ietf:params:xml:ns:yang:ietf-connectionless-oam-methods&quot;;
  prefix cloam-methods;

  import ietf-interfaces {
    prefix if;
  }
  import ietf-connectionless-oam {
    prefix cl-oam;
  }
<span class="grey"><a href="/doc/html/rfc8533">RFC 8533</a>         YANG Model for CL OAM Retrieval Methods      April 2019</span>

  organization
    &quot;IETF LIME Working Group&quot;;
  contact
    &quot;WG Web:   &lt;<a href="https://datatracker.ietf.org/wg/lime">https://datatracker.ietf.org/wg/lime</a>&gt;
     WG List:  &lt;mailto:<a href="mailto:lmap@ietf.org">lmap@ietf.org</a>&gt;

     Deepak Kumar &lt;<a href="mailto:dekumar@cisco.com">dekumar@cisco.com</a>&gt;
     Qin Wu &lt;<a href="mailto:bill.wu@huawei.com">bill.wu@huawei.com</a>&gt;
     Srihari Raghavan &lt;<a href="mailto:rihari@cisco.com">rihari@cisco.com</a>&gt;
     Michael Wang &lt;<a href="mailto:wangzitao@huawei.com">wangzitao@huawei.com</a>&gt;
     Reshad Rahman &lt;<a href="mailto:rrahman@cisco.com">rrahman@cisco.com</a>&gt;&quot;;
  description
    &quot;This YANG module defines the RPC operations for
     connectionless OAM to be used within the IETF
     in a protocol-independent manner.  It is
     assumed that each protocol maps corresponding
     abstracts to its native format.  Each protocol
     may extend the YANG data model defined here to
     include protocol-specific extensions.

     Copyright (c) 2019 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).

     This version of this YANG module is part of <a href="/doc/html/rfc8533">RFC 8533</a>; see
     the RFC itself for full legal notices.&quot;;

  revision 2019-04-16 {
    description
      &quot;Initial revision.&quot;;
    reference
      &quot;<a href="/doc/html/rfc8533">RFC 8533</a>: Retrieval Methods YANG Data Model for the Management
       of Operations, Administration, and Maintenance (OAM)
       Protocols That Use Connectionless Communications&quot;;
  }

  identity protocol-id {
    description
      &quot;This is the base identity for a generic protocol
       ID.  The protocol registry can be found at
       <a href="https://www.iana.org/protocols">https://www.iana.org/protocols</a>.&quot;;
  }
<span class="grey"><a href="/doc/html/rfc8533">RFC 8533</a>         YANG Model for CL OAM Retrieval Methods      April 2019</span>

  identity protocol-id-internet {
    base protocol-id;
    description
      &quot;Identity for Internet Protocols.&quot;;
  }

  identity protocol-id-proprietary {
    base protocol-id;
    description
      &quot;Identity for proprietary protocols (e.g.,
       IP SLA).&quot;;
  }

  identity protocol-id-sfc {
    base protocol-id;
    description
      &quot;Identity for Service Function Chaining.&quot;;
  }

  identity protocol-id-mpls {
    base protocol-id;
    description
      &quot;The MPLS protocol.&quot;;
  }

  identity protocol-id-mpls-tp {
    base protocol-id;
    description
      &quot;The MPLS-TP protocol.&quot;;
  }

  identity protocol-id-twamp {
    base protocol-id;
    description
      &quot;The Two-Way Active Measurement Protocol (TWAMP)
       protocol.&quot;;
  }

  identity protocol-id-bier {
    base protocol-id;
    description
      &quot;The Bit Index Explicit Replication (BIER)
       protocol.&quot;;
  }

  identity status-code {
    description
      &quot;This is base identity for a status code.&quot;;
<span class="grey"><a href="/doc/html/rfc8533">RFC 8533</a>         YANG Model for CL OAM Retrieval Methods      April 2019</span>

  }

  identity success-reach {
    base status-code;
    description
      &quot;Indicates that the destination being verified
       is reachable (see <a href="/doc/html/rfc7276">RFC 7276</a>).&quot;;
    reference
      &quot;<a href="/doc/html/rfc7276">RFC 7276</a>: An Overview of Operations, Administration, and
       Maintenance (OAM) Tools&quot;;
  }

  identity fail-reach {
    base status-code;
    description
      &quot;Indicates that the destination being verified
       is not reachable (see <a href="/doc/html/rfc7276">RFC 7276</a>).&quot;;
    reference
      &quot;<a href="/doc/html/rfc7276">RFC 7276</a>: An Overview of Operations, Administration, and
       Maintenance (OAM) Tools&quot;;
  }

  identity success-path-verification {
    base status-code;
    description
      &quot;Indicates that the path verification is performed
       successfully (see <a href="/doc/html/rfc7276">RFC 7276</a>).&quot;;
    reference
      &quot;<a href="/doc/html/rfc7276">RFC 7276</a>: An Overview of Operations, Administration, and
       Maintenance (OAM) Tools&quot;;
  }

  identity fail-path-verification {
    base status-code;
    description
      &quot;Indicates that the path verification fails
       (see <a href="/doc/html/rfc7276">RFC 7276</a>).&quot;;
    reference
      &quot;<a href="/doc/html/rfc7276">RFC 7276</a>: An Overview of Operations, Administration, and
       Maintenance (OAM) Tools&quot;;
  }

  identity status-sub-code {
    description
      &quot;IdentityBase status-sub-code.&quot;;
  }

  identity invalid-cc {
<span class="grey"><a href="/doc/html/rfc8533">RFC 8533</a>         YANG Model for CL OAM Retrieval Methods      April 2019</span>

    base status-sub-code;
    description
      &quot;Indicates that the Continuity Check message is invalid
       (see <a href="/doc/html/rfc7276">RFC 7276</a>).&quot;;
    reference
      &quot;<a href="/doc/html/rfc7276">RFC 7276</a>: An Overview of Operations, Administration, and
       Maintenance (OAM) Tools&quot;;
  }

  identity invalid-pd {
    base status-sub-code;
    description
      &quot;Indicates that the path discovery message is invalid
       (see <a href="/doc/html/rfc7276">RFC 7276</a>).&quot;;
    reference
      &quot;<a href="/doc/html/rfc7276">RFC 7276</a>: An Overview of Operations, Administration, and
       Maintenance (OAM) Tools&quot;;
  }

  identity protocol-id-meta-data {
    description
      &quot;This is the base identity for metadata that corresponds
       to the protocol ID.&quot;;
  }

  identity protocol-internet-number {
    base protocol-id-meta-data;
    description
      &quot;Internet Protocol number for standard
       Internet Protocols (IANA-assigned Internet
       Protocol numbers) to help in protocol processing.
       The Protocol Numbers registry can be found at
       <a href="https://www.iana.org/assignments/protocol-numbers">https://www.iana.org/assignments/protocol-numbers</a>.&quot;;
  }

  grouping rpc-input-parameters {
    container destination-tp {
      uses cl-oam:tp-address;
      description
        &quot;Destination test point.&quot;;
    }
    leaf source-interface {
      type if:interface-ref;
      mandatory true;
      description
        &quot;Source interface.&quot;;
    }
    leaf outbound-interface {
<span class="grey"><a href="/doc/html/rfc8533">RFC 8533</a>         YANG Model for CL OAM Retrieval Methods      April 2019</span>

      type if:interface-ref;
      mandatory true;
      description
        &quot;Outbound interface.&quot;;
    }
    leaf vrf {
      type cl-oam:routing-instance-ref;
      description
        &quot;Virtual Routing and Forwarding (VRF) instance.&quot;;
    }
    description
      &quot;Grouping for RPC input parameters&quot;;
  }

  rpc continuity-check {
    if-feature &quot;cl-oam:continuity-check&quot;;
    description
      &quot;Continuity Check RPC operation as per <a href="/doc/html/rfc7276">RFC 7276</a>.&quot;;
    reference
      &quot;<a href="/doc/html/rfc7276">RFC 7276</a>: An Overview of Operations, Administration, and
       Maintenance (OAM) Tools&quot;;
    input {
      uses rpc-input-parameters;
      uses cl-oam:session-type {
        description
          &quot;If session-type is specified, then session-type
              must be set to on demand&quot;;
      }
      leaf count {
        type uint32 {
          range &quot;0..4294967295&quot; {
            description
              &quot;The overall number of packets to be transmitted
               by the sender.  The value of the count will be set
               to zero (0) on creation and will thereafter
               increase monotonically until it reaches a maximum
               value of 2^32-1 (4294967295 decimal), when it wraps
               around and starts increasing again from zero.&quot;;
          }
        }
        default &quot;5&quot;;
        description
          &quot;Specifies the number of
           packets that will be sent.  By
           default, the packet number is
           set to 5.&quot;;
      }
      leaf ttl {
<span class="grey"><a href="/doc/html/rfc8533">RFC 8533</a>         YANG Model for CL OAM Retrieval Methods      April 2019</span>

        type uint8;
        default &quot;255&quot;;
        description
          &quot;Time to live (TTL) used to limit the lifetime
           of data packets transmitted in the network
           to prevent looping.  The TTL value is decremented
           for every hop that the packet traverses.  If the
           TTL is zero, the data packet will be discarded.&quot;;
      }
      leaf packet-size {
        type uint32 {
          range &quot;64..10000&quot;;
        }
        default &quot;64&quot;;
        description
          &quot;Packet size of the Continuity Check message, in octets.
           By default, the packet size is set to 64 octets.&quot;;
      }
    }
    output {
      container response-info {
        leaf protocol-id {
          type identityref {
            base protocol-id;
          }
          mandatory true;
          description
            &quot;Protocol used in the Continuity Check message.
             This could be a standard protocol (e.g.,
             TCP/IP protocols, MPLS, etc.) or a proprietary
             protocol as identified by this field.&quot;;
        }
        leaf protocol-id-meta-data {
          type identityref {
            base protocol-id-meta-data;
          }
          description
            &quot;An optional metadata related to the protocol ID.
             For example, this could be the Internet Protocol
             number for standard Internet Protocols used for
             help with protocol processing.&quot;;
        }
        leaf status-code {
          type identityref {
            base status-code;
          }
          mandatory true;
          description
<span class="grey"><a href="/doc/html/rfc8533">RFC 8533</a>         YANG Model for CL OAM Retrieval Methods      April 2019</span>

            &quot;Status code for Continuity Check RPC operation.
             This could be a basic status code (e.g., destination
             is reachable or destination is not reachable; see <a href="/doc/html/rfc7276">RFC 7276</a>)
             or some customized status code as identified by this
             field.&quot;;
          reference
            &quot;<a href="/doc/html/rfc7276">RFC 7276</a>: An Overview of Operations, Administration, and
             Maintenance (OAM) Tools&quot;;
        }
        leaf status-sub-code {
          type identityref {
            base status-sub-code;
          }
          mandatory true;
          description
            &quot;An optional status-sub-code for Continuity Check
             RPC operation.  If the basic status code is destination
             reachable, this status-sub-code doesn&#x27;t need to be
             specified.  If the basic status code is destination
             unreachable, the status-sub-code can be used to specify
             the detailed reasons.  This could be a basic
             sub-status-code (such as an invalid Continuity Check) or
             other error codes specific to the protocol under use for
             the Continuity Checks.  For example, if ICMP is the
             protocol under use, the error codes defined in <a href="/doc/html/rfc4443">RFC 4443</a>
             can be used to specify the reasons specific to ICMP.
             This technology-specific status-sub-code can be
             defined in technology-specific models.&quot;;
          reference
            &quot;<a href="/doc/html/rfc4443">RFC 4443</a>: The IETF Administrative Oversight Committee
             (IAOC) Member Selection Guidelines and Process.&quot;;
        }
        description
          &quot;Status code and status-sub-code for Continuity Check RPC
           operation.&quot;;
      }
      uses cl-oam:continuity-check-data;
    }
  }

  rpc path-discovery {
    if-feature &quot;cl-oam:path-discovery&quot;;
    description
      &quot;Path discovery RPC operation as per <a href="/doc/html/rfc7276">RFC 7276</a>.&quot;;
    reference
      &quot;<a href="/doc/html/rfc7276">RFC 7276</a>: An Overview of Operations, Administration, and
       Maintenance (OAM) Tools&quot;;
    input {
<span class="grey"><a href="/doc/html/rfc8533">RFC 8533</a>         YANG Model for CL OAM Retrieval Methods      April 2019</span>

      uses rpc-input-parameters;
      uses cl-oam:session-type {
        description
          &quot;If session-type is specified, then session-type
            must be set to on demand&quot;;
      }
      leaf max-ttl {
        type uint8;
        default &quot;255&quot;;
        description
          &quot;Maximum TTL indicates the maximum number of hops that
           a packet is permitted to travel before being discarded
           by a router.  By default, the maximum TTL is set to
           255.&quot;;
      }
    }
    output {
      list response-list {
        key &quot;response-index&quot;;
        description
          &quot;Path discovery response list.&quot;;
        leaf response-index {
          type uint32;
          mandatory true;
          description
            &quot;Response index.&quot;;
        }
        leaf protocol-id {
          type identityref {
            base protocol-id;
          }
          mandatory true;
          description
            &quot;Protocol used in path discovery.  This could be a
             standard protocol (e.g., TCP/IP protocols, MPLS, etc.)
             or a proprietary protocol as identified by
             this field.&quot;;
        }
        leaf protocol-id-meta-data {
          type identityref {
            base protocol-id-meta-data;
          }
          description
            &quot;An optional metadata related to the protocol ID.
             For example, this could be the Internet Protocol
             number for standard Internet Protocols used for
             help with protocol processing.&quot;;
        }
<span class="grey"><a href="/doc/html/rfc8533">RFC 8533</a>         YANG Model for CL OAM Retrieval Methods      April 2019</span>

        leaf status-code {
          type identityref {
            base status-code;
          }
          mandatory true;
          description
            &quot;Status code for Continuity Check RPC operation.
             This could be a basic status code (e.g., destination
             is reachable or destination is not reachable) or some
             customized status code as identified by this field.&quot;;
        }
        leaf status-sub-code {
          type identityref {
            base status-sub-code;
          }
          mandatory true;
          description
            &quot;An optional status-sub-code for Continuity Check
             RPC operation.  If the basic status code is destination
             reachable, this status-sub-code doesn&#x27;t need to be
             specified.  If the basic status code is destination
             unreachable, the status-sub-code can be used to specify
             the detailed reasons.  This could be a basic
             sub-status-code (such as an invalid Continuity Check) or
             other error codes specific to the protocol under use for
             Continuity Checks.  For example, if ICMP is the protocol
             under use, the error codes defined in <a href="/doc/html/rfc4443">RFC 4443</a>
             can be used to specify the reasons specific to ICMP.
             This technology-specific status-sub-code can be defined
             in technology-specific models.&quot;;
          reference
            &quot;<a href="/doc/html/rfc4443">RFC 4443</a>: The IETF Administrative Oversight Committee
             (IAOC) Member Selection Guidelines and Process.&quot;;
        }
      }
      uses cl-oam:path-discovery-data;
    }
  }
}
