module ietf-network-topology-state {
  yang-version 1.1;
  namespace &quot;urn:ietf:params:xml:ns:yang:ietf-network-topology-state&quot;;
  prefix nt-s;

  import ietf-network-state {
    prefix nw-s;
    reference
      &quot;<a href="/doc/html/rfc8345">RFC 8345</a>: A YANG Data Model for Network Topologies&quot;;
  }
  import ietf-network-topology {
    prefix nt;
    reference
      &quot;<a href="/doc/html/rfc8345">RFC 8345</a>: A YANG Data Model for Network Topologies&quot;;
  }

  organization
    &quot;IETF I2RS (Interface to the Routing System) Working Group&quot;;

  contact
    &quot;WG Web:    &lt;<a href="https://datatracker.ietf.org/wg/i2rs/">https://datatracker.ietf.org/wg/i2rs/</a>&gt;
     WG List:   &lt;mailto:<a href="mailto:i2rs@ietf.org">i2rs@ietf.org</a>&gt;

     Editor:    Alexander Clemm
                &lt;mailto:<a href="mailto:ludwig@clemm.org">ludwig@clemm.org</a>&gt;

     Editor:    Jan Medved
                &lt;mailto:<a href="mailto:jmedved@cisco.com">jmedved@cisco.com</a>&gt;

     Editor:    Robert Varga
                &lt;mailto:<a href="mailto:robert.varga@pantheon.tech">robert.varga@pantheon.tech</a>&gt;

     Editor:    Nitin Bahadur
                &lt;mailto:<a href="mailto:nitin_bahadur@yahoo.com">nitin_bahadur@yahoo.com</a>&gt;

     Editor:    Hariharan Ananthakrishnan
                &lt;mailto:<a href="mailto:hari@packetdesign.com">hari@packetdesign.com</a>&gt;

     Editor:    Xufeng Liu
                &lt;mailto:<a href="mailto:xufeng.liu.ietf@gmail.com">xufeng.liu.ietf@gmail.com</a>&gt;&quot;;

<span class="grey"><a href="/doc/html/rfc8345">RFC 8345</a>         YANG Data Model for Network Topologies       March 2018</span>

    description
      &quot;This module defines a common base data model for network
       topology state, representing topology that either (1) is learned
       or (2) results from applying topology that has been configured
       per the &#x27;ietf-network-topology&#x27; data model, mirroring the
       corresponding data nodes in this data model.  It augments the
       base network state data model with links to connect nodes, as
       well as termination points to terminate links on nodes.

       The data model mirrors &#x27;ietf-network-topology&#x27; but contains only
       read-only state data.  The data model is not needed when the
       underlying implementation infrastructure supports the Network
       Management Datastore Architecture (NMDA).

       Copyright (c) 2018 IETF Trust and the persons identified as
       authors of the code.  All rights reserved.

       Redistribution and use in source and binary forms, with or
       without modification, is permitted pursuant to, and subject
       to the license terms contained in, the Simplified BSD License
       set forth in <a href="#section-4">Section 4</a>.c of the IETF Trust&#x27;s Legal Provisions
       Relating to IETF Documents
       (<a href="https://trustee.ietf.org/license-info">https://trustee.ietf.org/license-info</a>).

       This version of this YANG module is part of <a href="/doc/html/rfc8345">RFC 8345</a>;
       see the RFC itself for full legal notices.&quot;;

    revision 2018-02-26 {
      description
        &quot;Initial revision.&quot;;
      reference
        &quot;<a href="/doc/html/rfc8345">RFC 8345</a>: A YANG Data Model for Network Topologies&quot;;
    }

<span class="grey"><a href="/doc/html/rfc8345">RFC 8345</a>         YANG Data Model for Network Topologies       March 2018</span>

    grouping link-ref {
      description
        &quot;References a link in a specific network.  Although this
         grouping is not used in this module, it is defined here for
         the convenience of augmenting modules.&quot;;
      leaf link-ref {
        type leafref {
          path &quot;/nw-s:networks/nw-s:network[nw-s:network-id=current()&quot;+
            &quot;/../network-ref]/nt-s:link/nt-s:link-id&quot;;
          require-instance false;
        }
        description
          &quot;A type for an absolute reference to a link instance.
           (This type should not be used for relative references.
           In such a case, a relative path should be used instead.)&quot;;
      }
      uses nw-s:network-ref;
    }

    grouping tp-ref {
      description
        &quot;References a termination point in a specific node.  Although
         this grouping is not used in this module, it is defined here
         for the convenience of augmenting modules.&quot;;
      leaf tp-ref {
        type leafref {
          path &quot;/nw-s:networks/nw-s:network[nw-s:network-id=current()&quot;+
            &quot;/../network-ref]/nw-s:node[nw-s:node-id=current()/../&quot;+
            &quot;node-ref]/nt-s:termination-point/nt-s:tp-id&quot;;
          require-instance false;
        }
        description
          &quot;A type for an absolute reference to a termination point.
           (This type should not be used for relative references.
           In such a case, a relative path should be used instead.)&quot;;
      }
      uses nw-s:node-ref;
    }

    augment &quot;/nw-s:networks/nw-s:network&quot; {
      description
        &quot;Add links to the network data model.&quot;;
      list link {
        key &quot;link-id&quot;;
        description
          &quot;A network link connects a local (source) node and
           a remote (destination) node via a set of the respective
           node&#x27;s termination points.  It is possible to have several
<span class="grey"><a href="/doc/html/rfc8345">RFC 8345</a>         YANG Data Model for Network Topologies       March 2018</span>

           links between the same source and destination nodes.
           Likewise, a link could potentially be re-homed between
           termination points.  Therefore, in order to ensure that we
           would always know to distinguish between links, every link
           is identified by a dedicated link identifier.  Note that a
           link models a point-to-point link, not a multipoint link.&quot;;
        container source {
          description
            &quot;This container holds the logical source of a particular
             link.&quot;;
          leaf source-node {
            type leafref {
              path &quot;../../../nw-s:node/nw-s:node-id&quot;;
              require-instance false;
            }
            description
              &quot;Source node identifier.  Must be in the same topology.&quot;;
          }
          leaf source-tp {
            type leafref {
              path &quot;../../../nw-s:node[nw-s:node-id=current()/../&quot;+
                &quot;source-node]/termination-point/tp-id&quot;;
              require-instance false;
            }
            description
              &quot;This termination point is located within the source node
               and terminates the link.&quot;;
          }
        }
        container destination {
          description
            &quot;This container holds the logical destination of a
             particular link.&quot;;
          leaf dest-node {
            type leafref {
              path &quot;../../../nw-s:node/nw-s:node-id&quot;;
            require-instance false;
            }
            description
              &quot;Destination node identifier.  Must be in the same
               network.&quot;;
          }

<span class="grey"><a href="/doc/html/rfc8345">RFC 8345</a>         YANG Data Model for Network Topologies       March 2018</span>

          leaf dest-tp {
            type leafref {
              path &quot;../../../nw-s:node[nw-s:node-id=current()/../&quot;+
                &quot;dest-node]/termination-point/tp-id&quot;;
              require-instance false;
            }
            description
              &quot;This termination point is located within the
               destination node and terminates the link.&quot;;
          }
        }
        leaf link-id {
          type nt:link-id;
          description
            &quot;The identifier of a link in the topology.
             A link is specific to a topology to which it belongs.&quot;;
        }
        list supporting-link {
          key &quot;network-ref link-ref&quot;;
          description
            &quot;Identifies the link or links on which this link depends.&quot;;
          leaf network-ref {
            type leafref {
              path &quot;../../../nw-s:supporting-network/nw-s:network-ref&quot;;
            require-instance false;
            }
            description
              &quot;This leaf identifies in which underlay topology
               the supporting link is present.&quot;;
          }
          leaf link-ref {
            type leafref {
              path &quot;/nw-s:networks/nw-s:network[nw-s:network-id=&quot;+
                &quot;current()/../network-ref]/link/link-id&quot;;
              require-instance false;
            }
            description
              &quot;This leaf identifies a link that is a part
               of this link&#x27;s underlay.  Reference loops in which
               a link identifies itself as its underlay, either
               directly or transitively, are not allowed.&quot;;
          }
        }
      }
    }

<span class="grey"><a href="/doc/html/rfc8345">RFC 8345</a>         YANG Data Model for Network Topologies       March 2018</span>

    augment &quot;/nw-s:networks/nw-s:network/nw-s:node&quot; {
      description
        &quot;Augments termination points that terminate links.
         Termination points can ultimately be mapped to interfaces.&quot;;
      list termination-point {
        key &quot;tp-id&quot;;
        description
          &quot;A termination point can terminate a link.
           Depending on the type of topology, a termination point
           could, for example, refer to a port or an interface.&quot;;
        leaf tp-id {
          type nt:tp-id;
          description
            &quot;Termination point identifier.&quot;;
        }
        list supporting-termination-point {
          key &quot;network-ref node-ref tp-ref&quot;;
          description
            &quot;This list identifies any termination points on which a
             given termination point depends or onto which it maps.
             Those termination points will themselves be contained
             in a supporting node.  This dependency information can be
             inferred from the dependencies between links.  Therefore,
             this item is not separately configurable.  Hence, no
             corresponding constraint needs to be articulated.
             The corresponding information is simply provided by the
             implementing system.&quot;;
          leaf network-ref {
            type leafref {
              path &quot;../../../nw-s:supporting-node/nw-s:network-ref&quot;;
            require-instance false;
            }
            description
              &quot;This leaf identifies in which topology the
               supporting termination point is present.&quot;;
          }
          leaf node-ref {
            type leafref {
              path &quot;../../../nw-s:supporting-node/nw-s:node-ref&quot;;
            require-instance false;
            }
            description
              &quot;This leaf identifies in which node the supporting
               termination point is present.&quot;;
          }

<span class="grey"><a href="/doc/html/rfc8345">RFC 8345</a>         YANG Data Model for Network Topologies       March 2018</span>

          leaf tp-ref {
            type leafref {
              path &quot;/nw-s:networks/nw-s:network[nw-s:network-id=&quot;+
                &quot;current()/../network-ref]/nw-s:node[nw-s:node-id=&quot;+
                &quot;current()/../node-ref]/termination-point/tp-id&quot;;
              require-instance false;
            }
            description
              &quot;Reference to the underlay node (the underlay node must
               be in a different topology).&quot;;
          }
        }
      }
    }
  }
