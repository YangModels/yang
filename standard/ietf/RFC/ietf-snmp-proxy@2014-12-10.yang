submodule ietf-snmp-proxy {

  belongs-to ietf-snmp {
    prefix snmp;
  }

  include ietf-snmp-common;
  include ietf-snmp-target;

  organization
    &quot;IETF NETMOD (NETCONF Data Modeling Language) Working Group&quot;;

  contact
    &quot;WG Web:   &lt;<a href="https://tools.ietf.org/wg/netmod/">http://tools.ietf.org/wg/netmod/</a>&gt;
     WG List:  &lt;mailto:<a href="mailto:netmod@ietf.org">netmod@ietf.org</a>&gt;

     WG Chair: Thomas Nadeau
               &lt;mailto:<a href="mailto:tnadeau@lucidvision.com">tnadeau@lucidvision.com</a>&gt;

     WG Chair: Juergen Schoenwaelder
               &lt;mailto:<a href="mailto:j.schoenwaelder@jacobs-university.de">j.schoenwaelder@jacobs-university.de</a>&gt;

     Editor:   Martin Bjorklund
               &lt;mailto:<a href="mailto:mbj@tail-f.com">mbj@tail-f.com</a>&gt;

     Editor:   Juergen Schoenwaelder
               &lt;mailto:<a href="mailto:j.schoenwaelder@jacobs-university.de">j.schoenwaelder@jacobs-university.de</a>&gt;&quot;;

  description
    &quot;This submodule contains a collection of YANG definitions
     for configuring SNMP proxies.

     Copyright (c) 2014 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).

     This version of this YANG module is part of <a href="/doc/html/rfc7407">RFC 7407</a>; see
     the RFC itself for full legal notices.&quot;;
<span class="grey"><a href="/doc/html/rfc7407">RFC 7407</a>         YANG Data Model for SNMP Configuration    December 2014</span>

     reference
       &quot;<a href="/doc/html/rfc3413">RFC 3413</a>: Simple Network Management Protocol (SNMP)
          Applications&quot;;

     revision 2014-12-10 {
       description
         &quot;Initial revision.&quot;;
       reference
         &quot;<a href="/doc/html/rfc7407">RFC 7407</a>: A YANG Data Model for SNMP Configuration&quot;;
     }

     feature proxy {
       description
         &quot;A server implements this feature if it can act as an
         SNMP proxy.&quot;;
       reference
         &quot;<a href="/doc/html/rfc3413">RFC 3413</a>: Simple Network Management Protocol (SNMP)
            Applications&quot;;
     }

     augment /snmp:snmp {
       if-feature snmp:proxy;

       list proxy {
         key name;

         description
           &quot;List of proxy parameters.&quot;;
         reference
           &quot;<a href="/doc/html/rfc3413">RFC 3413</a>: Simple Network Management Protocol (SNMP).
              Applications.
              SNMP-PROXY-MIB.snmpProxyTable&quot;;

         leaf name {
           type snmp:identifier;
           description
             &quot;Identifies the proxy parameter entry.&quot;;
           reference
             &quot;<a href="/doc/html/rfc3413">RFC 3413</a>: Simple Network Management Protocol (SNMP).
                Applications.
                SNMP-PROXY-MIB.snmpProxyName&quot;;
         }
         leaf type {
           type enumeration {
             enum read { value 1; }
             enum write { value 2; }
             enum trap { value 3; }
             enum inform { value 4; }
<span class="grey"><a href="/doc/html/rfc7407">RFC 7407</a>         YANG Data Model for SNMP Configuration    December 2014</span>

           }
           mandatory true;
           reference
             &quot;<a href="/doc/html/rfc3413">RFC 3413</a>: Simple Network Management Protocol (SNMP).
                Applications.
                SNMP-PROXY-MIB.snmpProxyType&quot;;
         }
         leaf context-engine-id {
           type snmp:engine-id;
           mandatory true;
           reference
             &quot;<a href="/doc/html/rfc3413">RFC 3413</a>: Simple Network Management Protocol (SNMP).
                Applications.
                SNMP-PROXY-MIB.snmpProxyContextEngineID&quot;;
         }
         leaf context-name {
           type snmp:context-name;
           reference
             &quot;<a href="/doc/html/rfc3413">RFC 3413</a>: Simple Network Management Protocol (SNMP).
                Applications.
                SNMP-PROXY-MIB.snmpProxyContextName&quot;;
         }
         leaf target-params-in {
           type snmp:identifier;
           description
             &quot;The name of a target parameters list entry.

              Implementations MAY restrict the values of this
              leaf to be one of the available values of
              /snmp/target-params/name in a valid configuration.&quot;;
           reference
             &quot;<a href="/doc/html/rfc3413">RFC 3413</a>: Simple Network Management Protocol (SNMP).
                Applications.
                SNMP-PROXY-MIB.snmpProxyTargetParamsIn&quot;;
         }
         leaf single-target-out {
           when &quot;../type = &#x27;read&#x27; or ../type = &#x27;write&#x27;&quot;;
           type snmp:identifier;
           description
             &quot;Implementations MAY restrict the values of this leaf
              to be one of the available values of /snmp/target/name in
              a valid configuration.&quot;;
           reference
             &quot;<a href="/doc/html/rfc3413">RFC 3413</a>: Simple Network Management Protocol (SNMP).
                Applications.
                SNMP-PROXY-MIB.snmpProxySingleTargetOut&quot;;
         }

<span class="grey"><a href="/doc/html/rfc7407">RFC 7407</a>         YANG Data Model for SNMP Configuration    December 2014</span>

         leaf multiple-target-out {
           when &quot;../type = &#x27;trap&#x27; or ../type = &#x27;inform&#x27;&quot;;
           type snmp:tag-value;
           description
             &quot;Implementations MAY restrict the values of this leaf
              to be one of the available values of /snmp/target/tag in
              a valid configuration.&quot;;
           reference
             &quot;<a href="/doc/html/rfc3413">RFC 3413</a>: Simple Network Management Protocol (SNMP).
                Applications.
                SNMP-PROXY-MIB.snmpProxyMultipleTargetOut&quot;;
         }
       }
     }
   }
