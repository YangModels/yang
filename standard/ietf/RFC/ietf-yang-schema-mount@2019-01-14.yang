module ietf-yang-schema-mount {
  yang-version 1.1;
  namespace &quot;urn:ietf:params:xml:ns:yang:ietf-yang-schema-mount&quot;;
  prefix yangmnt;

  import ietf-inet-types {
    prefix inet;
    reference
      &quot;<a href="/doc/html/rfc6991">RFC 6991</a>: Common YANG Data Types&quot;;
  }

  import ietf-yang-types {
    prefix yang;
    reference
      &quot;<a href="/doc/html/rfc6991">RFC 6991</a>: Common YANG Data Types&quot;;
  }

  organization
    &quot;IETF NETMOD (NETCONF Data Modeling Language) Working Group&quot;;

  contact
    &quot;WG Web:   &lt;<a href="https://datatracker.ietf.org/wg/netmod/">https://datatracker.ietf.org/wg/netmod/</a>&gt;
     WG List:  &lt;mailto:<a href="mailto:netmod@ietf.org">netmod@ietf.org</a>&gt;

     Editor:   Martin Bjorklund
               &lt;mailto:<a href="mailto:mbj@tail-f.com">mbj@tail-f.com</a>&gt;

<span class="grey"><a href="/doc/html/rfc8528">RFC 8528</a>                    YANG Schema Mount                 March 2019</span>

        Editor:   Ladislav Lhotka
                  &lt;mailto:<a href="mailto:lhotka@nic.cz">lhotka@nic.cz</a>&gt;&quot;;

     description
       &quot;This module defines a YANG extension statement that can be used
        to incorporate data models defined in other YANG modules in a
        module.  It also defines operational state data that specify the
        overall structure of the data model.

        The key words &#x27;MUST&#x27;, &#x27;MUST NOT&#x27;, &#x27;REQUIRED&#x27;, &#x27;SHALL&#x27;, &#x27;SHALL
        NOT&#x27;, &#x27;SHOULD&#x27;, &#x27;SHOULD NOT&#x27;, &#x27;RECOMMENDED&#x27;, &#x27;NOT RECOMMENDED&#x27;,
        &#x27;MAY&#x27;, and &#x27;OPTIONAL&#x27; in this document are to be interpreted as
        described in <a href="/doc/html/bcp14">BCP 14</a> (<a href="/doc/html/rfc2119">RFC 2119</a>) (<a href="/doc/html/rfc8174">RFC 8174</a>) when, and only when,
        they appear in all capitals, as shown here.

        Copyright (c) 2019 IETF Trust and the persons identified as
        authors of the code.  All rights reserved.

        Redistribution and use in source and binary forms, with or
        without modification, is permitted pursuant to, and subject to
        the license terms contained in, the Simplified BSD License set
        forth in <a href="#section-4">Section 4</a>.c of the IETF Trust&#x27;s Legal Provisions
        Relating to IETF Documents
        (<a href="https://trustee.ietf.org/license-info">https://trustee.ietf.org/license-info</a>).

        This version of this YANG module is part of <a href="/doc/html/rfc8528">RFC 8528</a>;
        see the RFC itself for full legal notices.&quot;;

     revision 2019-01-14 {
       description
         &quot;Initial revision.&quot;;
       reference
         &quot;<a href="/doc/html/rfc8528">RFC 8528</a>: YANG Schema Mount&quot;;
     }

     /*
      * Extensions
      */

     extension mount-point {
       argument label;
       description
         &quot;The argument &#x27;label&#x27; is a YANG identifier, i.e., it is of the
          type &#x27;yang:yang-identifier&#x27;.

          The &#x27;mount-point&#x27; statement MUST NOT be used in a YANG
          version 1 module, neither explicitly nor via a &#x27;uses&#x27;
          statement.
<span class="grey"><a href="/doc/html/rfc8528">RFC 8528</a>                    YANG Schema Mount                 March 2019</span>

          The &#x27;mount-point&#x27; statement MAY be present as a substatement
          of &#x27;container&#x27; and &#x27;list&#x27; and MUST NOT be present elsewhere.
          There MUST NOT be more than one &#x27;mount-point&#x27; statement in a
          given &#x27;container&#x27; or &#x27;list&#x27; statement.

          If a mount point is defined within a grouping, its label is
          bound to the module where the grouping is used.

          A mount point defines a place in the node hierarchy where
          other data models may be attached.  A server that implements a
          module with a mount point populates the
          &#x27;/schema-mounts/mount-point&#x27; list with detailed information on
          which data models are mounted at each mount point.

          Note that the &#x27;mount-point&#x27; statement does not define a new
          data node.&quot;;
     }

     /*
      * State data nodes
      */

     container schema-mounts {
       config false;
       description
         &quot;Contains information about the structure of the overall
          mounted data model implemented in the server.&quot;;
       list namespace {
         key &quot;prefix&quot;;
         description
           &quot;This list provides a mapping of namespace prefixes that are
            used in XPath expressions of &#x27;parent-reference&#x27; leafs to the
            corresponding namespace URI references.&quot;;
         leaf prefix {
           type yang:yang-identifier;
           description
             &quot;Namespace prefix.&quot;;
         }
         leaf uri {
           type inet:uri;
           description
             &quot;Namespace URI reference.&quot;;
         }
       }
       list mount-point {
         key &quot;module label&quot;;

<span class="grey"><a href="/doc/html/rfc8528">RFC 8528</a>                    YANG Schema Mount                 March 2019</span>

         description
           &quot;Each entry of this list specifies a schema for a particular
            mount point.

            Each mount point MUST be defined using the &#x27;mount-point&#x27;
            extension in one of the modules listed in the server&#x27;s
            YANG library instance with conformance type &#x27;implement&#x27;.&quot;;
         leaf module {
           type yang:yang-identifier;
           description
             &quot;Name of a module containing the mount point.&quot;;
         }
         leaf label {
           type yang:yang-identifier;
           description
             &quot;Label of the mount point defined using the &#x27;mount-point&#x27;
              extension.&quot;;
         }
         leaf config {
           type boolean;
           default &quot;true&quot;;
           description
             &quot;If this leaf is set to &#x27;false&#x27;, then all data nodes in the
              mounted schema are read-only (&#x27;config false&#x27;), regardless
              of their &#x27;config&#x27; property.&quot;;
         }
         choice schema-ref {
           mandatory true;
           description
             &quot;Alternatives for specifying the schema.&quot;;
           container inline {
             presence
               &quot;A complete self-contained schema is mounted at the
                mount point.&quot;;
             description
               &quot;This node indicates that the server has mounted at least
                the module &#x27;ietf-yang-library&#x27; at the mount point, and
                its instantiation provides the information about the
                mounted schema.

                Different instances of the mount point may have
                different schemas mounted.&quot;;
           }
           container shared-schema {
             presence
               &quot;The mounted schema together with the &#x27;parent-reference&#x27;
                make up the schema for this mount point.&quot;;

<span class="grey"><a href="/doc/html/rfc8528">RFC 8528</a>                    YANG Schema Mount                 March 2019</span>

             description
               &quot;This node indicates that the server has mounted at least
                the module &#x27;ietf-yang-library&#x27; at the mount point, and
                its instantiation provides the information about the
                mounted schema.  When XPath expressions in the mounted
                schema are evaluated, the &#x27;parent-reference&#x27; leaf-list
                is taken into account.

                Different instances of the mount point MUST have the
                same schema mounted.&quot;;
             leaf-list parent-reference {
               type yang:xpath1.0;
               description
                 &quot;Entries of this leaf-list are XPath 1.0 expressions
                  that are evaluated in the following context:

                  - The context node is the node in the parent data tree
                    where the mount-point is defined.

                  - The accessible tree is the parent data tree
                    *without* any nodes defined in modules that are
                    mounted inside the parent schema.

                  - The context position and context size are both equal
                    to 1.

                  - The set of variable bindings is empty.

                  - The function library is the core function library
                    defined in the W3C XPath 1.0 document
                    (<a href="https://www.w3.org/TR/1999/REC-xpath-19991116">http://www.w3.org/TR/1999/REC-xpath-19991116</a>) and
                    the functions defined in <a href="/doc/html/rfc7950#section-10">Section&amp;nbsp;10 of RFC 7950</a>.

                  - The set of namespace declarations is defined by the
                    &#x27;namespace&#x27; list under &#x27;schema-mounts&#x27;.

                  Each XPath expression MUST evaluate to a node-set
                  (possibly empty).  For the purposes of evaluating
                  XPath expressions whose context nodes are defined in
                  the mounted schema, the union of all these node-sets
                  together with ancestor nodes are added to the
                  accessible data tree.

                  Note that in the case &#x27;ietf-yang-schema-mount&#x27; is
                  itself mounted, a &#x27;parent-reference&#x27; in the mounted
                  module may refer to nodes that were brought into the
                  accessible tree through a &#x27;parent-reference&#x27; in the
                  parent schema.&quot;;
<span class="grey"><a href="/doc/html/rfc8528">RFC 8528</a>                    YANG Schema Mount                 March 2019</span>

             }
           }
         }
       }
     }
   }
