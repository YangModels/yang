module ietf-yang-smiv2 {

  namespace &quot;urn:ietf:params:xml:ns:yang:ietf-yang-smiv2&quot;;
  prefix &quot;smiv2&quot;;

  organization
   &quot;IETF NETMOD (NETCONF Data Modeling Language) Working Group&quot;;

  contact
   &quot;WG Web:   &lt;<a href="https://tools.ietf.org/wg/netmod/">http://tools.ietf.org/wg/netmod/</a>&gt;
    WG List:  &lt;mailto:<a href="mailto:netmod@ietf.org">netmod@ietf.org</a>&gt;

    WG Chair: David Kessens
              &lt;mailto:<a href="mailto:david.kessens@nsn.com">david.kessens@nsn.com</a>&gt;

    WG Chair: Juergen Schoenwaelder
              &lt;mailto:<a href="mailto:j.schoenwaelder@jacobs-university.de">j.schoenwaelder@jacobs-university.de</a>&gt;

    Editor:   Juergen Schoenwaelder
              &lt;mailto:<a href="mailto:j.schoenwaelder@jacobs-university.de">j.schoenwaelder@jacobs-university.de</a>&gt;&quot;;

  description
   &quot;This module defines YANG extensions that are used to translate
    SMIv2 concepts into YANG.

    Copyright (c) 2012 IETF Trust and the persons identified as
    authors of the code.  All rights reserved.

    Redistribution and use in source and binary forms, with or
    without modification, is permitted pursuant to, and subject
    to the license terms contained in, the Simplified BSD License
    set forth in <a href="#section-4">Section 4</a>.c of the IETF Trust&#x27;s Legal Provisions
<span class="grey"><a href="/doc/html/rfc6643">RFC 6643</a>              Translation of SMIv2 to YANG             July 2012</span>

     Relating to IETF Documents
     (<a href="https://trustee.ietf.org/license-info">http://trustee.ietf.org/license-info</a>).

     This version of this YANG module is part of <a href="/doc/html/rfc6643">RFC 6643</a>; see
     the RFC itself for full legal notices.&quot;;

   revision 2012-06-22 {
     description
      &quot;Initial revision.&quot;;
     reference
      &quot;<a href="/doc/html/rfc6643">RFC 6643</a>: Translation of Structure of Management Information
       Version 2 (SMIv2) MIB Modules to YANG Modules&quot;;
   }

   identity object-identity {
     description
      &quot;Base identity for all SMIv2 OBJECT-IDENTITYs.&quot;;
   }

   typedef opaque {
     type binary;
     description
      &quot;The Opaque type supports the capability to pass arbitrary ASN.1
       syntax.  A value is encoded using the ASN.1 Basic Encoding Rules
       into a string of octets.  This, in turn, is encoded as an OCTET
       STRING, in effect &#x27;double-wrapping&#x27; the original ASN.1 value.

       In the value set and its semantics, this type is equivalent to
       the Opaque type of the SMIv2.  This type exists in the SMIv2
       solely for backward-compatibility reasons and this is also
       true for this YANG data type.&quot;;
     reference
      &quot;<a href="/doc/html/rfc2578">RFC 2578</a>: Structure of Management Information Version 2 (SMIv2)&quot;;
   }

   extension display-hint {
     argument &quot;format&quot;;
     description
      &quot;The display-hint statement takes as an argument the DISPLAY-HINT
       assigned to an SMIv2 textual convention.&quot;;
     reference
      &quot;<a href="/doc/html/rfc2579">RFC 2579</a>: Textual Conventions for SMIv2&quot;;
   }

<span class="grey"><a href="/doc/html/rfc6643">RFC 6643</a>              Translation of SMIv2 to YANG             July 2012</span>

   extension max-access {
     argument &quot;access&quot;;
     description
      &quot;The max-access statement takes as an argument the MAX-ACCESS
       assigned to an SMIv2 object definition.

       The MAX-ACCESS value is SMIv2 specific and has no impact on
       the access provided to YANG objects through protocols such
       as NETCONF.&quot;;
     reference
      &quot;<a href="/doc/html/rfc2578">RFC 2578</a>: Structure of Management Information Version 2 (SMIv2)&quot;;
   }

   extension defval {
     argument &quot;value&quot;;
     description
      &quot;The defval statement takes as an argument a default value
       defined by an SMIv2 DEFVAL clause.  Note that the value is in
       the SMIv2 value space defined by the SMIv2 syntax of the
       corresponding object and not in the YANG value space
       defined by the corresponding YANG data type.&quot;;
     reference
      &quot;<a href="/doc/html/rfc2578">RFC 2578</a>: Structure of Management Information Version 2 (SMIv2)&quot;;
   }

   extension implied {
     argument &quot;index&quot;;
     description
      &quot;If an SMIv2 INDEX object is preceded by the IMPLIED keyword, then
       the implied statement is present in the YANG module and takes as
       an argument the name of the IMPLIED index object.&quot;;
     reference
      &quot;<a href="/doc/html/rfc2578">RFC 2578</a>: Structure of Management Information Version 2 (SMIv2)&quot;;
    }

   extension alias {
     argument &quot;descriptor&quot;;
     description
      &quot;The alias statement introduces an SMIv2 descriptor.  The body of
       the alias statement is expected to contain an oid statement that
       provides the numeric OID associated with the descriptor.&quot;;
     reference
      &quot;<a href="/doc/html/rfc2578">RFC 2578</a>: Structure of Management Information Version 2 (SMIv2)&quot;;
   }

<span class="grey"><a href="/doc/html/rfc6643">RFC 6643</a>              Translation of SMIv2 to YANG             July 2012</span>

   extension oid {
     argument &quot;value&quot;;
     description
      &quot;The oid statement takes as an argument the object identifier
       assigned to an SMIv2 definition.  The object identifier value
       is written in decimal dotted notation.&quot;;
     reference
      &quot;<a href="/doc/html/rfc2578">RFC 2578</a>: Structure of Management Information Version 2 (SMIv2)&quot;;
   }

   extension subid {
     argument &quot;value&quot;;
     description
      &quot;The subid statement takes as an argument the last sub-identifier
       of the object identifier assigned to an SMIv2 definition.  The
       sub-identifier value is a single positive decimal natural number.
       The subid statement may not be used as a substatement to any
       top-level node in a YANG document.  The subid substatement may
       be used only as a substatement to a node having a parent node
       defined with either an smiv2:oid or smiv2:subid substatement.&quot;;
     reference
      &quot;<a href="/doc/html/rfc2578">RFC 2578</a>: Structure of Management Information Version 2 (SMIv2)&quot;;
   }

 }
