module ietf-yang-patch {
  yang-version 1.1;
  namespace &quot;urn:ietf:params:xml:ns:yang:ietf-yang-patch&quot;;
  prefix &quot;ypatch&quot;;

  import ietf-restconf { prefix rc; }

  organization
    &quot;IETF NETCONF (Network Configuration) Working Group&quot;;

  contact
    &quot;WG Web:   &lt;<a href="https://datatracker.ietf.org/wg/netconf/">https://datatracker.ietf.org/wg/netconf/</a>&gt;
     WG List:  &lt;mailto:<a href="mailto:netconf@ietf.org">netconf@ietf.org</a>&gt;

     Author:   Andy Bierman
               &lt;mailto:<a href="mailto:andy@yumaworks.com">andy@yumaworks.com</a>&gt;

     Author:   Martin Bjorklund
               &lt;mailto:<a href="mailto:mbj@tail-f.com">mbj@tail-f.com</a>&gt;

     Author:   Kent Watsen
               &lt;mailto:<a href="mailto:kwatsen@juniper.net">kwatsen@juniper.net</a>&gt;&quot;;

  description
    &quot;This module contains conceptual YANG specifications
     for the YANG Patch and YANG Patch Status data structures.

     Note that the YANG definitions within this module do not
     represent configuration data of any kind.
     The YANG grouping statements provide a normative syntax
     for XML and JSON message-encoding purposes.

     Copyright (c) 2017 IETF Trust and the persons identified as
     authors of the code.  All rights reserved.

<span class="grey"><a href="/doc/html/rfc8072">RFC 8072</a>                       YANG Patch                  February 2017</span>

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc8072">RFC 8072</a>; see
        the RFC itself for full legal notices.&quot;;

     revision 2017-02-22 {
       description
         &quot;Initial revision.&quot;;
       reference
         &quot;<a href="/doc/html/rfc8072">RFC 8072</a>: YANG Patch Media Type.&quot;;
     }

     typedef target-resource-offset {
       type string;
       description
         &quot;Contains a data resource identifier string representing
          a sub-resource within the target resource.
          The document root for this expression is the
          target resource that is specified in the
          protocol operation (e.g., the URI for the PATCH request).

          This string is encoded according to the same rules as those
          for a data resource identifier in a RESTCONF request URI.&quot;;
       reference
          &quot;<a href="/doc/html/rfc8040#section-3.5.3">RFC 8040, Section&amp;nbsp;3.5.3</a>.&quot;;
     }

     rc:yang-data &quot;yang-patch&quot; {
       uses yang-patch;
     }

     rc:yang-data &quot;yang-patch-status&quot; {
       uses yang-patch-status;
     }

<span class="grey"><a href="/doc/html/rfc8072">RFC 8072</a>                       YANG Patch                  February 2017</span>

     grouping yang-patch {

       description
         &quot;A grouping that contains a YANG container representing the
          syntax and semantics of a YANG Patch edit request message.&quot;;

       container yang-patch {
         description
           &quot;Represents a conceptual sequence of datastore edits,
            called a patch.  Each patch is given a client-assigned
            patch identifier.  Each edit MUST be applied
            in ascending order, and all edits MUST be applied.
            If any errors occur, then the target datastore MUST NOT
            be changed by the YANG Patch operation.

            It is possible for a datastore constraint violation to occur
            due to any node in the datastore, including nodes not
            included in the &#x27;edit&#x27; list.  Any validation errors MUST
            be reported in the reply message.&quot;;

         reference
           &quot;<a href="/doc/html/rfc7950#section-8.3">RFC 7950, Section&amp;nbsp;8.3</a>.&quot;;

         leaf patch-id {
           type string;
           mandatory true;
           description
             &quot;An arbitrary string provided by the client to identify
              the entire patch.  Error messages returned by the server
              that pertain to this patch will be identified by this
              &#x27;patch-id&#x27; value.  A client SHOULD attempt to generate
              unique &#x27;patch-id&#x27; values to distinguish between
              transactions from multiple clients in any audit logs
              maintained by the server.&quot;;
         }

         leaf comment {
           type string;
           description
             &quot;An arbitrary string provided by the client to describe
              the entire patch.  This value SHOULD be present in any
              audit logging records generated by the server for the
              patch.&quot;;
         }

<span class="grey"><a href="/doc/html/rfc8072">RFC 8072</a>                       YANG Patch                  February 2017</span>

         list edit {
           key edit-id;
           ordered-by user;

           description
             &quot;Represents one edit within the YANG Patch request message.
              The &#x27;edit&#x27; list is applied in the following manner:

                - The first edit is conceptually applied to a copy
                  of the existing target datastore, e.g., the
                  running configuration datastore.
                - Each ascending edit is conceptually applied to
                  the result of the previous edit(s).
                - After all edits have been successfully processed,
                  the result is validated according to YANG constraints.
                - If successful, the server will attempt to apply
                  the result to the target datastore.&quot;;

           leaf edit-id {
             type string;
             description
               &quot;Arbitrary string index for the edit.
                Error messages returned by the server that pertain
                to a specific edit will be identified by this value.&quot;;
           }

           leaf operation {
             type enumeration {
               enum create {
                 description
                   &quot;The target data node is created using the supplied
                    value, only if it does not already exist.  The
                    &#x27;target&#x27; leaf identifies the data node to be
                    created, not the parent data node.&quot;;
               }
               enum delete {
                 description
                   &quot;Delete the target node, only if the data resource
                    currently exists; otherwise, return an error.&quot;;
               }

<span class="grey"><a href="/doc/html/rfc8072">RFC 8072</a>                       YANG Patch                  February 2017</span>

               enum insert {
                 description
                   &quot;Insert the supplied value into a user-ordered
                    list or leaf-list entry.  The target node must
                    represent a new data resource.  If the &#x27;where&#x27;
                    parameter is set to &#x27;before&#x27; or &#x27;after&#x27;, then
                    the &#x27;point&#x27; parameter identifies the insertion
                    point for the target node.&quot;;
               }
               enum merge {
                 description
                   &quot;The supplied value is merged with the target data
                    node.&quot;;
               }
               enum move {
                 description
                   &quot;Move the target node.  Reorder a user-ordered
                    list or leaf-list.  The target node must represent
                    an existing data resource.  If the &#x27;where&#x27; parameter
                    is set to &#x27;before&#x27; or &#x27;after&#x27;, then the &#x27;point&#x27;
                    parameter identifies the insertion point to move
                    the target node.&quot;;
               }
               enum replace {
                 description
                   &quot;The supplied value is used to replace the target
                    data node.&quot;;
               }
               enum remove {
                 description
                   &quot;Delete the target node if it currently exists.&quot;;
               }
             }
             mandatory true;
             description
               &quot;The datastore operation requested for the associated
                &#x27;edit&#x27; entry.&quot;;
           }

<span class="grey"><a href="/doc/html/rfc8072">RFC 8072</a>                       YANG Patch                  February 2017</span>

           leaf target {
             type target-resource-offset;
             mandatory true;
             description
               &quot;Identifies the target data node for the edit
                operation.  If the target has the value &#x27;/&#x27;, then
                the target data node is the target resource.
                The target node MUST identify a data resource,
                not the datastore resource.&quot;;
           }

           leaf point {
             when &quot;(../operation = &#x27;insert&#x27; or ../operation = &#x27;move&#x27;)&quot;
                + &quot;and (../where = &#x27;before&#x27; or ../where = &#x27;after&#x27;)&quot; {
               description
                 &quot;This leaf only applies for &#x27;insert&#x27; or &#x27;move&#x27;
                  operations, before or after an existing entry.&quot;;
             }
             type target-resource-offset;
             description
               &quot;The absolute URL path for the data node that is being
                used as the insertion point or move point for the
                target of this &#x27;edit&#x27; entry.&quot;;
           }

           leaf where {
             when &quot;../operation = &#x27;insert&#x27; or ../operation = &#x27;move&#x27;&quot; {
               description
                 &quot;This leaf only applies for &#x27;insert&#x27; or &#x27;move&#x27;
                  operations.&quot;;
             }
             type enumeration {
               enum before {
                 description
                   &quot;Insert or move a data node before the data resource
                    identified by the &#x27;point&#x27; parameter.&quot;;
               }
               enum after {
                 description
                   &quot;Insert or move a data node after the data resource
                    identified by the &#x27;point&#x27; parameter.&quot;;
               }

<span class="grey"><a href="/doc/html/rfc8072">RFC 8072</a>                       YANG Patch                  February 2017</span>

               enum first {
                 description
                   &quot;Insert or move a data node so it becomes ordered
                    as the first entry.&quot;;
               }
               enum last {
                 description
                   &quot;Insert or move a data node so it becomes ordered
                    as the last entry.&quot;;
               }
             }
             default last;
             description
               &quot;Identifies where a data resource will be inserted
                or moved.  YANG only allows these operations for
                list and leaf-list data nodes that are
                &#x27;ordered-by user&#x27;.&quot;;
           }

           anydata value {
             when &quot;../operation = &#x27;create&#x27; &quot;
                + &quot;or ../operation = &#x27;merge&#x27; &quot;
                + &quot;or ../operation = &#x27;replace&#x27; &quot;
                + &quot;or ../operation = &#x27;insert&#x27;&quot; {
               description
                 &quot;The anydata &#x27;value&#x27; is only used for &#x27;create&#x27;,
                  &#x27;merge&#x27;, &#x27;replace&#x27;, and &#x27;insert&#x27; operations.&quot;;
             }
             description
               &quot;Value used for this edit operation.  The anydata &#x27;value&#x27;
                contains the target resource associated with the
                &#x27;target&#x27; leaf.

                For example, suppose the target node is a YANG container
                named foo:

                    container foo {
                      leaf a { type string; }
                      leaf b { type int32; }
                    }

<span class="grey"><a href="/doc/html/rfc8072">RFC 8072</a>                       YANG Patch                  February 2017</span>

                The &#x27;value&#x27; node contains one instance of foo:

                    &lt;value&gt;
                       &lt;foo xmlns=&#x27;example-foo-namespace&#x27;&gt;
                          &lt;a&gt;some value&lt;/a&gt;
                          &lt;b&gt;42&lt;/b&gt;
                       &lt;/foo&gt;
                    &lt;/value&gt;
                 &quot;;
           }
         }
       }

     } // grouping yang-patch

     grouping yang-patch-status {

       description
         &quot;A grouping that contains a YANG container representing the
          syntax and semantics of a YANG Patch Status response
          message.&quot;;

       container yang-patch-status {
         description
           &quot;A container representing the response message sent by the
            server after a YANG Patch edit request message has been
            processed.&quot;;

         leaf patch-id {
           type string;
           mandatory true;
           description
             &quot;The &#x27;patch-id&#x27; value used in the request.&quot;;
         }

         choice global-status {
           description
             &quot;Report global errors or complete success.
              If there is no case selected, then errors
              are reported in the &#x27;edit-status&#x27; container.&quot;;

<span class="grey"><a href="/doc/html/rfc8072">RFC 8072</a>                       YANG Patch                  February 2017</span>

           case global-errors {
             uses rc:errors;
             description
               &quot;This container will be present if global errors that
                are unrelated to a specific edit occurred.&quot;;
           }
           leaf ok {
             type empty;
             description
               &quot;This leaf will be present if the request succeeded
                and there are no errors reported in the &#x27;edit-status&#x27;
                container.&quot;;
           }
         }

         container edit-status {
           description
             &quot;This container will be present if there are
              edit-specific status responses to report.
              If all edits succeeded and the &#x27;global-status&#x27;
              returned is &#x27;ok&#x27;, then a server MAY omit this
              container.&quot;;

           list edit {
             key edit-id;

             description
               &quot;Represents a list of status responses,
                corresponding to edits in the YANG Patch
                request message.  If an &#x27;edit&#x27; entry was
                skipped or not reached by the server,
                then this list will not contain a corresponding
                entry for that edit.&quot;;

             leaf edit-id {
               type string;
                description
                  &quot;Response status is for the &#x27;edit&#x27; list entry
                   with this &#x27;edit-id&#x27; value.&quot;;
             }

<span class="grey"><a href="/doc/html/rfc8072">RFC 8072</a>                       YANG Patch                  February 2017</span>

             choice edit-status-choice {
               description
                 &quot;A choice between different types of status
                  responses for each &#x27;edit&#x27; entry.&quot;;
               leaf ok {
                 type empty;
                 description
                   &quot;This &#x27;edit&#x27; entry was invoked without any
                    errors detected by the server associated
                    with this edit.&quot;;
               }
               case errors {
                 uses rc:errors;
                 description
                   &quot;The server detected errors associated with the
                    edit identified by the same &#x27;edit-id&#x27; value.&quot;;
               }
             }
           }
         }
       }
     }  // grouping yang-patch-status

   }
