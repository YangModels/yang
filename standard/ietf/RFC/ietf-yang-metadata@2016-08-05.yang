module ietf-yang-metadata {

  namespace &quot;urn:ietf:params:xml:ns:yang:ietf-yang-metadata&quot;;

  prefix &quot;md&quot;;

  organization
    &quot;IETF NETMOD (NETCONF Data Modeling Language) Working Group&quot;;

  contact
    &quot;WG Web:   &lt;<a href="https://datatracker.ietf.org/wg/netmod/">https://datatracker.ietf.org/wg/netmod/</a>&gt;

     WG List:  &lt;mailto:<a href="mailto:netmod@ietf.org">netmod@ietf.org</a>&gt;

     WG Chair: Lou Berger
               &lt;mailto:<a href="mailto:lberger@labn.net">lberger@labn.net</a>&gt;

     WG Chair: Kent Watsen
               &lt;mailto:<a href="mailto:kwatsen@juniper.net">kwatsen@juniper.net</a>&gt;

     Editor:   Ladislav Lhotka
               &lt;mailto:<a href="mailto:lhotka@nic.cz">lhotka@nic.cz</a>&gt;&quot;;

  description
    &quot;This YANG module defines an &#x27;extension&#x27; statement that allows
     for defining metadata annotations.

     Copyright (c) 2016 IETF Trust and the persons identified as
     authors of the code.  All rights reserved.

     Redistribution and use in source and binary forms, with or
     without modification, is permitted pursuant to, and subject to
     the license terms contained in, the Simplified BSD License set
     forth in <a href="#section-4">Section 4</a>.c of the IETF Trust&#x27;s Legal Provisions
     Relating to IETF Documents
     (<a href="https://trustee.ietf.org/license-info">http://trustee.ietf.org/license-info</a>).

     This version of this YANG module is part of <a href="/doc/html/rfc7952">RFC 7952</a>
     (<a href="https://www.rfc-editor.org/info/rfc7952">http://www.rfc-editor.org/info/rfc7952</a>); see the RFC itself
     for full legal notices.&quot;;

<span class="grey"><a href="/doc/html/rfc7952">RFC 7952</a>                      YANG Metadata                  August 2016</span>

     revision 2016-08-05 {
       description
         &quot;Initial revision.&quot;;
       reference
         &quot;<a href="/doc/html/rfc7952">RFC 7952</a>: Defining and Using Metadata with YANG&quot;;
     }

     extension annotation {
       argument name;
       description
         &quot;This extension allows for defining metadata annotations in
          YANG modules.  The &#x27;md:annotation&#x27; statement can appear only
          at the top level of a YANG module or submodule, i.e., it
          becomes a new alternative in the ABNF production rule for
          &#x27;body-stmts&#x27; (<a href="/doc/html/rfc7950#section-14">Section&amp;nbsp;14 in RFC 7950</a>).

          The argument of the &#x27;md:annotation&#x27; statement defines the name
          of the annotation.  Syntactically, it is a YANG identifier as
          defined in <a href="/doc/html/rfc7950#section-6.2">Section&amp;nbsp;6.2 of RFC 7950</a>.

          An annotation defined with this &#x27;extension&#x27; statement inherits
          the namespace and other context from the YANG module in which
          it is defined.

          The data type of the annotation value is specified in the same
          way as for a leaf data node using the &#x27;type&#x27; statement.

          The semantics of the annotation and other documentation can be
          specified using the following standard YANG substatements (all
          are optional): &#x27;description&#x27;, &#x27;if-feature&#x27;, &#x27;reference&#x27;,
          &#x27;status&#x27;, and &#x27;units&#x27;.

          A server announces support for a particular annotation by
          including the module in which the annotation is defined among
          the advertised YANG modules, e.g., in a NETCONF &lt;hello&gt;
          message or in the YANG library (<a href="/doc/html/rfc7950">RFC 7950</a>).  The annotation can
          then be attached to any instance of a data node defined in any
          YANG module that is advertised by the server.

          XML encoding and JSON encoding of annotations are defined in
          <a href="/doc/html/rfc7952">RFC 7952</a>.&quot;;
     }
   }
