module ietf-snmp {

  namespace &quot;urn:ietf:params:xml:ns:yang:ietf-snmp&quot;;
  prefix snmp;

  include ietf-snmp-common {
    revision-date 2014-12-10;
  }
  include ietf-snmp-engine {
<span class="grey"><a href="/doc/html/rfc7407">RFC 7407</a>         YANG Data Model for SNMP Configuration    December 2014</span>

       revision-date 2014-12-10;
     }
     include ietf-snmp-target {
       revision-date 2014-12-10;
     }
     include ietf-snmp-notification {
       revision-date 2014-12-10;
     }
     include ietf-snmp-proxy {
       revision-date 2014-12-10;
     }
     include ietf-snmp-community {
       revision-date 2014-12-10;
     }
     include ietf-snmp-usm {
       revision-date 2014-12-10;
     }
     include ietf-snmp-tsm {
       revision-date 2014-12-10;
     }
     include ietf-snmp-vacm {
       revision-date 2014-12-10;
     }
     include ietf-snmp-tls {
       revision-date 2014-12-10;
     }
     include ietf-snmp-ssh {
       revision-date 2014-12-10;
     }

     organization
       &quot;IETF NETMOD (NETCONF Data Modeling Language) Working Group&quot;;

     contact
       &quot;WG Web:   &lt;<a href="https://tools.ietf.org/wg/netmod/">http://tools.ietf.org/wg/netmod/</a>&gt;
        WG List:  &lt;mailto:<a href="mailto:netmod@ietf.org">netmod@ietf.org</a>&gt;

        WG Chair: Thomas Nadeau
                  &lt;mailto:<a href="mailto:tnadeau@lucidvision.com">tnadeau@lucidvision.com</a>&gt;

        WG Chair: Juergen Schoenwaelder
                  &lt;mailto:<a href="mailto:j.schoenwaelder@jacobs-university.de">j.schoenwaelder@jacobs-university.de</a>&gt;

        Editor:   Martin Bjorklund
                  &lt;mailto:<a href="mailto:mbj@tail-f.com">mbj@tail-f.com</a>&gt;

        Editor:   Juergen Schoenwaelder
                  &lt;mailto:<a href="mailto:j.schoenwaelder@jacobs-university.de">j.schoenwaelder@jacobs-university.de</a>&gt;&quot;;
<span class="grey"><a href="/doc/html/rfc7407">RFC 7407</a>         YANG Data Model for SNMP Configuration    December 2014</span>

     description
       &quot;This module contains a collection of YANG definitions for
        configuring SNMP engines.

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc7407">RFC 7407</a>; see
        the RFC itself for full legal notices.&quot;;

     revision 2014-12-10 {
       description
         &quot;Initial revision.&quot;;
       reference
         &quot;<a href="/doc/html/rfc7407">RFC 7407</a>: A YANG Data Model for SNMP Configuration&quot;;
     }

   }
