module ietf-l3-unicast-topology {
  yang-version 1.1;
  namespace
    &quot;urn:ietf:params:xml:ns:yang:ietf-l3-unicast-topology&quot;;
  prefix &quot;l3t&quot;;
  import ietf-network {
    prefix &quot;nw&quot;;
  }
  import ietf-network-topology {
    prefix &quot;nt&quot;;
  }
<span class="grey"><a href="/doc/html/rfc8346">RFC 8346</a>            YANG Data Model for L3 Topologies         March 2018</span>

     import ietf-inet-types {
       prefix &quot;inet&quot;;
     }
     import ietf-routing-types {
       prefix &quot;rt-types&quot;;
     }
     organization
       &quot;IETF I2RS (Interface to the Routing System) Working Group&quot;;
     contact
       &quot;WG Web:    &lt;<a href="https://datatracker.ietf.org/wg/i2rs/">https://datatracker.ietf.org/wg/i2rs/</a>&gt;
        WG List:   &lt;mailto:<a href="mailto:i2rs@ietf.org">i2rs@ietf.org</a>&gt;
        Editor:    Alexander Clemm
                   &lt;mailto:<a href="mailto:ludwig@clemm.org">ludwig@clemm.org</a>&gt;
        Editor:    Jan Medved
                   &lt;mailto:<a href="mailto:jmedved@cisco.com">jmedved@cisco.com</a>&gt;
        Editor:    Robert Varga
                   &lt;mailto:<a href="mailto:robert.varga@pantheon.tech">robert.varga@pantheon.tech</a>&gt;
        Editor:    Xufeng Liu
                   &lt;mailto:<a href="mailto:xufeng.liu.ietf@gmail.com">xufeng.liu.ietf@gmail.com</a>&gt;
        Editor:    Nitin Bahadur
                   &lt;mailto:<a href="mailto:nitin_bahadur@yahoo.com">nitin_bahadur@yahoo.com</a>&gt;
        Editor:    Hariharan Ananthakrishnan
                   &lt;mailto:<a href="mailto:hari@packetdesign.com">hari@packetdesign.com</a>&gt;&quot;;
     description
       &quot;This module defines a model for Layer 3 Unicast
        topologies.

        Copyright (c) 2018 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">https://trustee.ietf.org/license-info</a>).

        This version of this YANG module is part of
        <a href="/doc/html/rfc8346">RFC 8346</a>; see the RFC itself for full legal notices.&quot;;
     revision &quot;2018-02-26&quot; {
       description
         &quot;Initial revision.&quot;;
       reference
         &quot;<a href="/doc/html/rfc8346">RFC 8346</a>: A YANG Data Model for Layer 3 Topologies&quot;;
     }

     identity flag-identity {
       description &quot;Base type for flags&quot;;
<span class="grey"><a href="/doc/html/rfc8346">RFC 8346</a>            YANG Data Model for L3 Topologies         March 2018</span>

     }

     typedef l3-event-type {
       type enumeration {
         enum &quot;add&quot; {
           description
             &quot;A Layer 3 node, link, prefix, or termination point has
             been added&quot;;
         }
         enum &quot;remove&quot; {
           description
             &quot;A Layer 3 node, link, prefix, or termination point has
             been removed&quot;;
         }
         enum &quot;update&quot; {
           description
             &quot;A Layer 3 node, link, prefix, or termination point has
             been updated&quot;;
         }
       }
       description &quot;Layer 3 event type for notifications&quot;;
     }

     typedef prefix-flag-type {
       type identityref {
         base &quot;flag-identity&quot;;
       }
       description &quot;Prefix flag attributes&quot;;
     }

     typedef node-flag-type {
       type identityref {
         base &quot;flag-identity&quot;;
       }
       description &quot;Node flag attributes&quot;;
     }

     typedef link-flag-type {
       type identityref {
         base &quot;flag-identity&quot;;
       }
       description &quot;Link flag attributes&quot;;
     }

     typedef l3-flag-type {
       type identityref {
         base &quot;flag-identity&quot;;
       }
<span class="grey"><a href="/doc/html/rfc8346">RFC 8346</a>            YANG Data Model for L3 Topologies         March 2018</span>

       description &quot;L3 flag attributes&quot;;
     }

     grouping l3-prefix-attributes {
       description
         &quot;L3 prefix attributes&quot;;
       leaf prefix {
         type inet:ip-prefix;
         description
           &quot;IP prefix value&quot;;
       }
       leaf metric {
         type uint32;
         description
           &quot;Prefix metric&quot;;
       }
       leaf-list flag {
         type prefix-flag-type;
         description
           &quot;Prefix flags&quot;;
       }
     }
     grouping l3-unicast-topology-type {
       description &quot;Identifies the topology type to be L3 Unicast.&quot;;
       container l3-unicast-topology {
         presence &quot;indicates L3 Unicast topology&quot;;
         description
           &quot;The presence of the container node indicates L3 Unicast
           topology&quot;;
       }
     }
     grouping l3-topology-attributes {
       description &quot;Topology scope attributes&quot;;
       container l3-topology-attributes {
         description &quot;Contains topology attributes&quot;;
         leaf name {
           type string;
           description
             &quot;Name of the topology&quot;;
         }
         leaf-list flag {
           type l3-flag-type;
           description
             &quot;Topology flags&quot;;
         }
       }
     }
     grouping l3-node-attributes {
<span class="grey"><a href="/doc/html/rfc8346">RFC 8346</a>            YANG Data Model for L3 Topologies         March 2018</span>

       description &quot;L3 node scope attributes&quot;;
       container l3-node-attributes {
         description
           &quot;Contains node attributes&quot;;
         leaf name {
           type inet:domain-name;
           description
             &quot;Node name&quot;;
         }
         leaf-list flag {
           type node-flag-type;
           description
             &quot;Node flags&quot;;
         }
         leaf-list router-id {
           type rt-types:router-id;
           description
             &quot;Router-id for the node&quot;;
         }
         list prefix {
           key &quot;prefix&quot;;
           description
             &quot;A list of prefixes along with their attributes&quot;;
           uses l3-prefix-attributes;
         }
       }
     }
     grouping l3-link-attributes {
       description
         &quot;L3 link scope attributes&quot;;
       container l3-link-attributes {
         description
           &quot;Contains link attributes&quot;;
         leaf name {
           type string;
           description
             &quot;Link Name&quot;;
         }
         leaf-list flag {
           type link-flag-type;
           description
             &quot;Link flags&quot;;
         }
         leaf metric1 {
           type uint64;
           description
               &quot;Link Metric 1&quot;;
         }
<span class="grey"><a href="/doc/html/rfc8346">RFC 8346</a>            YANG Data Model for L3 Topologies         March 2018</span>

         leaf metric2 {
           type uint64;
           description
               &quot;Link Metric 2&quot;;
         }
       }
     }
     grouping l3-termination-point-attributes {
       description &quot;L3 termination point scope attributes&quot;;
       container l3-termination-point-attributes {
         description
           &quot;Contains termination point attributes&quot;;
         choice termination-point-type {
           description
             &quot;Indicates the termination point type&quot;;
           case ip {
             leaf-list ip-address {
               type inet:ip-address;
               description
                 &quot;IPv4 or IPv6 address.&quot;;
             }
           }
           case unnumbered {
             leaf unnumbered-id {
               type uint32;
               description
                 &quot;Unnumbered interface identifier.
                  The identifier will correspond to the ifIndex value
                  of the interface, i.e., the ifIndex value of the
                  ifEntry that represents the interface in
                  implementations where the Interfaces Group MIB
                  (<a href="/doc/html/rfc2863">RFC 2863</a>) is supported.&quot;;
               reference
                 &quot;<a href="/doc/html/rfc2863">RFC 2863</a>: The Interfaces Group MIB&quot;;
             }
           }
           case interface-name {
             leaf interface-name {
               type string;
               description
                 &quot;Name of the interface.  The name can (but does not
                  have to) correspond to an interface reference of a
                  containing node&#x27;s interface, i.e., the path name of a
                  corresponding interface data node on the containing
                  node reminiscent of data type interface-ref defined
                  in <a href="/doc/html/rfc8343">RFC 8343</a>. It should be noted that data type
                  interface-ref of <a href="/doc/html/rfc8343">RFC 8343</a> cannot be used directly,

<span class="grey"><a href="/doc/html/rfc8346">RFC 8346</a>            YANG Data Model for L3 Topologies         March 2018</span>

                  as this data type is used to reference an interface
                  in a datastore of a single node in the network, not
                  to uniquely reference interfaces across a network.&quot;;
               reference
                 &quot;<a href="/doc/html/rfc8343">RFC 8343</a>: A YANG Data Model for Interface Management&quot;;
             }
           }
         }
       }
     }
     augment &quot;/nw:networks/nw:network/nw:network-types&quot; {
       description
         &quot;Introduces new network type for L3 Unicast topology&quot;;
       uses l3-unicast-topology-type;
     }
     augment &quot;/nw:networks/nw:network&quot; {
       when &quot;nw:network-types/l3t:l3-unicast-topology&quot; {
         description
           &quot;Augmentation parameters apply only for networks with
           L3 Unicast topology&quot;;
       }
       description
           &quot;L3 Unicast for the network as a whole&quot;;
       uses l3-topology-attributes;
     }
     augment &quot;/nw:networks/nw:network/nw:node&quot; {
       when &quot;../nw:network-types/l3t:l3-unicast-topology&quot; {
         description
           &quot;Augmentation parameters apply only for networks with
           L3 Unicast topology&quot;;
       }
       description
           &quot;L3 Unicast node-level attributes &quot;;
       uses l3-node-attributes;
     }
     augment &quot;/nw:networks/nw:network/nt:link&quot; {
       when &quot;../nw:network-types/l3t:l3-unicast-topology&quot; {
         description
           &quot;Augmentation parameters apply only for networks with
           L3 Unicast topology&quot;;
       }
       description
         &quot;Augments topology link attributes&quot;;
       uses l3-link-attributes;
     }
     augment &quot;/nw:networks/nw:network/nw:node/&quot;
            +&quot;nt:termination-point&quot; {
       when &quot;../../nw:network-types/l3t:l3-unicast-topology&quot; {
<span class="grey"><a href="/doc/html/rfc8346">RFC 8346</a>            YANG Data Model for L3 Topologies         March 2018</span>

         description
           &quot;Augmentation parameters apply only for networks with
           L3 Unicast topology&quot;;
       }
       description &quot;Augments topology termination point configuration&quot;;
       uses l3-termination-point-attributes;
     }
     notification l3-node-event {
       description
         &quot;Notification event for L3 node&quot;;
       leaf l3-event-type {
         type l3-event-type;
         description
           &quot;Event type&quot;;
       }
       uses nw:node-ref;
       uses l3-unicast-topology-type;
       uses l3-node-attributes;
     }
     notification l3-link-event {
       description
         &quot;Notification event for L3 link&quot;;
       leaf l3-event-type {
         type l3-event-type;
         description
           &quot;Event type&quot;;
       }
       uses nt:link-ref;
       uses l3-unicast-topology-type;
       uses l3-link-attributes;
     }
     notification l3-prefix-event {
       description
         &quot;Notification event for L3 prefix&quot;;
       leaf l3-event-type {
         type l3-event-type;
         description
           &quot;Event type&quot;;
       }
       uses nw:node-ref;
       uses l3-unicast-topology-type;
       container prefix {
         description
           &quot;Contains L3 prefix attributes&quot;;
         uses l3-prefix-attributes;
       }
     }
     notification termination-point-event {
<span class="grey"><a href="/doc/html/rfc8346">RFC 8346</a>            YANG Data Model for L3 Topologies         March 2018</span>

       description
         &quot;Notification event for L3 termination point&quot;;
       leaf l3-event-type {
         type l3-event-type;
         description
           &quot;Event type&quot;;
       }
       uses nt:tp-ref;
       uses l3-unicast-topology-type;
       uses l3-termination-point-attributes;
     }
   }
