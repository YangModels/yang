module ietf-microwave-types {
  yang-version 1.1;
  namespace &quot;urn:ietf:params:xml:ns:yang:ietf-microwave-types&quot;;
  prefix mw-types;

  organization
    &quot;Internet Engineering Task Force (IETF) CCAMP WG&quot;;
  contact
    &quot;WG List: &lt;mailto:<a href="mailto:ccamp@ietf.org">ccamp@ietf.org</a>&gt;

     Editors:
      Jonas Ahlberg (<a href="mailto:jonas.ahlberg@ericsson.com">jonas.ahlberg@ericsson.com</a>)
      Min Ye (<a href="mailto:amy.yemin@huawei.com">amy.yemin@huawei.com</a>)
      Xi Li (<a href="mailto:Xi.Li@neclab.eu">Xi.Li@neclab.eu</a>)
      Daniela Spreafico (<a href="mailto:daniela.spreafico@nokia.com">daniela.spreafico@nokia.com</a>)
      Marko Vaupotic (<a href="mailto:Marko.Vaupotic@aviatnet.com">Marko.Vaupotic@aviatnet.com</a>)&quot;;
  description
    &quot;This module contains a collection of YANG data types
     considered generally useful for microwave interfaces.

     Copyright (c) 2019 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).

     This version of this YANG module is part of <a href="/doc/html/rfc8561">RFC 8561</a>; see
     the RFC itself for full legal notices.&quot;;

  revision 2019-06-19 {
    description
      &quot;Initial revision.&quot;;
    reference
      &quot;<a href="/doc/html/rfc8561">RFC 8561</a>: A YANG Data Model for Microwave Radio Link&quot;;
  }

<span class="grey"><a href="/doc/html/rfc8561">RFC 8561</a>          Microwave Radio Link YANG Data Model         June 2019</span>

     /*
      * Radio-link-terminal mode identities
      */

     identity rlt-mode {
       description
         &quot;A description of the mode in which the radio link
          terminal is configured.  The format is X plus Y.
          X represents the number of bonded carrier terminations.
          Y represents the number of protecting carrier
          terminations.&quot;;
     }

     identity one-plus-zero {
       base rlt-mode;
       description
         &quot;1 carrier termination only.&quot;;
     }

     identity one-plus-one {
       base rlt-mode;
       description
         &quot;1 carrier termination
          and 1 protecting carrier termination.&quot;;
     }

     identity two-plus-zero {
       base rlt-mode;
       description
         &quot;2 bonded carrier terminations.&quot;;
     }

     /*
      * Coding and modulation identities
      */

     identity coding-modulation {
       description
         &quot;The coding and modulation schemes.&quot;;
     }

     identity half-bpsk {
       base coding-modulation;
       description
         &quot;Half BPSK coding and modulation scheme.&quot;;
     }

<span class="grey"><a href="/doc/html/rfc8561">RFC 8561</a>          Microwave Radio Link YANG Data Model         June 2019</span>

     identity half-bpsk-strong {
       base half-bpsk;
       description
         &quot;Half BPSK strong coding and modulation scheme.&quot;;
     }

     identity half-bpsk-light {
       base half-bpsk;
       description
         &quot;Half BPSK light coding and modulation scheme.&quot;;
     }

     identity bpsk {
       base coding-modulation;
       description
         &quot;BPSK coding and modulation scheme.&quot;;
     }

     identity bpsk-strong {
       base bpsk;
       description
         &quot;BPSK strong coding and modulation scheme.&quot;;
     }

     identity bpsk-light {
       base bpsk;
       description
         &quot;BPSK light coding and modulation scheme.&quot;;
     }

     identity qpsk {
       base coding-modulation;
       description
         &quot;QPSK coding and modulation scheme.&quot;;
     }

     identity qam-4 {
       base coding-modulation;
       description
         &quot;4 QAM coding and modulation scheme.&quot;;
     }

     identity qam-4-strong {
       base qam-4;
       description
         &quot;4 QAM strong coding and modulation scheme.&quot;;
     }

<span class="grey"><a href="/doc/html/rfc8561">RFC 8561</a>          Microwave Radio Link YANG Data Model         June 2019</span>

     identity qam-4-light {
       base qam-4;
       description
         &quot;4 QAM light coding and modulation scheme.&quot;;
     }

     identity qam-16 {
       base coding-modulation;
       description
         &quot;16 QAM coding and modulation scheme.&quot;;
     }

     identity qam-16-strong {
       base qam-16;
       description
         &quot;16 QAM strong coding and modulation scheme.&quot;;
     }

     identity qam-16-light {
       base qam-16;
       description
         &quot;16 QAM light coding and modulation scheme.&quot;;
     }

     identity qam-32 {
       base coding-modulation;
       description
         &quot;32 QAM coding and modulation scheme.&quot;;
     }

     identity qam-32-strong {
       base qam-32;
       description
         &quot;32 QAM strong coding and modulation scheme.&quot;;
     }

     identity qam-32-light {
       base qam-32;
       description
         &quot;32 QAM light coding and modulation scheme.&quot;;
     }

     identity qam-64 {
       base coding-modulation;
       description
         &quot;64 QAM coding and modulation scheme.&quot;;
     }

<span class="grey"><a href="/doc/html/rfc8561">RFC 8561</a>          Microwave Radio Link YANG Data Model         June 2019</span>

     identity qam-64-strong {
       base qam-64;
       description
         &quot;64 QAM strong coding and modulation scheme.&quot;;
     }

     identity qam-64-light {
       base qam-64;
       description
         &quot;64 QAM light coding and modulation scheme.&quot;;
     }

     identity qam-128 {
       base coding-modulation;
       description
         &quot;128 QAM coding and modulation scheme.&quot;;
     }

     identity qam-128-strong {
       base qam-128;
       description
         &quot;128 QAM strong coding and modulation scheme.&quot;;
     }

     identity qam-128-light {
       base qam-128;
       description
         &quot;128 QAM light coding and modulation scheme.&quot;;
     }

     identity qam-256 {
       base coding-modulation;
       description
         &quot;256 QAM coding and modulation scheme.&quot;;
     }

     identity qam-256-strong {
       base qam-256;
       description
         &quot;256 QAM strong coding and modulation scheme.&quot;;
     }

     identity qam-256-light {
       base qam-256;
       description
         &quot;256 QAM light coding and modulation scheme.&quot;;
     }

<span class="grey"><a href="/doc/html/rfc8561">RFC 8561</a>          Microwave Radio Link YANG Data Model         June 2019</span>

     identity qam-512 {
       base coding-modulation;
       description
         &quot;512 QAM coding and modulation scheme.&quot;;
     }

     identity qam-512-strong {
       base qam-512;
       description
         &quot;512 QAM strong coding and modulation scheme.&quot;;
     }

     identity qam-512-light {
       base qam-512;
       description
         &quot;512 QAM light coding and modulation scheme.&quot;;
     }

     identity qam-1024 {
       base coding-modulation;
       description
         &quot;1024 QAM coding and modulation scheme.&quot;;
     }

     identity qam-1024-strong {
       base qam-1024;
       description
         &quot;1024 QAM strong coding and modulation scheme.&quot;;
     }

     identity qam-1024-light {
       base qam-1024;
       description
         &quot;1024 QAM light coding and modulation scheme.&quot;;
     }

     identity qam-2048 {
       base coding-modulation;
       description
         &quot;2048 QAM coding and modulation scheme.&quot;;
     }

     identity qam-2048-strong {
       base qam-2048;
       description
         &quot;2048 QAM strong coding and modulation scheme.&quot;;
     }

<span class="grey"><a href="/doc/html/rfc8561">RFC 8561</a>          Microwave Radio Link YANG Data Model         June 2019</span>

     identity qam-2048-light {
       base qam-2048;
       description
         &quot;2048 QAM light coding and modulation scheme.&quot;;
     }

     identity qam-4096 {
       base coding-modulation;
       description
         &quot;4096 QAM coding and modulation scheme.&quot;;
     }

     identity qam-4096-strong {
       base qam-4096;
       description
         &quot;4096 QAM strong coding and modulation scheme.&quot;;
     }

     identity qam-4096-light {
       base qam-4096;
       description
         &quot;4096 QAM light coding and modulation scheme.&quot;;
     }

     /*
      * TDM-type identities
      */

     identity tdm-type {
       description
         &quot;A description of the type of TDM connection,
          also indicating the supported capacity of the
          connection.&quot;;
     }

     identity E1 {
       base tdm-type;
       description
         &quot;E1 connection, 2.048 Mbit/s.&quot;;
     }

     identity STM-1 {
       base tdm-type;
       description
         &quot;STM-1 connection, 155.52 Mbit/s.&quot;;
     }
   }
