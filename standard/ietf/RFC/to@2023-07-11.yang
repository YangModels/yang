yang-version 1.1;
namespace "urn:example:example-service-assurance-device-acme";
prefix example-device-acme;

import ietf-service-assurance {
  prefix sain;
  reference
    "RFC 9418: YANG Modules for Service Assurance";
}
import ietf-service-assurance-device {
  prefix sain-device;
  reference
    "RFC 9418: YANG Modules for Service Assurance";
}

organization
  "IETF OPSAWG Working Group";
contact
  "WG Web:   <https://datatracker.ietf.org/wg/opsawg/>
   WG List:  <mailto:opsawg@ietf.org>
   Author:   Benoit Claise  <mailto:benoit.claise@huawei.com>
   Author:   Jean Quilbeuf   <mailto:jean.quilbeuf@huawei.com>";
description
  "This example module extends the ietf-service-assurance-device
   module to add specific support for devices of the Acme
   Corporation. ";

revision 2023-07-11 {
  description
    "Initial revision.";
  reference
    "RFC 9418: YANG Modules for Service Assurance";
}

identity device-acme-type {
  base sain-device:device-type;
  description
    "Network device is healthy.";
}

augment "/sain:subservices/sain:subservice/sain:parameter" {
  when "derived-from-or-self(sain:type, 'device-acme-type')";
  description
    "Augments the parameter choice from the ietf-service-assurance
     module with a case specific to the device-acme subservice.";
  container parameters {
    description
      "Parameters for the device-acme subservice type.";
    leaf device {
      type string;
      mandatory true;
      description
        "The device to monitor.";
    }
    leaf acme-specific-parameter {
      type string;
      mandatory true;
      description
        "The Acme-Corporation-specific parameter.";
    }
  }
}
}
