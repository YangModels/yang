module ietf-lime-time-types {
  yang-version 1.1;
  namespace &quot;urn:ietf:params:xml:ns:yang:ietf-lime-time-types&quot;;
  prefix lime;

  organization
    &quot;IETF LIME Working Group&quot;;
  contact
    &quot;WG Web:   &lt;<a href="https://datatracker.ietf.org/wg/lime">https://datatracker.ietf.org/wg/lime</a>&gt;
     WG List:  &lt;mailto:<a href="mailto:lmap@ietf.org">lmap@ietf.org</a>&gt;

     Editor:   Qin Wu
               &lt;<a href="mailto:bill.wu@huawei.com">bill.wu@huawei.com</a>&gt;&quot;;
  description
    &quot;This module provides time-related definitions used by the data
     models written for Layer Independent OAM Management in the
     Multi-Layer Environment (LIME).  This module defines
     identities but no schema tree elements.

<span class="grey"><a href="/doc/html/rfc8532">RFC 8532</a>           Connectionless OAM YANG Data Model         April 2019</span>

        Copyright (c) 2019 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc8532">RFC 8532</a>; see
        the RFC itself for full legal notices.&quot;;

     revision 2019-04-16 {
       description
         &quot;Initial version.&quot;;
       reference
         &quot;<a href="/doc/html/rfc8532">RFC 8532</a>: Generic YANG Data Model for the Management of
          Operations, Administration, and Maintenance (OAM) Protocols
          That Use Connectionless Communications&quot;;
     }

     /*** Collection of common types related to time ***/
     /*** Time unit identity ***/

     identity time-unit-type {
       description
         &quot;Time unit type.&quot;;
     }

     identity hours {
       base time-unit-type;
       description
         &quot;Time unit in hours.&quot;;
     }

     identity minutes {
       base time-unit-type;
       description
         &quot;Time unit in minutes.&quot;;
     }

     identity seconds {
       base time-unit-type;
       description
         &quot;Time unit in seconds.&quot;;
     }

<span class="grey"><a href="/doc/html/rfc8532">RFC 8532</a>           Connectionless OAM YANG Data Model         April 2019</span>

     identity milliseconds {
       base time-unit-type;
       description
         &quot;Time unit in milliseconds.&quot;;
     }

     identity microseconds {
       base time-unit-type;
       description
         &quot;Time unit in microseconds.&quot;;
     }

     identity nanoseconds {
       base time-unit-type;
       description
         &quot;Time unit in nanoseconds.&quot;;
     }

     /*** Timestamp format Identity ***/

     identity timestamp-type {
       description
         &quot;Base identity for Timestamp Type.&quot;;
     }

     identity truncated-ptp {
       base timestamp-type;
       description
         &quot;Identity for 64-bit short-format PTP timestamp.&quot;;
     }

     identity truncated-ntp {
       base timestamp-type;
       description
         &quot;Identity for 32-bit short-format NTP timestamp.&quot;;
     }

     identity ntp64 {
       base timestamp-type;
       description
         &quot;Identity for 64-bit NTP timestamp.&quot;;
     }

     identity icmp {
       base timestamp-type;
       description
         &quot;Identity for 32-bit ICMP timestamp.&quot;;
     }
<span class="grey"><a href="/doc/html/rfc8532">RFC 8532</a>           Connectionless OAM YANG Data Model         April 2019</span>

     identity ptp80 {
       base timestamp-type;
       description
         &quot;Identity for 80-bit PTP timestamp.&quot;;
     }
   }
