module ietf-l2vpn-svc {
  yang-version 1.1;
  namespace &quot;urn:ietf:params:xml:ns:yang:ietf-l2vpn-svc&quot;;
  prefix l2vpn-svc;

  import ietf-inet-types {
    prefix inet;
  }
  import ietf-yang-types {
    prefix yang;
  }
  import ietf-netconf-acm {
    prefix nacm;
  }

<span class="grey"><a href="/doc/html/rfc8466">RFC 8466</a>               L2VPN Service Model (L2SM)           October 2018</span>

  organization
    &quot;IETF L2SM Working Group.&quot;;
  contact
    &quot;WG Web:   &lt;<a href="https://datatracker.ietf.org/wg/l2sm/">https://datatracker.ietf.org/wg/l2sm/</a>&gt;
     WG List:  &lt;mailto:<a href="mailto:l2sm@ietf.org">l2sm@ietf.org</a>&gt;
     Editor:   Giuseppe Fioccola
               &lt;mailto:<a href="mailto:giuseppe.fioccola@tim.it">giuseppe.fioccola@tim.it</a>&gt;&quot;;
  description
    &quot;This YANG module defines a generic service configuration model
     for Layer 2 VPN services common across all vendor
     implementations.

     Copyright (c) 2018 IETF Trust and the persons
     identified as authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">https://trustee.ietf.org/license-info</a>).

     This version of this YANG module is part of <a href="/doc/html/rfc8466">RFC 8466</a>;
     see the RFC itself for full legal notices.&quot;;

  revision 2018-10-09 {
    description
      &quot;Initial revision.&quot;;
    reference
      &quot;<a href="/doc/html/rfc8466">RFC 8466</a>: A YANG Data Model for Layer 2 Virtual Private
       Network (L2VPN) Service Delivery&quot;;
  }

  feature carrierscarrier {
    description
      &quot;Enables the support of carriers&#x27; carriers (CsC).&quot;;
  }

  feature ethernet-oam {
    description
      &quot;Enables the support of Ethernet Service OAM.&quot;;
  }

  feature extranet-vpn {
    description
      &quot;Enables the support of extranet VPNs.&quot;;
  }

<span class="grey"><a href="/doc/html/rfc8466">RFC 8466</a>               L2VPN Service Model (L2SM)           October 2018</span>

  feature l2cp-control {
    description
      &quot;Enables the support of L2CP control.&quot;;
  }

  feature input-bw {
    description
      &quot;Enables the support of input bandwidth in a VPN.&quot;;
  }

  feature output-bw {
    description
      &quot;Enables the support of output bandwidth in a VPN.&quot;;
  }

  feature uni-list {
    description
      &quot;Enables the support of a list of UNIs in a VPN.&quot;;
  }

  feature cloud-access {
    description
      &quot;Allows the VPN to connect to a Cloud Service Provider (CSP)
       or an ISP.&quot;;
  }

  feature oam-3ah {
    description
      &quot;Enables the support of OAM 802.3ah.&quot;;
  }

  feature micro-bfd {
    description
      &quot;Enables the support of micro-BFD.&quot;;
  }

  feature bfd {
    description
      &quot;Enables the support of BFD.&quot;;
  }

  feature signaling-options {
    description
      &quot;Enables the support of signaling options.&quot;;
  }

  feature site-diversity {
    description
<span class="grey"><a href="/doc/html/rfc8466">RFC 8466</a>               L2VPN Service Model (L2SM)           October 2018</span>

      &quot;Enables the support of site diversity constraints in a VPN.&quot;;
  }

  feature encryption {
    description
      &quot;Enables the support of encryption.&quot;;
  }

  feature always-on {
    description
      &quot;Enables support for the &#x27;always-on&#x27; access constraint.&quot;;
  }

  feature requested-type {
    description
      &quot;Enables support for the &#x27;requested-type&#x27; access constraint.&quot;;
  }

  feature bearer-reference {
    description
      &quot;Enables support for the &#x27;bearer-reference&#x27; access
       constraint.&quot;;
  }

  feature qos {
    description
      &quot;Enables support for QoS.&quot;;
  }

  feature qos-custom {
    description
      &quot;Enables the support of a custom QoS profile.&quot;;
  }

  feature lag-interface {
    description
      &quot;Enables LAG interfaces.&quot;;
  }

  feature vlan {
    description
      &quot;Enables the support of VLANs.&quot;;
  }

  feature dot1q {
    description
      &quot;Enables the support of dot1Q.&quot;;
  }
<span class="grey"><a href="/doc/html/rfc8466">RFC 8466</a>               L2VPN Service Model (L2SM)           October 2018</span>

  feature qinq {
    description
      &quot;Enables the support of QinQ.&quot;;
  }

  feature qinany {
    description
      &quot;Enables the support of QinAny.&quot;;
  }

  feature vxlan {
    description
      &quot;Enables the support of VXLANs.&quot;;
  }

  feature lan-tag {
    description
      &quot;Enables LAN tag support in a VPN.&quot;;
  }

  feature target-sites {
    description
      &quot;Enables the support of the &#x27;target-sites&#x27;
       match-flow parameter.&quot;;
  }

  feature bum {
    description
      &quot;Enables BUM capabilities in a VPN.&quot;;
  }

  feature mac-loop-prevention {
    description
      &quot;Enables the MAC loop-prevention capability in a VPN.&quot;;
  }

  feature lacp {
    description
      &quot;Enables the Link Aggregation Control Protocol (LACP)
       capability in a VPN.&quot;;
  }

  feature mac-addr-limit {
    description
      &quot;Enables the MAC address limit capability in a VPN.&quot;;
  }

  feature acl {
<span class="grey"><a href="/doc/html/rfc8466">RFC 8466</a>               L2VPN Service Model (L2SM)           October 2018</span>

    description
      &quot;Enables the ACL capability in a VPN.&quot;;
  }

  feature cfm {
    description
      &quot;Enables the 802.1ag CFM capability in a VPN.&quot;;
  }

  feature y-1731 {
    description
      &quot;Enables the Y.1731 capability in a VPN.&quot;;
  }

  typedef svc-id {
    type string;
    description
      &quot;Defines the type of service component identifier.&quot;;
  }

  typedef ccm-priority-type {
    type uint8 {
      range &quot;0..7&quot;;
    }
    description
      &quot;A 3-bit priority value to be used in the VLAN tag,
       if present in the transmitted frame.&quot;;
  }

  typedef control-mode {
    type enumeration {
      enum peer {
        description
          &quot;&#x27;peer&#x27; mode, i.e., participate in the protocol towards
           the CE.  Peering is common for LACP and the Ethernet
           Local Management Interface (E-LMI) and, occasionally,
           for LLDP.  For VPLSs and VPWSs, the subscriber can also
           request that the SP peer enable spanning tree.&quot;;
      }
      enum tunnel {
        description
          &quot;&#x27;tunnel&#x27; mode, i.e., pass to the egress or destination
           site.  For EPLs, the expectation is that L2CP frames are
           tunneled.&quot;;
      }
      enum discard {
        description
          &quot;&#x27;discard&#x27; mode, i.e., discard the frame.&quot;;
<span class="grey"><a href="/doc/html/rfc8466">RFC 8466</a>               L2VPN Service Model (L2SM)           October 2018</span>

      }
    }
    description
      &quot;Defines the type of control mode on L2CP protocols.&quot;;
  }

  typedef neg-mode {
    type enumeration {
      enum full-duplex {
        description
          &quot;Defines full-duplex mode.&quot;;
      }
      enum auto-neg {
        description
          &quot;Defines auto-negotiation mode.&quot;;
      }
    }
    description
      &quot;Defines the type of negotiation mode.&quot;;
  }

  identity site-network-access-type {
    description
      &quot;Base identity for the site-network-access type.&quot;;
  }

  identity point-to-point {
    base site-network-access-type;
    description
      &quot;Identity for a point-to-point connection.&quot;;
  }

  identity multipoint {
    base site-network-access-type;
    description
      &quot;Identity for a multipoint connection, e.g.,
       an Ethernet broadcast segment.&quot;;
  }

  identity tag-type {
    description
      &quot;Base identity from which all tag types are derived.&quot;;
  }

  identity c-vlan {
    base tag-type;
    description
      &quot;A CVLAN tag, normally using the 0x8100 Ethertype.&quot;;
<span class="grey"><a href="/doc/html/rfc8466">RFC 8466</a>               L2VPN Service Model (L2SM)           October 2018</span>

  }

  identity s-vlan {
    base tag-type;
    description
      &quot;An SVLAN tag.&quot;;
  }

  identity c-s-vlan {
    base tag-type;
    description
      &quot;Using both a CVLAN tag and an SVLAN tag.&quot;;
  }

  identity multicast-tree-type {
    description
      &quot;Base identity for the multicast tree type.&quot;;
  }

  identity ssm-tree-type {
    base multicast-tree-type;
    description
      &quot;Identity for the Source-Specific Multicast (SSM) tree type.&quot;;
    reference &quot;<a href="/doc/html/rfc8299">RFC 8299</a>: YANG Data Model for L3VPN Service Delivery&quot;;
  }

  identity asm-tree-type {
    base multicast-tree-type;
    description
      &quot;Identity for the Any-Source Multicast (ASM) tree type.&quot;;
    reference &quot;<a href="/doc/html/rfc8299">RFC 8299</a>: YANG Data Model for L3VPN Service Delivery&quot;;
  }

  identity bidir-tree-type {
    base multicast-tree-type;
    description
      &quot;Identity for the bidirectional tree type.&quot;;
    reference &quot;<a href="/doc/html/rfc8299">RFC 8299</a>: YANG Data Model for L3VPN Service Delivery&quot;;
  }

  identity multicast-gp-address-mapping {
    description
      &quot;Identity for mapping type.&quot;;
  }

  identity static-mapping {
    base multicast-gp-address-mapping;
    description
<span class="grey"><a href="/doc/html/rfc8466">RFC 8466</a>               L2VPN Service Model (L2SM)           October 2018</span>

      &quot;Identity for static mapping, i.e., attach the interface
       to the multicast group as a static member.&quot;;
  }

  identity dynamic-mapping {
    base multicast-gp-address-mapping;
    description
      &quot;Identity for dynamic mapping, i.e., an interface was added
       to the multicast group as a result of snooping.&quot;;
  }

  identity tf-type {
    description
      &quot;Identity for the traffic type.&quot;;
  }

  identity multicast-traffic {
    base tf-type;
    description
      &quot;Identity for multicast traffic.&quot;;
  }

  identity broadcast-traffic {
    base tf-type;
    description
      &quot;Identity for broadcast traffic.&quot;;
  }

  identity unknown-unicast-traffic {
    base tf-type;
    description
      &quot;Identity for unknown unicast traffic.&quot;;
  }

  identity encapsulation-type {
    description
      &quot;Identity for the encapsulation type.&quot;;
  }

  identity ethernet {
    base encapsulation-type;
    description
      &quot;Identity for Ethernet type.&quot;;
  }

  identity vlan {
    base encapsulation-type;
    description
<span class="grey"><a href="/doc/html/rfc8466">RFC 8466</a>               L2VPN Service Model (L2SM)           October 2018</span>

      &quot;Identity for the VLAN type.&quot;;
  }

  identity carrierscarrier-type {
    description
      &quot;Identity of the CsC type.&quot;;
  }

  identity ldp {
    base carrierscarrier-type;
    description
      &quot;Use LDP as the signaling protocol
       between the PE and the CE.&quot;;
  }

  identity bgp {
    base carrierscarrier-type;
    description
      &quot;Use BGP (as per <a href="/doc/html/rfc8277">RFC 8277</a>) as the signaling protocol
       between the PE and the CE.
       In this case, BGP must also be configured as
       the routing protocol.&quot;;
  }

  identity eth-inf-type {
    description
      &quot;Identity of the Ethernet interface type.&quot;;
  }

  identity tagged {
    base eth-inf-type;
    description
      &quot;Identity of the tagged interface type.&quot;;
  }

  identity untagged {
    base eth-inf-type;
    description
      &quot;Identity of the untagged interface type.&quot;;
  }

  identity lag {
    base eth-inf-type;
    description
      &quot;Identity of the LAG interface type.&quot;;
  }

  identity bw-type {
<span class="grey"><a href="/doc/html/rfc8466">RFC 8466</a>               L2VPN Service Model (L2SM)           October 2018</span>

    description
      &quot;Identity of the bandwidth type.&quot;;
  }

  identity bw-per-cos {
    base bw-type;
    description
      &quot;Bandwidth is per CoS.&quot;;
  }

  identity bw-per-port {
    base bw-type;
    description
      &quot;Bandwidth is per site network access.&quot;;
  }

  identity bw-per-site {
    base bw-type;
    description
      &quot;Bandwidth is per site.  It is applicable to
       all the site network accesses within the site.&quot;;
  }

  identity bw-per-svc {
    base bw-type;
    description
      &quot;Bandwidth is per VPN service.&quot;;
  }

  identity site-vpn-flavor {
    description
      &quot;Base identity for the site VPN service flavor.&quot;;
  }

  identity site-vpn-flavor-single {
    base site-vpn-flavor;
    description
      &quot;Identity for the site VPN service flavor.
       Used when the site belongs to only one VPN.&quot;;
  }

  identity site-vpn-flavor-multi {
    base site-vpn-flavor;
    description
      &quot;Identity for the site VPN service flavor.
       Used when a logical connection of a site
       belongs to multiple VPNs.&quot;;
  }
<span class="grey"><a href="/doc/html/rfc8466">RFC 8466</a>               L2VPN Service Model (L2SM)           October 2018</span>

  identity site-vpn-flavor-nni {
    base site-vpn-flavor;
    description
      &quot;Identity for the site VPN service flavor.
       Used to describe an NNI option A connection.&quot;;
  }

  identity service-type {
    description
      &quot;Base identity of the service type.&quot;;
  }

  identity vpws {
    base service-type;
    description
      &quot;Point-to-point Virtual Private Wire Service (VPWS)
       service type.&quot;;
  }

  identity pwe3 {
    base service-type;
    description
      &quot;Pseudowire Emulation Edge to Edge (PWE3) service type.&quot;;
  }

  identity ldp-l2tp-vpls {
    base service-type;
    description
      &quot;LDP-based or L2TP-based multipoint Virtual Private LAN
       Service (VPLS) service type.  This VPLS uses LDP-signaled
       Pseudowires or L2TP-signaled Pseudowires.&quot;;
  }

  identity bgp-vpls {
    base service-type;
    description
      &quot;BGP-based multipoint VPLS service type.  This VPLS uses a
       BGP control plane as described in RFCs 4761 and 6624.&quot;;
  }

  identity vpws-evpn {
    base service-type;
    description
      &quot;VPWS service type using Ethernet VPNs (EVPNs)
       as specified in <a href="/doc/html/rfc7432">RFC 7432</a>.&quot;;
  }

  identity pbb-evpn {
<span class="grey"><a href="/doc/html/rfc8466">RFC 8466</a>               L2VPN Service Model (L2SM)           October 2018</span>

    base service-type;
    description
      &quot;Provider Backbone Bridge (PBB) service type using
       EVPNs as specified in <a href="/doc/html/rfc7432">RFC 7432</a>.&quot;;
  }

  identity bundling-type {
    description
      &quot;The base identity for the bundling type.  It supports
       multiple CE-VLANs associated with an L2VPN service or
       all CE-VLANs associated with an L2VPN service.&quot;;
  }

  identity multi-svc-bundling {
    base bundling-type;
    description
      &quot;Identity for multi-service bundling, i.e.,
       multiple CE-VLAN IDs can be associated with an
       L2VPN service at a site.&quot;;
  }

  identity one2one-bundling {
    base bundling-type;
    description
      &quot;Identity for one-to-one service bundling, i.e.,
       each L2VPN can be associated with only one CE-VLAN ID
       at a site.&quot;;
  }

  identity all2one-bundling {
    base bundling-type;
    description
      &quot;Identity for all-to-one bundling, i.e., all CE-VLAN IDs
       are mapped to one L2VPN service.&quot;;
  }

  identity color-id {
    description
      &quot;Base identity of the color ID.&quot;;
  }

  identity color-id-cvlan {
    base color-id;
    description
      &quot;Identity of the color ID based on a CVLAN.&quot;;
  }

  identity cos-id {
<span class="grey"><a href="/doc/html/rfc8466">RFC 8466</a>               L2VPN Service Model (L2SM)           October 2018</span>

    description
      &quot;Identity of the CoS ID.&quot;;
  }

  identity cos-id-pcp {
    base cos-id;
    description
      &quot;Identity of the CoS ID based on the
       Port Control Protocol (PCP).&quot;;
  }

  identity cos-id-dscp {
    base cos-id;
    description
      &quot;Identity of the CoS ID based on DSCP.&quot;;
  }

  identity color-type {
    description
      &quot;Identity of color types.&quot;;
  }

  identity green {
    base color-type;
    description
      &quot;Identity of the &#x27;green&#x27; color type.&quot;;
  }

  identity yellow {
    base color-type;
    description
      &quot;Identity of the &#x27;yellow&#x27; color type.&quot;;
  }

  identity red {
    base color-type;
    description
      &quot;Identity of the &#x27;red&#x27; color type.&quot;;
  }

  identity policing {
    description
      &quot;Identity of the type of policing applied.&quot;;
  }

  identity one-rate-two-color {
    base policing;
    description
<span class="grey"><a href="/doc/html/rfc8466">RFC 8466</a>               L2VPN Service Model (L2SM)           October 2018</span>

      &quot;Identity of one-rate, two-color (1R2C).&quot;;
  }

  identity two-rate-three-color {
    base policing;
    description
      &quot;Identity of two-rate, three-color (2R3C).&quot;;
  }

  identity bum-type {
    description
      &quot;Identity of the BUM type.&quot;;
  }

  identity broadcast {
    base bum-type;
    description
      &quot;Identity of broadcast.&quot;;
  }

  identity unicast {
    base bum-type;
    description
      &quot;Identity of unicast.&quot;;
  }

  identity multicast {
    base bum-type;
    description
      &quot;Identity of multicast.&quot;;
  }

  identity loop-prevention-type {
    description
      &quot;Identity of loop prevention.&quot;;
  }

  identity shut {
    base loop-prevention-type;
    description
      &quot;Identity of shut protection.&quot;;
  }

  identity trap {
    base loop-prevention-type;
    description
      &quot;Identity of trap protection.&quot;;
  }
<span class="grey"><a href="/doc/html/rfc8466">RFC 8466</a>               L2VPN Service Model (L2SM)           October 2018</span>

  identity lacp-state {
    description
      &quot;Identity of the LACP state.&quot;;
  }

  identity lacp-on {
    base lacp-state;
    description
      &quot;Identity of LACP on.&quot;;
  }

  identity lacp-off {
    base lacp-state;
    description
      &quot;Identity of LACP off.&quot;;
  }

  identity lacp-mode {
    description
      &quot;Identity of the LACP mode.&quot;;
  }

  identity lacp-passive {
    base lacp-mode;
    description
      &quot;Identity of LACP passive.&quot;;
  }

  identity lacp-active {
    base lacp-mode;
    description
      &quot;Identity of LACP active.&quot;;
  }

  identity lacp-speed {
    description
      &quot;Identity of the LACP speed.&quot;;
  }

  identity lacp-fast {
    base lacp-speed;
    description
      &quot;Identity of LACP fast.&quot;;
  }

  identity lacp-slow {
    base lacp-speed;
    description
<span class="grey"><a href="/doc/html/rfc8466">RFC 8466</a>               L2VPN Service Model (L2SM)           October 2018</span>

      &quot;Identity of LACP slow.&quot;;
  }

  identity bw-direction {
    description
      &quot;Identity for the bandwidth direction.&quot;;
  }

  identity input-bw {
    base bw-direction;
    description
      &quot;Identity for the input bandwidth.&quot;;
  }

  identity output-bw {
    base bw-direction;
    description
      &quot;Identity for the output bandwidth.&quot;;
  }

  identity management {
    description
      &quot;Base identity for the site management scheme.&quot;;
  }

  identity co-managed {
    base management;
    description
      &quot;Identity for a co-managed site.&quot;;
  }

  identity customer-managed {
    base management;
    description
      &quot;Identity for a customer-managed site.&quot;;
  }

  identity provider-managed {
    base management;
    description
      &quot;Identity for a provider-managed site.&quot;;
  }

  identity address-family {
    description
      &quot;Identity for an address family.&quot;;
  }

<span class="grey"><a href="/doc/html/rfc8466">RFC 8466</a>               L2VPN Service Model (L2SM)           October 2018</span>

  identity ipv4 {
    base address-family;
    description
      &quot;Identity for an IPv4 address family.&quot;;
  }

  identity ipv6 {
    base address-family;
    description
      &quot;Identity for an IPv6 address family.&quot;;
  }

  identity vpn-topology {
    description
      &quot;Base identity for the VPN topology.&quot;;
  }

  identity any-to-any {
    base vpn-topology;
    description
      &quot;Identity for the any-to-any VPN topology.&quot;;
  }

  identity hub-spoke {
    base vpn-topology;
    description
      &quot;Identity for the Hub-and-Spoke VPN topology.&quot;;
  }

  identity hub-spoke-disjoint {
    base vpn-topology;
    description
      &quot;Identity for the Hub-and-Spoke VPN topology,
       where Hubs cannot communicate with each other.&quot;;
  }

  identity site-role {
    description
      &quot;Base identity for a site type.&quot;;
  }

  identity any-to-any-role {
    base site-role;
    description
      &quot;Site in an any-to-any L2VPN.&quot;;
  }

  identity spoke-role {
<span class="grey"><a href="/doc/html/rfc8466">RFC 8466</a>               L2VPN Service Model (L2SM)           October 2018</span>

    base site-role;
    description
      &quot;Spoke site in a Hub-and-Spoke L2VPN.&quot;;
  }

  identity hub-role {
    base site-role;
    description
      &quot;Hub site in a Hub-and-Spoke L2VPN.&quot;;
  }

  identity pm-type {
    description
      &quot;Performance-monitoring type.&quot;;
  }

  identity loss {
    base pm-type;
    description
      &quot;Loss measurement.&quot;;
  }

  identity delay {
    base pm-type;
    description
      &quot;Delay measurement.&quot;;
  }

  identity fault-alarm-defect-type {
    description
      &quot;Indicates the alarm-priority defect (i.e., the
       lowest-priority defect that is allowed to
       generate a fault alarm).&quot;;
  }

  identity remote-rdi {
    base fault-alarm-defect-type;
    description
      &quot;Indicates the aggregate health
       of the Remote MEPs.&quot;;
  }

  identity remote-mac-error {
    base fault-alarm-defect-type;
    description
      &quot;Indicates that one or more of the Remote MEPs are
       reporting a failure in their Port Status TLVs or
       Interface Status TLVs.&quot;;
<span class="grey"><a href="/doc/html/rfc8466">RFC 8466</a>               L2VPN Service Model (L2SM)           October 2018</span>

  }

  identity remote-invalid-ccm {
    base fault-alarm-defect-type;
    description
      &quot;Indicates that at least one of the Remote MEP
       state machines is not receiving valid
       Continuity Check Messages (CCMs) from its Remote MEP.&quot;;
  }

  identity invalid-ccm {
    base fault-alarm-defect-type;
    description
      &quot;Indicates that one or more invalid CCMs have been
       received and that a period of time 3.5 times the length
       of those CCMs&#x27; transmission intervals has not yet expired.&quot;;
  }

  identity cross-connect-ccm {
    base fault-alarm-defect-type;
    description
      &quot;Indicates that one or more cross-connect CCMs have been
       received and that 3.5 times the period of at least one of
       those CCMs&#x27; transmission intervals has not yet expired.&quot;;
  }

  identity frame-delivery-mode {
    description
      &quot;Delivery types.&quot;;
  }

  identity discard {
    base frame-delivery-mode;
    description
      &quot;Service frames are discarded.&quot;;
  }

  identity unconditional {
    base frame-delivery-mode;
    description
      &quot;Service frames are unconditionally delivered to the
       destination site.&quot;;
  }

  identity unknown-discard {
    base frame-delivery-mode;
    description
      &quot;Service frames are conditionally delivered to the
<span class="grey"><a href="/doc/html/rfc8466">RFC 8466</a>               L2VPN Service Model (L2SM)           October 2018</span>

       destination site.  Packets with unknown destination addresses
       will be discarded.&quot;;
  }

  identity placement-diversity {
    description
      &quot;Base identity for site placement constraints.&quot;;
  }

  identity bearer-diverse {
    base placement-diversity;
    description
      &quot;Identity for bearer diversity.
       The bearers should not use common elements.&quot;;
  }

  identity pe-diverse {
    base placement-diversity;
    description
      &quot;Identity for PE diversity.&quot;;
  }

  identity pop-diverse {
    base placement-diversity;
    description
      &quot;Identity for POP diversity.&quot;;
  }

  identity linecard-diverse {
    base placement-diversity;
    description
      &quot;Identity for linecard diversity.&quot;;
  }

  identity same-pe {
    base placement-diversity;
    description
      &quot;Identity for having sites connected on the same PE.&quot;;
  }

  identity same-bearer {
    base placement-diversity;
    description
      &quot;Identity for having sites connected using the same bearer.&quot;;
  }

  identity tagged-inf-type {
    description
<span class="grey"><a href="/doc/html/rfc8466">RFC 8466</a>               L2VPN Service Model (L2SM)           October 2018</span>

      &quot;Identity for the tagged interface type.&quot;;
  }

  identity priority-tagged {
    base tagged-inf-type;
    description
      &quot;Identity for the priority-tagged interface.&quot;;
  }

  identity qinq {
    base tagged-inf-type;
    description
      &quot;Identity for the QinQ tagged interface.&quot;;
  }

  identity dot1q {
    base tagged-inf-type;
    description
      &quot;Identity for the dot1Q VLAN tagged interface.&quot;;
  }

  identity qinany {
    base tagged-inf-type;
    description
      &quot;Identity for the QinAny tagged interface.&quot;;
  }

  identity vxlan {
    base tagged-inf-type;
    description
      &quot;Identity for the VXLAN tagged interface.&quot;;
  }

  identity provision-model {
    description
      &quot;Base identity for the provision model.&quot;;
  }

  identity single-side-provision {
    description
      &quot;Identity for single-sided provisioning with discovery.&quot;;
  }

  identity doubled-side-provision {
    description
      &quot;Identity for double-sided provisioning.&quot;;
  }

<span class="grey"><a href="/doc/html/rfc8466">RFC 8466</a>               L2VPN Service Model (L2SM)           October 2018</span>

  identity mac-learning-mode {
    description
      &quot;MAC learning mode.&quot;;
  }

  identity data-plane {
    base mac-learning-mode;
    description
      &quot;User MAC addresses are learned through ARP broadcast.&quot;;
  }

  identity control-plane {
    base mac-learning-mode;
    description
      &quot;User MAC addresses are advertised through EVPN-BGP.&quot;;
  }

  identity vpn-policy-filter-type {
    description
      &quot;Base identity for the filter type.&quot;;
  }

  identity lan {
    base vpn-policy-filter-type;
    description
      &quot;Identity for a LAN tag filter type.&quot;;
  }

  identity mac-action {
    description
      &quot;Base identity for a MAC action.&quot;;
  }

  identity drop {
    base mac-action;
    description
      &quot;Identity for dropping a packet.&quot;;
  }

  identity flood {
    base mac-action;
    description
      &quot;Identity for packet flooding.&quot;;
  }

  identity warning {
    base mac-action;
    description
<span class="grey"><a href="/doc/html/rfc8466">RFC 8466</a>               L2VPN Service Model (L2SM)           October 2018</span>

      &quot;Identity for sending a warning log message.&quot;;
  }

  identity qos-profile-direction {
    description
      &quot;Base identity for the QoS-profile direction.&quot;;
   }

  identity site-to-wan {
    base qos-profile-direction;
    description
      &quot;Identity for the site-to-WAN direction.&quot;;
  }

  identity wan-to-site {
    base qos-profile-direction;
    description
      &quot;Identity for the WAN-to-site direction.&quot;;
  }

  identity bidirectional {
    base qos-profile-direction;
    description
      &quot;Identity for both the WAN-to-site direction
       and the site-to-WAN direction.&quot;;
  }

  identity vxlan-peer-mode {
    description
      &quot;Base identity for the VXLAN peer mode.&quot;;
  }

  identity static-mode {
    base vxlan-peer-mode;
    description
      &quot;Identity for VXLAN access in the static mode.&quot;;
  }

  identity bgp-mode {
    base vxlan-peer-mode;
    description
      &quot;Identity for VXLAN access by BGP EVPN learning.&quot;;
  }

  identity customer-application {
    description
      &quot;Base identity for a customer application.&quot;;
  }
<span class="grey"><a href="/doc/html/rfc8466">RFC 8466</a>               L2VPN Service Model (L2SM)           October 2018</span>

  identity web {
    base customer-application;
    description
      &quot;Identity for a web application (e.g., HTTP, HTTPS).&quot;;
  }

  identity mail {
    base customer-application;
    description
      &quot;Identity for a mail application.&quot;;
  }

  identity file-transfer {
    base customer-application;
    description
      &quot;Identity for a file-transfer application
       (e.g., FTP, SFTP).&quot;;
  }

  identity database {
    base customer-application;
    description
      &quot;Identity for a database application.&quot;;
  }

  identity social {
    base customer-application;
    description
      &quot;Identity for a social-network application.&quot;;
  }

  identity games {
    base customer-application;
    description
      &quot;Identity for a gaming application.&quot;;
  }

  identity p2p {
    base customer-application;
    description
      &quot;Identity for a peer-to-peer application.&quot;;
  }

  identity network-management {
    base customer-application;
    description
      &quot;Identity for a management application
       (e.g., Telnet, syslog, SNMP).&quot;;
<span class="grey"><a href="/doc/html/rfc8466">RFC 8466</a>               L2VPN Service Model (L2SM)           October 2018</span>

  }

  identity voice {
    base customer-application;
    description
      &quot;Identity for a voice application.&quot;;
  }

  identity video {
    base customer-application;
    description
      &quot;Identity for a videoconference application.&quot;;
  }

  identity embb {
    base customer-application;
    description
      &quot;Identity for the enhanced Mobile Broadband (eMBB)
       application.  Note that the eMBB application
       requires strict threshold values for a wide variety
       of network performance parameters (e.g., data rate,
       latency, loss rate, reliability).&quot;;
  }

  identity urllc {
    base customer-application;
    description
      &quot;Identity for the Ultra-Reliable and Low Latency
       Communications (URLLC) application.  Note that the
       URLLC application requires strict threshold values for
       a wide variety of network performance parameters
       (e.g., latency, reliability).&quot;;
  }

  identity mmtc {
    base customer-application;
    description
      &quot;Identity for the massive Machine Type
       Communications (mMTC) application.  Note that the
       mMTC application requires strict threshold values for
       a wide variety of network performance parameters
       (e.g., data rate, latency, loss rate, reliability).&quot;;
  }

  grouping site-acl {
    container access-control-list {
      if-feature &quot;acl&quot;;
      list mac {
<span class="grey"><a href="/doc/html/rfc8466">RFC 8466</a>               L2VPN Service Model (L2SM)           October 2018</span>

        key &quot;mac-address&quot;;
        leaf mac-address {
          type yang:mac-address;
          description
            &quot;MAC addresses.&quot;;
        }
        description
          &quot;List of MAC addresses.&quot;;
      }
      description
        &quot;Container for the ACL.&quot;;
    }
    description
      &quot;Grouping that defines the ACL.&quot;;
  }

  grouping site-bum {
    container broadcast-unknown-unicast-multicast {
      if-feature &quot;bum&quot;;
      leaf multicast-site-type {
        type enumeration {
          enum receiver-only {
            description
              &quot;The site only has receivers.&quot;;
          }
          enum source-only {
            description
              &quot;The site only has sources.&quot;;
          }
          enum source-receiver {
            description
              &quot;The site has both sources and receivers.&quot;;
          }
        }
        default &quot;source-receiver&quot;;
        description
          &quot;Type of multicast site.&quot;;
      }
      list multicast-gp-address-mapping {
        key &quot;id&quot;;
        leaf id {
          type uint16;
          description
            &quot;Unique identifier for the mapping.&quot;;
        }
        leaf vlan-id {
          type uint16 {
            range &quot;0..1024&quot;;
<span class="grey"><a href="/doc/html/rfc8466">RFC 8466</a>               L2VPN Service Model (L2SM)           October 2018</span>

          }
          mandatory true;
          description
            &quot;The VLAN ID of the multicast group.
             The range of the 12-bit VLAN ID is 0 to 1024.&quot;;
        }
        leaf mac-gp-address {
          type yang:mac-address;
          mandatory true;
          description
            &quot;The MAC address of the multicast group.&quot;;
        }
        leaf port-lag-number {
          type uint32;
          description
            &quot;The ports/LAGs belonging to the multicast group.&quot;;
        }
        description
          &quot;List of port-to-group mappings.&quot;;
      }
      leaf bum-overall-rate {
        type uint64;
        units &quot;bps&quot;;
        description
          &quot;Overall rate for BUM.&quot;;
      }
      list bum-rate-per-type {
        key &quot;type&quot;;
        leaf type {
          type identityref {
            base bum-type;
          }
          description
            &quot;BUM type.&quot;;
        }
        leaf rate {
          type uint64;
          units &quot;bps&quot;;
          description
            &quot;Rate for BUM.&quot;;
        }
        description
          &quot;List of limit rates for the BUM type.&quot;;
      }
      description
        &quot;Container of BUM configurations.&quot;;
    }
    description
<span class="grey"><a href="/doc/html/rfc8466">RFC 8466</a>               L2VPN Service Model (L2SM)           October 2018</span>

      &quot;Grouping for BUM.&quot;;
  }

  grouping site-mac-loop-prevention {
    container mac-loop-prevention {
      if-feature &quot;mac-loop-prevention&quot;;
      leaf protection-type {
        type identityref {
          base loop-prevention-type;
        }
        default &quot;trap&quot;;
        description
          &quot;Protection type.  By default, the protection
           type is &#x27;trap&#x27;.&quot;;
      }
      leaf frequency {
        type uint32;
        default &quot;5&quot;;
        description
          &quot;The number of times to detect MAC duplication, where
           a &#x27;duplicate MAC address&#x27; situation has occurred and
           the duplicate MAC address has been added to a list of
           duplicate MAC addresses.  By default, the number of
           times is 5.&quot;;
      }
      leaf retry-timer {
        type uint32;
        units &quot;seconds&quot;;
        description
          &quot;The retry timer.  When the retry timer expires,
           the duplicate MAC address will be flushed from
           the MAC-VRF.&quot;;
      }
      description
        &quot;Container of MAC loop-prevention parameters.&quot;;
    }
    description
      &quot;Grouping for MAC loop prevention.&quot;;
  }

  grouping site-service-qos-profile {
    container qos {
      if-feature &quot;qos&quot;;
      container qos-classification-policy {
        list rule {
          key &quot;id&quot;;
          ordered-by user;
          leaf id {
<span class="grey"><a href="/doc/html/rfc8466">RFC 8466</a>               L2VPN Service Model (L2SM)           October 2018</span>

            type string;
            description
              &quot;A description identifying the QoS classification
               policy rule.&quot;;
          }
          choice match-type {
            default &quot;match-flow&quot;;
            case match-flow {
              container match-flow {
                leaf dscp {
                  type inet:dscp;
                  description
                    &quot;DSCP value.&quot;;
                }
                leaf dot1q {
                  type uint16;
                  description
                    &quot;802.1Q matching.  It is a VLAN tag added into
                     a frame.&quot;;
                }
                leaf pcp {
                  type uint8 {
                    range &quot;0..7&quot;;
                  }
                  description
                    &quot;PCP value.&quot;;
                }
                leaf src-mac {
                  type yang:mac-address;
                  description
                    &quot;Source MAC.&quot;;
                }
                leaf dst-mac {
                  type yang:mac-address;
                  description
                    &quot;Destination MAC.&quot;;
                }
                leaf color-type {
                  type identityref {
                    base color-type;
                  }
                  description
                    &quot;Color types.&quot;;
                }
                leaf-list target-sites {
                  if-feature &quot;target-sites&quot;;
                  type svc-id;
                  description
<span class="grey"><a href="/doc/html/rfc8466">RFC 8466</a>               L2VPN Service Model (L2SM)           October 2018</span>

                    &quot;Identifies a site as a traffic destination.&quot;;
                }
                leaf any {
                  type empty;
                  description
                    &quot;Allow all.&quot;;
                }
                leaf vpn-id {
                  type svc-id;
                  description
                    &quot;Reference to the target VPN.&quot;;
                }
                description
                  &quot;Describes flow-matching criteria.&quot;;
              }
            }
            case match-application {
              leaf match-application {
                type identityref {
                  base customer-application;
                }
                description
                  &quot;Defines the application to match.&quot;;
              }
            }
            description
              &quot;Choice for classification.&quot;;
          }
          leaf target-class-id {
            type string;
            description
              &quot;Identification of the CoS.
               This identifier is internal to the
               administration.&quot;;
          }
          description
            &quot;List of marking rules.&quot;;
        }
        description
          &quot;Configuration of the traffic classification policy.&quot;;
      }
      container qos-profile {
        choice qos-profile {
          description
            &quot;Choice for the QoS profile.
             Can be a standard profile or a customized profile.&quot;;
          case standard {
            description
<span class="grey"><a href="/doc/html/rfc8466">RFC 8466</a>               L2VPN Service Model (L2SM)           October 2018</span>

              &quot;Standard QoS profile.&quot;;
            leaf profile {
              type leafref {
                path &quot;/l2vpn-svc/vpn-profiles/&quot;
                   + &quot;valid-provider-identifiers/&quot;
                   + &quot;qos-profile-identifier&quot;;
              }
              description
                &quot;QoS profile to be used.&quot;;
            }
          }
          case custom {
            description
              &quot;Customized QoS profile.&quot;;
            container classes {
              if-feature &quot;qos-custom&quot;;
              list class {
                key &quot;class-id&quot;;
                leaf class-id {
                  type string;
                  description
                    &quot;Identification of the CoS.  This identifier is
                     internal to the administration.&quot;;
                }
                leaf direction {
                  type identityref {
                    base qos-profile-direction;
                  }
                  default &quot;bidirectional&quot;;
                  description
                    &quot;The direction in which the QoS profile is
                     applied.  By default, the direction is
                     bidirectional.&quot;;
                }
                leaf policing {
                  type identityref {
                    base policing;
                  }
                  default &quot;one-rate-two-color&quot;;
                  description
                    &quot;The policing type can be either one-rate,
                     two-color (1R2C) or two-rate, three-color
                     (2R3C).  By default, the policing type is
                     &#x27;one-rate-two-color&#x27;.&quot;;
                }
                leaf byte-offset {
                  type uint16;
                  description
<span class="grey"><a href="/doc/html/rfc8466">RFC 8466</a>               L2VPN Service Model (L2SM)           October 2018</span>

                    &quot;Number of bytes in the service frame header
                     that are excluded from the QoS calculation
                     (e.g., extra VLAN tags).&quot;;
                }
                container frame-delay {
                  choice flavor {
                    case lowest {
                      leaf use-lowest-latency {
                        type empty;
                        description
                          &quot;The traffic class should use the path
                           with the lowest delay.&quot;;
                      }
                    }
                    case boundary {
                      leaf delay-bound {
                        type uint16;
                        units &quot;milliseconds&quot;;
                        description
                          &quot;The traffic class should use a path
                           with a defined maximum delay.&quot;;
                      }
                    }
                    description
                      &quot;Delay constraint on the traffic class.&quot;;
                  }
                  description
                    &quot;Delay constraint on the traffic class.&quot;;
                }
                container frame-jitter {
                  choice flavor {
                    case lowest {
                      leaf use-lowest-jitter {
                        type empty;
                        description
                          &quot;The traffic class should use the path
                           with the lowest jitter.&quot;;
                      }
                    }
                    case boundary {
                      leaf delay-bound {
                        type uint32;
                        units &quot;microseconds&quot;;
                        description
                          &quot;The traffic class should use a path
                           with a defined maximum jitter.&quot;;
                      }
                    }
<span class="grey"><a href="/doc/html/rfc8466">RFC 8466</a>               L2VPN Service Model (L2SM)           October 2018</span>

                    description
                      &quot;Jitter constraint on the traffic class.&quot;;
                  }
                  description
                    &quot;Jitter constraint on the traffic class.&quot;;
                }
                container frame-loss {
                  leaf rate {
                    type decimal64 {
                      fraction-digits 2;
                      range &quot;0..100&quot;;
                    }
                    units &quot;percent&quot;;
                    description
                      &quot;Frame loss rate constraint on the traffic
                       class.&quot;;
                  }
                  description
                    &quot;Container for frame loss rate.&quot;;
                }
                container bandwidth {
                  leaf guaranteed-bw-percent {
                    type decimal64 {
                      fraction-digits 5;
                      range &quot;0..100&quot;;
                    }
                    units &quot;percent&quot;;
                    mandatory true;
                    description
                      &quot;Used to define the guaranteed bandwidth
                       as a percentage of the available service
                       bandwidth.&quot;;
                  }
                  leaf end-to-end {
                    type empty;
                    description
                      &quot;Used if the bandwidth reservation
                       must be done on the MPLS network too.&quot;;
                  }
                  description
                    &quot;Bandwidth constraint on the traffic class.&quot;;
                }
                description
                  &quot;List of CoS entries.&quot;;
              }
              description
                &quot;Container for list of CoS entries.&quot;;
            }
<span class="grey"><a href="/doc/html/rfc8466">RFC 8466</a>               L2VPN Service Model (L2SM)           October 2018</span>

          }
        }
        description
          &quot;Qos profile configuration.&quot;;
      }
      description
        &quot;QoS configuration.&quot;;
    }
    description
      &quot;Grouping that defines QoS parameters for a site.&quot;;
  }

  grouping site-service-mpls {
    container carrierscarrier {
      if-feature &quot;carrierscarrier&quot;;
      leaf signaling-type {
        type identityref {
          base carrierscarrier-type;
        }
        default &quot;bgp&quot;;
        description
          &quot;CsC.  By default, the signaling type is &#x27;bgp&#x27;.&quot;;
      }
      description
        &quot;Container for CsC.&quot;;
    }
    description
      &quot;Grouping for CsC.&quot;;
  }

  container l2vpn-svc {
    container vpn-profiles {
      container valid-provider-identifiers {
        leaf-list cloud-identifier {
          if-feature &quot;cloud-access&quot;;
          type string;
          description
            &quot;Identification of the public cloud service or
             Internet service.  Local to each administration.&quot;;
        }
        leaf-list qos-profile-identifier {
          type string;
          description
            &quot;Identification of the QoS profile to be used.
             Local to each administration.&quot;;
        }
        leaf-list bfd-profile-identifier {
          type string;
<span class="grey"><a href="/doc/html/rfc8466">RFC 8466</a>               L2VPN Service Model (L2SM)           October 2018</span>

          description
            &quot;Identification of the SP BFD profile to be used.
             Local to each administration.&quot;;
        }
        leaf-list remote-carrier-identifier {
          type string;
          description
            &quot;Identification of the remote carrier name to be used.
             It can be an L2VPN partner, data-center SP, or
             private CSP.  Local to each administration.&quot;;
        }
        nacm:default-deny-write;
        description
          &quot;Container for valid provider identifiers.&quot;;
      }
      description
        &quot;Container for VPN profiles.&quot;;
    }
    container vpn-services {
      list vpn-service {
        key &quot;vpn-id&quot;;
        leaf vpn-id {
          type svc-id;
          description
            &quot;Defines a service identifier.&quot;;
        }
        leaf vpn-svc-type {
          type identityref {
            base service-type;
          }
          default &quot;vpws&quot;;
          description
            &quot;Service type.  By default, the service type is &#x27;vpws&#x27;.&quot;;
        }
        leaf customer-name {
          type string;
          description
            &quot;Customer name.&quot;;
        }
        leaf svc-topo {
          type identityref {
            base vpn-topology;
          }
          default &quot;any-to-any&quot;;
          description
            &quot;Defines the service topology, e.g.,
             &#x27;any-to-any&#x27;, &#x27;hub-spoke&#x27;.&quot;;
        }
<span class="grey"><a href="/doc/html/rfc8466">RFC 8466</a>               L2VPN Service Model (L2SM)           October 2018</span>

        container cloud-accesses {
          if-feature &quot;cloud-access&quot;;
          list cloud-access {
            key &quot;cloud-identifier&quot;;
            leaf cloud-identifier {
              type leafref {
                path &quot;/l2vpn-svc/vpn-profiles/&quot;
                   + &quot;valid-provider-identifiers&quot;
                   + &quot;/cloud-identifier&quot;;
              }
              description
                &quot;Identification of the cloud service.
                 Local to each administration.&quot;;
            }
            choice list-flavor {
              case permit-any {
                leaf permit-any {
                  type empty;
                  description
                    &quot;Allow all sites.&quot;;
                }
              }
              case deny-any-except {
                leaf-list permit-site {
                  type leafref {
                    path &quot;/l2vpn-svc/sites/site/site-id&quot;;
                  }
                  description
                    &quot;Site ID to be authorized.&quot;;
                }
              }
              case permit-any-except {
                leaf-list deny-site {
                  type leafref {
                    path &quot;/l2vpn-svc/sites/site/site-id&quot;;
                  }
                  description
                    &quot;Site ID to be denied.&quot;;
                }
              }
              description
                &quot;Choice for cloud access policy.
                 By default, all sites in the L2VPN
                 MUST be authorized to access the cloud.&quot;;
            }
            description
              &quot;Cloud access configuration.&quot;;
          }
<span class="grey"><a href="/doc/html/rfc8466">RFC 8466</a>               L2VPN Service Model (L2SM)           October 2018</span>

          description
            &quot;Container for cloud access configurations.&quot;;
        }
        container frame-delivery {
          if-feature &quot;bum&quot;;
          container customer-tree-flavors {
            leaf-list tree-flavor {
              type identityref {
                base multicast-tree-type;
              }
              description
                &quot;Type of tree to be used.&quot;;
            }
            description
              &quot;Types of trees used by the customer.&quot;;
          }
          container bum-deliveries {
            list bum-delivery {
              key &quot;frame-type&quot;;
              leaf frame-type {
                type identityref {
                  base tf-type;
                }
                description
                  &quot;Type of frame delivery.  It supports unicast
                   frame delivery, multicast frame delivery,
                   and broadcast frame delivery.&quot;;
              }
              leaf delivery-mode {
                type identityref {
                  base frame-delivery-mode;
                }
                default &quot;unconditional&quot;;
                description
                  &quot;Defines the frame delivery mode
                   (&#x27;unconditional&#x27; (default), &#x27;conditional&#x27;,
                   or &#x27;discard&#x27;).  By default, service frames are
                   unconditionally delivered to the destination site.&quot;;
              }
              description
                &quot;List of frame delivery types and modes.&quot;;
            }
            description
              &quot;Defines the frame delivery types and modes.&quot;;
          }
          leaf multicast-gp-port-mapping {
            type identityref {
              base multicast-gp-address-mapping;
<span class="grey"><a href="/doc/html/rfc8466">RFC 8466</a>               L2VPN Service Model (L2SM)           October 2018</span>

            }
            mandatory true;
            description
              &quot;Describes the way in which each interface is
               associated with the multicast group.&quot;;
          }
          description
            &quot;Multicast global parameters for the VPN service.&quot;;
        }
        container extranet-vpns {
          if-feature &quot;extranet-vpn&quot;;
          list extranet-vpn {
            key &quot;vpn-id&quot;;
            leaf vpn-id {
              type svc-id;
              description
                &quot;Identifies the target VPN that the local VPN wants to
                 access.&quot;;
            }
            leaf local-sites-role {
              type identityref {
                base site-role;
              }
              default &quot;any-to-any-role&quot;;
              description
                &quot;Describes the role of the local sites in the target
                 VPN topology.  In the any-to-any VPN service topology,
                 the local sites must have the same role, which will be
                 &#x27;any-to-any-role&#x27;.  In the Hub-and-Spoke VPN service
                 topology or the Hub-and-Spoke-Disjoint VPN service
                 topology, the local sites must have a Hub role or a
                 Spoke role.&quot;;
            }
            description
              &quot;List of extranet VPNs to which the local VPN
               is attached.&quot;;
          }
          description
            &quot;Container for extranet VPN configurations.&quot;;
        }
        leaf ce-vlan-preservation {
          type boolean;
          mandatory true;
          description
            &quot;Preserves the CE-VLAN ID from ingress to egress, i.e.,
             the CE-VLAN tag of the egress frame is identical to
             that of the ingress frame that yielded this
             egress service frame.  If all-to-one bundling within
<span class="grey"><a href="/doc/html/rfc8466">RFC 8466</a>               L2VPN Service Model (L2SM)           October 2018</span>

             a site is enabled, then preservation applies to all
             ingress service frames.  If all-to-one bundling is
             disabled, then preservation applies to tagged
             ingress service frames having CE-VLAN IDs 1 through 4094.&quot;;
        }
        leaf ce-vlan-cos-preservation {
          type boolean;
          mandatory true;
          description
            &quot;CE VLAN CoS preservation.  The PCP bits in the CE-VLAN tag
             of the egress frame are identical to those of the
             ingress frame that yielded this egress service frame.&quot;;
        }
        leaf carrierscarrier {
          if-feature &quot;carrierscarrier&quot;;
          type boolean;
          default &quot;false&quot;;
          description
            &quot;The VPN is using CsC, and so MPLS is required.&quot;;
        }
        description
          &quot;List of VPN services.&quot;;
      }
      description
        &quot;Container for VPN services.&quot;;
    }
    container sites {
      list site {
        key &quot;site-id&quot;;
        leaf site-id {
          type string;
          description
            &quot;Identifier of the site.&quot;;
        }
        leaf site-vpn-flavor {
          type identityref {
            base site-vpn-flavor;
          }
          default &quot;site-vpn-flavor-single&quot;;
          description
            &quot;Defines the way that the VPN multiplexing is
             done, e.g., whether the site belongs to
             a single VPN site or a multi-VPN site.  By
             default, the site belongs to a single VPN.&quot;;
        }
        container devices {
          when &quot;derived-from-or-self(../management/type, &quot;
             + &quot;&#x27;l2vpn-svc:provider-managed&#x27;) or &quot;
<span class="grey"><a href="/doc/html/rfc8466">RFC 8466</a>               L2VPN Service Model (L2SM)           October 2018</span>

             + &quot;derived-from-or-self(../management/type, &quot;
             + &quot;&#x27;l2vpn-svc:co-managed&#x27;)&quot; {
            description
              &quot;Applicable only for a provider-managed or
               co-managed device.&quot;;
          }
          list device {
            key &quot;device-id&quot;;
            leaf device-id {
              type string;
              description
                &quot;Identifier for the device.&quot;;
            }
            leaf location {
              type leafref {
                path &quot;../../../locations/location/location-id&quot;;
              }
              mandatory true;
              description
                &quot;Location of the device.&quot;;
            }
            container management {
              when &quot;derived-from-or-self(../../../management/type, &quot;
                 + &quot;&#x27;l2vpn-svc:co-managed&#x27;)&quot; {
                description
                  &quot;Applicable only for a co-managed device.&quot;;
              }
              leaf transport {
                type identityref {
                  base address-family;
                }
                description
                  &quot;Transport protocol or address family
                   used for management.&quot;;
              }
              leaf address {
                when &#x27;(../ transport)&#x27; {
                  description
                    &quot;If the address family is specified, then the
                     address should also be specified.  If the
                     transport is not specified, then the address
                     should not be specified.&quot;;
                }
                type inet:ip-address;
                description
                  &quot;Management address.&quot;;
              }
              description
<span class="grey"><a href="/doc/html/rfc8466">RFC 8466</a>               L2VPN Service Model (L2SM)           October 2018</span>

                &quot;Management configuration.  Applicable only for a
                 co-managed device.&quot;;
            }
            description
              &quot;List of devices requested by the customer.&quot;;
          }
          description
            &quot;Device configurations.&quot;;
        }
        container management {
          leaf type {
            type identityref {
              base management;
            }
            mandatory true;
            description
              &quot;Management type of the connection.&quot;;
          }
          description
            &quot;Management configuration.&quot;;
        }
        container locations {
          list location {
            key &quot;location-id&quot;;
            leaf location-id {
              type string;
              description
                &quot;Location ID.&quot;;
            }
            leaf address {
              type string;
              description
                &quot;Address (number and street) of the site.&quot;;
            }
            leaf postal-code {
              type string;
              description
                &quot;Postal code of the site.  The format of &#x27;postal-code&#x27;
                 is similar to the &#x27;PC&#x27; (postal code) label format
                 defined in <a href="/doc/html/rfc4119">RFC 4119</a>.&quot;;
            }
            leaf state {
              type string;
              description
                &quot;State (region) of the site.  This leaf can also be used
                 to describe a region of a country that does not have
                 states.&quot;;
            }
<span class="grey"><a href="/doc/html/rfc8466">RFC 8466</a>               L2VPN Service Model (L2SM)           October 2018</span>

            leaf city {
              type string;
              description
                &quot;City of the site.&quot;;
            }
            leaf country-code {
              type string;
              description
                &quot;Country of the site.  The format of &#x27;country-code&#x27; is
                 similar to the &#x27;country&#x27; label defined in <a href="/doc/html/rfc4119">RFC 4119</a>.&quot;;
            }
            description
              &quot;List of locations.&quot;;
          }
          description
            &quot;Location of the site.&quot;;
        }
        container site-diversity {
          if-feature &quot;site-diversity&quot;;
          container groups {
            list group {
              key &quot;group-id&quot;;
              leaf group-id {
                type string;
                description
                  &quot;The group-id to which the site belongs.&quot;;
              }
              description
                &quot;List of group-ids.&quot;;
            }
            description
              &quot;Groups to which the site belongs.
               All site network accesses will inherit those group
               values.&quot;;
          }
          description
            &quot;The type of diversity constraint.&quot;;
        }
        container vpn-policies {
          list vpn-policy {
            key &quot;vpn-policy-id&quot;;
            leaf vpn-policy-id {
              type string;
              description
                &quot;Unique identifier for the VPN policy.&quot;;
            }
            list entries {
              key &quot;id&quot;;
<span class="grey"><a href="/doc/html/rfc8466">RFC 8466</a>               L2VPN Service Model (L2SM)           October 2018</span>

              leaf id {
                type string;
                description
                  &quot;Unique identifier for the policy entry.&quot;;
              }
              container filters {
                list filter {
                  key &quot;type&quot;;
                  ordered-by user;
                  leaf type {
                    type identityref {
                      base vpn-policy-filter-type;
                    }
                    description
                      &quot;Type of VPN policy filter.&quot;;
                  }
                  leaf-list lan-tag {
                    when &quot;derived-from-or-self(../type, &quot;
                       + &quot;&#x27;l2vpn-svc:lan&#x27;)&quot; {
                      description
                        &quot;Only applies when the VPN policy filter is a
                         LAN tag filter.&quot;;
                    }
                    if-feature &quot;lan-tag&quot;;
                    type uint32;
                    description
                      &quot;List of Ethernet LAN tags to be matched.  An
                       Ethernet LAN tag identifies a particular
                       broadcast domain in a VPN.&quot;;
                  }
                  description
                    &quot;List of filters used on the site.  This list can
                     be augmented.&quot;;
                }
                description
                  &quot;If a more granular VPN attachment is necessary,
                   filtering can be used.  If used, it permits the
                   splitting of site LANs among multiple VPNs.  The
                   site LAN can be split based on either the LAN tag or
                   the LAN prefix.  If no filter is used, all the LANs
                   will be part of the same VPNs with the same role.&quot;;
              }
              list vpn {
                key &quot;vpn-id&quot;;
                leaf vpn-id {
                  type leafref {
                    path &quot;/l2vpn-svc/vpn-services/vpn-service/vpn-id&quot;;
                  }
<span class="grey"><a href="/doc/html/rfc8466">RFC 8466</a>               L2VPN Service Model (L2SM)           October 2018</span>

                  description
                    &quot;Reference to an L2VPN.&quot;;
                }
                leaf site-role {
                  type identityref {
                    base site-role;
                  }
                  default &quot;any-to-any-role&quot;;
                  description
                    &quot;Role of the site in the L2VPN.&quot;;
                }
                description
                  &quot;List of VPNs with which the LAN is associated.&quot;;
              }
              description
                &quot;List of entries for an export policy.&quot;;
            }
            description
              &quot;List of VPN policies.&quot;;
          }
          description
            &quot;VPN policy.&quot;;
        }
        container service {
          uses site-service-qos-profile;
          uses site-service-mpls;
          description
            &quot;Service parameters on the attachment.&quot;;
        }
        uses site-bum;
        uses site-mac-loop-prevention;
        uses site-acl;
        leaf actual-site-start {
          type yang:date-and-time;
          config false;
          description
            &quot;This leaf is optional.  It indicates the date and time
             when the service at a particular site actually started.&quot;;
        }
        leaf actual-site-stop {
          type yang:date-and-time;
          config false;
          description
            &quot;This leaf is optional.  It indicates the date and time
             when the service at a particular site actually stopped.&quot;;
        }
        leaf bundling-type {
          type identityref {
<span class="grey"><a href="/doc/html/rfc8466">RFC 8466</a>               L2VPN Service Model (L2SM)           October 2018</span>

            base bundling-type;
          }
          default &quot;one2one-bundling&quot;;
          description
            &quot;Bundling type.  By default, each L2VPN
             can be associated with only one
             CE-VLAN, i.e., one-to-one bundling is used.&quot;;
        }
        leaf default-ce-vlan-id {
          type uint32;
          mandatory true;
          description
            &quot;Default CE VLAN ID set at the site level.&quot;;
        }
        container site-network-accesses {
          list site-network-access {
            key &quot;network-access-id&quot;;
            leaf network-access-id {
              type string;
              description
                &quot;Identifier of network access.&quot;;
            }
            leaf remote-carrier-name {
              when &quot;derived-from-or-self(../../../site-vpn-flavor,&quot;
                 + &quot;&#x27;l2vpn-svc:site-vpn-flavor-nni&#x27;)&quot; {
                description
                  &quot;Relevant when the site&#x27;s VPN flavor is
                   &#x27;site-vpn-flavor-nni&#x27;.&quot;;
              }
              type leafref {
                path &quot;/l2vpn-svc/vpn-profiles/&quot;
                   + &quot;valid-provider-identifiers&quot;
                   + &quot;/remote-carrier-identifier&quot;;
              }
              description
                &quot;Remote carrier name.  The &#x27;remote-carrier-name&#x27;
                 parameter must be configured only when
                 &#x27;site-vpn-flavor&#x27; is set to &#x27;site-vpn-flavor-nni&#x27;.
                 If it is not set, it indicates that the customer
                 does not know the remote carrier&#x27;s name
                 beforehand.&quot;;
            }
            leaf type {
              type identityref {
                base site-network-access-type;
              }
              default &quot;point-to-point&quot;;
              description
<span class="grey"><a href="/doc/html/rfc8466">RFC 8466</a>               L2VPN Service Model (L2SM)           October 2018</span>

                &quot;Describes the type of connection, e.g.,
                 point-to-point or multipoint.&quot;;
            }
            choice location-flavor {
              case location {
                when &quot;derived-from-or-self(../../management/type, &quot;
                   + &quot;&#x27;l2vpn-svc:customer-managed&#x27;)&quot; {
                  description
                    &quot;Applicable only for a customer-managed device.&quot;;
                }
                leaf location-reference {
                  type leafref {
                    path &quot;../../../locations/location/location-id&quot;;
                  }
                  description
                    &quot;Location of the site-network-access.&quot;;
                }
              }
              case device {
                when &quot;derived-from-or-self(../../management/type, &quot;
                   + &quot;&#x27;l2vpn-svc:provider-managed&#x27;) or &quot;
                   + &quot;derived-from-or-self(../../management/type, &quot;
                   + &quot;&#x27;l2vpn-svc:co-managed&#x27;)&quot; {
                  description
                    &quot;Applicable only for a provider-managed
                     or co-managed device.&quot;;
                }
                leaf device-reference {
                  type leafref {
                    path &quot;../../../devices/device/device-id&quot;;
                  }
                  description
                    &quot;Identifier of the CE to use.&quot;;
                }
              }
              mandatory true;
              description
                &quot;Choice of how to describe the site&#x27;s location.&quot;;
            }
            container access-diversity {
              if-feature &quot;site-diversity&quot;;
              container groups {
                list group {
                  key &quot;group-id&quot;;
                  leaf group-id {
                    type string;
                    description
                      &quot;Group-id to which the site belongs.&quot;;
<span class="grey"><a href="/doc/html/rfc8466">RFC 8466</a>               L2VPN Service Model (L2SM)           October 2018</span>

                  }
                  description
                    &quot;List of group-ids.&quot;;
                }
                description
                  &quot;Groups to which the site or site-network-access
                   belongs.&quot;;
              }
              container constraints {
                list constraint {
                  key &quot;constraint-type&quot;;
                  leaf constraint-type {
                    type identityref {
                      base placement-diversity;
                    }
                    description
                      &quot;The type of diversity constraint.&quot;;
                  }
                  container target {
                    choice target-flavor {
                      default &quot;id&quot;;
                      case id {
                        list group {
                          key &quot;group-id&quot;;
                          leaf group-id {
                            type string;
                            description
                              &quot;The constraint will apply against this
                               particular group-id.&quot;;
                          }
                          description
                            &quot;List of groups.&quot;;
                        }
                      }
                      case all-accesses {
                        leaf all-other-accesses {
                          type empty;
                          description
                            &quot;The constraint will apply against all other
                             site network accesses of this site.&quot;;
                        }
                      }
                      case all-groups {
                        leaf all-other-groups {
                          type empty;
                          description
                            &quot;The constraint will apply against all other
                             groups the customer is managing.&quot;;
<span class="grey"><a href="/doc/html/rfc8466">RFC 8466</a>               L2VPN Service Model (L2SM)           October 2018</span>

                        }
                      }
                      description
                        &quot;Choice for the group definition.&quot;;
                    }
                    description
                      &quot;The constraint will apply against
                       this list of groups.&quot;;
                  }
                  description
                    &quot;List of constraints.&quot;;
                }
                description
                  &quot;Constraints for placing this site network access.&quot;;
              }
              description
                &quot;Diversity parameters.&quot;;
            }
            container bearer {
              container requested-type {
                if-feature &quot;requested-type&quot;;
                leaf type {
                  type string;
                  description
                    &quot;Type of requested bearer: Ethernet, ATM, Frame
                     Relay, IP Layer 2 transport, Frame Relay Data
                     Link Connection Identifier (DLCI), SONET/SDH,
                     PPP.&quot;;
                }
                leaf strict {
                  type boolean;
                  default &quot;false&quot;;
                  description
                    &quot;Defines whether the requested type is a preference
                     or a strict requirement.&quot;;
                }
                description
                  &quot;Container for requested types.&quot;;
              }
              leaf always-on {
                if-feature &quot;always-on&quot;;
                type boolean;
                default &quot;true&quot;;
                description
                  &quot;Request for an &#x27;always-on&#x27; access type.
                   For example, this could mean no dial-in access
                   type.&quot;;
              }
<span class="grey"><a href="/doc/html/rfc8466">RFC 8466</a>               L2VPN Service Model (L2SM)           October 2018</span>

              leaf bearer-reference {
                if-feature &quot;bearer-reference&quot;;
                type string;
                description
                  &quot;An internal reference for the SP.&quot;;
              }
              description
                &quot;Bearer-specific parameters.  To be augmented.&quot;;
            }
            container connection {
              leaf encapsulation-type {
                type identityref {
                  base encapsulation-type;
                }
                default &quot;ethernet&quot;;
                description
                  &quot;Encapsulation type.  By default, the
                   encapsulation type is set to &#x27;ethernet&#x27;.&quot;;
              }
              leaf eth-inf-type {
                type identityref {
                  base eth-inf-type;
                }
                default &quot;untagged&quot;;
                description
                  &quot;Ethernet interface type.  By default, the
                   Ethernet interface type is set to &#x27;untagged&#x27;.&quot;;
              }
              container tagged-interface {
                leaf type {
                  type identityref {
                    base tagged-inf-type;
                  }
                  default &quot;priority-tagged&quot;;
                  description
                    &quot;Tagged interface type.  By default,
                     the type of the tagged interface is
                     &#x27;priority-tagged&#x27;.&quot;;
                }
                container dot1q-vlan-tagged {
                  when &quot;derived-from-or-self(../type, &quot;
                     + &quot;&#x27;l2vpn-svc:dot1q&#x27;)&quot; {
                    description
                      &quot;Only applies when the type of the tagged
                       interface is &#x27;dot1q&#x27;.&quot;;
                  }
                  if-feature &quot;dot1q&quot;;
                  leaf tg-type {
<span class="grey"><a href="/doc/html/rfc8466">RFC 8466</a>               L2VPN Service Model (L2SM)           October 2018</span>

                    type identityref {
                      base tag-type;
                    }
                    default &quot;c-vlan&quot;;
                    description
                      &quot;Tag type.  By default, the tag type is
                       &#x27;c-vlan&#x27;.&quot;;
                  }
                  leaf cvlan-id {
                    type uint16;
                    mandatory true;
                    description
                      &quot;VLAN identifier.&quot;;
                  }
                  description
                    &quot;Tagged interface.&quot;;
                }
                container priority-tagged {
                  when &quot;derived-from-or-self(../type, &quot;
                     + &quot;&#x27;l2vpn-svc:priority-tagged&#x27;)&quot; {
                    description
                      &quot;Only applies when the type of the tagged
                       interface is &#x27;priority-tagged&#x27;.&quot;;
                  }
                  leaf tag-type {
                    type identityref {
                      base tag-type;
                    }
                    default &quot;c-vlan&quot;;
                    description
                      &quot;Tag type.  By default, the tag type is
                       &#x27;c-vlan&#x27;.&quot;;
                  }
                  description
                    &quot;Priority tagged.&quot;;
                }
                container qinq {
                  when &quot;derived-from-or-self(../type, &quot;
                     + &quot;&#x27;l2vpn-svc:qinq&#x27;)&quot; {
                    description
                      &quot;Only applies when the type of the tagged
                       interface is &#x27;qinq&#x27;.&quot;;
                  }
                  if-feature &quot;qinq&quot;;
                  leaf tag-type {
                    type identityref {
                      base tag-type;
                    }
<span class="grey"><a href="/doc/html/rfc8466">RFC 8466</a>               L2VPN Service Model (L2SM)           October 2018</span>

                    default &quot;c-s-vlan&quot;;
                    description
                      &quot;Tag type.  By default, the tag type is
                       &#x27;c-s-vlan&#x27;.&quot;;
                  }
                  leaf svlan-id {
                    type uint16;
                    mandatory true;
                    description
                      &quot;SVLAN identifier.&quot;;
                  }
                  leaf cvlan-id {
                    type uint16;
                    mandatory true;
                    description
                      &quot;CVLAN identifier.&quot;;
                  }
                  description
                    &quot;QinQ.&quot;;
                }
                container qinany {
                  when &quot;derived-from-or-self(../type, &quot;
                     + &quot;&#x27;l2vpn-svc:qinany&#x27;)&quot; {
                    description
                      &quot;Only applies when the type of the tagged
                       interface is &#x27;qinany&#x27;.&quot;;
                  }
                  if-feature &quot;qinany&quot;;
                  leaf tag-type {
                    type identityref {
                      base tag-type;
                    }
                    default &quot;s-vlan&quot;;
                    description
                      &quot;Tag type.  By default, the tag type is
                       &#x27;s-vlan&#x27;.&quot;;
                  }
                  leaf svlan-id {
                    type uint16;
                    mandatory true;
                    description
                      &quot;SVLAN ID.&quot;;
                  }
                  description
                    &quot;Container for QinAny.&quot;;
                }
                container vxlan {
                  when &quot;derived-from-or-self(../type, &quot;
<span class="grey"><a href="/doc/html/rfc8466">RFC 8466</a>               L2VPN Service Model (L2SM)           October 2018</span>

                     + &quot;&#x27;l2vpn-svc:vxlan&#x27;)&quot; {
                    description
                      &quot;Only applies when the type of the tagged
                       interface is &#x27;vxlan&#x27;.&quot;;
                  }
                  if-feature &quot;vxlan&quot;;
                  leaf vni-id {
                    type uint32;
                    mandatory true;
                    description
                      &quot;VXLAN Network Identifier (VNI).&quot;;
                  }
                  leaf peer-mode {
                    type identityref {
                      base vxlan-peer-mode;
                    }
                    default &quot;static-mode&quot;;
                    description
                      &quot;Specifies the VXLAN access mode.  By default,
                       the peer mode is set to &#x27;static-mode&#x27;.&quot;;
                  }
                  list peer-list {
                    key &quot;peer-ip&quot;;
                    leaf peer-ip {
                      type inet:ip-address;
                      description
                        &quot;Peer IP.&quot;;
                    }
                    description
                      &quot;List of peer IP addresses.&quot;;
                  }
                  description
                    &quot;QinQ.&quot;;
                }
                description
                  &quot;Container for tagged interfaces.&quot;;
              }
              container untagged-interface {
                leaf speed {
                  type uint32;
                  units &quot;mbps&quot;;
                  default &quot;10&quot;;
                  description
                    &quot;Port speed.&quot;;
                }
                leaf mode {
                  type neg-mode;
                  default &quot;auto-neg&quot;;
<span class="grey"><a href="/doc/html/rfc8466">RFC 8466</a>               L2VPN Service Model (L2SM)           October 2018</span>

                  description
                    &quot;Negotiation mode.&quot;;
                }
                leaf phy-mtu {
                  type uint32;
                  units &quot;bytes&quot;;
                  description
                    &quot;PHY MTU.&quot;;
                }
                leaf lldp {
                  type boolean;
                  default &quot;false&quot;;
                  description
                    &quot;LLDP.  Indicates that LLDP is supported.&quot;;
                }
                container oam-802.3ah-link {
                  if-feature &quot;oam-3ah&quot;;
                  leaf enabled {
                    type boolean;
                    default &quot;false&quot;;
                    description
                      &quot;Indicates whether or not to support
                       OAM 802.3ah links.&quot;;
                  }
                  description
                    &quot;Container for OAM 802.3ah links.&quot;;
                }
                leaf uni-loop-prevention {
                  type boolean;
                  default &quot;false&quot;;
                  description
                    &quot;If this leaf is set to &#x27;true&#x27;, then the port
                     automatically goes down when a physical
                     loopback is detected.&quot;;
                }
                description
                  &quot;Container of untagged interface attribute
                   configurations.&quot;;
              }
              container lag-interfaces {
                if-feature &quot;lag-interface&quot;;
                list lag-interface {
                  key &quot;index&quot;;
                  leaf index {
                    type string;
                    description
                      &quot;LAG interface index.&quot;;
                  }
<span class="grey"><a href="/doc/html/rfc8466">RFC 8466</a>               L2VPN Service Model (L2SM)           October 2018</span>

                  container lacp {
                    if-feature &quot;lacp&quot;;
                    leaf enabled {
                      type boolean;
                      default &quot;false&quot;;
                      description
                        &quot;LACP on/off.  By default, LACP is disabled.&quot;;
                    }
                    leaf mode {
                      type neg-mode;
                      description
                        &quot;LACP mode.  LACP modes have active mode and
                         passive mode (&#x27;false&#x27;).  &#x27;Active mode&#x27; means
                         initiating the auto-speed negotiation and
                         trying to form an Ethernet channel with the
                         other end.  &#x27;Passive mode&#x27; means not initiating
                         the negotiation but responding to LACP packets
                         initiated by the other end (e.g., full duplex
                         or half duplex).&quot;;
                    }
                    leaf speed {
                      type uint32;
                      units &quot;mbps&quot;;
                      default &quot;10&quot;;
                      description
                        &quot;LACP speed.  By default, the LACP speed is 10
                         Mbps.&quot;;
                    }
                    leaf mini-link-num {
                      type uint32;
                      description
                        &quot;Defines the minimum number of links that must
                         be active before the aggregating link is put
                         into service.&quot;;
                    }
                    leaf system-priority {
                      type uint16;
                      default &quot;32768&quot;;
                      description
                        &quot;Indicates the LACP priority for the system.
                         The range is from 0 to 65535.
                         The default is 32768.&quot;;
                    }
                    container micro-bfd {
                      if-feature &quot;micro-bfd&quot;;
                      leaf enabled {
                        type enumeration {
                          enum on {
<span class="grey"><a href="/doc/html/rfc8466">RFC 8466</a>               L2VPN Service Model (L2SM)           October 2018</span>

                            description
                              &quot;Micro-bfd on.&quot;;
                          }
                          enum off {
                            description
                              &quot;Micro-bfd off.&quot;;
                          }
                        }
                        default &quot;off&quot;;
                        description
                          &quot;Micro-BFD on/off.  By default, micro-BFD
                           is set to &#x27;off&#x27;.&quot;;
                      }
                      leaf interval {
                        type uint32;
                        units &quot;milliseconds&quot;;
                        description
                          &quot;BFD interval.&quot;;
                      }
                      leaf hold-timer {
                        type uint32;
                        units &quot;milliseconds&quot;;
                        description
                          &quot;BFD hold timer.&quot;;
                      }
                      description
                        &quot;Container of micro-BFD configurations.&quot;;
                    }
                    container bfd {
                      if-feature &quot;bfd&quot;;
                      leaf enabled {
                        type boolean;
                        default &quot;false&quot;;
                        description
                          &quot;BFD activation.  By default, BFD is not
                           activated.&quot;;
                      }
                      choice holdtime {
                        default &quot;fixed&quot;;
                        case profile {
                          leaf profile-name {
                            type leafref {
                              path &quot;/l2vpn-svc/vpn-profiles/&quot;
                                 + &quot;valid-provider-identifiers&quot;
                                 + &quot;/bfd-profile-identifier&quot;;
                            }
                            description
                              &quot;SP well-known profile.&quot;;
<span class="grey"><a href="/doc/html/rfc8466">RFC 8466</a>               L2VPN Service Model (L2SM)           October 2018</span>

                          }
                          description
                            &quot;SP well-known profile.&quot;;
                        }
                        case fixed {
                          leaf fixed-value {
                            type uint32;
                            units &quot;milliseconds&quot;;
                            description
                              &quot;Expected hold time expressed in
                               milliseconds.&quot;;
                          }
                        }
                        description
                          &quot;Choice for the hold-time flavor.&quot;;
                      }
                      description
                        &quot;Container for BFD.&quot;;
                    }
                    container member-links {
                      list member-link {
                        key &quot;name&quot;;
                        leaf name {
                          type string;
                          description
                            &quot;Member link name.&quot;;
                        }
                        leaf speed {
                          type uint32;
                          units &quot;mbps&quot;;
                          default &quot;10&quot;;
                          description
                            &quot;Port speed.&quot;;
                        }
                        leaf mode {
                          type neg-mode;
                          default &quot;auto-neg&quot;;
                          description
                            &quot;Negotiation mode.&quot;;
                        }
                        leaf link-mtu {
                          type uint32;
                          units &quot;bytes&quot;;
                          description
                            &quot;Link MTU size.&quot;;
                        }
                        container oam-802.3ah-link {
                          if-feature &quot;oam-3ah&quot;;
<span class="grey"><a href="/doc/html/rfc8466">RFC 8466</a>               L2VPN Service Model (L2SM)           October 2018</span>

                          leaf enabled {
                            type boolean;
                            default &quot;false&quot;;
                            description
                              &quot;Indicates whether OAM 802.3ah links are
                               supported.&quot;;
                          }
                          description
                            &quot;Container for OAM 802.3ah links.&quot;;
                        }
                        description
                          &quot;Member link.&quot;;
                      }
                      description
                        &quot;Container of the member link list.&quot;;
                    }
                    leaf flow-control {
                      type boolean;
                      default &quot;false&quot;;
                      description
                        &quot;Flow control.  Indicates whether flow control
                         is supported.&quot;;
                    }
                    leaf lldp {
                      type boolean;
                      default &quot;false&quot;;
                      description
                        &quot;LLDP.  Indicates whether LLDP is supported.&quot;;
                    }
                    description
                      &quot;LACP.&quot;;
                  }
                  description
                    &quot;List of LAG interfaces.&quot;;
                }
                description
                  &quot;Container of LAG interface attribute
                   configurations.&quot;;
              }
              list cvlan-id-to-svc-map {
                key &quot;svc-id&quot;;
                leaf svc-id {
                  type leafref {
                    path &quot;/l2vpn-svc/vpn-services/vpn-service/vpn-id&quot;;
                  }
                  description
                    &quot;VPN service identifier.&quot;;
                }
<span class="grey"><a href="/doc/html/rfc8466">RFC 8466</a>               L2VPN Service Model (L2SM)           October 2018</span>

                list cvlan-id {
                  key &quot;vid&quot;;
                  leaf vid {
                    type uint16;
                    description
                      &quot;CVLAN ID.&quot;;
                  }
                  description
                    &quot;List of CVLAN-ID-to-SVC-map configurations.&quot;;
                }
                description
                  &quot;List of CVLAN-ID-to-L2VPN-service-map
                   configurations.&quot;;
              }
              container l2cp-control {
                if-feature &quot;l2cp-control&quot;;
                leaf stp-rstp-mstp {
                  type control-mode;
                  description
                    &quot;STP / Rapid STP (RSTP) / Multiple STP (MSTP)
                     protocol type applicable to all sites.&quot;;
                }
                leaf pause {
                  type control-mode;
                  description
                    &quot;Pause protocol type applicable to all sites.&quot;;
                }
                leaf lacp-lamp {
                  type control-mode;
                  description
                    &quot;LACP / Link Aggregation Marker Protocol (LAMP).&quot;;
                }
                leaf link-oam {
                  type control-mode;
                  description
                    &quot;Link OAM.&quot;;
                }
                leaf esmc {
                  type control-mode;
                  description
                    &quot;Ethernet Synchronization Messaging Channel
                     (ESMC).&quot;;
                }
                leaf l2cp-802.1x {
                  type control-mode;
                  description
                    &quot;IEEE 802.1x.&quot;;
                }
<span class="grey"><a href="/doc/html/rfc8466">RFC 8466</a>               L2VPN Service Model (L2SM)           October 2018</span>

                leaf e-lmi {
                  type control-mode;
                  description
                    &quot;E-LMI.&quot;;
                }
                leaf lldp {
                  type boolean;
                  description
                    &quot;LLDP protocol type applicable to all sites.&quot;;
                }
                leaf ptp-peer-delay {
                  type control-mode;
                  description
                    &quot;Precision Time Protocol (PTP) peer delay.&quot;;
                }
                leaf garp-mrp {
                  type control-mode;
                  description
                    &quot;GARP/MRP.&quot;;
                }
                description
                  &quot;Container of L2CP control configurations.&quot;;
              }
              container oam {
                if-feature &quot;ethernet-oam&quot;;
                leaf md-name {
                  type string;
                  mandatory true;
                  description
                    &quot;Maintenance domain name.&quot;;
                }
                leaf md-level {
                  type uint16 {
                    range &quot;0..255&quot;;
                  }
                  mandatory true;
                  description
                    &quot;Maintenance domain level.  The level may be
                     restricted in certain protocols (e.g.,
                     protocols in Layer 0 to Layer 7).&quot;;
                }
                list cfm-8021-ag {
                  if-feature &quot;cfm&quot;;
                  key &quot;maid&quot;;
                  leaf maid {
                    type string;
                    mandatory true;
                    description
<span class="grey"><a href="/doc/html/rfc8466">RFC 8466</a>               L2VPN Service Model (L2SM)           October 2018</span>

                      &quot;Identifies a Maintenance Association (MA).&quot;;
                  }
                  leaf mep-id {
                    type uint32;
                    description
                      &quot;Local Maintenance Entity Group End Point (MEP)
                       ID.  The non-existence of this leaf means
                       that no defects are to be reported.&quot;;
                  }
                  leaf mep-level {
                    type uint32;
                    description
                      &quot;Defines the MEP level.  The non-existence of this
                       leaf means that no defects are to be reported.&quot;;
                  }
                  leaf mep-up-down {
                    type enumeration {
                      enum up {
                        description
                          &quot;MEP up.&quot;;
                      }
                      enum down {
                        description
                          &quot;MEP down.&quot;;
                      }
                    }
                    default &quot;up&quot;;
                    description
                      &quot;MEP up/down.  By default, MEP up is used.
                       The non-existence of this leaf means that
                       no defects are to be reported.&quot;;
                  }
                  leaf remote-mep-id {
                    type uint32;
                    description
                      &quot;Remote MEP ID.  The non-existence of this leaf
                       means that no defects are to be reported.&quot;;
                  }
                  leaf cos-for-cfm-pdus {
                    type uint32;
                    description
                      &quot;CoS for CFM PDUs.  The non-existence of this leaf
                       means that no defects are to be reported.&quot;;
                  }
                  leaf ccm-interval {
                    type uint32;
                    units &quot;milliseconds&quot;;
                    default &quot;10000&quot;;
<span class="grey"><a href="/doc/html/rfc8466">RFC 8466</a>               L2VPN Service Model (L2SM)           October 2018</span>

                    description
                      &quot;CCM interval.  By default, the CCM interval is
                       10,000 milliseconds (10 seconds).&quot;;
                  }
                  leaf ccm-holdtime {
                    type uint32;
                    units &quot;milliseconds&quot;;
                    default &quot;35000&quot;;
                    description
                      &quot;CCM hold time.  By default, the CCM hold time
                       is 3.5 times the CCM interval.&quot;;
                  }
                  leaf alarm-priority-defect {
                    type identityref {
                      base fault-alarm-defect-type;
                    }
                    default &quot;remote-invalid-ccm&quot;;
                    description
                      &quot;The lowest-priority defect that is
                       allowed to generate a fault alarm.  By default,
                       &#x27;fault-alarm-defect-type&#x27; is set to
                       &#x27;remote-invalid-ccm&#x27;.  The non-existence of
                       this leaf means that no defects are
                       to be reported.&quot;;
                  }
                  leaf ccm-p-bits-pri {
                    type ccm-priority-type;
                    description
                      &quot;The priority parameter for CCMs transmitted by
                       the MEP.  The non-existence of this leaf means
                       that no defects are to be reported.&quot;;
                  }
                  description
                    &quot;List of 802.1ag CFM attributes.&quot;;
                }
                list y-1731 {
                  if-feature &quot;y-1731&quot;;
                  key &quot;maid&quot;;
                  leaf maid {
                    type string;
                    mandatory true;
                    description
                      &quot;Identifies an MA.&quot;;
                  }
                  leaf mep-id {
                    type uint32;
                    description
                      &quot;Local MEP ID.  The non-existence of this leaf
<span class="grey"><a href="/doc/html/rfc8466">RFC 8466</a>               L2VPN Service Model (L2SM)           October 2018</span>

                       means that no measurements are to be reported.&quot;;
                  }
                  leaf type {
                    type identityref {
                      base pm-type;
                    }
                    default &quot;delay&quot;;
                    description
                      &quot;Performance-monitoring types.  By default, the
                       performance-monitoring type is set to &#x27;delay&#x27;.
                       The non-existence of this leaf means that no
                       measurements are to be reported.&quot;;
                  }
                  leaf remote-mep-id {
                    type uint32;
                    description
                      &quot;Remote MEP ID.  The non-existence of this
                       leaf means that no measurements are to be
                       reported.&quot;;
                  }
                  leaf message-period {
                    type uint32;
                    units &quot;milliseconds&quot;;
                    default &quot;10000&quot;;
                    description
                      &quot;Defines the interval between Y.1731
                       performance-monitoring messages.  The message
                       period is expressed in milliseconds.&quot;;
                  }
                  leaf measurement-interval {
                    type uint32;
                    units &quot;seconds&quot;;
                    description
                      &quot;Specifies the measurement interval for
                       statistics.  The measurement interval is
                       expressed in seconds.&quot;;
                  }
                  leaf cos {
                    type uint32;
                    description
                      &quot;CoS.  The non-existence of this leaf means that
                       no measurements are to be reported.&quot;;
                  }
                  leaf loss-measurement {
                    type boolean;
                    default &quot;false&quot;;
                    description
                      &quot;Indicates whether or not to enable loss
<span class="grey"><a href="/doc/html/rfc8466">RFC 8466</a>               L2VPN Service Model (L2SM)           October 2018</span>

                       measurement.  By default, loss
                       measurement is not enabled.&quot;;
                  }
                  leaf synthetic-loss-measurement {
                    type boolean;
                    default &quot;false&quot;;
                    description
                      &quot;Indicates whether or not to enable synthetic loss
                       measurement.  By default, synthetic loss
                       measurement is not enabled.&quot;;
                  }
                  container delay-measurement {
                    leaf enable-dm {
                      type boolean;
                      default &quot;false&quot;;
                      description
                        &quot;Indicates whether or not to enable delay
                         measurement.  By default, delay measurement
                         is not enabled.&quot;;
                    }
                    leaf two-way {
                      type boolean;
                      default &quot;false&quot;;
                      description
                        &quot;Indicates whether delay measurement is two-way
                         (&#x27;true&#x27;) or one-way (&#x27;false&#x27;).  By default,
                         one-way measurement is enabled.&quot;;
                    }
                    description
                      &quot;Container for delay measurement.&quot;;
                  }
                  leaf frame-size {
                    type uint32;
                    units &quot;bytes&quot;;
                    description
                      &quot;Frame size.  The non-existence of this leaf
                       means that no measurements are to be reported.&quot;;
                  }
                  leaf session-type {
                    type enumeration {
                      enum proactive {
                        description
                          &quot;Proactive mode.&quot;;
                      }
                      enum on-demand {
                        description
                          &quot;On-demand mode.&quot;;
                      }
<span class="grey"><a href="/doc/html/rfc8466">RFC 8466</a>               L2VPN Service Model (L2SM)           October 2018</span>

                    }
                    default &quot;on-demand&quot;;
                    description
                      &quot;Session type.  By default, the session type
                       is &#x27;on-demand&#x27;.  The non-existence of this
                       leaf means that no measurements are to be
                       reported.&quot;;
                  }
                  description
                    &quot;List of configured Y-1731 instances.&quot;;
                }
                description
                  &quot;Container for Ethernet Service OAM.&quot;;
              }
              description
                &quot;Container for connection requirements.&quot;;
            }
            container availability {
              leaf access-priority {
                type uint32;
                default &quot;100&quot;;
                description
                  &quot;Access priority.  The higher the access-priority
                   value, the higher the preference will be for the
                   access in question.&quot;;
              }
              choice redundancy-mode {
                case single-active {
                  leaf single-active {
                    type empty;
                    description
                      &quot;Single-active mode.&quot;;
                  }
                  description
                    &quot;In single-active mode, only one node forwards
                     traffic to and from the Ethernet segment.&quot;;
                }
                case all-active {
                  leaf all-active {
                    type empty;
                    description
                      &quot;All-active mode.&quot;;
                  }
                  description
                    &quot;In all-active mode, all nodes can forward
                     traffic.&quot;;
                }
                description
<span class="grey"><a href="/doc/html/rfc8466">RFC 8466</a>               L2VPN Service Model (L2SM)           October 2018</span>

                  &quot;Redundancy mode choice.&quot;;
              }
              description
                &quot;Container of available optional configurations.&quot;;
            }
            container vpn-attachment {
              choice attachment-flavor {
                case vpn-id {
                  leaf vpn-id {
                    type leafref {
                      path &quot;/l2vpn-svc/vpn-services/vpn-service/vpn-id&quot;;
                    }
                    description
                      &quot;Reference to an L2VPN.  Referencing a vpn-id
                       provides an easy way to attach a particular
                       logical access to a VPN.  In this case,
                       the vpn-id must be configured.&quot;;
                  }
                  leaf site-role {
                    type identityref {
                      base site-role;
                    }
                    default &quot;any-to-any-role&quot;;
                    description
                      &quot;Role of the site in the L2VPN.  When referencing
                       a vpn-id, the site-role setting must be added to
                       express the role of the site in the target VPN
                       service topology.&quot;;
                  }
                }
                case vpn-policy-id {
                  leaf vpn-policy-id {
                    type leafref {
                      path &quot;../../../../vpn-policies/vpn-policy/&quot;
                         + &quot;vpn-policy-id&quot;;
                    }
                    description
                      &quot;Reference to a VPN policy.&quot;;
                  }
                }
                mandatory true;
                description
                  &quot;Choice for the VPN attachment flavor.&quot;;
              }
              description
                &quot;Defines the VPN attachment of a site.&quot;;
            }
            container service {
<span class="grey"><a href="/doc/html/rfc8466">RFC 8466</a>               L2VPN Service Model (L2SM)           October 2018</span>

              container svc-bandwidth {
                if-feature &quot;input-bw&quot;;
                list bandwidth {
                  key &quot;direction type&quot;;
                  leaf direction {
                    type identityref {
                      base bw-direction;
                    }
                    description
                      &quot;Indicates the bandwidth direction.  It can be
                       the bandwidth download direction from the SP to
                       the site or the bandwidth upload direction from
                       the site to the SP.&quot;;
                  }
                  leaf type {
                    type identityref {
                      base bw-type;
                    }
                    description
                      &quot;Bandwidth type.  By default, the bandwidth type
                       is set to &#x27;bw-per-cos&#x27;.&quot;;
                  }
                  leaf cos-id {
                    when &quot;derived-from-or-self(../type, &quot;
                       + &quot;&#x27;l2vpn-svc:bw-per-cos&#x27;)&quot; {
                      description
                        &quot;Relevant when the bandwidth type is set to
                         &#x27;bw-per-cos&#x27;.&quot;;
                    }
                    type uint8;
                    description
                      &quot;Identifier of the CoS, indicated by DSCP or a
                       CE-VLAN CoS (802.1p) value in the service frame.
                       If the bandwidth type is set to &#x27;bw-per-cos&#x27;,
                       the CoS ID MUST also be specified.&quot;;
                  }
                  leaf vpn-id {
                    when &quot;derived-from-or-self(../type, &quot;
                       + &quot;&#x27;l2vpn-svc:bw-per-svc&#x27;)&quot; {
                      description
                        &quot;Relevant when the bandwidth type is
                         set as bandwidth per VPN service.&quot;;
                    }
                    type svc-id;
                    description
                      &quot;Identifies the target VPN.  If the bandwidth
                       type is set as bandwidth per VPN service, the
                       vpn-id MUST be specified.&quot;;
<span class="grey"><a href="/doc/html/rfc8466">RFC 8466</a>               L2VPN Service Model (L2SM)           October 2018</span>

                  }
                  leaf cir {
                    type uint64;
                    units &quot;bps&quot;;
                    mandatory true;
                    description
                      &quot;Committed Information Rate.  The maximum number
                       of bits that a port can receive or send over
                       an interface in one second.&quot;;
                  }
                  leaf cbs {
                    type uint64;
                    units &quot;bps&quot;;
                    mandatory true;
                    description
                      &quot;Committed Burst Size (CBS).  Controls the bursty
                       nature of the traffic.  Traffic that does not
                       use the configured Committed Information Rate
                       (CIR) accumulates credits until the credits
                       reach the configured CBS.&quot;;
                  }
                  leaf eir {
                    type uint64;
                    units &quot;bps&quot;;
                    description
                      &quot;Excess Information Rate (EIR), i.e., excess frame
                       delivery allowed that is not subject to an SLA.
                       The traffic rate can be limited by the EIR.&quot;;
                  }
                  leaf ebs {
                    type uint64;
                    units &quot;bps&quot;;
                    description
                      &quot;Excess Burst Size (EBS).  The bandwidth available
                       for burst traffic from the EBS is subject to the
                       amount of bandwidth that is accumulated during
                       periods when traffic allocated by the EIR
                       policy is not used.&quot;;
                  }
                  leaf pir {
                    type uint64;
                    units &quot;bps&quot;;
                    description
                      &quot;Peak Information Rate, i.e., maximum frame
                       delivery allowed.  It is equal to or less
                       than the sum of the CIR and the EIR.&quot;;
                  }
                  leaf pbs {
<span class="grey"><a href="/doc/html/rfc8466">RFC 8466</a>               L2VPN Service Model (L2SM)           October 2018</span>

                    type uint64;
                    units &quot;bps&quot;;
                    description
                      &quot;Peak Burst Size.  It is measured in bytes per
                       second.&quot;;
                  }
                  description
                    &quot;List of bandwidth values (e.g., per CoS,
                     per vpn-id).&quot;;
                }
                description
                  &quot;From the customer site&#x27;s perspective, the service
                   input/output bandwidth of the connection or
                   download/upload bandwidth from the SP/site
                   to the site/SP.&quot;;
              }
              leaf svc-mtu {
                type uint16;
                units &quot;bytes&quot;;
                mandatory true;
                description
                  &quot;SVC MTU.  It is also known as the maximum
                   transmission unit or maximum frame size.  When
                   a frame is larger than the MTU, it is broken
                   down, or fragmented, into smaller pieces by
                   the network protocol to accommodate the MTU
                   of the network.  If CsC is enabled,
                   the requested svc-mtu leaf will refer to the
                   MPLS MTU and not to the link MTU.&quot;;
              }
              uses site-service-qos-profile;
              uses site-service-mpls;
              description
                &quot;Container for services.&quot;;
            }
            uses site-bum;
            uses site-mac-loop-prevention;
            uses site-acl;
            container mac-addr-limit {
              if-feature &quot;mac-addr-limit&quot;;
              leaf limit-number {
                type uint16;
                default &quot;2&quot;;
                description
                  &quot;Maximum number of MAC addresses learned from
                   the subscriber for a single service instance.
                   The default allowed maximum number of MAC
                   addresses is 2.&quot;;
<span class="grey"><a href="/doc/html/rfc8466">RFC 8466</a>               L2VPN Service Model (L2SM)           October 2018</span>

              }
              leaf time-interval {
                type uint32;
                units &quot;seconds&quot;;
                default &quot;300&quot;;
                description
                  &quot;The aging time of the MAC address.  By default,
                   the aging time is set to 300 seconds.&quot;;
              }
              leaf action {
                type identityref {
                  base mac-action;
                }
                default &quot;warning&quot;;
                description
                  &quot;Specifies the action taken when the upper limit is
                   exceeded: drop the packet, flood the packet, or
                   simply send a warning log message.  By default,
                   the action is set to &#x27;warning&#x27;.&quot;;
              }
              description
                &quot;Container of MAC address limit configurations.&quot;;
            }
            description
              &quot;List of site network accesses.&quot;;
          }
          description
            &quot;Container of port configurations.&quot;;
        }
        description
          &quot;List of sites.&quot;;
      }
      description
        &quot;Container of site configurations.&quot;;
    }
    description
      &quot;Container for L2VPN services.&quot;;
  }
}
