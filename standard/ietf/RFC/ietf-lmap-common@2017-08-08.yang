module ietf-lmap-common {

  yang-version 1.1;
  namespace &quot;urn:ietf:params:xml:ns:yang:ietf-lmap-common&quot;;
  prefix &quot;lmap&quot;;

  import ietf-inet-types {
    prefix inet;
  }

  organization
    &quot;IETF Large-Scale Measurement of Broadband Performance
     Working Group&quot;;

  contact
    &quot;WG Web:   &lt;<a href="https://datatracker.ietf.org/wg/lmap">https://datatracker.ietf.org/wg/lmap</a>&gt;
     WG List:  &lt;mailto:<a href="mailto:lmap@ietf.org">lmap@ietf.org</a>&gt;

     Editor:   Juergen Schoenwaelder
               &lt;<a href="mailto:j.schoenwaelder@jacobs-university.de">j.schoenwaelder@jacobs-university.de</a>&gt;

     Editor:   Vaibhav Bajpai
               &lt;<a href="mailto:bajpaiv@in.tum.de">bajpaiv@in.tum.de</a>&gt;&quot;;

  description
    &quot;This module provides common definitions used by the data
     models written for Large-Scale Measurement Platforms (LMAPs).
     This module defines typedefs and groupings but no schema
     tree elements.&quot;;

<span class="grey"><a href="/doc/html/rfc8194">RFC 8194</a>                YANG Data Model for LMAP             August 2017</span>

     revision &quot;2017-08-08&quot; {
       description
         &quot;Initial version&quot;;
       reference
         &quot;<a href="/doc/html/rfc8194">RFC 8194</a>: A YANG Data Model for LMAP Measurement Agents&quot;;
     }

     /*
      * Typedefs
      */

     typedef identifier {
       type string {
         length &quot;1..max&quot;;
       }
       description
         &quot;A string value used to name something.&quot;;
     }

     typedef tag {
       type string {
         length &quot;1..max&quot;;
       }
       description
         &quot;A tag consists of at least one character.&quot;;
     }

     typedef glob-pattern {
       type string {
         length &quot;1..max&quot;;
       }
       description
         &#x27;A glob style pattern (following POSIX.2 fnmatch() without
          special treatment of file paths):

            *         matches a sequence of characters
            ?         matches a single character
            [seq]     matches any character in seq
            [!seq]    matches any character not in seq

          A backslash followed by a character matches the following
          character.  In particular:

            \*        matches *
            \?        matches ?
            \\        matches \

<span class="grey"><a href="/doc/html/rfc8194">RFC 8194</a>                YANG Data Model for LMAP             August 2017</span>

          A sequence seq may be a sequence of characters (e.g., [abc]
          or a range of characters (e.g., [a-c]).&#x27;;
     }

     typedef wildcard {
       type string {
         pattern &#x27;\*&#x27;;
       }
       description
         &quot;A wildcard for calendar scheduling entries.&quot;;
     }

     typedef cycle-number {
       type string {
         pattern &#x27;[0-9]{8}\.[0-9]{6}&#x27;;
       }
       description
         &quot;A cycle number represented in the format YYYYMMDD.HHMMSS
          where YYYY represents the year, MM the month (1..12), DD
          the day of the months (01..31), HH the hour (00..23), MM
          the minute (00..59), and SS the second (00..59).  The cycle
          number is using Coordinated Universal Time (UTC).&quot;;
     }

     typedef month {
       type enumeration {
         enum january {
           value 1;
           description
             &quot;January of the Gregorian calendar.&quot;;
         }
         enum february {
           value 2;
           description
             &quot;February of the Gregorian calendar.&quot;;
         }
         enum march {
           value 3;
           description
             &quot;March of the Gregorian calendar.&quot;;
         }
         enum april {
           value 4;
           description
             &quot;April of the Gregorian calendar.&quot;;
         }

<span class="grey"><a href="/doc/html/rfc8194">RFC 8194</a>                YANG Data Model for LMAP             August 2017</span>

         enum may {
           value 5;
           description
             &quot;May of the Gregorian calendar.&quot;;
         }
         enum june {
           value 6;
           description
             &quot;June of the Gregorian calendar.&quot;;
         }
         enum july {
           value 7;
           description
             &quot;July of the Gregorian calendar.&quot;;
         }
         enum august {
           value 8;
           description
             &quot;August of the Gregorian calendar.&quot;;
         }
         enum september {
           value 9;
           description
             &quot;September of the Gregorian calendar.&quot;;
         }
         enum october {
           value 10;
           description
             &quot;October of the Gregorian calendar.&quot;;
         }
         enum november {
           value 11;
           description
             &quot;November of the Gregorian calendar.&quot;;
         }
         enum december {
           value 12;
           description
             &quot;December of the Gregorian calendar.&quot;;
         }
       }
       description
         &quot;A type modeling the month in the Gregorian calendar.&quot;;
     }

<span class="grey"><a href="/doc/html/rfc8194">RFC 8194</a>                YANG Data Model for LMAP             August 2017</span>

     typedef month-or-all {
       type union {
         type month;
         type wildcard;
       }
       description
         &quot;A month or a wildcard indicating all twelve months.&quot;;
     }

     typedef day-of-month {
       type uint8 { range &quot;1..31&quot;; }
       description
         &quot;A day of a month of the Gregorian calendar.&quot;;
     }

     typedef day-of-months-or-all {
       type union {
         type day-of-month;
         type wildcard;
       }
       description
         &quot;A day of a month or a wildcard indicating all days
          of a month.&quot;;
     }

     typedef weekday {
       type enumeration {
         enum monday {
           value 1;
           description
             &quot;Monday of the Gregorian calendar.&quot;;
         }
         enum tuesday {
           value 2;
           description
             &quot;Tuesday of the Gregorian calendar.&quot;;
         }
         enum wednesday {
           value 3;
           description
             &quot;Wednesday of the Gregorian calendar.&quot;;
         }
         enum thursday {
           value 4;
           description
             &quot;Thursday of the Gregorian calendar.&quot;;
         }

<span class="grey"><a href="/doc/html/rfc8194">RFC 8194</a>                YANG Data Model for LMAP             August 2017</span>

         enum friday {
           value 5;
           description
             &quot;Friday of the Gregorian calendar.&quot;;
         }
         enum saturday {
           value 6;
           description
             &quot;Saturday of the Gregorian calendar.&quot;;
         }
         enum sunday {
           value 7;
           description
             &quot;Sunday of the Gregorian calendar.&quot;;
         }
       }
       description
        &quot;A type modeling the weekdays in the Gregorian calendar.
         The numbering follows the ISO 8601 scheme.&quot;;
       reference
        &quot;ISO 8601:2004: Data elements and interchange formats --
                        Information interchange -- Representation
                        of dates and times&quot;;
     }

     typedef weekday-or-all {
       type union {
         type weekday;
         type wildcard;
       }
       description
         &quot;A weekday or a wildcard indicating all seven weekdays.&quot;;
     }

     typedef hour {
       type uint8 { range &quot;0..23&quot;; }
       description
         &quot;An hour of a day.&quot;;
     }

     typedef hour-or-all {
       type union {
         type hour;
         type wildcard;
       }
       description
         &quot;An hour of a day or a wildcard indicating all hours
          of a day.&quot;;
<span class="grey"><a href="/doc/html/rfc8194">RFC 8194</a>                YANG Data Model for LMAP             August 2017</span>

     }

     typedef minute {
       type uint8 { range &quot;0..59&quot;; }
       description
         &quot;A minute of an hour.&quot;;
     }

     typedef minute-or-all {
       type union {
         type minute;
         type wildcard;
       }
       description
         &quot;A minute of an hour or a wildcard indicating all
          minutes of an hour.&quot;;
     }

     typedef second {
       type uint8 { range &quot;0..59&quot;; }
       description
         &quot;A second of a minute.&quot;;
     }

     typedef second-or-all {
       type union {
         type second;
         type wildcard;
       }
       description
         &quot;A second of a minute or a wildcard indicating all
          seconds of a minute.&quot;;
     }

     typedef status-code {
       type int32;
       description
         &quot;A status code returned by the execution of a Task.  Note
          that the actual range is implementation dependent, but it
          should be portable to use values in the range 0..127 for
          regular exit codes.  By convention, 0 indicates successful
          termination.  Negative values may be used to indicate
          abnormal termination due to a signal; the absolute value
          may identify the signal number in this case.&quot;;
     }

<span class="grey"><a href="/doc/html/rfc8194">RFC 8194</a>                YANG Data Model for LMAP             August 2017</span>

     typedef timezone-offset {
       type string {
         pattern &#x27;Z|[\+\-]\d{2}:\d{2}&#x27;;
       }
       description
         &quot;A time zone offset as it is used by the date-and-time type
          defined in the ietf-yang-types module.  The value Z is
          equivalent to +00:00.  The value -00:00 indicates an
          unknown time-offset.&quot;;
       reference
         &quot;<a href="/doc/html/rfc6991">RFC 6991</a>: Common YANG Data Types&quot;;
     }

     /*
      * Groupings
      */

     grouping registry-grouping {
       description
         &quot;This grouping models a list of entries in a registry
          that identify functions of a Task.&quot;;

       list function {
         key uri;
         description
           &quot;A list of entries in a registry identifying functions.&quot;;

         leaf uri {
           type inet:uri;
           description
             &quot;A URI identifying an entry in a registry.&quot;;
         }

         leaf-list role {
           type string;
           description
             &quot;A set of roles for the identified registry entry.&quot;;
         }
       }
     }

     grouping options-grouping {
       description
         &quot;A list of options of a Task.  Each option is a name/value
          pair (where the value may be absent).&quot;;

       list option {
         key &quot;id&quot;;
<span class="grey"><a href="/doc/html/rfc8194">RFC 8194</a>                YANG Data Model for LMAP             August 2017</span>

         ordered-by user;
         description
           &quot;A list of options passed to the Task.  It is a list of
            key/value pairs and may be used to model options.
            Options may be used to identify the role of a Task
            or to pass a Channel name to a Task.&quot;;

         leaf id {
           type lmap:identifier;
           description
             &quot;An identifier uniquely identifying an option.  This
              identifier is required by YANG to uniquely identify
              a name/value pair, but it otherwise has no semantic
              value&quot;;
         }

         leaf name {
           type string;
           description
             &quot;The name of the option.&quot;;
         }

         leaf value {
           type string;
           description
             &quot;The value of the option.&quot;;
         }
       }
     }
   }
