module iana-routing-types {
  namespace &quot;urn:ietf:params:xml:ns:yang:iana-routing-types&quot;;
  prefix iana-rt-types;

  organization
    &quot;IANA&quot;;
  contact
    &quot;Internet Assigned Numbers Authority

     Postal: ICANN
             12025 Waterfront Drive, Suite 300
             Los Angeles, CA  90094-2536
             United States of America
     Tel:    +1 310 301 5800
     &lt;mailto:<a href="mailto:iana@iana.org">iana@iana.org</a>&gt;&quot;;

  description
    &quot;This module contains a collection of YANG data types
     considered defined by IANA and used for routing
     protocols.

     Copyright (c) 2017 IETF Trust and the persons
     identified as authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">https://trustee.ietf.org/license-info</a>).

     This version of this YANG module is part of <a href="/doc/html/rfc8294">RFC 8294</a>; see
     the RFC itself for full legal notices.&quot;;

   revision 2017-12-04 {
     description &quot;Initial revision.&quot;;
     reference
       &quot;<a href="/doc/html/rfc8294">RFC 8294</a>: Common YANG Data Types for the Routing Area.
        <a href="#section-4">Section 4</a>.&quot;;
  }

<span class="grey"><a href="/doc/html/rfc8294">RFC 8294</a>                 Routing Area YANG Types           December 2017</span>

     /*** Collection of IANA types related to routing ***/
     /*** IANA Address Family enumeration ***/

     typedef address-family {
       type enumeration {
         enum ipv4 {
           value 1;
           description
             &quot;IPv4 Address Family.&quot;;
         }

         enum ipv6 {
           value 2;
           description
             &quot;IPv6 Address Family.&quot;;
         }

         enum nsap {
           value 3;
           description
             &quot;OSI Network Service Access Point (NSAP) Address Family.&quot;;
         }

         enum hdlc {
           value 4;
           description
             &quot;High-Level Data Link Control (HDLC) Address Family.&quot;;
         }

         enum bbn1822 {
           value 5;
           description
             &quot;Bolt, Beranek, and Newman Report 1822 (BBN 1822)
              Address Family.&quot;;
         }

         enum ieee802 {
           value 6;
           description
             &quot;IEEE 802 Committee Address Family
              (aka Media Access Control (MAC) address).&quot;;
         }

         enum e163 {
           value 7;
           description
             &quot;ITU-T E.163 Address Family.&quot;;
         }
<span class="grey"><a href="/doc/html/rfc8294">RFC 8294</a>                 Routing Area YANG Types           December 2017</span>

         enum e164 {
           value 8;
           description
             &quot;ITU-T E.164 (Switched Multimegabit Data Service (SMDS),
              Frame Relay, ATM) Address Family.&quot;;
         }

         enum f69 {
           value 9;
           description
             &quot;ITU-T F.69 (Telex) Address Family.&quot;;
         }

         enum x121 {
           value 10;
           description
             &quot;ITU-T X.121 (X.25, Frame Relay) Address Family.&quot;;
         }

         enum ipx {
           value 11;
           description
             &quot;Novell Internetwork Packet Exchange (IPX)
              Address Family.&quot;;
         }

         enum appletalk {
           value 12;
           description
             &quot;Apple AppleTalk Address Family.&quot;;
         }

         enum decnet-iv {
           value 13;
           description
             &quot;Digital Equipment DECnet Phase IV Address Family.&quot;;
         }

         enum vines {
           value 14;
           description
             &quot;Banyan Vines Address Family.&quot;;
         }

<span class="grey"><a href="/doc/html/rfc8294">RFC 8294</a>                 Routing Area YANG Types           December 2017</span>

         enum e164-nsap {
           value 15;
           description
             &quot;ITU-T E.164 with NSAP sub-address Address Family.&quot;;
         }

         enum dns {
           value 16;
           description
             &quot;Domain Name System (DNS) Address Family.&quot;;
         }

         enum distinguished-name {
           value 17;
           description
             &quot;Distinguished Name Address Family.&quot;;
         }

         enum as-num {
           value 18;
           description
             &quot;Autonomous System (AS) Number Address Family.&quot;;
         }

         enum xtp-v4 {
           value 19;
           description
             &quot;Xpress Transport Protocol (XTP) over IPv4
              Address Family.&quot;;
         }

         enum xtp-v6 {
           value 20;
           description
             &quot;XTP over IPv6 Address Family.&quot;;
         }

         enum xtp-native {
           value 21;
           description
             &quot;XTP native mode Address Family.&quot;;
         }

         enum fc-port {
           value 22;
           description
             &quot;Fibre Channel (FC) World-Wide Port Name Address Family.&quot;;
         }
<span class="grey"><a href="/doc/html/rfc8294">RFC 8294</a>                 Routing Area YANG Types           December 2017</span>

         enum fc-node {
           value 23;
           description
             &quot;FC World-Wide Node Name Address Family.&quot;;
         }

         enum gwid {
           value 24;
           description
             &quot;ATM Gateway Identifier (GWID) Number Address Family.&quot;;
         }

         enum l2vpn {
           value 25;
           description
             &quot;Layer 2 VPN (L2VPN) Address Family.&quot;;
         }

         enum mpls-tp-section-eid {
           value 26;
           description
             &quot;MPLS Transport Profile (MPLS-TP) Section Endpoint
              Identifier Address Family.&quot;;
         }

         enum mpls-tp-lsp-eid {
           value 27;
           description
             &quot;MPLS-TP Label Switched Path (LSP) Endpoint Identifier
              Address Family.&quot;;
         }

         enum mpls-tp-pwe-eid {
           value 28;
           description
             &quot;MPLS-TP Pseudowire Endpoint Identifier Address Family.&quot;;
         }

         enum mt-v4 {
           value 29;
           description
             &quot;Multi-Topology IPv4 Address Family.&quot;;
         }

<span class="grey"><a href="/doc/html/rfc8294">RFC 8294</a>                 Routing Area YANG Types           December 2017</span>

         enum mt-v6 {
           value 30;
           description
             &quot;Multi-Topology IPv6 Address Family.&quot;;
         }

         enum eigrp-common-sf {
           value 16384;
           description
             &quot;Enhanced Interior Gateway Routing Protocol (EIGRP)
              Common Service Family Address Family.&quot;;
         }

         enum eigrp-v4-sf {
           value 16385;
           description
             &quot;EIGRP IPv4 Service Family Address Family.&quot;;
         }

         enum eigrp-v6-sf {
           value 16386;
           description
             &quot;EIGRP IPv6 Service Family Address Family.&quot;;
         }

         enum lcaf {
           value 16387;
           description
             &quot;Locator/ID Separation Protocol (LISP)
              Canonical Address Format (LCAF) Address Family.&quot;;
         }

         enum bgp-ls {
           value 16388;
           description
             &quot;Border Gateway Protocol - Link State (BGP-LS)
              Address Family.&quot;;
         }

         enum mac-48 {
           value 16389;
           description
             &quot;IEEE 48-bit MAC Address Family.&quot;;
         }

<span class="grey"><a href="/doc/html/rfc8294">RFC 8294</a>                 Routing Area YANG Types           December 2017</span>

         enum mac-64 {
           value 16390;
           description
             &quot;IEEE 64-bit MAC Address Family.&quot;;
         }

         enum trill-oui {
           value 16391;
           description
             &quot;Transparent Interconnection of Lots of Links (TRILL)
              IEEE Organizationally Unique Identifier (OUI)
              Address Family.&quot;;
         }

         enum trill-mac-24 {
           value 16392;
           description
             &quot;TRILL final 3 octets of 48-bit MAC Address Family.&quot;;
         }

         enum trill-mac-40 {
           value 16393;
           description
             &quot;TRILL final 5 octets of 64-bit MAC Address Family.&quot;;
         }

         enum ipv6-64 {
           value 16394;
           description
             &quot;First 8 octets (64 bits) of IPv6 address
              Address Family.&quot;;
         }

         enum trill-rbridge-port-id {
           value 16395;
           description
             &quot;TRILL Routing Bridge (RBridge) Port ID Address Family.&quot;;
         }

         enum trill-nickname {
           value 16396;
           description
             &quot;TRILL Nickname Address Family.&quot;;
         }
       }

<span class="grey"><a href="/doc/html/rfc8294">RFC 8294</a>                 Routing Area YANG Types           December 2017</span>

       description
         &quot;Enumeration containing all the IANA-defined
          Address Families.&quot;;

     }

     /*** Subsequent Address Family Identifiers (SAFIs) ***/
     /*** for multiprotocol BGP enumeration ***/

     typedef bgp-safi {
       type enumeration {
         enum unicast-safi {
           value 1;
           description
             &quot;Unicast SAFI.&quot;;
         }

         enum multicast-safi {
           value 2;
           description
             &quot;Multicast SAFI.&quot;;
         }

         enum labeled-unicast-safi {
           value 4;
           description
             &quot;Labeled Unicast SAFI.&quot;;
         }

         enum multicast-vpn-safi {
           value 5;
           description
             &quot;Multicast VPN SAFI.&quot;;
         }

         enum pseudowire-safi {
           value 6;
           description
             &quot;Multi-segment Pseudowire VPN SAFI.&quot;;
         }

         enum tunnel-encap-safi {
           value 7;
           description
             &quot;Tunnel Encap SAFI.&quot;;
         }

<span class="grey"><a href="/doc/html/rfc8294">RFC 8294</a>                 Routing Area YANG Types           December 2017</span>

         enum mcast-vpls-safi {
           value 8;
           description
             &quot;Multicast Virtual Private LAN Service (VPLS) SAFI.&quot;;
         }

         enum tunnel-safi {
           value 64;
           description
             &quot;Tunnel SAFI.&quot;;
         }

         enum vpls-safi {
           value 65;
           description
             &quot;VPLS SAFI.&quot;;
         }

         enum mdt-safi {
           value 66;
           description
             &quot;Multicast Distribution Tree (MDT) SAFI.&quot;;
         }

         enum v4-over-v6-safi {
           value 67;
           description
             &quot;IPv4 over IPv6 SAFI.&quot;;
         }

         enum v6-over-v4-safi {
           value 68;
           description
             &quot;IPv6 over IPv4 SAFI.&quot;;
         }

         enum l1-vpn-auto-discovery-safi {
           value 69;
           description
             &quot;Layer 1 VPN Auto-Discovery SAFI.&quot;;
         }

         enum evpn-safi {
           value 70;
           description
             &quot;Ethernet VPN (EVPN) SAFI.&quot;;
         }

<span class="grey"><a href="/doc/html/rfc8294">RFC 8294</a>                 Routing Area YANG Types           December 2017</span>

         enum bgp-ls-safi {
           value 71;
           description
             &quot;BGP-LS SAFI.&quot;;
         }

         enum bgp-ls-vpn-safi {
           value 72;
           description
             &quot;BGP-LS VPN SAFI.&quot;;
         }

         enum sr-te-safi {
           value 73;
           description
             &quot;Segment Routing - Traffic Engineering (SR-TE) SAFI.&quot;;
         }

         enum labeled-vpn-safi {
           value 128;
           description
             &quot;MPLS Labeled VPN SAFI.&quot;;
         }

         enum multicast-mpls-vpn-safi {
           value 129;
           description
             &quot;Multicast for BGP/MPLS IP VPN SAFI.&quot;;
         }

         enum route-target-safi {
           value 132;
           description
             &quot;Route Target SAFI.&quot;;
         }

         enum ipv4-flow-spec-safi {
           value 133;
           description
             &quot;IPv4 Flow Specification SAFI.&quot;;
         }

         enum vpnv4-flow-spec-safi {
           value 134;
           description
             &quot;IPv4 VPN Flow Specification SAFI.&quot;;
         }

<span class="grey"><a href="/doc/html/rfc8294">RFC 8294</a>                 Routing Area YANG Types           December 2017</span>

         enum vpn-auto-discovery-safi {
           value 140;
           description
             &quot;VPN Auto-Discovery SAFI.&quot;;
         }
       }
       description
         &quot;Enumeration for BGP SAFI.&quot;;
       reference
         &quot;<a href="/doc/html/rfc4760">RFC 4760</a>: Multiprotocol Extensions for BGP-4.&quot;;
     }
   }
