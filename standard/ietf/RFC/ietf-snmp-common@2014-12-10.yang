submodule ietf-snmp-common {

  belongs-to ietf-snmp {
    prefix snmp;
  }

  import ietf-yang-types {
    prefix yang;
  }

  organization
    &quot;IETF NETMOD (NETCONF Data Modeling Language) Working Group&quot;;

  contact
    &quot;WG Web:   &lt;<a href="https://tools.ietf.org/wg/netmod/">http://tools.ietf.org/wg/netmod/</a>&gt;
     WG List:  &lt;mailto:<a href="mailto:netmod@ietf.org">netmod@ietf.org</a>&gt;
<span class="grey"><a href="/doc/html/rfc7407">RFC 7407</a>         YANG Data Model for SNMP Configuration    December 2014</span>

        WG Chair: Thomas Nadeau
                  &lt;mailto:<a href="mailto:tnadeau@lucidvision.com">tnadeau@lucidvision.com</a>&gt;

        WG Chair: Juergen Schoenwaelder
                  &lt;mailto:<a href="mailto:j.schoenwaelder@jacobs-university.de">j.schoenwaelder@jacobs-university.de</a>&gt;

        Editor:   Martin Bjorklund
                  &lt;mailto:<a href="mailto:mbj@tail-f.com">mbj@tail-f.com</a>&gt;

        Editor:   Juergen Schoenwaelder
                  &lt;mailto:<a href="mailto:j.schoenwaelder@jacobs-university.de">j.schoenwaelder@jacobs-university.de</a>&gt;&quot;;

     description
       &quot;This submodule contains a collection of common YANG definitions
        for configuring SNMP engines.

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc7407">RFC 7407</a>; see
        the RFC itself for full legal notices.&quot;;

     revision 2014-12-10 {
       description
         &quot;Initial revision.&quot;;
       reference
         &quot;<a href="/doc/html/rfc7407">RFC 7407</a>: A YANG Data Model for SNMP Configuration&quot;;
     }

     /* Collection of SNMP-specific data types */

     typedef admin-string {
       type string {
         length &quot;0..255&quot;;
       }
       description
         &quot;Represents SnmpAdminString as defined in <a href="/doc/html/rfc3411">RFC 3411</a>.

         Note that the size of an SnmpAdminString is measured in
         octets, not characters.&quot;;

<span class="grey"><a href="/doc/html/rfc7407">RFC 7407</a>         YANG Data Model for SNMP Configuration    December 2014</span>

       reference
         &quot;<a href="/doc/html/rfc3411">RFC 3411</a>: An Architecture for Describing Simple Network
            Management Protocol (SNMP) Management Frameworks.
            SNMP-FRAMEWORK-MIB.SnmpAdminString&quot;;
     }

     typedef identifier {
       type admin-string {
         length &quot;1..32&quot;;
       }
       description
         &quot;Identifiers are used to name items in the SNMP configuration
         datastore.&quot;;
     }

     typedef context-name {
       type admin-string {
         length &quot;0..32&quot;;
       }
       description
         &quot;The context type represents an SNMP context name.&quot;;
       reference
         &quot;<a href="/doc/html/rfc3411">RFC 3411</a>: An Architecture for Describing Simple Network
            Management Protocol (SNMP) Management Frameworks&quot;;
     }

     typedef security-name {
       type admin-string {
         length &quot;1..32&quot;;
       }
       description
         &quot;The security-name type represents an SNMP security name.&quot;;
       reference
         &quot;<a href="/doc/html/rfc3411">RFC 3411</a>: An Architecture for Describing Simple Network
            Management Protocol (SNMP) Management Frameworks&quot;;
     }

     typedef security-model {
       type union {
         type enumeration {
           enum v1  { value 1; }
           enum v2c { value 2; }
           enum usm { value 3; }
           enum tsm { value 4; }
         }
         type int32 {
           range &quot;1..2147483647&quot;;
         }
<span class="grey"><a href="/doc/html/rfc7407">RFC 7407</a>         YANG Data Model for SNMP Configuration    December 2014</span>

       }
       reference
         &quot;<a href="/doc/html/rfc3411">RFC 3411</a>: An Architecture for Describing Simple Network
            Management Protocol (SNMP) Management Frameworks&quot;;
     }

     typedef security-model-or-any {
       type union {
         type enumeration {
           enum any { value 0; }
         }
         type security-model;
       }
       reference
         &quot;<a href="/doc/html/rfc3411">RFC 3411</a>: An Architecture for Describing Simple Network
            Management Protocol (SNMP) Management Frameworks&quot;;
     }

     typedef security-level {
       type enumeration {
         enum no-auth-no-priv { value 1; }
         enum auth-no-priv    { value 2; }
         enum auth-priv       { value 3; }
       }
       reference
         &quot;<a href="/doc/html/rfc3411">RFC 3411</a>: An Architecture for Describing Simple Network
            Management Protocol (SNMP) Management Frameworks&quot;;
     }

     typedef engine-id {
       type yang:hex-string {
         pattern &#x27;([0-9a-fA-F]){2}(:([0-9a-fA-F]){2}){4,31}&#x27;;
       }
       description
         &quot;The engine ID specified as a list of colon-specified
         hexadecimal octets, e.g., &#x27;80:00:02:b8:04:61:62:63&#x27;.&quot;;
       reference
         &quot;<a href="/doc/html/rfc3411">RFC 3411</a>: An Architecture for Describing Simple Network
            Management Protocol (SNMP) Management Frameworks&quot;;
     }

     typedef wildcard-object-identifier {
       type string;
       description
         &quot;The wildcard-object-identifier type represents an SNMP object
         identifier where subidentifiers can be given either as a label,
         in numeric form, or a wildcard, represented by an asterisk
         (&#x27;*&#x27;).&quot;;
<span class="grey"><a href="/doc/html/rfc7407">RFC 7407</a>         YANG Data Model for SNMP Configuration    December 2014</span>

     }

     typedef tag-value {
       type string {
         length &quot;0..255&quot;;
       }
       description
         &quot;Represents SnmpTagValue as defined in <a href="/doc/html/rfc3413">RFC 3413</a>.

         Note that the size of an SnmpTagValue is measured in
         octets, not characters.&quot;;
       reference
         &quot;<a href="/doc/html/rfc3413">RFC 3413</a>: Simple Network Management Protocol (SNMP)
            Applications.
            SNMP-TARGET-MIB.SnmpTagValue&quot;;
     }

     container snmp {
       description
         &quot;Top-level container for SNMP-related configuration and
         status objects.&quot;;
     }

   }
