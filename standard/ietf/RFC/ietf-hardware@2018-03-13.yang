module ietf-hardware {
  yang-version 1.1;
  namespace &quot;urn:ietf:params:xml:ns:yang:ietf-hardware&quot;;
  prefix hw;

  import ietf-inet-types {
    prefix inet;
  }
  import ietf-yang-types {
    prefix yang;
  }
  import iana-hardware {
    prefix ianahw;
  }

  organization
    &quot;IETF NETMOD (Network Modeling) Working Group&quot;;

  contact
    &quot;WG Web:   &lt;<a href="https://datatracker.ietf.org/wg/netmod/">https://datatracker.ietf.org/wg/netmod/</a>&gt;
     WG List:  &lt;mailto:<a href="mailto:netmod@ietf.org">netmod@ietf.org</a>&gt;

     Editor:   Andy Bierman
               &lt;mailto:<a href="mailto:andy@yumaworks.com">andy@yumaworks.com</a>&gt;

     Editor:   Martin Bjorklund
               &lt;mailto:<a href="mailto:mbj@tail-f.com">mbj@tail-f.com</a>&gt;

     Editor:   Jie Dong
               &lt;mailto:<a href="mailto:jie.dong@huawei.com">jie.dong@huawei.com</a>&gt;

     Editor:   Dan Romascanu
               &lt;mailto:<a href="mailto:dromasca@gmail.com">dromasca@gmail.com</a>&gt;&quot;;

  description
    &quot;This module contains a collection of YANG definitions for
     managing hardware.

     This data model is designed for the Network Management Datastore
     Architecture (NMDA) defined in <a href="/doc/html/rfc8342">RFC 8342</a>.
<span class="grey"><a href="/doc/html/rfc8348">RFC 8348</a>                YANG Hardware Management              March 2018</span>

       Copyright (c) 2018 IETF Trust and the persons identified as
       authors of the code.  All rights reserved.

       Redistribution and use in source and binary forms, with or
       without modification, is permitted pursuant to, and subject
       to the license terms contained in, the Simplified BSD License
       set forth in <a href="#section-4">Section 4</a>.c of the IETF Trust&#x27;s Legal Provisions
       Relating to IETF Documents
       (<a href="https://trustee.ietf.org/license-info">https://trustee.ietf.org/license-info</a>).

       This version of this YANG module is part of <a href="/doc/html/rfc8348">RFC 8348</a>; see
       the RFC itself for full legal notices.&quot;;

    revision 2018-03-13 {
      description
        &quot;Initial revision.&quot;;
      reference
        &quot;<a href="/doc/html/rfc8348">RFC 8348</a>: A YANG Data Model for Hardware Management&quot;;
    }

    /*
     * Features
     */

    feature entity-mib {
      description
        &quot;This feature indicates that the device implements
         the ENTITY-MIB.&quot;;
      reference
        &quot;<a href="/doc/html/rfc6933">RFC 6933</a>: Entity MIB (Version 4)&quot;;
    }

    feature hardware-state {
      description
        &quot;Indicates that ENTITY-STATE-MIB objects are supported&quot;;
      reference
        &quot;<a href="/doc/html/rfc4268">RFC 4268</a>: Entity State MIB&quot;;
    }

    feature hardware-sensor {
      description
        &quot;Indicates that ENTITY-SENSOR-MIB objects are supported&quot;;
      reference
        &quot;<a href="/doc/html/rfc3433">RFC 3433</a>: Entity Sensor Management Information Base&quot;;
    }

    /*
     * Typedefs
<span class="grey"><a href="/doc/html/rfc8348">RFC 8348</a>                YANG Hardware Management              March 2018</span>

     */

    typedef admin-state {
      type enumeration {
        enum unknown {
          value 1;
          description
            &quot;The resource is unable to report administrative state.&quot;;
        }
        enum locked {
          value 2;
          description
            &quot;The resource is administratively prohibited from use.&quot;;
        }
        enum shutting-down {
          value 3;
          description
            &quot;The resource usage is administratively limited to current
             instances of use.&quot;;
        }
        enum unlocked {
          value 4;
          description
            &quot;The resource is not administratively prohibited from
             use.&quot;;
        }
      }
      description
        &quot;Represents the various possible administrative states.&quot;;
      reference
        &quot;<a href="/doc/html/rfc4268">RFC 4268</a>: Entity State MIB - EntityAdminState&quot;;
    }

    typedef oper-state {
      type enumeration {
        enum unknown {
          value 1;
          description
            &quot;The resource is unable to report its operational state.&quot;;
        }
        enum disabled {
          value 2;
          description
            &quot;The resource is totally inoperable.&quot;;
        }
        enum enabled {
          value 3;

<span class="grey"><a href="/doc/html/rfc8348">RFC 8348</a>                YANG Hardware Management              March 2018</span>

          description
            &quot;The resource is partially or fully operable.&quot;;
        }
        enum testing {
          value 4;
          description
            &quot;The resource is currently being tested and cannot
             therefore report whether or not it is operational.&quot;;
        }
      }
      description
        &quot;Represents the possible values of operational states.&quot;;
      reference
        &quot;<a href="/doc/html/rfc4268">RFC 4268</a>: Entity State MIB - EntityOperState&quot;;
    }

    typedef usage-state {
      type enumeration {
        enum unknown {
          value 1;
          description
            &quot;The resource is unable to report usage state.&quot;;
        }
        enum idle {
          value 2;
          description
            &quot;The resource is servicing no users.&quot;;
        }
        enum active {
          value 3;
          description
            &quot;The resource is currently in use, and it has sufficient
             spare capacity to provide for additional users.&quot;;
        }
        enum busy {
          value 4;
          description
            &quot;The resource is currently in use, but it currently has no
             spare capacity to provide for additional users.&quot;;
        }
      }
      description
        &quot;Represents the possible values of usage states.&quot;;
      reference
        &quot;<a href="/doc/html/rfc4268">RFC 4268</a>: Entity State MIB -  EntityUsageState&quot;;
    }

    typedef alarm-state {
<span class="grey"><a href="/doc/html/rfc8348">RFC 8348</a>                YANG Hardware Management              March 2018</span>

      type bits {
        bit unknown {
          position 0;
          description
            &quot;The resource is unable to report alarm state.&quot;;
        }
        bit under-repair {
          position 1;
          description
            &quot;The resource is currently being repaired, which, depending
             on the implementation, may make the other values in this
             bit string not meaningful.&quot;;
        }
        bit critical {
          position 2;
          description
            &quot;One or more critical alarms are active against the
             resource.&quot;;
        }
        bit major {
          position 3;
          description
            &quot;One or more major alarms are active against the
             resource.&quot;;
        }
        bit minor {
          position 4;
          description
            &quot;One or more minor alarms are active against the
             resource.&quot;;
        }
        bit warning {
          position 5;
          description
            &quot;One or more warning alarms are active against the
             resource.&quot;;
        }
        bit indeterminate {
          position 6;
          description
            &quot;One or more alarms of whose perceived severity cannot be
             determined are active against this resource.&quot;;
        }
      }
      description
        &quot;Represents the possible values of alarm states.  An alarm is a
         persistent indication of an error or warning condition.

<span class="grey"><a href="/doc/html/rfc8348">RFC 8348</a>                YANG Hardware Management              March 2018</span>

         When no bits of this attribute are set, then no active alarms
         are known against this component and it is not under repair.&quot;;
      reference
        &quot;<a href="/doc/html/rfc4268">RFC 4268</a>: Entity State MIB - EntityAlarmStatus&quot;;
    }

    typedef standby-state {
      type enumeration {
        enum unknown {
          value 1;
          description
            &quot;The resource is unable to report standby state.&quot;;
        }
        enum hot-standby {
          value 2;
          description
            &quot;The resource is not providing service, but it will be
             immediately able to take over the role of the resource to
             be backed up, without the need for initialization
             activity, and will contain the same information as the
             resource to be backed up.&quot;;
        }
        enum cold-standby {
          value 3;
          description
            &quot;The resource is to back up another resource, but it will
             not be immediately able to take over the role of a
             resource to be backed up and will require some
             initialization activity.&quot;;
        }
        enum providing-service {
          value 4;
          description
            &quot;The resource is providing service.&quot;;
        }
      }
      description
        &quot;Represents the possible values of standby states.&quot;;
      reference
        &quot;<a href="/doc/html/rfc4268">RFC 4268</a>: Entity State MIB - EntityStandbyStatus&quot;;
    }

    typedef sensor-value-type {
      type enumeration {
        enum other {
          value 1;
          description
            &quot;A measure other than those listed below.&quot;;
<span class="grey"><a href="/doc/html/rfc8348">RFC 8348</a>                YANG Hardware Management              March 2018</span>

        }
        enum unknown {
          value 2;
          description
            &quot;An unknown measurement or arbitrary, relative numbers&quot;;
        }
        enum volts-AC {
          value 3;
          description
            &quot;A measure of electric potential (alternating current).&quot;;
        }
        enum volts-DC {
          value 4;
          description
            &quot;A measure of electric potential (direct current).&quot;;
        }
        enum amperes {
          value 5;
          description
            &quot;A measure of electric current.&quot;;
        }
        enum watts {
          value 6;
          description
            &quot;A measure of power.&quot;;
        }
        enum hertz {
          value 7;
          description
            &quot;A measure of frequency.&quot;;
        }
        enum celsius {
          value 8;
          description
            &quot;A measure of temperature.&quot;;
        }
        enum percent-RH {
          value 9;
          description
            &quot;A measure of percent relative humidity.&quot;;
        }
        enum rpm {
          value 10;
          description
            &quot;A measure of shaft revolutions per minute.&quot;;
        }
        enum cmm {
          value 11;
<span class="grey"><a href="/doc/html/rfc8348">RFC 8348</a>                YANG Hardware Management              March 2018</span>

          description
            &quot;A measure of cubic meters per minute (airflow).&quot;;
        }
        enum truth-value {
          value 12;
          description
            &quot;Value is one of 1 (true) or 2 (false)&quot;;
        }
      }
      description
        &quot;A node using this data type represents the sensor measurement
         data type associated with a physical sensor value.  The actual
         data units are determined by examining a node of this type
         together with the associated sensor-value-scale node.

         A node of this type SHOULD be defined together with nodes of
         type sensor-value-scale and type sensor-value-precision.
         These three types are used to identify the semantics of a node
         of type sensor-value.&quot;;
      reference
        &quot;<a href="/doc/html/rfc3433">RFC 3433</a>: Entity Sensor Management Information Base -
                   EntitySensorDataType&quot;;
    }

    typedef sensor-value-scale {
      type enumeration {
        enum yocto {
          value 1;
          description
            &quot;Data scaling factor of 10^-24.&quot;;
        }
        enum zepto {
          value 2;
          description
            &quot;Data scaling factor of 10^-21.&quot;;
        }
        enum atto {
          value 3;
          description
            &quot;Data scaling factor of 10^-18.&quot;;
        }
        enum femto {
          value 4;
          description
            &quot;Data scaling factor of 10^-15.&quot;;
        }
        enum pico {
          value 5;
<span class="grey"><a href="/doc/html/rfc8348">RFC 8348</a>                YANG Hardware Management              March 2018</span>

          description
            &quot;Data scaling factor of 10^-12.&quot;;
        }
        enum nano {
          value 6;
          description
            &quot;Data scaling factor of 10^-9.&quot;;
        }
        enum micro {
          value 7;
          description
            &quot;Data scaling factor of 10^-6.&quot;;
        }
        enum milli {
          value 8;
          description
            &quot;Data scaling factor of 10^-3.&quot;;
        }
        enum units {
          value 9;
          description
            &quot;Data scaling factor of 10^0.&quot;;
        }
        enum kilo {
          value 10;
          description
            &quot;Data scaling factor of 10^3.&quot;;
        }
        enum mega {
          value 11;
          description
            &quot;Data scaling factor of 10^6.&quot;;
        }
        enum giga {
          value 12;
          description
            &quot;Data scaling factor of 10^9.&quot;;
        }
        enum tera {
          value 13;
          description
            &quot;Data scaling factor of 10^12.&quot;;
        }
        enum peta {
          value 14;
          description
            &quot;Data scaling factor of 10^15.&quot;;
        }
<span class="grey"><a href="/doc/html/rfc8348">RFC 8348</a>                YANG Hardware Management              March 2018</span>

        enum exa {
          value 15;
          description
            &quot;Data scaling factor of 10^18.&quot;;
        }
        enum zetta {
          value 16;
          description
            &quot;Data scaling factor of 10^21.&quot;;
        }
        enum yotta {
          value 17;
          description
            &quot;Data scaling factor of 10^24.&quot;;
        }
      }
      description
        &quot;A node using this data type represents a data scaling factor,
         represented with an International System of Units (SI) prefix.
         The actual data units are determined by examining a node of
         this type together with the associated sensor-value-type.

         A node of this type SHOULD be defined together with nodes of
         type sensor-value-type and type sensor-value-precision.
         Together, associated nodes of these three types are used to
         identify the semantics of a node of type sensor-value.&quot;;
      reference
        &quot;<a href="/doc/html/rfc3433">RFC 3433</a>: Entity Sensor Management Information Base -
                   EntitySensorDataScale&quot;;
    }

    typedef sensor-value-precision {
      type int8 {
        range &quot;-8 .. 9&quot;;
      }
      description
        &quot;A node using this data type represents a sensor value
         precision range.

         A node of this type SHOULD be defined together with nodes of
         type sensor-value-type and type sensor-value-scale.  Together,
         associated nodes of these three types are used to identify the
         semantics of a node of type sensor-value.

         If a node of this type contains a value in the range 1 to 9,
         it represents the number of decimal places in the fractional
         part of an associated sensor-value fixed-point number.

<span class="grey"><a href="/doc/html/rfc8348">RFC 8348</a>                YANG Hardware Management              March 2018</span>

         If a node of this type contains a value in the range -8 to -1,
         it represents the number of accurate digits in the associated
         sensor-value fixed-point number.

         The value zero indicates the associated sensor-value node is
         not a fixed-point number.

         Server implementers must choose a value for the associated
         sensor-value-precision node so that the precision and accuracy
         of the associated sensor-value node is correctly indicated.

         For example, a component representing a temperature sensor
         that can measure 0 to 100 degrees C in 0.1 degree
         increments, +/- 0.05 degrees, would have a
         sensor-value-precision value of &#x27;1&#x27;, a sensor-value-scale
         value of &#x27;units&#x27;, and a sensor-value ranging from &#x27;0&#x27; to
         &#x27;1000&#x27;.  The sensor-value would be interpreted as
         &#x27;degrees C * 10&#x27;.&quot;;
      reference
        &quot;<a href="/doc/html/rfc3433">RFC 3433</a>: Entity Sensor Management Information Base -
                   EntitySensorPrecision&quot;;
    }

    typedef sensor-value {
      type int32 {
        range &quot;-1000000000 .. 1000000000&quot;;
      }
      description
       &quot;A node using this data type represents a sensor value.

        A node of this type SHOULD be defined together with nodes of
        type sensor-value-type, type sensor-value-scale, and
        type sensor-value-precision.  Together, associated nodes of
        those three types are used to identify the semantics of a node
        of this data type.

        The semantics of a node using this data type are determined by
        the value of the associated sensor-value-type node.

        If the associated sensor-value-type node is equal to &#x27;voltsAC&#x27;,
        &#x27;voltsDC&#x27;, &#x27;amperes&#x27;, &#x27;watts&#x27;, &#x27;hertz&#x27;, &#x27;celsius&#x27;, or &#x27;cmm&#x27;,
        then a node of this type MUST contain a fixed-point number
        ranging from -999,999,999 to +999,999,999.  The value
        -1000000000 indicates an underflow error.  The value
        +1000000000 indicates an overflow error.  The
        sensor-value-precision indicates how many fractional digits
        are represented in the associated sensor-value node.

<span class="grey"><a href="/doc/html/rfc8348">RFC 8348</a>                YANG Hardware Management              March 2018</span>

        If the associated sensor-value-type node is equal to
        &#x27;percentRH&#x27;, then a node of this type MUST contain a number
        ranging from 0 to 100.

        If the associated sensor-value-type node is equal to &#x27;rpm&#x27;,
        then a node of this type MUST contain a number ranging from
        -999,999,999 to +999,999,999.

        If the associated sensor-value-type node is equal to
        &#x27;truth-value&#x27;, then a node of this type MUST contain either the
        value 1 (true) or the value 2 (false).

        If the associated sensor-value-type node is equal to &#x27;other&#x27; or
        &#x27;unknown&#x27;, then a node of this type MUST contain a number
        ranging from -1000000000 to 1000000000.&quot;;
      reference
        &quot;<a href="/doc/html/rfc3433">RFC 3433</a>: Entity Sensor Management Information Base -
                   EntitySensorValue&quot;;
    }

    typedef sensor-status {
      type enumeration {
        enum ok {
          value 1;
          description
            &quot;Indicates that the server can obtain the sensor value.&quot;;
        }
        enum unavailable {
          value 2;
          description
            &quot;Indicates that the server presently cannot obtain the
             sensor value.&quot;;
        }
        enum nonoperational {
          value 3;
          description
            &quot;Indicates that the server believes the sensor is broken.
             The sensor could have a hard failure (disconnected wire)
             or a soft failure such as out-of-range, jittery, or wildly
             fluctuating readings.&quot;;
        }
      }
      description
        &quot;A node using this data type represents the operational status
         of a physical sensor.&quot;;
      reference
        &quot;<a href="/doc/html/rfc3433">RFC 3433</a>: Entity Sensor Management Information Base -
                   EntitySensorStatus&quot;;
<span class="grey"><a href="/doc/html/rfc8348">RFC 8348</a>                YANG Hardware Management              March 2018</span>

    }

    /*
     * Data nodes
     */

    container hardware {
      description
        &quot;Data nodes representing components.

         If the server supports configuration of hardware components,
         then this data model is instantiated in the configuration
         datastores supported by the server.  The leaf-list &#x27;datastore&#x27;
         for the module &#x27;ietf-hardware&#x27; in the YANG library provides
         this information.&quot;;

      leaf last-change {
        type yang:date-and-time;
        config false;
        description
          &quot;The time the &#x27;/hardware/component&#x27; list changed in the
           operational state.&quot;;
      }

      list component {
        key name;
        description
          &quot;List of components.

           When the server detects a new hardware component, it
           initializes a list entry in the operational state.

           If the server does not support configuration of hardware
           components, list entries in the operational state are
           initialized with values for all nodes as detected by the
           implementation.

           Otherwise, this procedure is followed:

             1. If there is an entry in the &#x27;/hardware/component&#x27; list
                in the intended configuration with values for the nodes
                &#x27;class&#x27;, &#x27;parent&#x27;, and &#x27;parent-rel-pos&#x27; that are equal
                to the detected values, then the list entry in the
                operational state is initialized with the configured
                values, including the &#x27;name&#x27;.

<span class="grey"><a href="/doc/html/rfc8348">RFC 8348</a>                YANG Hardware Management              March 2018</span>

             2. Otherwise (i.e., there is no matching configuration
                entry), the list entry in the operational state is
                initialized with values for all nodes as detected by
                the implementation.

           If the &#x27;/hardware/component&#x27; list in the intended
           configuration is modified, then the system MUST behave as if
           it re-initializes itself and follow the procedure in (1).&quot;;
        reference
          &quot;<a href="/doc/html/rfc6933">RFC 6933</a>: Entity MIB (Version 4) - entPhysicalEntry&quot;;

        leaf name {
          type string;
          description
            &quot;The name assigned to this component.

             This name is not required to be the same as
             entPhysicalName.&quot;;
        }

        leaf class {
          type identityref {
            base ianahw:hardware-class;
          }
          mandatory true;
          description
            &quot;An indication of the general hardware type of the
             component.&quot;;
          reference
            &quot;<a href="/doc/html/rfc6933">RFC 6933</a>: Entity MIB (Version 4) - entPhysicalClass&quot;;
        }

        leaf physical-index {
          if-feature entity-mib;
          type int32 {
            range &quot;1..2147483647&quot;;
          }
          config false;
          description
            &quot;The entPhysicalIndex for the entPhysicalEntry represented
             by this list entry.&quot;;
          reference
            &quot;<a href="/doc/html/rfc6933">RFC 6933</a>: Entity MIB (Version 4) - entPhysicalIndex&quot;;
        }

        leaf description {
          type string;
          config false;
<span class="grey"><a href="/doc/html/rfc8348">RFC 8348</a>                YANG Hardware Management              March 2018</span>

          description
            &quot;A textual description of the component.  This node should
             contain a string that identifies the manufacturer&#x27;s name
             for the component and should be set to a distinct value
             for each version or model of the component.&quot;;
          reference
            &quot;<a href="/doc/html/rfc6933">RFC 6933</a>: Entity MIB (Version 4) - entPhysicalDescr&quot;;
        }

        leaf parent {
          type leafref {
            path &quot;../../component/name&quot;;
            require-instance false;
          }
          description
            &quot;The name of the component that physically contains this
             component.

             If this leaf is not instantiated, it indicates that this
             component is not contained in any other component.

             In the event that a physical component is contained by
             more than one physical component (e.g., double-wide
             modules), this node contains the name of one of these
             components.  An implementation MUST use the same name
             every time this node is instantiated.&quot;;
          reference
            &quot;<a href="/doc/html/rfc6933">RFC 6933</a>: Entity MIB (Version 4) - entPhysicalContainedIn&quot;;
        }

        leaf parent-rel-pos {
          type int32 {
            range &quot;0 .. 2147483647&quot;;
          }
          description
            &quot;An indication of the relative position of this child
             component among all its sibling components.  Sibling
             components are defined as components that:

               o share the same value of the &#x27;parent&#x27; node and

               o share a common base identity for the &#x27;class&#x27; node.

             Note that the last rule gives implementations flexibility
             in how components are numbered.  For example, some
             implementations might have a single number series for all
             components derived from &#x27;ianahw:port&#x27;, while some others
             might have different number series for different
<span class="grey"><a href="/doc/html/rfc8348">RFC 8348</a>                YANG Hardware Management              March 2018</span>

             components with identities derived from &#x27;ianahw:port&#x27; (for
             example, one for registered jack 45 (RJ45) and one for
             small form-factor pluggable (SFP)).&quot;;

          reference
            &quot;<a href="/doc/html/rfc6933">RFC 6933</a>: Entity MIB (Version 4) -
                       entPhysicalParentRelPos&quot;;
        }

        leaf-list contains-child {
          type leafref {
            path &quot;../../component/name&quot;;
          }
          config false;
          description
            &quot;The name of the contained component.&quot;;
          reference
            &quot;<a href="/doc/html/rfc6933">RFC 6933</a>: Entity MIB (Version 4) - entPhysicalChildIndex&quot;;
        }

        leaf hardware-rev {
          type string;
          config false;
          description
            &quot;The vendor-specific hardware revision string for the
             component.  The preferred value is the hardware revision
             identifier actually printed on the component itself (if
             present).&quot;;
          reference
            &quot;<a href="/doc/html/rfc6933">RFC 6933</a>: Entity MIB (Version 4) -
                       entPhysicalHardwareRev&quot;;
        }

        leaf firmware-rev {
          type string;
          config false;
          description
            &quot;The vendor-specific firmware revision string for the
             component.&quot;;
          reference
            &quot;<a href="/doc/html/rfc6933">RFC 6933</a>: Entity MIB (Version 4) -
                       entPhysicalFirmwareRev&quot;;
        }

        leaf software-rev {
          type string;
          config false;

<span class="grey"><a href="/doc/html/rfc8348">RFC 8348</a>                YANG Hardware Management              March 2018</span>

          description
            &quot;The vendor-specific software revision string for the
             component.&quot;;
          reference
            &quot;<a href="/doc/html/rfc6933">RFC 6933</a>: Entity MIB (Version 4) -
                       entPhysicalSoftwareRev&quot;;
        }

        leaf serial-num {
          type string;
          config false;
          description
            &quot;The vendor-specific serial number string for the
             component.  The preferred value is the serial number
             string actually printed on the component itself (if
             present).&quot;;
          reference
            &quot;<a href="/doc/html/rfc6933">RFC 6933</a>: Entity MIB (Version 4) - entPhysicalSerialNum&quot;;
        }

        leaf mfg-name {
          type string;
          config false;
          description
            &quot;The name of the manufacturer of this physical component.
             The preferred value is the manufacturer name string
             actually printed on the component itself (if present).

             Note that comparisons between instances of the
             &#x27;model-name&#x27;, &#x27;firmware-rev&#x27;, &#x27;software-rev&#x27;, and
             &#x27;serial-num&#x27; nodes are only meaningful amongst components
             with the same value of &#x27;mfg-name&#x27;.

             If the manufacturer name string associated with the
             physical component is unknown to the server, then this
             node is not instantiated.&quot;;
          reference
            &quot;<a href="/doc/html/rfc6933">RFC 6933</a>: Entity MIB (Version 4) - entPhysicalMfgName&quot;;
        }

        leaf model-name {
          type string;
          config false;
          description
            &quot;The vendor-specific model name identifier string
             associated with this physical component.  The preferred
             value is the customer-visible part number, which may be
             printed on the component itself.
<span class="grey"><a href="/doc/html/rfc8348">RFC 8348</a>                YANG Hardware Management              March 2018</span>

             If the model name string associated with the physical
             component is unknown to the server, then this node is not
             instantiated.&quot;;
          reference
            &quot;<a href="/doc/html/rfc6933">RFC 6933</a>: Entity MIB (Version 4) - entPhysicalModelName&quot;;
        }

        leaf alias {
          type string;
          description
            &quot;An &#x27;alias&#x27; name for the component, as specified by a
             network manager, that provides a non-volatile &#x27;handle&#x27; for
             the component.

             If no configured value exists, the server MAY set the
             value of this node to a locally unique value in the
             operational state.

             A server implementation MAY map this leaf to the
             entPhysicalAlias MIB object.  Such an implementation needs
             to use some mechanism to handle the differences in size
             and characters allowed between this leaf and
             entPhysicalAlias.  The definition of such a mechanism is
             outside the scope of this document.&quot;;
          reference
            &quot;<a href="/doc/html/rfc6933">RFC 6933</a>: Entity MIB (Version 4) - entPhysicalAlias&quot;;
        }

        leaf asset-id {
          type string;
          description
            &quot;This node is a user-assigned asset tracking identifier for
             the component.

             A server implementation MAY map this leaf to the
             entPhysicalAssetID MIB object.  Such an implementation
             needs to use some mechanism to handle the differences in
             size and characters allowed between this leaf and
             entPhysicalAssetID.  The definition of such a mechanism is
             outside the scope of this document.&quot;;
          reference
            &quot;<a href="/doc/html/rfc6933">RFC 6933</a>: Entity MIB (Version 4) - entPhysicalAssetID&quot;;
        }

        leaf is-fru {
          type boolean;
          config false;

<span class="grey"><a href="/doc/html/rfc8348">RFC 8348</a>                YANG Hardware Management              March 2018</span>

          description
            &quot;This node indicates whether or not this component is
             considered a &#x27;field-replaceable unit&#x27; by the vendor.  If
             this node contains the value &#x27;true&#x27;, then this component
             identifies a field-replaceable unit.  For all components
             that are permanently contained within a field-replaceable
             unit, the value &#x27;false&#x27; should be returned for this
             node.&quot;;
          reference
            &quot;<a href="/doc/html/rfc6933">RFC 6933</a>: Entity MIB (Version 4) - entPhysicalIsFRU&quot;;
        }

        leaf mfg-date {
          type yang:date-and-time;
          config false;
          description
            &quot;The date of manufacturing of the managed component.&quot;;
          reference
            &quot;<a href="/doc/html/rfc6933">RFC 6933</a>: Entity MIB (Version 4) - entPhysicalMfgDate&quot;;
        }

        leaf-list uri {
          type inet:uri;
          description
            &quot;This node contains identification information about the
             component.&quot;;
          reference
            &quot;<a href="/doc/html/rfc6933">RFC 6933</a>: Entity MIB (Version 4) - entPhysicalUris&quot;;
        }

        leaf uuid {
          type yang:uuid;
          config false;
          description
            &quot;A Universally Unique Identifier of the component.&quot;;
          reference
            &quot;<a href="/doc/html/rfc6933">RFC 6933</a>: Entity MIB (Version 4) - entPhysicalUUID&quot;;
        }

        container state {
          if-feature hardware-state;
          description
            &quot;State-related nodes&quot;;
          reference
            &quot;<a href="/doc/html/rfc4268">RFC 4268</a>: Entity State MIB&quot;;

          leaf state-last-changed {
            type yang:date-and-time;
<span class="grey"><a href="/doc/html/rfc8348">RFC 8348</a>                YANG Hardware Management              March 2018</span>

            config false;
            description
              &quot;The date and time when the value of any of the
               admin-state, oper-state, usage-state, alarm-state, or
               standby-state changed for this component.

               If there has been no change since the last
               re-initialization of the local system, this node
               contains the date and time of local system
               initialization.  If there has been no change since the
               component was added to the local system, this node
               contains the date and time of the insertion.&quot;;
            reference
              &quot;<a href="/doc/html/rfc4268">RFC 4268</a>: Entity State MIB - entStateLastChanged&quot;;
          }

          leaf admin-state {
            type admin-state;
            description
              &quot;The administrative state for this component.

               This node refers to a component&#x27;s administrative
               permission to service both other components within its
               containment hierarchy as well other users of its
               services defined by means outside the scope of this
               module.

               Some components exhibit only a subset of the remaining
               administrative state values.  Some components cannot be
               locked; hence, this node exhibits only the &#x27;unlocked&#x27;
               state.  Other components cannot be shut down gracefully;
               hence, this node does not exhibit the &#x27;shutting-down&#x27;
               state.&quot;;
            reference
              &quot;<a href="/doc/html/rfc4268">RFC 4268</a>: Entity State MIB - entStateAdmin&quot;;
          }

          leaf oper-state {
            type oper-state;
            config false;
            description
              &quot;The operational state for this component.

               Note that this node does not follow the administrative
               state.  An administrative state of &#x27;down&#x27; does not
               predict an operational state of &#x27;disabled&#x27;.

<span class="grey"><a href="/doc/html/rfc8348">RFC 8348</a>                YANG Hardware Management              March 2018</span>

               Note that some implementations may not be able to
               accurately report oper-state while the admin-state node
               has a value other than &#x27;unlocked&#x27;.  In these cases, this
               node MUST have a value of &#x27;unknown&#x27;.&quot;;
            reference
              &quot;<a href="/doc/html/rfc4268">RFC 4268</a>: Entity State MIB - entStateOper&quot;;
          }

          leaf usage-state {
            type usage-state;
            config false;
            description
              &quot;The usage state for this component.

               This node refers to a component&#x27;s ability to service
               more components in a containment hierarchy.

               Some components will exhibit only a subset of the usage
               state values.  Components that are unable to ever
               service any components within a containment hierarchy
               will always have a usage state of &#x27;busy&#x27;.  In some
               cases, a component will be able to support only one
               other component within its containment hierarchy and
               will therefore only exhibit values of &#x27;idle&#x27; and
               &#x27;busy&#x27;.&quot;;
            reference
              &quot;<a href="/doc/html/rfc4268">RFC 4268</a>: Entity State MIB - entStateUsage&quot;;
          }

          leaf alarm-state {
            type alarm-state;
            config false;
            description
              &quot;The alarm state for this component.  It does not
               include the alarms raised on child components within its
               containment hierarchy.&quot;;
            reference
              &quot;<a href="/doc/html/rfc4268">RFC 4268</a>: Entity State MIB - entStateAlarm&quot;;
          }

          leaf standby-state {
            type standby-state;
            config false;
            description
              &quot;The standby state for this component.

<span class="grey"><a href="/doc/html/rfc8348">RFC 8348</a>                YANG Hardware Management              March 2018</span>

               Some components will exhibit only a subset of the
               remaining standby state values.  If this component
               cannot operate in a standby role, the value of this node
               will always be &#x27;providing-service&#x27;.&quot;;
            reference
              &quot;<a href="/doc/html/rfc4268">RFC 4268</a>: Entity State MIB - entStateStandby&quot;;
          }
        }

        container sensor-data {
          when &#x27;derived-from-or-self(../class,
                                     &quot;ianahw:sensor&quot;)&#x27; {
            description
              &quot;Sensor data nodes present for any component of type
               &#x27;sensor&#x27;&quot;;
          }
          if-feature hardware-sensor;
          config false;

          description
            &quot;Sensor-related nodes.&quot;;
          reference
            &quot;<a href="/doc/html/rfc3433">RFC 3433</a>: Entity Sensor Management Information Base&quot;;

          leaf value {
            type sensor-value;
            description
              &quot;The most recent measurement obtained by the server
               for this sensor.

               A client that periodically fetches this node should also
               fetch the nodes &#x27;value-type&#x27;, &#x27;value-scale&#x27;, and
               &#x27;value-precision&#x27;, since they may change when the value
               is changed.&quot;;
            reference
              &quot;<a href="/doc/html/rfc3433">RFC 3433</a>: Entity Sensor Management Information Base -
                         entPhySensorValue&quot;;
          }

          leaf value-type {
            type sensor-value-type;
            description
              &quot;The type of data units associated with the
               sensor value&quot;;
            reference
              &quot;<a href="/doc/html/rfc3433">RFC 3433</a>: Entity Sensor Management Information Base -
                         entPhySensorType&quot;;
          }
<span class="grey"><a href="/doc/html/rfc8348">RFC 8348</a>                YANG Hardware Management              March 2018</span>

          leaf value-scale {
            type sensor-value-scale;
            description
              &quot;The (power of 10) scaling factor associated
               with the sensor value&quot;;
            reference
              &quot;<a href="/doc/html/rfc3433">RFC 3433</a>: Entity Sensor Management Information Base -
                         entPhySensorScale&quot;;
          }

          leaf value-precision {
            type sensor-value-precision;
            description
              &quot;The number of decimal places of precision
               associated with the sensor value&quot;;
            reference
              &quot;<a href="/doc/html/rfc3433">RFC 3433</a>: Entity Sensor Management Information Base -
                         entPhySensorPrecision&quot;;
          }

          leaf oper-status {
            type sensor-status;
            description
              &quot;The operational status of the sensor.&quot;;
            reference
              &quot;<a href="/doc/html/rfc3433">RFC 3433</a>: Entity Sensor Management Information Base -
                         entPhySensorOperStatus&quot;;
          }

          leaf units-display {
            type string;
            description
              &quot;A textual description of the data units that should be
               used in the display of the sensor value.&quot;;
            reference
              &quot;<a href="/doc/html/rfc3433">RFC 3433</a>: Entity Sensor Management Information Base -
                         entPhySensorUnitsDisplay&quot;;
          }

          leaf value-timestamp {
            type yang:date-and-time;
            description
              &quot;The time the status and/or value of this sensor was last
               obtained by the server.&quot;;
            reference
              &quot;<a href="/doc/html/rfc3433">RFC 3433</a>: Entity Sensor Management Information Base -
                         entPhySensorValueTimeStamp&quot;;
          }
<span class="grey"><a href="/doc/html/rfc8348">RFC 8348</a>                YANG Hardware Management              March 2018</span>

          leaf value-update-rate {
            type uint32;
            units &quot;milliseconds&quot;;
            description
              &quot;An indication of the frequency that the server updates
               the associated &#x27;value&#x27; node, represented in
               milliseconds.  The value zero indicates:

                - the sensor value is updated on demand (e.g.,
                  when polled by the server for a get-request),

                - the sensor value is updated when the sensor
                  value changes (event-driven), or

                - the server does not know the update rate.&quot;;
            reference
              &quot;<a href="/doc/html/rfc3433">RFC 3433</a>: Entity Sensor Management Information Base -
                         entPhySensorValueUpdateRate&quot;;
          }
        }
      }
    }

    /*
     * Notifications
     */

    notification hardware-state-change {
      description
        &quot;A hardware-state-change notification is generated when the
         value of /hardware/last-change changes in the operational
         state.&quot;;
      reference
        &quot;<a href="/doc/html/rfc6933">RFC 6933</a>: Entity MIB (Version 4) - entConfigChange&quot;;
    }

    notification hardware-state-oper-enabled {
      if-feature hardware-state;
      description
        &quot;A hardware-state-oper-enabled notification signifies that a
         component has transitioned into the &#x27;enabled&#x27; state.&quot;;

      leaf name {
        type leafref {
          path &quot;/hardware/component/name&quot;;
        }

<span class="grey"><a href="/doc/html/rfc8348">RFC 8348</a>                YANG Hardware Management              March 2018</span>

        description
          &quot;The name of the component that has transitioned into the
           &#x27;enabled&#x27; state.&quot;;
      }
      leaf admin-state {
        type leafref {
          path &quot;/hardware/component/state/admin-state&quot;;
        }
        description
          &quot;The administrative state for the component.&quot;;
      }
      leaf alarm-state {
        type leafref {
          path &quot;/hardware/component/state/alarm-state&quot;;
        }
        description
          &quot;The alarm state for the component.&quot;;
      }
      reference
        &quot;<a href="/doc/html/rfc4268">RFC 4268</a>: Entity State MIB - entStateOperEnabled&quot;;
    }

    notification hardware-state-oper-disabled {
      if-feature hardware-state;
      description
        &quot;A hardware-state-oper-disabled notification signifies that a
         component has transitioned into the &#x27;disabled&#x27; state.&quot;;

      leaf name {
        type leafref {
          path &quot;/hardware/component/name&quot;;
        }
        description
          &quot;The name of the component that has transitioned into the
           &#x27;disabled&#x27; state.&quot;;
      }
      leaf admin-state {
        type leafref {
          path &quot;/hardware/component/state/admin-state&quot;;
        }
        description
          &quot;The administrative state for the component.&quot;;
      }
      leaf alarm-state {
        type leafref {
          path &quot;/hardware/component/state/alarm-state&quot;;
        }

<span class="grey"><a href="/doc/html/rfc8348">RFC 8348</a>                YANG Hardware Management              March 2018</span>

        description
          &quot;The alarm state for the component.&quot;;
      }
      reference
        &quot;<a href="/doc/html/rfc4268">RFC 4268</a>: Entity State MIB - entStateOperDisabled&quot;;
    }

  }
