submodule ietf-ipv6-router-advertisements {

  yang-version &quot;1.1&quot;;

  belongs-to ietf-ipv6-unicast-routing {
    prefix &quot;v6ur&quot;;
  }

  import ietf-inet-types {
    prefix &quot;inet&quot;;
  }

  import ietf-interfaces {
    prefix &quot;if&quot;;
  }

  import ietf-ip {
    prefix &quot;ip&quot;;
  }

  organization
    &quot;IETF NETMOD (NETCONF Data Modeling Language) Working Group&quot;;
<span class="grey"><a href="/doc/html/rfc8022">RFC 8022</a>                 YANG Routing Management           November 2016</span>

     contact
       &quot;WG Web:   &lt;<a href="https://datatracker.ietf.org/wg/netmod/">https://datatracker.ietf.org/wg/netmod/</a>&gt;
        WG List:  &lt;mailto:<a href="mailto:netmod@ietf.org">netmod@ietf.org</a>&gt;

        WG Chair: Lou Berger
                  &lt;mailto:<a href="mailto:lberger@labn.net">lberger@labn.net</a>&gt;

        WG Chair: Kent Watsen
                  &lt;mailto:<a href="mailto:kwatsen@juniper.net">kwatsen@juniper.net</a>&gt;

        Editor:   Ladislav Lhotka
                  &lt;mailto:<a href="mailto:lhotka@nic.cz">lhotka@nic.cz</a>&gt;

        Editor:   Acee Lindem
                  &lt;mailto:<a href="mailto:acee@cisco.com">acee@cisco.com</a>&gt;&quot;;

     description
       &quot;This YANG module augments the &#x27;ietf-ip&#x27; module with
        configuration and state data of IPv6 router advertisements.

        Copyright (c) 2016 IETF Trust and the persons identified as
        authors of the code.  All rights reserved.

        Redistribution and use in source and binary forms, with or
        without modification, is permitted pursuant to, and subject to
        the license terms contained in, the Simplified BSD License set
        forth in <a href="#section-4">Section 4</a>.c of the IETF Trust&#x27;s Legal Provisions
        Relating to IETF Documents
        (<a href="https://trustee.ietf.org/license-info">http://trustee.ietf.org/license-info</a>).

        The key words &#x27;MUST&#x27;, &#x27;MUST NOT&#x27;, &#x27;REQUIRED&#x27;, &#x27;SHALL&#x27;, &#x27;SHALL
        NOT&#x27;, &#x27;SHOULD&#x27;, &#x27;SHOULD NOT&#x27;, &#x27;RECOMMENDED&#x27;, &#x27;MAY&#x27;, and
        &#x27;OPTIONAL&#x27; in the module text are to be interpreted as described
        in <a href="/doc/html/rfc2119">RFC 2119</a>.

        This version of this YANG module is part of <a href="/doc/html/rfc8022">RFC 8022</a>;
        see the RFC itself for full legal notices.&quot;;

     reference
       &quot;<a href="/doc/html/rfc4861">RFC 4861</a>: Neighbor Discovery for IP version 6 (IPv6).&quot;;

     revision 2016-11-04 {
       description
         &quot;Initial revision.&quot;;
       reference
         &quot;<a href="/doc/html/rfc8022">RFC 8022</a>: A YANG Data Model for Routing Management&quot;;
     }

<span class="grey"><a href="/doc/html/rfc8022">RFC 8022</a>                 YANG Routing Management           November 2016</span>

     /* State data */

     augment &quot;/if:interfaces-state/if:interface/ip:ipv6&quot; {
       description
         &quot;Augment interface state data with parameters of IPv6 router
          advertisements.&quot;;
       container ipv6-router-advertisements {
         description
           &quot;Parameters of IPv6 Router Advertisements.&quot;;
         leaf send-advertisements {
           type boolean;
           description
             &quot;A flag indicating whether or not the router sends periodic
              Router Advertisements and responds to Router
              Solicitations.&quot;;
         }
         leaf max-rtr-adv-interval {
           type uint16 {
             range &quot;4..1800&quot;;
           }
           units &quot;seconds&quot;;
           description
             &quot;The maximum time allowed between sending unsolicited
              multicast Router Advertisements from the interface.&quot;;
         }
         leaf min-rtr-adv-interval {
           type uint16 {
             range &quot;3..1350&quot;;
           }
           units &quot;seconds&quot;;
           description
             &quot;The minimum time allowed between sending unsolicited
              multicast Router Advertisements from the interface.&quot;;
         }
         leaf managed-flag {
           type boolean;
           description
             &quot;The value that is placed in the &#x27;Managed address
              configuration&#x27; flag field in the Router Advertisement.&quot;;
         }
         leaf other-config-flag {
           type boolean;
           description
             &quot;The value that is placed in the &#x27;Other configuration&#x27; flag
              field in the Router Advertisement.&quot;;
         }
         leaf link-mtu {
           type uint32;
<span class="grey"><a href="/doc/html/rfc8022">RFC 8022</a>                 YANG Routing Management           November 2016</span>

           description
             &quot;The value that is placed in MTU options sent by the
              router.  A value of zero indicates that no MTU options are
              sent.&quot;;
         }
         leaf reachable-time {
           type uint32 {
             range &quot;0..3600000&quot;;
           }
           units &quot;milliseconds&quot;;
           description
             &quot;The value that is placed in the Reachable Time field in
              the Router Advertisement messages sent by the router.  A
              value of zero means unspecified (by this router).&quot;;
         }
         leaf retrans-timer {
           type uint32;
           units &quot;milliseconds&quot;;
           description
             &quot;The value that is placed in the Retrans Timer field in the
              Router Advertisement messages sent by the router.  A value
              of zero means unspecified (by this router).&quot;;
         }

         leaf cur-hop-limit {
           type uint8;
           description
             &quot;The value that is placed in the Cur Hop Limit field in the
              Router Advertisement messages sent by the router.  A value
              of zero means unspecified (by this router).&quot;;
         }
         leaf default-lifetime {
           type uint16 {
             range &quot;0..9000&quot;;
           }
           units &quot;seconds&quot;;
           description
             &quot;The value that is placed in the Router Lifetime field of
              Router Advertisements sent from the interface, in seconds.
              A value of zero indicates that the router is not to be
              used as a default router.&quot;;
         }
         container prefix-list {
           description
             &quot;A list of prefixes that are placed in Prefix Information
              options in Router Advertisement messages sent from the
              interface.

<span class="grey"><a href="/doc/html/rfc8022">RFC 8022</a>                 YANG Routing Management           November 2016</span>

              By default, these are all prefixes that the router
              advertises via routing protocols as being on-link for the
              interface from which the advertisement is sent.&quot;;
           list prefix {
             key &quot;prefix-spec&quot;;
             description
               &quot;Advertised prefix entry and its parameters.&quot;;
             leaf prefix-spec {
               type inet:ipv6-prefix;
               description
                 &quot;IPv6 address prefix.&quot;;
             }
             leaf valid-lifetime {
               type uint32;
               units &quot;seconds&quot;;
               description
                 &quot;The value that is placed in the Valid Lifetime in the
                  Prefix Information option.  The designated value of
                  all 1&#x27;s (0xffffffff) represents infinity.

                  An implementation SHOULD keep this value constant in
                  consecutive advertisements except when it is
                  explicitly changed in configuration.&quot;;
             }
             leaf on-link-flag {
               type boolean;
               description
                 &quot;The value that is placed in the on-link flag (&#x27;L-bit&#x27;)
                  field in the Prefix Information option.&quot;;
             }
             leaf preferred-lifetime {
               type uint32;
               units &quot;seconds&quot;;
               description
                 &quot;The value that is placed in the Preferred Lifetime in
                  the Prefix Information option, in seconds.  The
                  designated value of all 1&#x27;s (0xffffffff) represents
                  infinity.

                  An implementation SHOULD keep this value constant in
                  consecutive advertisements except when it is
                  explicitly changed in configuration.&quot;;
             }
             leaf autonomous-flag {
               type boolean;
               description
                 &quot;The value that is placed in the Autonomous Flag field
                  in the Prefix Information option.&quot;;
<span class="grey"><a href="/doc/html/rfc8022">RFC 8022</a>                 YANG Routing Management           November 2016</span>

             }
           }
         }
       }
     }

     /* Configuration data */

     augment &quot;/if:interfaces/if:interface/ip:ipv6&quot; {
       description
         &quot;Augment interface configuration with parameters of IPv6 router
          advertisements.&quot;;
       container ipv6-router-advertisements {
         description
           &quot;Configuration of IPv6 Router Advertisements.&quot;;
         leaf send-advertisements {
           type boolean;
           default &quot;false&quot;;
           description
             &quot;A flag indicating whether or not the router sends periodic
              Router Advertisements and responds to Router
              Solicitations.&quot;;
           reference
             &quot;<a href="/doc/html/rfc4861">RFC 4861</a>: Neighbor Discovery for IP version 6 (IPv6) -
              AdvSendAdvertisements.&quot;;
         }
         leaf max-rtr-adv-interval {
           type uint16 {
             range &quot;4..1800&quot;;
           }
           units &quot;seconds&quot;;
           default &quot;600&quot;;
           description
             &quot;The maximum time allowed between sending unsolicited
              multicast Router Advertisements from the interface.&quot;;
           reference
             &quot;<a href="/doc/html/rfc4861">RFC 4861</a>: Neighbor Discovery for IP version 6 (IPv6) -
              MaxRtrAdvInterval.&quot;;
         }
         leaf min-rtr-adv-interval {
           type uint16 {
             range &quot;3..1350&quot;;
           }
           units &quot;seconds&quot;;
           must &quot;. &lt;= 0.75 * ../max-rtr-adv-interval&quot; {
             description
               &quot;The value MUST NOT be greater than 75% of
                &#x27;max-rtr-adv-interval&#x27;.&quot;;
<span class="grey"><a href="/doc/html/rfc8022">RFC 8022</a>                 YANG Routing Management           November 2016</span>

           }
           description
             &quot;The minimum time allowed between sending unsolicited
              multicast Router Advertisements from the interface.

              The default value to be used operationally if this leaf is
              not configured is determined as follows:

              - if max-rtr-adv-interval &gt;= 9 seconds, the default
                value is 0.33 * max-rtr-adv-interval;

              - otherwise, it is 0.75 * max-rtr-adv-interval.&quot;;
           reference
             &quot;<a href="/doc/html/rfc4861">RFC 4861</a>: Neighbor Discovery for IP version 6 (IPv6) -
              MinRtrAdvInterval.&quot;;
         }
         leaf managed-flag {
           type boolean;
           default &quot;false&quot;;
           description
             &quot;The value to be placed in the &#x27;Managed address
              configuration&#x27; flag field in the Router Advertisement.&quot;;
           reference
             &quot;<a href="/doc/html/rfc4861">RFC 4861</a>: Neighbor Discovery for IP version 6 (IPv6) -
              AdvManagedFlag.&quot;;
         }
         leaf other-config-flag {
           type boolean;
           default &quot;false&quot;;
           description
             &quot;The value to be placed in the &#x27;Other configuration&#x27; flag
              field in the Router Advertisement.&quot;;
           reference
             &quot;<a href="/doc/html/rfc4861">RFC 4861</a>: Neighbor Discovery for IP version 6 (IPv6) -
              AdvOtherConfigFlag.&quot;;
         }
         leaf link-mtu {
           type uint32;
           default &quot;0&quot;;
           description
             &quot;The value to be placed in MTU options sent by the router.
              A value of zero indicates that no MTU options are sent.&quot;;
           reference
             &quot;<a href="/doc/html/rfc4861">RFC 4861</a>: Neighbor Discovery for IP version 6 (IPv6) -
              AdvLinkMTU.&quot;;
         }
         leaf reachable-time {
           type uint32 {
<span class="grey"><a href="/doc/html/rfc8022">RFC 8022</a>                 YANG Routing Management           November 2016</span>

             range &quot;0..3600000&quot;;
           }
           units &quot;milliseconds&quot;;
           default &quot;0&quot;;
           description
             &quot;The value to be placed in the Reachable Time field in the
              Router Advertisement messages sent by the router.  A value
              of zero means unspecified (by this router).&quot;;
           reference
             &quot;<a href="/doc/html/rfc4861">RFC 4861</a>: Neighbor Discovery for IP version 6 (IPv6) -
              AdvReachableTime.&quot;;
         }
         leaf retrans-timer {
           type uint32;
           units &quot;milliseconds&quot;;
           default &quot;0&quot;;
           description
             &quot;The value to be placed in the Retrans Timer field in the
              Router Advertisement messages sent by the router.  A value
              of zero means unspecified (by this router).&quot;;
           reference
             &quot;<a href="/doc/html/rfc4861">RFC 4861</a>: Neighbor Discovery for IP version 6 (IPv6) -
              AdvRetransTimer.&quot;;
         }
         leaf cur-hop-limit {
           type uint8;
           description
             &quot;The value to be placed in the Cur Hop Limit field in the
              Router Advertisement messages sent by the router.  A value
              of zero means unspecified (by this router).

              If this parameter is not configured, the device SHOULD use
              the value specified in IANA Assigned Numbers that was in
              effect at the time of implementation.&quot;;
           reference
             &quot;<a href="/doc/html/rfc4861">RFC 4861</a>: Neighbor Discovery for IP version 6 (IPv6) -
              AdvCurHopLimit.

              IANA: IP Parameters,
              <a href="http://www.iana">http://www.iana</a>.org/assignments/ip-parameters&quot;;
         }
         leaf default-lifetime {
           type uint16 {
             range &quot;0..9000&quot;;
           }
           units &quot;seconds&quot;;
           description
             &quot;The value to be placed in the Router Lifetime field of
<span class="grey"><a href="/doc/html/rfc8022">RFC 8022</a>                 YANG Routing Management           November 2016</span>

              Router Advertisements sent from the interface, in seconds.
              It MUST be either zero or between max-rtr-adv-interval and
              9000 seconds.  A value of zero indicates that the router
              is not to be used as a default router.  These limits may
              be overridden by specific documents that describe how IPv6
              operates over different link layers.

              If this parameter is not configured, the device SHOULD use
              a value of 3 * max-rtr-adv-interval.&quot;;
           reference
             &quot;<a href="/doc/html/rfc4861">RFC 4861</a>: Neighbor Discovery for IP version 6 (IPv6) -
              AdvDefaultLifeTime.&quot;;
         }
         container prefix-list {
           description
             &quot;Configuration of prefixes to be placed in Prefix
              Information options in Router Advertisement messages sent
              from the interface.

              Prefixes that are advertised by default but do not have
              their entries in the child &#x27;prefix&#x27; list are advertised
              with the default values of all parameters.

              The link-local prefix SHOULD NOT be included in the list
              of advertised prefixes.&quot;;
           reference
             &quot;<a href="/doc/html/rfc4861">RFC 4861</a>: Neighbor Discovery for IP version 6 (IPv6) -
              AdvPrefixList.&quot;;
           list prefix {
             key &quot;prefix-spec&quot;;
             description
               &quot;Configuration of an advertised prefix entry.&quot;;
             leaf prefix-spec {
               type inet:ipv6-prefix;
               description
                 &quot;IPv6 address prefix.&quot;;
             }
             choice control-adv-prefixes {
               default &quot;advertise&quot;;
               description
                 &quot;Either the prefix is explicitly removed from the
                  set of advertised prefixes, or the parameters with
                  which it is advertised are specified (default case).&quot;;
               leaf no-advertise {
                 type empty;
                 description
                   &quot;The prefix will not be advertised.

<span class="grey"><a href="/doc/html/rfc8022">RFC 8022</a>                 YANG Routing Management           November 2016</span>

                    This can be used for removing the prefix from the
                    default set of advertised prefixes.&quot;;
               }
               case advertise {
                 leaf valid-lifetime {
                   type uint32;
                   units &quot;seconds&quot;;
                   default &quot;2592000&quot;;
                   description
                     &quot;The value to be placed in the Valid Lifetime in
                      the Prefix Information option.  The designated
                      value of all 1&#x27;s (0xffffffff) represents
                      infinity.&quot;;
                   reference
                     &quot;<a href="/doc/html/rfc4861">RFC 4861</a>: Neighbor Discovery for IP version 6
                      (IPv6) - AdvValidLifetime.&quot;;
                 }
                 leaf on-link-flag {
                   type boolean;
                   default &quot;true&quot;;
                   description
                     &quot;The value to be placed in the on-link flag
                      (&#x27;L-bit&#x27;) field in the Prefix Information
                      option.&quot;;
                   reference
                     &quot;<a href="/doc/html/rfc4861">RFC 4861</a>: Neighbor Discovery for IP version 6
                      (IPv6) - AdvOnLinkFlag.&quot;;
                 }
                 leaf preferred-lifetime {
                   type uint32;
                   units &quot;seconds&quot;;
                   must &quot;. &lt;= ../valid-lifetime&quot; {
                     description
                       &quot;This value MUST NOT be greater than
                        valid-lifetime.&quot;;
                   }
                   default &quot;604800&quot;;
                   description
                     &quot;The value to be placed in the Preferred Lifetime
                      in the Prefix Information option.  The designated
                      value of all 1&#x27;s (0xffffffff) represents
                      infinity.&quot;;
                   reference
                     &quot;<a href="/doc/html/rfc4861">RFC 4861</a>: Neighbor Discovery for IP version 6
                      (IPv6) - AdvPreferredLifetime.&quot;;
                 }
                 leaf autonomous-flag {
                   type boolean;
<span class="grey"><a href="/doc/html/rfc8022">RFC 8022</a>                 YANG Routing Management           November 2016</span>

                   default &quot;true&quot;;
                   description
                     &quot;The value to be placed in the Autonomous Flag
                      field in the Prefix Information option.&quot;;
                   reference
                     &quot;<a href="/doc/html/rfc4861">RFC 4861</a>: Neighbor Discovery for IP version 6
                      (IPv6) - AdvAutonomousFlag.&quot;;
                 }
               }
             }
           }
         }
       }
     }
   }
