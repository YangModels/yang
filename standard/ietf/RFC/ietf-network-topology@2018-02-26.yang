module ietf-network-topology {
  yang-version 1.1;
  namespace &quot;urn:ietf:params:xml:ns:yang:ietf-network-topology&quot;;
  prefix nt;

  import ietf-inet-types {
    prefix inet;
    reference
      &quot;<a href="/doc/html/rfc6991">RFC 6991</a>: Common YANG Data Types&quot;;
  }
  import ietf-network {
    prefix nw;
    reference
      &quot;<a href="/doc/html/rfc8345">RFC 8345</a>: A YANG Data Model for Network Topologies&quot;;
  }

  organization
    &quot;IETF I2RS (Interface to the Routing System) Working Group&quot;;

  contact
    &quot;WG Web:    &lt;<a href="https://datatracker.ietf.org/wg/i2rs/">https://datatracker.ietf.org/wg/i2rs/</a>&gt;
     WG List:   &lt;mailto:<a href="mailto:i2rs@ietf.org">i2rs@ietf.org</a>&gt;

     Editor:    Alexander Clemm
                &lt;mailto:<a href="mailto:ludwig@clemm.org">ludwig@clemm.org</a>&gt;

     Editor:    Jan Medved
                &lt;mailto:<a href="mailto:jmedved@cisco.com">jmedved@cisco.com</a>&gt;

     Editor:    Robert Varga
                &lt;mailto:<a href="mailto:robert.varga@pantheon.tech">robert.varga@pantheon.tech</a>&gt;

     Editor:    Nitin Bahadur
                &lt;mailto:<a href="mailto:nitin_bahadur@yahoo.com">nitin_bahadur@yahoo.com</a>&gt;

     Editor:    Hariharan Ananthakrishnan
                &lt;mailto:<a href="mailto:hari@packetdesign.com">hari@packetdesign.com</a>&gt;

     Editor:    Xufeng Liu
                &lt;mailto:<a href="mailto:xufeng.liu.ietf@gmail.com">xufeng.liu.ietf@gmail.com</a>&gt;&quot;;

<span class="grey"><a href="/doc/html/rfc8345">RFC 8345</a>         YANG Data Model for Network Topologies       March 2018</span>

     description
       &quot;This module defines a common base model for a network topology,
        augmenting the base network data model with links to connect
        nodes, as well as termination points to terminate links
        on nodes.

        Copyright (c) 2018 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">https://trustee.ietf.org/license-info</a>).

        This version of this YANG module is part of <a href="/doc/html/rfc8345">RFC 8345</a>;
        see the RFC itself for full legal notices.&quot;;

     revision 2018-02-26 {
       description
         &quot;Initial revision.&quot;;
       reference
         &quot;<a href="/doc/html/rfc8345">RFC 8345</a>: A YANG Data Model for Network Topologies&quot;;
     }

     typedef link-id {
       type inet:uri;
       description
         &quot;An identifier for a link in a topology.  The precise
          structure of the link-id will be up to the implementation.
          The identifier SHOULD be chosen such that the same link in a
          real network topology will always be identified through the
          same identifier, even if the data model is instantiated in
          separate datastores.  An implementation MAY choose to capture
          semantics in the identifier -- for example, to indicate the
          type of link and/or the type of topology of which the link is
          a part.&quot;;
     }

     typedef tp-id {
       type inet:uri;
       description
         &quot;An identifier for termination points on a node.  The precise
          structure of the tp-id will be up to the implementation.
          The identifier SHOULD be chosen such that the same termination
          point in a real network topology will always be identified
          through the same identifier, even if the data model is
<span class="grey"><a href="/doc/html/rfc8345">RFC 8345</a>         YANG Data Model for Network Topologies       March 2018</span>

          instantiated in separate datastores.  An implementation MAY
          choose to capture semantics in the identifier -- for example,
          to indicate the type of termination point and/or the type of
          node that contains the termination point.&quot;;
     }

     grouping link-ref {
       description
         &quot;This grouping can be used to reference a link in a specific
          network.  Although it is not used in this module, it is
          defined here for the convenience of augmenting modules.&quot;;
       leaf link-ref {
         type leafref {
           path &quot;/nw:networks/nw:network[nw:network-id=current()/../&quot;+
             &quot;network-ref]/nt:link/nt:link-id&quot;;
           require-instance false;
         }
         description
           &quot;A type for an absolute reference to a link instance.
            (This type should not be used for relative references.
            In such a case, a relative path should be used instead.)&quot;;
       }
       uses nw:network-ref;
     }

     grouping tp-ref {
       description
         &quot;This grouping can be used to reference a termination point
          in a specific node.  Although it is not used in this module,
          it is defined here for the convenience of augmenting
          modules.&quot;;
       leaf tp-ref {
         type leafref {
           path &quot;/nw:networks/nw:network[nw:network-id=current()/../&quot;+
             &quot;network-ref]/nw:node[nw:node-id=current()/../&quot;+
             &quot;node-ref]/nt:termination-point/nt:tp-id&quot;;
           require-instance false;
         }
         description
           &quot;A type for an absolute reference to a termination point.
            (This type should not be used for relative references.
            In such a case, a relative path should be used instead.)&quot;;
       }
       uses nw:node-ref;
     }

<span class="grey"><a href="/doc/html/rfc8345">RFC 8345</a>         YANG Data Model for Network Topologies       March 2018</span>

     augment &quot;/nw:networks/nw:network&quot; {
       description
         &quot;Add links to the network data model.&quot;;
       list link {
         key &quot;link-id&quot;;
         description
           &quot;A network link connects a local (source) node and
            a remote (destination) node via a set of the respective
            node&#x27;s termination points.  It is possible to have several
            links between the same source and destination nodes.
            Likewise, a link could potentially be re-homed between
            termination points.  Therefore, in order to ensure that we
            would always know to distinguish between links, every link
            is identified by a dedicated link identifier.  Note that a
            link models a point-to-point link, not a multipoint link.&quot;;
         leaf link-id {
           type link-id;
           description
             &quot;The identifier of a link in the topology.
              A link is specific to a topology to which it belongs.&quot;;
         }
         container source {
           description
             &quot;This container holds the logical source of a particular
              link.&quot;;
           leaf source-node {
             type leafref {
               path &quot;../../../nw:node/nw:node-id&quot;;
               require-instance false;
             }
             description
               &quot;Source node identifier.  Must be in the same topology.&quot;;
           }
           leaf source-tp {
             type leafref {
               path &quot;../../../nw:node[nw:node-id=current()/../&quot;+
                 &quot;source-node]/termination-point/tp-id&quot;;
               require-instance false;
             }
             description
               &quot;This termination point is located within the source node
                and terminates the link.&quot;;
           }
         }

<span class="grey"><a href="/doc/html/rfc8345">RFC 8345</a>         YANG Data Model for Network Topologies       March 2018</span>

         container destination {
           description
             &quot;This container holds the logical destination of a
              particular link.&quot;;
           leaf dest-node {
             type leafref {
               path &quot;../../../nw:node/nw:node-id&quot;;
             require-instance false;
             }
             description
               &quot;Destination node identifier.  Must be in the same
                network.&quot;;
           }
           leaf dest-tp {
             type leafref {
               path &quot;../../../nw:node[nw:node-id=current()/../&quot;+
                 &quot;dest-node]/termination-point/tp-id&quot;;
               require-instance false;
             }
             description
               &quot;This termination point is located within the
                destination node and terminates the link.&quot;;
           }
         }
         list supporting-link {
           key &quot;network-ref link-ref&quot;;
           description
             &quot;Identifies the link or links on which this link depends.&quot;;
           leaf network-ref {
             type leafref {
               path &quot;../../../nw:supporting-network/nw:network-ref&quot;;
             require-instance false;
             }
             description
               &quot;This leaf identifies in which underlay topology
                the supporting link is present.&quot;;
           }

<span class="grey"><a href="/doc/html/rfc8345">RFC 8345</a>         YANG Data Model for Network Topologies       March 2018</span>

           leaf link-ref {
             type leafref {
               path &quot;/nw:networks/nw:network[nw:network-id=current()/&quot;+
                 &quot;../network-ref]/link/link-id&quot;;
               require-instance false;
             }
             description
               &quot;This leaf identifies a link that is a part
                of this link&#x27;s underlay.  Reference loops in which
                a link identifies itself as its underlay, either
                directly or transitively, are not allowed.&quot;;
           }
         }
       }
     }
     augment &quot;/nw:networks/nw:network/nw:node&quot; {
       description
         &quot;Augments termination points that terminate links.
          Termination points can ultimately be mapped to interfaces.&quot;;
       list termination-point {
         key &quot;tp-id&quot;;
         description
           &quot;A termination point can terminate a link.
            Depending on the type of topology, a termination point
            could, for example, refer to a port or an interface.&quot;;
         leaf tp-id {
           type tp-id;
           description
             &quot;Termination point identifier.&quot;;
         }
         list supporting-termination-point {
           key &quot;network-ref node-ref tp-ref&quot;;
           description
             &quot;This list identifies any termination points on which a
              given termination point depends or onto which it maps.
              Those termination points will themselves be contained
              in a supporting node.  This dependency information can be
              inferred from the dependencies between links.  Therefore,
              this item is not separately configurable.  Hence, no
              corresponding constraint needs to be articulated.
              The corresponding information is simply provided by the
              implementing system.&quot;;

<span class="grey"><a href="/doc/html/rfc8345">RFC 8345</a>         YANG Data Model for Network Topologies       March 2018</span>

           leaf network-ref {
             type leafref {
               path &quot;../../../nw:supporting-node/nw:network-ref&quot;;
             require-instance false;
             }
             description
               &quot;This leaf identifies in which topology the
                supporting termination point is present.&quot;;
           }
           leaf node-ref {
             type leafref {
               path &quot;../../../nw:supporting-node/nw:node-ref&quot;;
             require-instance false;
             }
             description
               &quot;This leaf identifies in which node the supporting
                termination point is present.&quot;;
           }
           leaf tp-ref {
             type leafref {
               path &quot;/nw:networks/nw:network[nw:network-id=current()/&quot;+
                 &quot;../network-ref]/nw:node[nw:node-id=current()/../&quot;+
                 &quot;node-ref]/termination-point/tp-id&quot;;
               require-instance false;
             }
             description
               &quot;Reference to the underlay node (the underlay node must
                be in a different topology).&quot;;
           }
         }
       }
     }
   }
