module ietf-foo {
  namespace "urn:ietf:params:xml:ns:yang:ietf-foo";
  prefix "foo";
  organization "...";
  contact "...";
  description "...";
  revision 2016-03-20 {
    description "Latest revision";
    reference "RFC FFFF: Foo Protocol";
  }
  // ... more statements
}
