module example-bfd-echo {
  namespace "tag:example.com,2021:example-bfd-echo";
  prefix example-bfd-echo;

  import ietf-bfd-types {
    prefix bfd-types;
  }
  import ietf-bfd {
    prefix bfd;
  }
  import ietf-bfd-ip-sh {
    prefix bfd-ip-sh;
  }
  import ietf-routing {
    prefix rt;
  }

  organization
    "IETF BFD Working Group";
  contact
    "WG Web:   <https://datatracker.ietf.org/wg/bfd/>
     WG List:  <mailto:rtg-bfd@ietf.org>

     Editor:   Reshad Rahman
               <mailto:reshad@yahoo.com>

     Editor:   Lianshu Zheng
               <mailto:veronique_cheng@hotmail.com>

     Editor:   Mahesh Jethanandani
               <mailto:mjethanandani@gmail.com>";
  description
    "This module contains an example YANG augmentation for
     configuration of the BFD Echo function.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC 9127; see the
     RFC itself for full legal notices.";

  revision 2021-09-03 {
    description
      "Initial revision.";
    reference
      "RFC 9127: YANG Data Model for Bidirectional Forwarding
       Detection (BFD)";
  }

  /*
   * Groupings
   */

  grouping echo-cfg-parms {
    description
      "BFD grouping for Echo configuration parameters.";
    leaf desired-min-echo-tx-interval {
      type uint32;
      units "microseconds";
      default "0";
      description
        "This is the minimum interval that the local system would
         like to use when transmitting BFD Echo packets.  If 0,
         the Echo function as defined in BFD (RFC 5880) is
         disabled.";
    }
    leaf required-min-echo-rx-interval {
      type uint32;
      units "microseconds";
      default "0";
      description
        "This is the Required Min Echo RX Interval as defined in BFD
         (RFC 5880).";
    }
  }

  augment "/rt:routing/rt:control-plane-protocols/"
        + "rt:control-plane-protocol/bfd:bfd/bfd-ip-sh:ip-sh/"
        + "bfd-ip-sh:sessions" {
    description
      "Augmentation for the BFD Echo function.";
    container echo {
      if-feature "bfd-types:echo-mode";
      description
        "BFD Echo function container.";
      uses echo-cfg-parms;
    }
  }
}
