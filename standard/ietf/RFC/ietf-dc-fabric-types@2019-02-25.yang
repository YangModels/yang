module ietf-dc-fabric-types {
  yang-version 1.1;
  namespace &quot;urn:ietf:params:xml:ns:yang:ietf-dc-fabric-types&quot;;
  prefix fabrictypes;

  import ietf-network {
    prefix nw;
    reference
      &quot;<a href="/doc/html/rfc8345">RFC 8345</a>: A YANG Data Model for Network Topologies&quot;;
  }

  organization
    &quot;IETF I2RS (Interface to the Routing System) Working Group&quot;;
  contact
    &quot;WG Web:    &lt;<a href="https://datatracker.ietf.org/wg/i2rs/">https://datatracker.ietf.org/wg/i2rs/</a>&gt;
     WG List:   &lt;mailto:<a href="mailto:i2rs@ietf.org">i2rs@ietf.org</a>&gt;

     Editor:    Yan Zhuang
                &lt;mailto:<a href="mailto:zhuangyan.zhuang@huawei.com">zhuangyan.zhuang@huawei.com</a>&gt;

     Editor:    Danian Shi
                &lt;mailto:<a href="mailto:shidanian@huawei.com">shidanian@huawei.com</a>&gt;&quot;;
  description
    &quot;This module contains a collection of YANG definitions for
     fabric.

     Copyright (c) 2019 IETF Trust and the persons identified
     as authors of the code.  All rights reserved.

     Redistribution and use in source and binary forms, with
     or without modification, is permitted pursuant to, and
     subject to the license terms contained in, the Simplified
     BSD License set forth in <a href="#section-4">Section 4</a>.c of the IETF Trust&#x27;s
     Legal Provisions Relating to IETF Documents
     (<a href="https://trustee.ietf.org/license-info">https://trustee.ietf.org/license-info</a>).

     This version of this YANG module is part of <a href="/doc/html/rfc8542">RFC 8542</a>;
     see the RFC itself for full legal notices.&quot;;

  revision 2019-02-25 {
    description
      &quot;Initial revision.&quot;;
<span class="grey"><a href="/doc/html/rfc8542">RFC 8542</a>            Data Model for DC Fabric Topology         March 2019</span>

    reference
      &quot;<a href="/doc/html/rfc8542">RFC 8542</a>: A YANG Data Model for Fabric Topology
       in Data-Center Networks&quot;;
  }

  identity fabric-type {
    description
      &quot;Base type for fabric networks&quot;;
  }

  identity vxlan-fabric {
    base fabric-type;
    description
      &quot;VXLAN fabric&quot;;
  }

  identity vlan-fabric {
    base fabric-type;
    description
      &quot;VLAN fabric&quot;;
  }

  identity trill-fabric {
    base fabric-type;
    description
      &quot;TRILL fabric&quot;;
  }

  identity port-type {
    description
      &quot;Base type for fabric port&quot;;
  }

  identity eth {
    base port-type;
    description
      &quot;Ethernet&quot;;
  }

  identity serial {
    base port-type;
    description
      &quot;Serial&quot;;
  }

  identity bandwidth {
    description
      &quot;Base for bandwidth&quot;;
<span class="grey"><a href="/doc/html/rfc8542">RFC 8542</a>            Data Model for DC Fabric Topology         March 2019</span>

  }

  identity bw-1M {
    base bandwidth;
    description
      &quot;1M&quot;;
  }

  identity bw-10M {
    base bandwidth;
    description
      &quot;10Mbps&quot;;
  }

  identity bw-100M {
    base bandwidth;
    description
      &quot;100Mbps&quot;;
  }

  identity bw-1G {
    base bandwidth;
    description
      &quot;1Gbps&quot;;
  }

  identity bw-10G {
    base bandwidth;
    description
      &quot;10Gbps&quot;;
  }

  identity bw-25G {
    base bandwidth;
    description
      &quot;25Gbps&quot;;
  }

  identity bw-40G {
    base bandwidth;
    description
      &quot;40Gbps&quot;;
  }

  identity bw-100G {
    base bandwidth;
    description
      &quot;100Gbps&quot;;
<span class="grey"><a href="/doc/html/rfc8542">RFC 8542</a>            Data Model for DC Fabric Topology         March 2019</span>

  }

  identity bw-400G {
    base bandwidth;
    description
      &quot;400Gbps&quot;;
  }

  identity device-role {
    description
      &quot;Base for the device role in a fabric.&quot;;
  }

  identity spine {
    base device-role;
    description
      &quot;This is a spine node in a fabric.&quot;;
  }

  identity leaf {
    base device-role;
    description
      &quot;This is a leaf node in a fabric.&quot;;
  }

  identity border {
    base device-role;
    description
      &quot;This is a border node to connect to other
       fabric/network.&quot;;
  }

  identity fabric-port-role {
    description
      &quot;Base for the port&#x27;s role in a fabric.&quot;;
  }

  identity internal {
    base fabric-port-role;
    description
      &quot;The port is used for devices to access each
       other within a fabric.&quot;;
  }

  identity external {
    base fabric-port-role;
    description
      &quot;The port is used for a fabric to connect to
<span class="grey"><a href="/doc/html/rfc8542">RFC 8542</a>            Data Model for DC Fabric Topology         March 2019</span>

       outside network.&quot;;
  }

  identity access {
    base fabric-port-role;
    description
      &quot;The port is used for an endpoint to connect
       to a fabric.&quot;;
  }

  identity service-capability {
    description
      &quot;Base for the service of the fabric &quot;;
  }

  identity ip-mapping {
    base service-capability;
    description
      &quot;NAT.&quot;;
  }

  identity acl-redirect {
    base service-capability;
    description
      &quot;ACL redirect, which can provide a Service Function Chain (SFC).&quot;;
  }

  identity dynamic-route-exchange {
    base service-capability;
    description
      &quot;Dynamic route exchange.&quot;;
  }

  /*
   * Typedefs
   */

  typedef fabric-id {
    type nw:node-id;
    description
      &quot;An identifier for a fabric in a topology.
       This identifier can be generated when composing a fabric.
       The composition of a fabric can be achieved by defining an
       RPC, which is left for vendor specific implementation
       and not provided in this model.&quot;;
  }

  typedef service-capabilities {
<span class="grey"><a href="/doc/html/rfc8542">RFC 8542</a>            Data Model for DC Fabric Topology         March 2019</span>

    type identityref {
      base service-capability;
    }
    description
      &quot;Service capability of the fabric&quot;;
  }

  typedef port-type {
    type identityref {
      base port-type;
    }
    description
      &quot;Port type: ethernet or serial or others.&quot;;
  }

  typedef bandwidth {
    type identityref {
      base bandwidth;
    }
    description
      &quot;Bandwidth of the port.&quot;;
  }

  typedef node-ref {
    type instance-identifier;
    description
      &quot;A reference to a node in topology&quot;;
  }

  typedef tp-ref {
    type instance-identifier;
    description
      &quot;A reference to a termination point in topology&quot;;
  }

  typedef link-ref {
    type instance-identifier;
    description
      &quot;A reference to a link in topology&quot;;
  }

  typedef underlay-network-type {
    type identityref {
      base fabric-type;
    }
    description
      &quot;The type of physical network that implements
       this fabric.  Examples are VLAN and TRILL.&quot;;
<span class="grey"><a href="/doc/html/rfc8542">RFC 8542</a>            Data Model for DC Fabric Topology         March 2019</span>

  }

  typedef device-role {
    type identityref {
      base device-role;
    }
    description
      &quot;Role of the device node.&quot;;
  }

  typedef fabric-port-role {
    type identityref {
      base fabric-port-role;
    }
    description
      &quot;Role of the port in a fabric.&quot;;
  }

  typedef fabric-port-type {
    type enumeration {
      enum layer2interface {
        description
          &quot;L2 interface&quot;;
      }
      enum layer3interface {
        description
          &quot;L3 interface&quot;;
      }
      enum layer2Tunnel {
        description
          &quot;L2 tunnel&quot;;
      }
      enum layer3Tunnel {
        description
          &quot;L3 tunnel&quot;;
      }
    }
    description
      &quot;Fabric port type&quot;;
  }

  grouping fabric-port {
    description
      &quot;Attributes of a fabric port.&quot;;
    leaf name {
      type string;
      description
        &quot;Name of the port.&quot;;
<span class="grey"><a href="/doc/html/rfc8542">RFC 8542</a>            Data Model for DC Fabric Topology         March 2019</span>

    }
    leaf role {
      type fabric-port-role;
      description
        &quot;Role of the port in a fabric.&quot;;
    }
    leaf type {
      type fabric-port-type;
      description
        &quot;Type of the port&quot;;
    }
    leaf device-port {
      type tp-ref;
      description
        &quot;The device port it mapped to.&quot;;
    }
    choice tunnel-option {
      description
        &quot;Tunnel options to connect two fabrics.
         It could be L2 Tunnel or L3 Tunnel.&quot;;
    }
  }
}
