module example-uses-geo-location {
  namespace
    "urn:example:example-uses-geo-location";
  prefix ugeo;
  import ietf-geo-location { prefix geo; }
  organization "Empty Org";
  contact "Example Author <eauthor@example.com>";
  description
    "Example use of geo-location";
  revision 2022-02-11 { reference "None"; }
  container locatable-items {
    description
      "The container of locatable items";
    list locatable-item {
      key name;
      description
        "A locatable item";
      leaf name {
        type string;
        description
          "The name of locatable item";
      }
      uses geo:geo-location;
    }
  }
}
