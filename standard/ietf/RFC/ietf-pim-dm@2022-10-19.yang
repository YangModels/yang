module ietf-pim-dm {
  yang-version 1.1;
  namespace "urn:ietf:params:xml:ns:yang:ietf-pim-dm";
  prefix pim-dm;

  import ietf-routing {
    prefix rt;
    reference
      "RFC 8349: A YANG Data Model for Routing Management (NMDA
       Version)";
  }
  import ietf-pim-base {
    prefix pim-base;
    reference
      "RFC 9128: A YANG Data Model for Protocol Independent
       Multicast (PIM)";
  }

  organization
    "IETF PIM Working Group";
  contact
    "WG Web:   &lt;https://datatracker.ietf.org/wg/pim/&gt;
     WG List:  &lt;mailto:pim@ietf.org&gt;

     Editor:   Xufeng Liu
               &lt;mailto:xufeng.liu.ietf@gmail.com&gt;

     Editor:   Pete McAllister
               &lt;mailto:pete.mcallister@metaswitch.com&gt;

     Editor:   Anish Peter
               &lt;mailto:anish.ietf@gmail.com&gt;

     Editor:   Mahesh Sivakumar
               &lt;mailto:sivakumar.mahesh@gmail.com&gt;

     Editor:   Yisong Liu
               &lt;mailto:liuyisong@chinamobile.com&gt;

     Editor:   Fangwei Hu
               &lt;mailto:hufwei@gmail.com&gt;";
  description
    "This YANG module defines a PIM (Protocol Independent Multicast)
     DM (Dense Mode) model.

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC 9128; see the
     RFC itself for full legal notices.";

  revision 2022-10-19 {
    description
      "Initial revision.";
    reference
      "RFC 9128: A YANG Data Model for Protocol Independent
       Multicast (PIM)";
  }

  /*
   * Configuration data nodes
   */

  augment "/rt:routing/rt:control-plane-protocols/"
        + "pim-base:pim/pim-base:address-family" {
    description
      "PIM-DM augmentation.";
    container dm {
      presence "Present to enable PIM-DM.";
      description
        "PIM-DM configuration data.";
    } // dm
  } // augment

  augment "/rt:routing/rt:control-plane-protocols/"
        + "pim-base:pim/pim-base:interfaces/pim-base:interface/"
        + "pim-base:address-family" {
    description
      "PIM-DM augmentation to 'pim-base:interface'.";
    container dm {
      presence "Present to enable PIM-DM.";
      description
        "PIM-DM configuration data.";
    } // dm
  } // augment

}
