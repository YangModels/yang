module ietf-ip {

 namespace &quot;urn:ietf:params:xml:ns:yang:ietf-ip&quot;;
 prefix ip;

 import ietf-interfaces {
   prefix if;
 }
 import ietf-inet-types {
   prefix inet;
 }
 import ietf-yang-types {
   prefix yang;
 }

 organization
   &quot;IETF NETMOD (NETCONF Data Modeling Language) Working Group&quot;;

 contact
   &quot;WG Web:   &lt;<a href="https://tools.ietf.org/wg/netmod/">http://tools.ietf.org/wg/netmod/</a>&gt;
    WG List:  &lt;mailto:<a href="mailto:netmod@ietf.org">netmod@ietf.org</a>&gt;

    WG Chair: Thomas Nadeau
              &lt;mailto:<a href="mailto:tnadeau@lucidvision.com">tnadeau@lucidvision.com</a>&gt;

    WG Chair: Juergen Schoenwaelder
              &lt;mailto:<a href="mailto:j.schoenwaelder@jacobs-university.de">j.schoenwaelder@jacobs-university.de</a>&gt;

    Editor:   Martin Bjorklund
              &lt;mailto:<a href="mailto:mbj@tail-f.com">mbj@tail-f.com</a>&gt;&quot;;

<span class="grey"><a href="/doc/html/rfc7277">RFC 7277</a>                   YANG IP Management                  June 2014</span>

    description
      &quot;This module contains a collection of YANG definitions for
       configuring IP implementations.

       Copyright (c) 2014 IETF Trust and the persons identified as
       authors of the code.  All rights reserved.

       Redistribution and use in source and binary forms, with or
       without modification, is permitted pursuant to, and subject
       to the license terms contained in, the Simplified BSD License
       set forth in <a href="#section-4">Section 4</a>.c of the IETF Trust&#x27;s Legal Provisions
       Relating to IETF Documents
       (<a href="https://trustee.ietf.org/license-info">http://trustee.ietf.org/license-info</a>).

       This version of this YANG module is part of <a href="/doc/html/rfc7277">RFC 7277</a>; see
       the RFC itself for full legal notices.&quot;;

    revision 2014-06-16 {
      description
        &quot;Initial revision.&quot;;
      reference
        &quot;<a href="/doc/html/rfc7277">RFC 7277</a>: A YANG Data Model for IP Management&quot;;
    }

    /*

     * Features
     */

    feature ipv4-non-contiguous-netmasks {
      description
        &quot;Indicates support for configuring non-contiguous
         subnet masks.&quot;;
    }

    feature ipv6-privacy-autoconf {
      description
        &quot;Indicates support for Privacy Extensions for Stateless Address
         Autoconfiguration in IPv6.&quot;;
      reference
        &quot;<a href="/doc/html/rfc4941">RFC 4941</a>: Privacy Extensions for Stateless Address
                   Autoconfiguration in IPv6&quot;;
    }

<span class="grey"><a href="/doc/html/rfc7277">RFC 7277</a>                   YANG IP Management                  June 2014</span>

    /*
     * Typedefs
     */

    typedef ip-address-origin {
      type enumeration {
        enum other {
          description
            &quot;None of the following.&quot;;
        }
        enum static {
          description
            &quot;Indicates that the address has been statically
             configured - for example, using NETCONF or a Command Line
             Interface.&quot;;
        }
        enum dhcp {
          description
            &quot;Indicates an address that has been assigned to this
             system by a DHCP server.&quot;;
        }
        enum link-layer {
          description
            &quot;Indicates an address created by IPv6 stateless
             autoconfiguration that embeds a link-layer address in its
             interface identifier.&quot;;
        }
        enum random {
          description
            &quot;Indicates an address chosen by the system at

             random, e.g., an IPv4 address within 169.254/16, an
             <a href="/doc/html/rfc4941">RFC 4941</a> temporary address, or an <a href="/doc/html/rfc7217">RFC 7217</a> semantically
             opaque address.&quot;;
          reference
            &quot;<a href="/doc/html/rfc4941">RFC 4941</a>: Privacy Extensions for Stateless Address
                       Autoconfiguration in IPv6
             <a href="/doc/html/rfc7217">RFC 7217</a>: A Method for Generating Semantically Opaque
                       Interface Identifiers with IPv6 Stateless
                       Address Autoconfiguration (SLAAC)&quot;;
        }
      }
      description
        &quot;The origin of an address.&quot;;
    }

<span class="grey"><a href="/doc/html/rfc7277">RFC 7277</a>                   YANG IP Management                  June 2014</span>

    typedef neighbor-origin {
      type enumeration {
        enum other {
          description
            &quot;None of the following.&quot;;
        }
        enum static {
          description
            &quot;Indicates that the mapping has been statically
             configured - for example, using NETCONF or a Command Line
             Interface.&quot;;
        }
        enum dynamic {
          description
            &quot;Indicates that the mapping has been dynamically resolved
             using, e.g., IPv4 ARP or the IPv6 Neighbor Discovery
             protocol.&quot;;
        }
      }
      description
        &quot;The origin of a neighbor entry.&quot;;
    }

    /*
     * Configuration data nodes
     */

    augment &quot;/if:interfaces/if:interface&quot; {
      description
        &quot;Parameters for configuring IP on interfaces.

         If an interface is not capable of running IP, the server
         must not allow the client to configure these parameters.&quot;;

      container ipv4 {
        presence
          &quot;Enables IPv4 unless the &#x27;enabled&#x27; leaf
           (which defaults to &#x27;true&#x27;) is set to &#x27;false&#x27;&quot;;
        description
          &quot;Parameters for the IPv4 address family.&quot;;

<span class="grey"><a href="/doc/html/rfc7277">RFC 7277</a>                   YANG IP Management                  June 2014</span>

        leaf enabled {
          type boolean;
          default true;
          description
            &quot;Controls whether IPv4 is enabled or disabled on this
             interface.  When IPv4 is enabled, this interface is
             connected to an IPv4 stack, and the interface can send
             and receive IPv4 packets.&quot;;
        }
        leaf forwarding {
          type boolean;
          default false;
          description
            &quot;Controls IPv4 packet forwarding of datagrams received by,
             but not addressed to, this interface.  IPv4 routers
             forward datagrams.  IPv4 hosts do not (except those
             source-routed via the host).&quot;;
        }
        leaf mtu {
          type uint16 {
            range &quot;68..max&quot;;
          }
          units octets;
          description
            &quot;The size, in octets, of the largest IPv4 packet that the
             interface will send and receive.

             The server may restrict the allowed values for this leaf,
             depending on the interface&#x27;s type.

             If this leaf is not configured, the operationally used MTU
             depends on the interface&#x27;s type.&quot;;
          reference
            &quot;<a href="/doc/html/rfc791">RFC 791</a>: Internet Protocol&quot;;
        }
        list address {
          key &quot;ip&quot;;
          description
            &quot;The list of configured IPv4 addresses on the interface.&quot;;

          leaf ip {
            type inet:ipv4-address-no-zone;
            description
              &quot;The IPv4 address on the interface.&quot;;
          }

<span class="grey"><a href="/doc/html/rfc7277">RFC 7277</a>                   YANG IP Management                  June 2014</span>

          choice subnet {
            mandatory true;
            description
              &quot;The subnet can be specified as a prefix-length, or,
               if the server supports non-contiguous netmasks, as
               a netmask.&quot;;
            leaf prefix-length {
              type uint8 {
                range &quot;0..32&quot;;
              }
              description
                &quot;The length of the subnet prefix.&quot;;
            }
            leaf netmask {
              if-feature ipv4-non-contiguous-netmasks;
              type yang:dotted-quad;
              description
                &quot;The subnet specified as a netmask.&quot;;
            }
          }
        }
        list neighbor {
          key &quot;ip&quot;;
          description
            &quot;A list of mappings from IPv4 addresses to
             link-layer addresses.

             Entries in this list are used as static entries in the
             ARP Cache.&quot;;
          reference
            &quot;<a href="/doc/html/rfc826">RFC 826</a>: An Ethernet Address Resolution Protocol&quot;;

          leaf ip {
            type inet:ipv4-address-no-zone;
            description
              &quot;The IPv4 address of the neighbor node.&quot;;
          }
          leaf link-layer-address {
            type yang:phys-address;
            mandatory true;
            description
              &quot;The link-layer address of the neighbor node.&quot;;
          }
        }

      }

<span class="grey"><a href="/doc/html/rfc7277">RFC 7277</a>                   YANG IP Management                  June 2014</span>

      container ipv6 {
        presence
          &quot;Enables IPv6 unless the &#x27;enabled&#x27; leaf
           (which defaults to &#x27;true&#x27;) is set to &#x27;false&#x27;&quot;;
        description
          &quot;Parameters for the IPv6 address family.&quot;;

        leaf enabled {
          type boolean;
          default true;
          description
            &quot;Controls whether IPv6 is enabled or disabled on this
             interface.  When IPv6 is enabled, this interface is
             connected to an IPv6 stack, and the interface can send
             and receive IPv6 packets.&quot;;
        }
        leaf forwarding {
          type boolean;
          default false;
          description
            &quot;Controls IPv6 packet forwarding of datagrams received by,
             but not addressed to, this interface.  IPv6 routers
             forward datagrams.  IPv6 hosts do not (except those
             source-routed via the host).&quot;;
          reference
            &quot;<a href="/doc/html/rfc4861">RFC 4861</a>: Neighbor Discovery for IP version 6 (IPv6)
                       <a href="#section-6.2.1">Section 6.2.1</a>, IsRouter&quot;;
        }
        leaf mtu {
          type uint32 {
            range &quot;1280..max&quot;;
          }
          units octets;
          description
            &quot;The size, in octets, of the largest IPv6 packet that the
             interface will send and receive.

             The server may restrict the allowed values for this leaf,
             depending on the interface&#x27;s type.

             If this leaf is not configured, the operationally used MTU
             depends on the interface&#x27;s type.&quot;;
          reference
            &quot;<a href="/doc/html/rfc2460">RFC 2460</a>: Internet Protocol, Version 6 (IPv6) Specification
                       <a href="#section-5">Section 5</a>&quot;;
        }

<span class="grey"><a href="/doc/html/rfc7277">RFC 7277</a>                   YANG IP Management                  June 2014</span>

        list address {
          key &quot;ip&quot;;
          description
            &quot;The list of configured IPv6 addresses on the interface.&quot;;

          leaf ip {
            type inet:ipv6-address-no-zone;
            description
              &quot;The IPv6 address on the interface.&quot;;
          }
          leaf prefix-length {
            type uint8 {
              range &quot;0..128&quot;;
            }
            mandatory true;
            description
              &quot;The length of the subnet prefix.&quot;;
          }
        }
        list neighbor {
          key &quot;ip&quot;;
          description
            &quot;A list of mappings from IPv6 addresses to
             link-layer addresses.

             Entries in this list are used as static entries in the
             Neighbor Cache.&quot;;
          reference
            &quot;<a href="/doc/html/rfc4861">RFC 4861</a>: Neighbor Discovery for IP version 6 (IPv6)&quot;;

          leaf ip {
            type inet:ipv6-address-no-zone;
            description
              &quot;The IPv6 address of the neighbor node.&quot;;
          }
          leaf link-layer-address {
            type yang:phys-address;
            mandatory true;
            description
              &quot;The link-layer address of the neighbor node.&quot;;
          }
        }

<span class="grey"><a href="/doc/html/rfc7277">RFC 7277</a>                   YANG IP Management                  June 2014</span>

        leaf dup-addr-detect-transmits {
          type uint32;
          default 1;
          description
            &quot;The number of consecutive Neighbor Solicitation messages
             sent while performing Duplicate Address Detection on a
             tentative address.  A value of zero indicates that
             Duplicate Address Detection is not performed on
             tentative addresses.  A value of one indicates a single
             transmission with no follow-up retransmissions.&quot;;
          reference
            &quot;<a href="/doc/html/rfc4862">RFC 4862</a>: IPv6 Stateless Address Autoconfiguration&quot;;
        }
        container autoconf {
          description
            &quot;Parameters to control the autoconfiguration of IPv6
             addresses, as described in <a href="/doc/html/rfc4862">RFC 4862</a>.&quot;;
          reference
            &quot;<a href="/doc/html/rfc4862">RFC 4862</a>: IPv6 Stateless Address Autoconfiguration&quot;;

          leaf create-global-addresses {
            type boolean;
            default true;
            description
              &quot;If enabled, the host creates global addresses as
               described in <a href="/doc/html/rfc4862">RFC 4862</a>.&quot;;
            reference
              &quot;<a href="/doc/html/rfc4862">RFC 4862</a>: IPv6 Stateless Address Autoconfiguration
                         <a href="#section-5.5">Section 5.5</a>&quot;;
          }
          leaf create-temporary-addresses {
            if-feature ipv6-privacy-autoconf;
            type boolean;
            default false;
            description
              &quot;If enabled, the host creates temporary addresses as
               described in <a href="/doc/html/rfc4941">RFC 4941</a>.&quot;;
            reference
              &quot;<a href="/doc/html/rfc4941">RFC 4941</a>: Privacy Extensions for Stateless Address
                         Autoconfiguration in IPv6&quot;;
          }

<span class="grey"><a href="/doc/html/rfc7277">RFC 7277</a>                   YANG IP Management                  June 2014</span>

          leaf temporary-valid-lifetime {
            if-feature ipv6-privacy-autoconf;
            type uint32;
            units &quot;seconds&quot;;
            default 604800;
            description
              &quot;The time period during which the temporary address
               is valid.&quot;;
            reference
              &quot;<a href="/doc/html/rfc4941">RFC 4941</a>: Privacy Extensions for Stateless Address
                         Autoconfiguration in IPv6
                         - TEMP_VALID_LIFETIME&quot;;
          }
          leaf temporary-preferred-lifetime {
            if-feature ipv6-privacy-autoconf;
            type uint32;
            units &quot;seconds&quot;;
            default 86400;
            description
              &quot;The time period during which the temporary address is
               preferred.&quot;;
            reference
              &quot;<a href="/doc/html/rfc4941">RFC 4941</a>: Privacy Extensions for Stateless Address
                         Autoconfiguration in IPv6
                         - TEMP_PREFERRED_LIFETIME&quot;;
          }
        }
      }
    }

    /*
     * Operational state data nodes
     */

    augment &quot;/if:interfaces-state/if:interface&quot; {
      description
        &quot;Data nodes for the operational state of IP on interfaces.&quot;;

      container ipv4 {
        presence &quot;Present if IPv4 is enabled on this interface&quot;;
        config false;
        description
          &quot;Interface-specific parameters for the IPv4 address family.&quot;;

<span class="grey"><a href="/doc/html/rfc7277">RFC 7277</a>                   YANG IP Management                  June 2014</span>

        leaf forwarding {
          type boolean;
          description
            &quot;Indicates whether IPv4 packet forwarding is enabled or
             disabled on this interface.&quot;;
        }
        leaf mtu {
          type uint16 {
            range &quot;68..max&quot;;
          }
          units octets;
          description
            &quot;The size, in octets, of the largest IPv4 packet that the
             interface will send and receive.&quot;;
          reference
            &quot;<a href="/doc/html/rfc791">RFC 791</a>: Internet Protocol&quot;;
        }
        list address {
          key &quot;ip&quot;;
          description
            &quot;The list of IPv4 addresses on the interface.&quot;;

          leaf ip {
            type inet:ipv4-address-no-zone;
            description
              &quot;The IPv4 address on the interface.&quot;;
          }
          choice subnet {
            description
              &quot;The subnet can be specified as a prefix-length, or,
               if the server supports non-contiguous netmasks, as
               a netmask.&quot;;
            leaf prefix-length {
              type uint8 {
                range &quot;0..32&quot;;
              }
              description
                &quot;The length of the subnet prefix.&quot;;
            }
            leaf netmask {
              if-feature ipv4-non-contiguous-netmasks;
              type yang:dotted-quad;
              description
                &quot;The subnet specified as a netmask.&quot;;
            }
          }

<span class="grey"><a href="/doc/html/rfc7277">RFC 7277</a>                   YANG IP Management                  June 2014</span>

          leaf origin {
            type ip-address-origin;
            description
              &quot;The origin of this address.&quot;;
          }
        }
        list neighbor {
          key &quot;ip&quot;;
          description
            &quot;A list of mappings from IPv4 addresses to
             link-layer addresses.

             This list represents the ARP Cache.&quot;;
          reference
            &quot;<a href="/doc/html/rfc826">RFC 826</a>: An Ethernet Address Resolution Protocol&quot;;

          leaf ip {
            type inet:ipv4-address-no-zone;
            description
              &quot;The IPv4 address of the neighbor node.&quot;;
          }
          leaf link-layer-address {
            type yang:phys-address;
            description
              &quot;The link-layer address of the neighbor node.&quot;;
          }
          leaf origin {
            type neighbor-origin;
            description
              &quot;The origin of this neighbor entry.&quot;;
          }
        }

      }

      container ipv6 {
        presence &quot;Present if IPv6 is enabled on this interface&quot;;
        config false;
        description
          &quot;Parameters for the IPv6 address family.&quot;;

<span class="grey"><a href="/doc/html/rfc7277">RFC 7277</a>                   YANG IP Management                  June 2014</span>

        leaf forwarding {
          type boolean;
          default false;
          description
            &quot;Indicates whether IPv6 packet forwarding is enabled or
             disabled on this interface.&quot;;
          reference
            &quot;<a href="/doc/html/rfc4861">RFC 4861</a>: Neighbor Discovery for IP version 6 (IPv6)
                       <a href="#section-6.2.1">Section 6.2.1</a>, IsRouter&quot;;
        }
        leaf mtu {
          type uint32 {
            range &quot;1280..max&quot;;
          }
          units octets;
          description
            &quot;The size, in octets, of the largest IPv6 packet that the
             interface will send and receive.&quot;;
          reference
            &quot;<a href="/doc/html/rfc2460">RFC 2460</a>: Internet Protocol, Version 6 (IPv6) Specification
                       <a href="#section-5">Section 5</a>&quot;;
        }
        list address {
          key &quot;ip&quot;;
          description
            &quot;The list of IPv6 addresses on the interface.&quot;;

          leaf ip {
            type inet:ipv6-address-no-zone;
            description
              &quot;The IPv6 address on the interface.&quot;;
          }
          leaf prefix-length {
            type uint8 {
              range &quot;0..128&quot;;
            }
            mandatory true;
            description
              &quot;The length of the subnet prefix.&quot;;
          }
          leaf origin {
            type ip-address-origin;
            description
              &quot;The origin of this address.&quot;;
          }

<span class="grey"><a href="/doc/html/rfc7277">RFC 7277</a>                   YANG IP Management                  June 2014</span>

          leaf status {
            type enumeration {
              enum preferred {
                description
                  &quot;This is a valid address that can appear as the
                   destination or source address of a packet.&quot;;
              }
              enum deprecated {
                description
                  &quot;This is a valid but deprecated address that should
                   no longer be used as a source address in new
                   communications, but packets addressed to such an
                   address are processed as expected.&quot;;
              }
              enum invalid {
                description
                  &quot;This isn&#x27;t a valid address, and it shouldn&#x27;t appear
                   as the destination or source address of a packet.&quot;;
              }
              enum inaccessible {
                description
                  &quot;The address is not accessible because the interface
                   to which this address is assigned is not
                   operational.&quot;;
              }
              enum unknown {
                description
                  &quot;The status cannot be determined for some reason.&quot;;
              }
              enum tentative {
                description
                  &quot;The uniqueness of the address on the link is being
                   verified.  Addresses in this state should not be
                   used for general communication and should only be
                   used to determine the uniqueness of the address.&quot;;
              }
              enum duplicate {
                description
                  &quot;The address has been determined to be non-unique on
                   the link and so must not be used.&quot;;
              }

<span class="grey"><a href="/doc/html/rfc7277">RFC 7277</a>                   YANG IP Management                  June 2014</span>

              enum optimistic {
                description
                  &quot;The address is available for use, subject to
                   restrictions, while its uniqueness on a link is
                   being verified.&quot;;
              }
            }
            description
              &quot;The status of an address.  Most of the states correspond
               to states from the IPv6 Stateless Address
               Autoconfiguration protocol.&quot;;
            reference
              &quot;<a href="/doc/html/rfc4293">RFC 4293</a>: Management Information Base for the
                         Internet Protocol (IP)
                         - IpAddressStatusTC
               <a href="/doc/html/rfc4862">RFC 4862</a>: IPv6 Stateless Address Autoconfiguration&quot;;
          }
        }
        list neighbor {
          key &quot;ip&quot;;
          description
            &quot;A list of mappings from IPv6 addresses to
             link-layer addresses.

             This list represents the Neighbor Cache.&quot;;
          reference
            &quot;<a href="/doc/html/rfc4861">RFC 4861</a>: Neighbor Discovery for IP version 6 (IPv6)&quot;;

          leaf ip {
            type inet:ipv6-address-no-zone;
            description
              &quot;The IPv6 address of the neighbor node.&quot;;
          }
          leaf link-layer-address {
            type yang:phys-address;
            description
              &quot;The link-layer address of the neighbor node.&quot;;
          }
          leaf origin {
            type neighbor-origin;
            description
              &quot;The origin of this neighbor entry.&quot;;
          }
          leaf is-router {
            type empty;
            description
              &quot;Indicates that the neighbor node acts as a router.&quot;;
          }
<span class="grey"><a href="/doc/html/rfc7277">RFC 7277</a>                   YANG IP Management                  June 2014</span>

          leaf state {
            type enumeration {
              enum incomplete {
                description
                  &quot;Address resolution is in progress, and the link-layer
                   address of the neighbor has not yet been
                   determined.&quot;;
              }
              enum reachable {
                description
                  &quot;Roughly speaking, the neighbor is known to have been
                   reachable recently (within tens of seconds ago).&quot;;
              }
              enum stale {
                description
                  &quot;The neighbor is no longer known to be reachable, but
                   until traffic is sent to the neighbor no attempt
                   should be made to verify its reachability.&quot;;
              }
              enum delay {
                description
                  &quot;The neighbor is no longer known to be reachable, and
                   traffic has recently been sent to the neighbor.
                   Rather than probe the neighbor immediately, however,
                   delay sending probes for a short while in order to
                   give upper-layer protocols a chance to provide
                   reachability confirmation.&quot;;
              }
              enum probe {
                description
                  &quot;The neighbor is no longer known to be reachable, and
                   unicast Neighbor Solicitation probes are being sent
                   to verify reachability.&quot;;
              }
            }
            description
              &quot;The Neighbor Unreachability Detection state of this
               entry.&quot;;
            reference
              &quot;<a href="/doc/html/rfc4861">RFC 4861</a>: Neighbor Discovery for IP version 6 (IPv6)
                         <a href="#section-7.3.2">Section 7.3.2</a>&quot;;
          }
        }
      }
    }
   }
