module ietf-yang-library {
  namespace &quot;urn:ietf:params:xml:ns:yang:ietf-yang-library&quot;;
  prefix &quot;yanglib&quot;;

  import ietf-yang-types {
    prefix yang;
  }
  import ietf-inet-types {
    prefix inet;
  }

<span class="grey"><a href="/doc/html/rfc7895">RFC 7895</a>                      YANG Library                     June 2016</span>

     organization
       &quot;IETF NETCONF (Network Configuration) Working Group&quot;;

     contact
       &quot;WG Web:   &lt;<a href="https://datatracker.ietf.org/wg/netconf/">https://datatracker.ietf.org/wg/netconf/</a>&gt;
        WG List:  &lt;mailto:<a href="mailto:netconf@ietf.org">netconf@ietf.org</a>&gt;

        WG Chair: Mehmet Ersue
                  &lt;mailto:<a href="mailto:mehmet.ersue@nsn.com">mehmet.ersue@nsn.com</a>&gt;

        WG Chair: Mahesh Jethanandani
                  &lt;mailto:<a href="mailto:mjethanandani@gmail.com">mjethanandani@gmail.com</a>&gt;

        Editor:   Andy Bierman
                  &lt;mailto:<a href="mailto:andy@yumaworks.com">andy@yumaworks.com</a>&gt;

        Editor:   Martin Bjorklund
                  &lt;mailto:<a href="mailto:mbj@tail-f.com">mbj@tail-f.com</a>&gt;

        Editor:   Kent Watsen
                  &lt;mailto:<a href="mailto:kwatsen@juniper.net">kwatsen@juniper.net</a>&gt;&quot;;

     description
       &quot;This module contains monitoring information about the YANG
        modules and submodules that are used within a YANG-based
        server.

        Copyright (c) 2016 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc7895">RFC 7895</a>; see
        the RFC itself for full legal notices.&quot;;

     revision 2016-06-21 {
       description
         &quot;Initial revision.&quot;;
       reference
         &quot;<a href="/doc/html/rfc7895">RFC 7895</a>: YANG Module Library.&quot;;
     }

<span class="grey"><a href="/doc/html/rfc7895">RFC 7895</a>                      YANG Library                     June 2016</span>

     /*
      * Typedefs
      */

     typedef revision-identifier {
       type string {
         pattern &#x27;\d{4}-\d{2}-\d{2}&#x27;;
       }
       description
         &quot;Represents a specific date in YYYY-MM-DD format.&quot;;
     }

     /*
      * Groupings
      */

     grouping module-list {
       description
         &quot;The module data structure is represented as a grouping
          so it can be reused in configuration or another monitoring
          data structure.&quot;;

       grouping common-leafs {
         description
           &quot;Common parameters for YANG modules and submodules.&quot;;

         leaf name {
           type yang:yang-identifier;
           description
             &quot;The YANG module or submodule name.&quot;;
         }
         leaf revision {
           type union {
             type revision-identifier;
             type string { length 0; }
           }
           description
             &quot;The YANG module or submodule revision date.
              A zero-length string is used if no revision statement
              is present in the YANG module or submodule.&quot;;
         }
       }

       grouping schema-leaf {
         description
           &quot;Common schema leaf parameter for modules and submodules.&quot;;

<span class="grey"><a href="/doc/html/rfc7895">RFC 7895</a>                      YANG Library                     June 2016</span>

         leaf schema {
           type inet:uri;
           description
             &quot;Contains a URL that represents the YANG schema
              resource for this module or submodule.

              This leaf will only be present if there is a URL
              available for retrieval of the schema for this entry.&quot;;
         }
       }

       list module {
         key &quot;name revision&quot;;
         description
           &quot;Each entry represents one revision of one module
            currently supported by the server.&quot;;

         uses common-leafs;
         uses schema-leaf;

         leaf namespace {
           type inet:uri;
           mandatory true;
           description
             &quot;The XML namespace identifier for this module.&quot;;
         }
         leaf-list feature {
           type yang:yang-identifier;
           description
             &quot;List of YANG feature names from this module that are
              supported by the server, regardless of whether they are
              defined in the module or any included submodule.&quot;;
         }
         list deviation {
           key &quot;name revision&quot;;
           description
             &quot;List of YANG deviation module names and revisions
              used by this server to modify the conformance of
              the module associated with this entry.  Note that
              the same module can be used for deviations for
              multiple modules, so the same entry MAY appear
              within multiple &#x27;module&#x27; entries.

              The deviation module MUST be present in the &#x27;module&#x27;
              list, with the same name and revision values.
              The &#x27;conformance-type&#x27; value will be &#x27;implement&#x27; for
              the deviation module.&quot;;
           uses common-leafs;
<span class="grey"><a href="/doc/html/rfc7895">RFC 7895</a>                      YANG Library                     June 2016</span>

         }
         leaf conformance-type {
           type enumeration {
             enum implement {
               description
                 &quot;Indicates that the server implements one or more
                  protocol-accessible objects defined in the YANG module
                  identified in this entry.  This includes deviation
                  statements defined in the module.

                  For YANG version 1.1 modules, there is at most one
                  module entry with conformance type &#x27;implement&#x27; for a
                  particular module name, since YANG 1.1 requires that,
                  at most, one revision of a module is implemented.

                  For YANG version 1 modules, there SHOULD NOT be more
                  than one module entry for a particular module name.&quot;;
             }
             enum import {
               description
                 &quot;Indicates that the server imports reusable definitions
                  from the specified revision of the module but does
                  not implement any protocol-accessible objects from
                  this revision.

                  Multiple module entries for the same module name MAY
                  exist.  This can occur if multiple modules import the
                  same module but specify different revision dates in
                  the import statements.&quot;;
             }
           }
           mandatory true;
           description
             &quot;Indicates the type of conformance the server is claiming
              for the YANG module identified by this entry.&quot;;
         }
         list submodule {
           key &quot;name revision&quot;;
           description
             &quot;Each entry represents one submodule within the
              parent module.&quot;;
           uses common-leafs;
           uses schema-leaf;
         }
       }
     }

<span class="grey"><a href="/doc/html/rfc7895">RFC 7895</a>                      YANG Library                     June 2016</span>

     /*
      * Operational state data nodes
      */

     container modules-state {
       config false;
       description
         &quot;Contains YANG module monitoring information.&quot;;

       leaf module-set-id {
         type string;
         mandatory true;
         description
           &quot;Contains a server-specific identifier representing
            the current set of modules and submodules.  The
            server MUST change the value of this leaf if the
            information represented by the &#x27;module&#x27; list instances
            has changed.&quot;;
       }

       uses module-list;
     }

     /*
      * Notifications
      */

     notification yang-library-change {
       description
         &quot;Generated when the set of modules and submodules supported
          by the server has changed.&quot;;
       leaf module-set-id {
         type leafref {
           path &quot;/yanglib:modules-state/yanglib:module-set-id&quot;;
         }
         mandatory true;
         description
           &quot;Contains the module-set-id value representing the
            set of modules and submodules supported at the server at
            the time the notification is generated.&quot;;
       }
     }

   }
