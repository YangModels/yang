module ietf-netconf {

  // the namespace for NETCONF XML definitions is unchanged
  // from <a href="/doc/html/rfc4741">RFC 4741</a>, which this document replaces
  namespace &quot;urn:ietf:params:xml:ns:netconf:base:1.0&quot;;

  prefix nc;

  import ietf-inet-types {
    prefix inet;
  }

  organization
    &quot;IETF NETCONF (Network Configuration) Working Group&quot;;

  contact
    &quot;WG Web:   &lt;<a href="https://tools.ietf.org/wg/netconf/">http://tools.ietf.org/wg/netconf/</a>&gt;
     WG List:  &lt;<a href="mailto:netconf@ietf.org">netconf@ietf.org</a>&gt;

     WG Chair: Bert Wijnen
               &lt;<a href="mailto:bertietf@bwijnen.net">bertietf@bwijnen.net</a>&gt;

     WG Chair: Mehmet Ersue
               &lt;<a href="mailto:mehmet.ersue@nsn.com">mehmet.ersue@nsn.com</a>&gt;

     Editor:   Martin Bjorklund
               &lt;<a href="mailto:mbj@tail-f.com">mbj@tail-f.com</a>&gt;

     Editor:   Juergen Schoenwaelder
               &lt;<a href="mailto:j.schoenwaelder@jacobs-university.de">j.schoenwaelder@jacobs-university.de</a>&gt;

     Editor:   Andy Bierman
               &lt;<a href="mailto:andy.bierman@brocade.com">andy.bierman@brocade.com</a>&gt;&quot;;
<span class="grey"><a href="/doc/html/rfc6241">RFC 6241</a>                    NETCONF Protocol                   June 2011</span>

    description
      &quot;NETCONF Protocol Data Types and Protocol Operations.

       Copyright (c) 2011 IETF Trust and the persons identified as
       the document authors.  All rights reserved.

       Redistribution and use in source and binary forms, with or
       without modification, is permitted pursuant to, and subject
       to the license terms contained in, the Simplified BSD License
       set forth in <a href="#section-4">Section 4</a>.c of the IETF Trust&#x27;s Legal Provisions
       Relating to IETF Documents
       (<a href="https://trustee.ietf.org/license-info">http://trustee.ietf.org/license-info</a>).

       This version of this YANG module is part of <a href="/doc/html/rfc6241">RFC 6241</a>; see
       the RFC itself for full legal notices.&quot;;
    revision 2011-06-01 {
      description
        &quot;Initial revision&quot;;
      reference
        &quot;<a href="/doc/html/rfc6241">RFC 6241</a>: Network Configuration Protocol&quot;;
    }

    extension get-filter-element-attributes {
      description
        &quot;If this extension is present within an &#x27;anyxml&#x27;
         statement named &#x27;filter&#x27;, which must be conceptually
         defined within the RPC input section for the &lt;get&gt;
         and &lt;get-config&gt; protocol operations, then the
         following unqualified XML attribute is supported
         within the &lt;filter&gt; element, within a &lt;get&gt; or
         &lt;get-config&gt; protocol operation:

           type : optional attribute with allowed
                  value strings &#x27;subtree&#x27; and &#x27;xpath&#x27;.
                  If missing, the default value is &#x27;subtree&#x27;.

         If the &#x27;xpath&#x27; feature is supported, then the
         following unqualified XML attribute is
         also supported:

           select: optional attribute containing a
                   string representing an XPath expression.
                   The &#x27;type&#x27; attribute must be equal to &#x27;xpath&#x27;
                   if this attribute is present.&quot;;
    }

    // NETCONF capabilities defined as features
    feature writable-running {
<span class="grey"><a href="/doc/html/rfc6241">RFC 6241</a>                    NETCONF Protocol                   June 2011</span>

      description
        &quot;NETCONF :writable-running capability;
         If the server advertises the :writable-running
         capability for a session, then this feature must
         also be enabled for that session.  Otherwise,
         this feature must not be enabled.&quot;;
      reference &quot;<a href="/doc/html/rfc6241#section-8.2">RFC 6241, Section&amp;nbsp;8.2</a>&quot;;
    }

    feature candidate {
      description
        &quot;NETCONF :candidate capability;
         If the server advertises the :candidate
         capability for a session, then this feature must
         also be enabled for that session.  Otherwise,
         this feature must not be enabled.&quot;;
      reference &quot;<a href="/doc/html/rfc6241#section-8.3">RFC 6241, Section&amp;nbsp;8.3</a>&quot;;
    }

    feature confirmed-commit {
      if-feature candidate;
      description
        &quot;NETCONF :confirmed-commit:1.1 capability;
         If the server advertises the :confirmed-commit:1.1
         capability for a session, then this feature must
         also be enabled for that session.  Otherwise,
         this feature must not be enabled.&quot;;

      reference &quot;<a href="/doc/html/rfc6241#section-8.4">RFC 6241, Section&amp;nbsp;8.4</a>&quot;;
    }

    feature rollback-on-error {
      description
        &quot;NETCONF :rollback-on-error capability;
         If the server advertises the :rollback-on-error
         capability for a session, then this feature must
         also be enabled for that session.  Otherwise,
         this feature must not be enabled.&quot;;
      reference &quot;<a href="/doc/html/rfc6241#section-8.5">RFC 6241, Section&amp;nbsp;8.5</a>&quot;;
    }

    feature validate {
      description
        &quot;NETCONF :validate:1.1 capability;
         If the server advertises the :validate:1.1
         capability for a session, then this feature must
         also be enabled for that session.  Otherwise,
         this feature must not be enabled.&quot;;
<span class="grey"><a href="/doc/html/rfc6241">RFC 6241</a>                    NETCONF Protocol                   June 2011</span>

      reference &quot;<a href="/doc/html/rfc6241#section-8.6">RFC 6241, Section&amp;nbsp;8.6</a>&quot;;
    }

    feature startup {
      description
        &quot;NETCONF :startup capability;
         If the server advertises the :startup
         capability for a session, then this feature must
         also be enabled for that session.  Otherwise,
         this feature must not be enabled.&quot;;
      reference &quot;<a href="/doc/html/rfc6241#section-8.7">RFC 6241, Section&amp;nbsp;8.7</a>&quot;;
    }

    feature url {
      description
        &quot;NETCONF :url capability;
         If the server advertises the :url
         capability for a session, then this feature must
         also be enabled for that session.  Otherwise,
         this feature must not be enabled.&quot;;
      reference &quot;<a href="/doc/html/rfc6241#section-8.8">RFC 6241, Section&amp;nbsp;8.8</a>&quot;;
    }

    feature xpath {
      description
        &quot;NETCONF :xpath capability;
         If the server advertises the :xpath
         capability for a session, then this feature must
         also be enabled for that session.  Otherwise,
         this feature must not be enabled.&quot;;
      reference &quot;<a href="/doc/html/rfc6241#section-8.9">RFC 6241, Section&amp;nbsp;8.9</a>&quot;;
    }

    // NETCONF Simple Types

    typedef session-id-type {
      type uint32 {
        range &quot;1..max&quot;;
      }
      description
        &quot;NETCONF Session Id&quot;;
    }

    typedef session-id-or-zero-type {
      type uint32;
      description
        &quot;NETCONF Session Id or Zero to indicate none&quot;;
    }
<span class="grey"><a href="/doc/html/rfc6241">RFC 6241</a>                    NETCONF Protocol                   June 2011</span>

    typedef error-tag-type {
      type enumeration {
         enum in-use {
           description
             &quot;The request requires a resource that
              already is in use.&quot;;
         }
         enum invalid-value {
           description
             &quot;The request specifies an unacceptable value for one
              or more parameters.&quot;;
         }
         enum too-big {
           description
             &quot;The request or response (that would be generated) is
              too large for the implementation to handle.&quot;;
         }
         enum missing-attribute {
           description
             &quot;An expected attribute is missing.&quot;;
         }
         enum bad-attribute {
           description
             &quot;An attribute value is not correct; e.g., wrong type,
              out of range, pattern mismatch.&quot;;
         }
         enum unknown-attribute {
           description
             &quot;An unexpected attribute is present.&quot;;
         }
         enum missing-element {
           description
             &quot;An expected element is missing.&quot;;
         }
         enum bad-element {
           description
             &quot;An element value is not correct; e.g., wrong type,
              out of range, pattern mismatch.&quot;;
         }
         enum unknown-element {
           description
             &quot;An unexpected element is present.&quot;;
         }
         enum unknown-namespace {
           description
             &quot;An unexpected namespace is present.&quot;;
         }
         enum access-denied {
<span class="grey"><a href="/doc/html/rfc6241">RFC 6241</a>                    NETCONF Protocol                   June 2011</span>

           description
             &quot;Access to the requested protocol operation or
              data model is denied because authorization failed.&quot;;
         }
         enum lock-denied {
           description
             &quot;Access to the requested lock is denied because the
              lock is currently held by another entity.&quot;;
         }
         enum resource-denied {
           description
             &quot;Request could not be completed because of
              insufficient resources.&quot;;
         }
         enum rollback-failed {
           description
             &quot;Request to roll back some configuration change (via
              rollback-on-error or &lt;discard-changes&gt; operations)
              was not completed for some reason.&quot;;

         }
         enum data-exists {
           description
             &quot;Request could not be completed because the relevant
              data model content already exists.  For example,
              a &#x27;create&#x27; operation was attempted on data that
              already exists.&quot;;
         }
         enum data-missing {
           description
             &quot;Request could not be completed because the relevant
              data model content does not exist.  For example,
              a &#x27;delete&#x27; operation was attempted on
              data that does not exist.&quot;;
         }
         enum operation-not-supported {
           description
             &quot;Request could not be completed because the requested
              operation is not supported by this implementation.&quot;;
         }
         enum operation-failed {
           description
             &quot;Request could not be completed because the requested
              operation failed for some reason not covered by
              any other error condition.&quot;;
         }
         enum partial-operation {
           description
<span class="grey"><a href="/doc/html/rfc6241">RFC 6241</a>                    NETCONF Protocol                   June 2011</span>

             &quot;This error-tag is obsolete, and SHOULD NOT be sent
              by servers conforming to this document.&quot;;
         }
         enum malformed-message {
           description
             &quot;A message could not be handled because it failed to
              be parsed correctly.  For example, the message is not
              well-formed XML or it uses an invalid character set.&quot;;
         }
       }
       description &quot;NETCONF Error Tag&quot;;
       reference &quot;<a href="/doc/html/rfc6241#appendix-A">RFC 6241, Appendix&amp;nbsp;A</a>&quot;;
    }

    typedef error-severity-type {
      type enumeration {
        enum error {
          description &quot;Error severity&quot;;
        }
        enum warning {
          description &quot;Warning severity&quot;;
        }
      }
      description &quot;NETCONF Error Severity&quot;;
      reference &quot;<a href="/doc/html/rfc6241#section-4.3">RFC 6241, Section&amp;nbsp;4.3</a>&quot;;
    }

    typedef edit-operation-type {
      type enumeration {
        enum merge {
          description
            &quot;The configuration data identified by the
             element containing this attribute is merged
             with the configuration at the corresponding
             level in the configuration datastore identified
             by the target parameter.&quot;;
        }
        enum replace {
          description
            &quot;The configuration data identified by the element
             containing this attribute replaces any related
             configuration in the configuration datastore
             identified by the target parameter.  If no such
             configuration data exists in the configuration
             datastore, it is created.  Unlike a
             &lt;copy-config&gt; operation, which replaces the
             entire target configuration, only the configuration
             actually present in the config parameter is affected.&quot;;
<span class="grey"><a href="/doc/html/rfc6241">RFC 6241</a>                    NETCONF Protocol                   June 2011</span>

        }
        enum create {
          description
            &quot;The configuration data identified by the element
             containing this attribute is added to the
             configuration if and only if the configuration
             data does not already exist in the configuration
             datastore.  If the configuration data exists, an
             &lt;rpc-error&gt; element is returned with an
             &lt;error-tag&gt; value of &#x27;data-exists&#x27;.&quot;;
        }
        enum delete {
          description
            &quot;The configuration data identified by the element
             containing this attribute is deleted from the
             configuration if and only if the configuration
             data currently exists in the configuration
             datastore.  If the configuration data does not
             exist, an &lt;rpc-error&gt; element is returned with
             an &lt;error-tag&gt; value of &#x27;data-missing&#x27;.&quot;;
        }
        enum remove {
          description
            &quot;The configuration data identified by the element
             containing this attribute is deleted from the
             configuration if the configuration
             data currently exists in the configuration
             datastore.  If the configuration data does not
             exist, the &#x27;remove&#x27; operation is silently ignored
             by the server.&quot;;
        }
      }
      default &quot;merge&quot;;
      description &quot;NETCONF &#x27;operation&#x27; attribute values&quot;;
      reference &quot;<a href="/doc/html/rfc6241#section-7.2">RFC 6241, Section&amp;nbsp;7.2</a>&quot;;
    }

    // NETCONF Standard Protocol Operations

    rpc get-config {
      description
        &quot;Retrieve all or part of a specified configuration.&quot;;

      reference &quot;<a href="/doc/html/rfc6241#section-7.1">RFC 6241, Section&amp;nbsp;7.1</a>&quot;;

      input {
        container source {
          description
<span class="grey"><a href="/doc/html/rfc6241">RFC 6241</a>                    NETCONF Protocol                   June 2011</span>

            &quot;Particular configuration to retrieve.&quot;;

          choice config-source {
            mandatory true;
            description
              &quot;The configuration to retrieve.&quot;;
            leaf candidate {
              if-feature candidate;
              type empty;
              description
                &quot;The candidate configuration is the config source.&quot;;
            }
            leaf running {
              type empty;
              description
                &quot;The running configuration is the config source.&quot;;
            }
            leaf startup {
              if-feature startup;
              type empty;
              description
                &quot;The startup configuration is the config source.
                 This is optional-to-implement on the server because
                 not all servers will support filtering for this
                 datastore.&quot;;
            }
          }
        }

        anyxml filter {
          description
            &quot;Subtree or XPath filter to use.&quot;;
          nc:get-filter-element-attributes;
        }
      }

      output {
        anyxml data {
          description
            &quot;Copy of the source datastore subset that matched
             the filter criteria (if any).  An empty data container
             indicates that the request did not produce any results.&quot;;
        }
      }
    }

    rpc edit-config {
      description
<span class="grey"><a href="/doc/html/rfc6241">RFC 6241</a>                    NETCONF Protocol                   June 2011</span>

        &quot;The &lt;edit-config&gt; operation loads all or part of a specified
         configuration to the specified target configuration.&quot;;

      reference &quot;<a href="/doc/html/rfc6241#section-7.2">RFC 6241, Section&amp;nbsp;7.2</a>&quot;;

      input {
        container target {
          description
            &quot;Particular configuration to edit.&quot;;

          choice config-target {
            mandatory true;
            description
              &quot;The configuration target.&quot;;

            leaf candidate {
              if-feature candidate;
              type empty;
              description
                &quot;The candidate configuration is the config target.&quot;;
            }
            leaf running {
              if-feature writable-running;
              type empty;
              description
                &quot;The running configuration is the config source.&quot;;
            }
          }
        }

        leaf default-operation {
          type enumeration {
            enum merge {
              description
                &quot;The default operation is merge.&quot;;
            }
            enum replace {
              description
                &quot;The default operation is replace.&quot;;
            }
            enum none {
              description
                &quot;There is no default operation.&quot;;
            }
          }
          default &quot;merge&quot;;
          description
            &quot;The default operation to use.&quot;;
<span class="grey"><a href="/doc/html/rfc6241">RFC 6241</a>                    NETCONF Protocol                   June 2011</span>

        }

        leaf test-option {
          if-feature validate;
          type enumeration {
            enum test-then-set {
              description
                &quot;The server will test and then set if no errors.&quot;;
            }
            enum set {
              description
                &quot;The server will set without a test first.&quot;;
            }

            enum test-only {
              description
                &quot;The server will only test and not set, even
                 if there are no errors.&quot;;
            }
          }
          default &quot;test-then-set&quot;;
          description
            &quot;The test option to use.&quot;;
        }

        leaf error-option {
          type enumeration {
            enum stop-on-error {
              description
                &quot;The server will stop on errors.&quot;;
            }
            enum continue-on-error {
              description
                &quot;The server may continue on errors.&quot;;
            }
            enum rollback-on-error {
              description
                &quot;The server will roll back on errors.
                 This value can only be used if the &#x27;rollback-on-error&#x27;
                 feature is supported.&quot;;
            }
          }
          default &quot;stop-on-error&quot;;
          description
            &quot;The error option to use.&quot;;
        }

        choice edit-content {
<span class="grey"><a href="/doc/html/rfc6241">RFC 6241</a>                    NETCONF Protocol                   June 2011</span>

          mandatory true;
          description
            &quot;The content for the edit operation.&quot;;

          anyxml config {
            description
              &quot;Inline Config content.&quot;;
          }
          leaf url {
            if-feature url;
            type inet:uri;
            description
              &quot;URL-based config content.&quot;;
          }
        }
      }
    }

    rpc copy-config {
      description
        &quot;Create or replace an entire configuration datastore with the
         contents of another complete configuration datastore.&quot;;

      reference &quot;<a href="/doc/html/rfc6241#section-7.3">RFC 6241, Section&amp;nbsp;7.3</a>&quot;;

      input {
        container target {
          description
            &quot;Particular configuration to copy to.&quot;;

          choice config-target {
            mandatory true;
            description
              &quot;The configuration target of the copy operation.&quot;;

            leaf candidate {
              if-feature candidate;
              type empty;
              description
                &quot;The candidate configuration is the config target.&quot;;
            }
            leaf running {
              if-feature writable-running;
              type empty;
              description
                &quot;The running configuration is the config target.
                 This is optional-to-implement on the server.&quot;;
            }
<span class="grey"><a href="/doc/html/rfc6241">RFC 6241</a>                    NETCONF Protocol                   June 2011</span>

            leaf startup {
              if-feature startup;
              type empty;
              description
                &quot;The startup configuration is the config target.&quot;;
            }
            leaf url {
              if-feature url;
              type inet:uri;
              description
                &quot;The URL-based configuration is the config target.&quot;;
            }
          }
        }

        container source {
          description
            &quot;Particular configuration to copy from.&quot;;

          choice config-source {
            mandatory true;
            description
              &quot;The configuration source for the copy operation.&quot;;

            leaf candidate {
              if-feature candidate;
              type empty;
              description
                &quot;The candidate configuration is the config source.&quot;;
            }
            leaf running {
              type empty;
              description
                &quot;The running configuration is the config source.&quot;;
            }
            leaf startup {
              if-feature startup;
              type empty;
              description
                &quot;The startup configuration is the config source.&quot;;
            }
            leaf url {
              if-feature url;
              type inet:uri;
              description
                &quot;The URL-based configuration is the config source.&quot;;
            }
            anyxml config {
<span class="grey"><a href="/doc/html/rfc6241">RFC 6241</a>                    NETCONF Protocol                   June 2011</span>

              description
                &quot;Inline Config content: &lt;config&gt; element.  Represents
                 an entire configuration datastore, not
                 a subset of the running datastore.&quot;;
            }
          }
        }
      }
    }

    rpc delete-config {
      description
        &quot;Delete a configuration datastore.&quot;;

      reference &quot;<a href="/doc/html/rfc6241#section-7.4">RFC 6241, Section&amp;nbsp;7.4</a>&quot;;

      input {
        container target {
          description
            &quot;Particular configuration to delete.&quot;;

          choice config-target {
            mandatory true;
            description
              &quot;The configuration target to delete.&quot;;

            leaf startup {
              if-feature startup;
              type empty;
              description
                &quot;The startup configuration is the config target.&quot;;
            }
            leaf url {
              if-feature url;
              type inet:uri;
              description
                &quot;The URL-based configuration is the config target.&quot;;
            }
          }
        }
      }
    }

    rpc lock {
      description
        &quot;The lock operation allows the client to lock the configuration
         system of a device.&quot;;

<span class="grey"><a href="/doc/html/rfc6241">RFC 6241</a>                    NETCONF Protocol                   June 2011</span>

      reference &quot;<a href="/doc/html/rfc6241#section-7.5">RFC 6241, Section&amp;nbsp;7.5</a>&quot;;

      input {
        container target {
          description
            &quot;Particular configuration to lock.&quot;;

          choice config-target {
            mandatory true;
            description
              &quot;The configuration target to lock.&quot;;

            leaf candidate {
              if-feature candidate;
              type empty;
              description
                &quot;The candidate configuration is the config target.&quot;;
            }
            leaf running {
              type empty;
              description
                &quot;The running configuration is the config target.&quot;;
            }
            leaf startup {
              if-feature startup;
              type empty;
              description
                &quot;The startup configuration is the config target.&quot;;
            }
          }
        }
      }
    }

    rpc unlock {
      description
        &quot;The unlock operation is used to release a configuration lock,
         previously obtained with the &#x27;lock&#x27; operation.&quot;;

      reference &quot;<a href="/doc/html/rfc6241#section-7.6">RFC 6241, Section&amp;nbsp;7.6</a>&quot;;

      input {
        container target {
          description
            &quot;Particular configuration to unlock.&quot;;

          choice config-target {
            mandatory true;
<span class="grey"><a href="/doc/html/rfc6241">RFC 6241</a>                    NETCONF Protocol                   June 2011</span>

            description
              &quot;The configuration target to unlock.&quot;;

            leaf candidate {
              if-feature candidate;
              type empty;
              description
                &quot;The candidate configuration is the config target.&quot;;
            }
            leaf running {
              type empty;
              description
                &quot;The running configuration is the config target.&quot;;
            }
            leaf startup {
              if-feature startup;
              type empty;
              description
                &quot;The startup configuration is the config target.&quot;;
            }
          }
        }
      }
    }

    rpc get {
      description
        &quot;Retrieve running configuration and device state information.&quot;;

      reference &quot;<a href="/doc/html/rfc6241#section-7.7">RFC 6241, Section&amp;nbsp;7.7</a>&quot;;

      input {
        anyxml filter {
          description
            &quot;This parameter specifies the portion of the system
             configuration and state data to retrieve.&quot;;
          nc:get-filter-element-attributes;
        }
      }

      output {
        anyxml data {
          description
            &quot;Copy of the running datastore subset and/or state
             data that matched the filter criteria (if any).
             An empty data container indicates that the request did not
             produce any results.&quot;;
        }
<span class="grey"><a href="/doc/html/rfc6241">RFC 6241</a>                    NETCONF Protocol                   June 2011</span>

      }
    }

    rpc close-session {
      description
        &quot;Request graceful termination of a NETCONF session.&quot;;

      reference &quot;<a href="/doc/html/rfc6241#section-7.8">RFC 6241, Section&amp;nbsp;7.8</a>&quot;;
    }

    rpc kill-session {
      description
        &quot;Force the termination of a NETCONF session.&quot;;

      reference &quot;<a href="/doc/html/rfc6241#section-7.9">RFC 6241, Section&amp;nbsp;7.9</a>&quot;;

      input {
        leaf session-id {
          type session-id-type;
          mandatory true;
          description
            &quot;Particular session to kill.&quot;;
        }
      }
    }

    rpc commit {
      if-feature candidate;

      description
        &quot;Commit the candidate configuration as the device&#x27;s new
         current configuration.&quot;;

      reference &quot;<a href="/doc/html/rfc6241#section-8.3.4.1">RFC 6241, Section&amp;nbsp;8.3.4.1</a>&quot;;

      input {
        leaf confirmed {
          if-feature confirmed-commit;
          type empty;
          description
            &quot;Requests a confirmed commit.&quot;;
          reference &quot;<a href="/doc/html/rfc6241#section-8.3.4.1">RFC 6241, Section&amp;nbsp;8.3.4.1</a>&quot;;
        }

        leaf confirm-timeout {
          if-feature confirmed-commit;
          type uint32 {
            range &quot;1..max&quot;;
<span class="grey"><a href="/doc/html/rfc6241">RFC 6241</a>                    NETCONF Protocol                   June 2011</span>

          }
          units &quot;seconds&quot;;
          default &quot;600&quot;;   // 10 minutes
          description
            &quot;The timeout interval for a confirmed commit.&quot;;
          reference &quot;<a href="/doc/html/rfc6241#section-8.3.4.1">RFC 6241, Section&amp;nbsp;8.3.4.1</a>&quot;;
        }

        leaf persist {
          if-feature confirmed-commit;
          type string;
          description
            &quot;This parameter is used to make a confirmed commit
             persistent.  A persistent confirmed commit is not aborted
             if the NETCONF session terminates.  The only way to abort
             a persistent confirmed commit is to let the timer expire,
             or to use the &lt;cancel-commit&gt; operation.

             The value of this parameter is a token that must be given
             in the &#x27;persist-id&#x27; parameter of &lt;commit&gt; or
             &lt;cancel-commit&gt; operations in order to confirm or cancel
             the persistent confirmed commit.

             The token should be a random string.&quot;;
          reference &quot;<a href="/doc/html/rfc6241#section-8.3.4.1">RFC 6241, Section&amp;nbsp;8.3.4.1</a>&quot;;
        }

        leaf persist-id {
          if-feature confirmed-commit;
          type string;
          description
            &quot;This parameter is given in order to commit a persistent
             confirmed commit.  The value must be equal to the value
             given in the &#x27;persist&#x27; parameter to the &lt;commit&gt; operation.
             If it does not match, the operation fails with an
            &#x27;invalid-value&#x27; error.&quot;;
          reference &quot;<a href="/doc/html/rfc6241#section-8.3.4.1">RFC 6241, Section&amp;nbsp;8.3.4.1</a>&quot;;
        }

      }
    }

    rpc discard-changes {
      if-feature candidate;

      description
        &quot;Revert the candidate configuration to the current
         running configuration.&quot;;
<span class="grey"><a href="/doc/html/rfc6241">RFC 6241</a>                    NETCONF Protocol                   June 2011</span>

      reference &quot;<a href="/doc/html/rfc6241#section-8.3.4.2">RFC 6241, Section&amp;nbsp;8.3.4.2</a>&quot;;
    }

    rpc cancel-commit {
      if-feature confirmed-commit;
      description
        &quot;This operation is used to cancel an ongoing confirmed commit.
         If the confirmed commit is persistent, the parameter
         &#x27;persist-id&#x27; must be given, and it must match the value of the
         &#x27;persist&#x27; parameter.&quot;;
      reference &quot;<a href="/doc/html/rfc6241#section-8.4.4.1">RFC 6241, Section&amp;nbsp;8.4.4.1</a>&quot;;

      input {
        leaf persist-id {
          type string;
          description
            &quot;This parameter is given in order to cancel a persistent
             confirmed commit.  The value must be equal to the value
             given in the &#x27;persist&#x27; parameter to the &lt;commit&gt; operation.
             If it does not match, the operation fails with an
            &#x27;invalid-value&#x27; error.&quot;;
        }
      }
    }

    rpc validate {
      if-feature validate;

      description
        &quot;Validates the contents of the specified configuration.&quot;;

      reference &quot;<a href="/doc/html/rfc6241#section-8.6.4.1">RFC 6241, Section&amp;nbsp;8.6.4.1</a>&quot;;

      input {
        container source {
          description
            &quot;Particular configuration to validate.&quot;;

          choice config-source {
            mandatory true;
            description
              &quot;The configuration source to validate.&quot;;

            leaf candidate {
              if-feature candidate;
              type empty;
              description
                &quot;The candidate configuration is the config source.&quot;;
<span class="grey"><a href="/doc/html/rfc6241">RFC 6241</a>                    NETCONF Protocol                   June 2011</span>

            }
            leaf running {
              type empty;
              description
                &quot;The running configuration is the config source.&quot;;
            }
            leaf startup {
              if-feature startup;
              type empty;
              description
                &quot;The startup configuration is the config source.&quot;;
            }
            leaf url {
              if-feature url;
              type inet:uri;
              description
                &quot;The URL-based configuration is the config source.&quot;;
            }
            anyxml config {
              description
                &quot;Inline Config content: &lt;config&gt; element.  Represents
                 an entire configuration datastore, not
                 a subset of the running datastore.&quot;;
            }
          }
        }
      }
    }

  }
