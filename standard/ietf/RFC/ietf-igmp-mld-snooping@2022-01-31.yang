module ietf-igmp-mld-snooping {
  yang-version 1.1;
  namespace "urn:ietf:params:xml:ns:yang:ietf-igmp-mld-snooping";
  prefix ims;

  import ietf-inet-types {
    prefix inet;
    reference
      "RFC 6991: Common YANG Data Types";
  }
  import ietf-yang-types {
    prefix yang;
    reference
      "RFC 6991: Common YANG Data Types";
  }
  import ietf-interfaces {
    prefix if;
    reference
      "RFC 8343: A YANG Data Model for Interface Management";
  }
  import ietf-routing {
    prefix rt;
    reference
      "RFC 8349: A YANG Data Model for Routing Management (NMDA
       Version)";
  }
  import ietf-routing-types {
    prefix rt-types;
    reference
      "RFC 8294: Common YANG Data Types for the Routing Area";
  }
  import ieee802-dot1q-bridge {
    prefix dot1q;
    reference
      "dot1Qcp: IEEE 802.1Qcp-2018 Standard for Local and
       Metropolitan area networks--Bridges and Bridged Networks
       --Amendment 30: YANG Data Model";
  }

  organization
    "IETF PIM Working Group";
  contact
    "WG Web:   &lt;http://datatracker.ietf.org/wg/pim/&gt;
     WG List:  &lt;mailto:pim@ietf.org&gt;

     Editors:  Hongji Zhao
               &lt;mailto:hongji.zhao@ericsson.com&gt;

               Xufeng Liu
               &lt;mailto:xufeng.liu.ietf@gmail.com&gt;

               Yisong Liu
               &lt;mailto:liuyisong@chinamobile.com&gt;

               Anish Peter
               &lt;mailto:anish.ietf@gmail.com&gt;

               Mahesh Sivakumar
               &lt;mailto:sivakumar.mahesh@gmail.com&gt;

    ";
  description
    "The module defines a collection of YANG definitions common for
     all devices that implement Internet Group Management Protocol
     (IGMP) and Multicast Listener Discovery (MLD) snooping, which is
     described in RFC 4541.

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (http://trustee.ietf.org/license-info).

     This version of this YANG module is part of RFC 9166; see the
     RFC itself for full legal notices.";

  revision 2022-01-31 {
    description
      "Initial revision.";
    reference
      "RFC 9166: A YANG Data Model for Internet Group Management
       Protocol (IGMP) and Multicast Listener Discovery (MLD)
       Snooping";
  }

  /*
   * Features
   */

  feature igmp-snooping {
    description
      "Support IGMP snooping.";
    reference
      "RFC 4541: Considerations for Internet Group Management
       Protocol (IGMP) and Multicast Listener Discovery (MLD)
       Snooping Switches";
  }

  feature mld-snooping {
    description
      "Support MLD snooping.";
    reference
      "RFC 4541: Considerations for Internet Group Management
       Protocol (IGMP) and Multicast Listener Discovery (MLD)
       Snooping Switches";
  }

  feature fast-leave {
    description
      "Support configuration of fast leave.  The fast leave feature
       does not send last member query messages to hosts.";
    reference
      "RFC 3376: Internet Group Management Protocol, Version 3";
  }

  feature static-l2-multicast-group {
    description
      "Support configuration of static L2 multicast group.";
  }

  feature static-mrouter-interface {
    description
      "Support multicast router interface explicitly configured
       by management.";
    reference
      "RFC 4541: Considerations for Internet Group Management
       Protocol (IGMP) and Multicast Listener Discovery (MLD)
       Snooping Switches";
  }

  feature action-clear-groups {
    description
      "Support clearing statistics by action for IGMP and MLD
       snooping.";
  }

  feature require-router-alert {
    description
      "Support configuration of require-router-alert.";
    reference
      "RFC 3376: Internet Group Management Protocol, Version 3";
  }

  feature lite-exclude-filter {
    description
      "Enable the support of the simplified EXCLUDE filter.";
    reference
      "RFC 5790: Lightweight Internet Group Management Protocol
       Version 3 (IGMPv3) and Multicast Listener Discovery Version
       2 (MLDv2) Protocols";
  }

  feature explicit-tracking {
    description
      "Support configuration of per-instance explicit-tracking.";
    reference
      "RFC 6636: Tuning the Behavior of the Internet Group Management
       Protocol (IGMP) and Multicast Listener Discovery (MLD) for
       Routers in Mobile and Wireless Networks";
  }

  /* identities */

  identity l2-service-type {
    description
      "Base identity for L2 service type in IGMP and MLD snooping.";
  }

  identity bridge {
    base l2-service-type;
    description
      "This identity represents bridge service.";
  }

  identity filter-mode {
    description
      "Base identity for filter mode in IGMP and MLD snooping.";
  }

  identity include {
    base filter-mode;
    description
      "This identity represents include mode.";
  }

  identity exclude {
    base filter-mode;
    description
      "This identity represents exclude mode.";
  }

  identity igmp-snooping {
    base rt:control-plane-protocol;
    description
      "IGMP snooping.";
  }

  identity mld-snooping {
    base rt:control-plane-protocol;
    description
      "MLD snooping.";
  }

  /*
   * Typedefs
   */

  typedef l2-service-type {
    type identityref {
      base l2-service-type;
    }
    description
      "The L2 service type used with IGMP and MLD
       snooping.";
  }

  typedef filter-mode-type {
    type identityref {
      base filter-mode;
    }
    description
      "The host filter mode.";
  }

  typedef igmp-mld-snooping-instance-ref {
    type leafref {
      path "/rt:routing/rt:control-plane-protocols"
         + "/rt:control-plane-protocol/rt:name";
    }
    description
      "This type is used by data models that need to
       reference IGMP or MLD snooping instance.";
  }

  /*
   * Groupings
   */

  grouping instance-config-attributes-igmp-mld-snooping {
    description
      "IGMP and MLD snooping configuration of each VLAN.";
    leaf enabled {
      type boolean;
      default "false";
      description
        "Set the value to true to enable IGMP and MLD snooping.";
    }
    leaf forwarding-table-type {
      type enumeration {
        enum mac {
          description
            "MAC-based lookup mode.";
        }
        enum ip {
          description
            "IP-based lookup mode.";
        }
      }
      default "ip";
      description
        "The default forwarding table type is ip.";
    }
    leaf explicit-tracking {
      if-feature "explicit-tracking";
      type boolean;
      default "false";
      description
        "Track the IGMPv3 and MLDv2 snooping membership reports
         from individual hosts.  It contributes to saving network
         resources and shortening leave latency.";
    }
    leaf lite-exclude-filter {
      if-feature "lite-exclude-filter";
      type empty;
      description
        "For IGMP snooping, the presence of this
         leaf enables the support of the simplified EXCLUDE filter
         in the Lightweight IGMPv3 protocol, which simplifies the
         standard versions of IGMPv3.
         For MLD Snooping, the presence of this
         leaf enables the support of the simplified EXCLUDE filter
         in the Lightweight MLDv2 protocol, which simplifies the
         standard versions of MLDv2.";
      reference
        "RFC 5790: Lightweight Internet Group Management Protocol
         Version 3 (IGMPv3) and Multicast Listener Discovery Version
         2 (MLDv2) Protocols";
    }
    leaf send-query {
      type boolean;
      default "false";
      description
        "When it is true, this switch will send out a periodic IGMP
         General Query Message or MLD General Query Message.";
    }
    leaf fast-leave {
      if-feature "fast-leave";
      type empty;
      description
        "When fast leave is enabled, the software assumes
         that no more than one host is present on each VLAN port.";
    }
    leaf last-member-query-interval {
      type uint16 {
        range "10..10230";
      }
      units "deciseconds";
      default "10";
      description
        "Last Member Query Interval, which may be tuned to modify
         the leave latency of the network.
         It is represented in units of 1/10 second.";
      reference
        "RFC 3376: Internet Group Management Protocol, Version 3,
         Section 8.8";
    }
    leaf query-interval {
      type uint16;
      units "seconds";
      default "125";
      description
        "The Query Interval is the interval between General Queries
         sent by the Querier.";
      reference
        "RFC 3376: Internet Group Management Protocol, Version 3,
         Sections 4.1.7, 8.2, and 8.14.2";
    }
    leaf query-max-response-time {
      type uint16;
      units "deciseconds";
      default "100";
      description
        "Query maximum response time specifies the maximum time
         allowed before sending a responding report.
         It is represented in units of 1/10 second.";
      reference
        "RFC 3376: Internet Group Management Protocol, Version 3,
         Sections 4.1.1, 8.3, and 8.14.3";
    }
    leaf require-router-alert {
      if-feature "require-router-alert";
      type boolean;
      default "false";
      description
        "When the value is true, a router alert should exist
         in the IP header of the IGMP or MLD packet.  If it
         doesn't exist, the IGMP or MLD packet will be ignored.";
      reference
        "RFC 3376: Internet Group Management Protocol, Version 3,
         Sections 9.1, 9.2, and 9.3";
    }
    leaf robustness-variable {
      type uint8 {
        range "1..7";
      }
      default "2";
      description
        "Querier's Robustness Variable allows tuning for the
         expected packet loss on a network.";
      reference
        "RFC 3376: Internet Group Management Protocol, Version 3,
         Sections 4.1.6, 8.1, and 8.14.1";
    }
    leaf-list static-bridge-mrouter-interface {
      when 'derived-from-or-self(../l2-service-type,"ims:bridge")';
      if-feature "static-mrouter-interface";
      type if:interface-ref;
      description
        "Static mrouter interface in bridge forwarding";
    }
  } // instance-config-attributes-igmp-mld-snooping

  grouping instance-state-group-attributes-igmp-mld-snooping {
    description
      "Attributes for both IGMP and MLD snooping groups.";
    leaf mac-address {
      type yang:phys-address;
      description
        "Destination MAC address for L2 multicast.";
    }
    leaf expire {
      type rt-types:timer-value-seconds16;
      units "seconds";
      description
        "The time left before multicast group timeout.";
    }
    leaf up-time {
      type uint32;
      units "seconds";
      mandatory true;
      description
        "The time elapsed since the L2 multicast record was
         created.";
    }
  } // instance-state-group-attributes-igmp-mld-snooping

  grouping instance-state-attributes-igmp-mld-snooping {
    description
      "State attributes for IGMP or MLD snooping instance.";
    leaf entries-count {
      type yang:gauge32;
      config false;
      description
        "The number of L2 multicast entries in IGMP and MLD
         snooping.";
    }
    leaf-list bridge-mrouter-interface {
      when 'derived-from-or-self(../l2-service-type,"ims:bridge")';
      type if:interface-ref;
      config false;
      description
        "Indicates a list of mrouter interfaces dynamically learned
         in a bridge.  When this switch receives IGMP/MLD queries
         from a multicast router on an interface, the interface will
         become an mrouter interface for IGMP/MLD snooping.";
    }
  } // instance-config-attributes-igmp-mld-snooping

  grouping instance-state-source-attributes-igmp-mld-snooping {
    description
      "State attributes for IGMP or MLD snooping instance.";
    leaf-list bridge-outgoing-interface {
      when 'derived-from-or-self(../../../l2-service-type,
            "ims:bridge")';
      type if:interface-ref;
      description
        "Outgoing interface in bridge forwarding.";
    }
    leaf up-time {
      type uint32;
      units "seconds";
      mandatory true;
      description
        "The time elapsed since L2 multicast record was created.";
    }
    leaf expire {
      type rt-types:timer-value-seconds16;
      units "seconds";
      description
        "The time left before multicast group timeout.";
    }
    leaf host-count {
      if-feature "explicit-tracking";
      type yang:gauge32;
      description
        "The number of host addresses.";
    }
  } // instance-state-source-attributes-igmp-mld-snooping

  grouping igmp-snooping-statistics {
    description
      "The statistics attributes for IGMP snooping.";
    leaf query-count {
      type yang:counter64;
      description
        "The number of Membership Query messages.";
      reference
        "RFC 2236: Internet Group Management Protocol, Version 2";
    }
    leaf membership-report-v1-count {
      type yang:counter64;
      description
        "The number of Version 1 Membership Report messages.";
      reference
        "RFC 1112: Host extensions for IP multicasting";
    }
    leaf membership-report-v2-count {
      type yang:counter64;
      description
        "The number of Version 2 Membership Report messages.";
      reference
        "RFC 2236: Internet Group Management Protocol, Version 2";
    }
    leaf membership-report-v3-count {
      type yang:counter64;
      description
        "The number of Version 3 Membership Report messages.";
      reference
        "RFC 3376: Internet Group Management Protocol, Version 3";
    }
    leaf leave-count {
      type yang:counter64;
      description
        "The number of Leave Group messages.";
      reference
        "RFC 2236: Internet Group Management Protocol, Version 2";
    }
    leaf pim-hello-count {
      type yang:counter64;
      description
        "The number of PIM hello messages.";
      reference
        "RFC 7761: Protocol Independent Multicast - Sparse Mode
         (PIM-SM): Protocol Specification (Revised)";
    }
  } // igmp-snooping-statistics

  grouping mld-snooping-statistics {
    description
      "The statistics attributes for MLD snooping.";
    leaf query-count {
      type yang:counter64;
      description
        "The number of Multicast Listener Query messages.";
      reference
        "RFC 3810: Multicast Listener Discovery Version 2 (MLDv2)
         for IPv6";
    }
    leaf report-v1-count {
      type yang:counter64;
      description
        "The number of Version 1 Multicast Listener Report.";
      reference
        "RFC 2710: Multicast Listener Discovery (MLD) for IPv6";
    }
    leaf report-v2-count {
      type yang:counter64;
      description
        "The number of Version 2 Multicast Listener Report.";
      reference
        "RFC 3810: Multicast Listener Discovery Version 2 (MLDv2)
         for IPv6";
    }
    leaf done-count {
      type yang:counter64;
      description
        "The number of Version 1 Multicast Listener Done.";
      reference
        "RFC 2710: Multicast Listener Discovery (MLD) for IPv6";
    }
    leaf pim-hello-count {
      type yang:counter64;
      description
        "The number of PIM hello messages.";
      reference
        "RFC 7761: Protocol Independent Multicast - Sparse Mode
         (PIM-SM): Protocol Specification (Revised)";
    }
  } // mld-snooping-statistics

  augment "/rt:routing/rt:control-plane-protocols"
        + "/rt:control-plane-protocol" {
    when 'derived-from-or-self(rt:type, "ims:igmp-snooping")' {
      description
        "This container is only valid for IGMP snooping.";
    }
    description
      "IGMP snooping augmentation to control-plane protocol
       configuration and state.";
    container igmp-snooping-instance {
      if-feature "igmp-snooping";
      description
        "IGMP snooping instance to configure igmp-snooping.";
      leaf l2-service-type {
        type l2-service-type;
        default "bridge";
        description
          "It indicates bridge or other services.";
      }
      uses instance-config-attributes-igmp-mld-snooping;
      leaf igmp-version {
        type uint8 {
          range "1..3";
        }
        default "2";
        description
          "IGMP version.";
      }
      leaf querier-source {
        type inet:ipv4-address;
        description
          "The source address of the IGMP General Query message,
           which is sent out by this switch.";
      }
      list static-l2-multicast-group {
        if-feature "static-l2-multicast-group";
        key "group source-addr";
        description
          "A static multicast route, (*,G) or (S,G).";
        leaf group {
          type rt-types:ipv4-multicast-group-address;
          description
            "Multicast group IPv4 address.";
        }
        leaf source-addr {
          type rt-types:ipv4-multicast-source-address;
          description
            "Multicast source IPv4 address.";
        }
        leaf-list bridge-outgoing-interface {
          when 'derived-from-or-self(../../l2-service-type,
                "ims:bridge")';
          type if:interface-ref;
          description
            "Outgoing interface in bridge forwarding.";
        }
      } // static-l2-multicast-group
      uses instance-state-attributes-igmp-mld-snooping;
      list group {
        key "address";
        config false;
        description
          "IGMP snooping information.";
        leaf address {
          type rt-types:ipv4-multicast-group-address;
          description
            "Multicast group IPv4 address.";
        }
        uses instance-state-group-attributes-igmp-mld-snooping;
        leaf last-reporter {
          type inet:ipv4-address;
          description
            "Address of the last host that has sent a report to join
             the multicast group.";
        }
        list source {
          key "address";
          description
            "Source IPv4 address for multicast stream.";
          leaf address {
            type rt-types:ipv4-multicast-source-address;
            description
              "Source IPv4 address for multicast stream.";
          }
          uses instance-state-source-attributes-igmp-mld-snooping;
          leaf last-reporter {
            type inet:ipv4-address;
            description
              "Address of the last host that has sent a report
               to join the multicast group.";
          }
          list host {
            if-feature "explicit-tracking";
            key "address";
            description
              "List of multicast membership hosts
               of the specific multicast source group.";
            leaf address {
              type inet:ipv4-address;
              description
                "Multicast membership host address.";
            }
            leaf filter-mode {
              type filter-mode-type;
              mandatory true;
              description
                "Filter mode for a multicast membership
                 host may be either include or exclude.";
            }
          } // list host
        } // list source
      } // list group
      container interfaces {
        config false;
        description
          "Contains the interfaces associated with the IGMP snooping
           instance.";
        list interface {
          key "name";
          description
            "A list of interfaces associated with the IGMP snooping
             instance.";
          leaf name {
            type if:interface-ref;
            description
              "The name of the interface.";
          }
          container statistics {
            description
              "The interface statistics for IGMP snooping.";
            leaf discontinuity-time {
              type yang:date-and-time;
              description
                "The time on the most recent occasion at which any
                 one or more of the statistic counters suffered a
                 discontinuity.  If no such discontinuities have
                 occurred since the last re-initialization of the
                 local management subsystem, then this node contains
                 the time the local management subsystem
                 re-initialized itself.";
            }
            container received {
              description
                "Number of received snooped IGMP packets.";
              uses igmp-snooping-statistics;
            }
            container sent {
              description
                "Number of sent snooped IGMP packets.";
              uses igmp-snooping-statistics;
            }
          }
        }
      }
      action clear-igmp-snooping-groups {
        if-feature "action-clear-groups";
        description
          "Clear IGMP snooping cache tables.";
        input {
          leaf group {
            type union {
              type enumeration {
                enum all-groups {
                  description
                    "All multicast group addresses.";
                }
              }
              type rt-types:ipv4-multicast-group-address;
            }
            mandatory true;
            description
              "Multicast group IPv4 address.  If value
               'all-groups' is specified, all IGMP snooping
               group entries are cleared for the specified source
               address.";
          }
          leaf source {
            type rt-types:ipv4-multicast-source-address;
            mandatory true;
            description
              "Multicast source IPv4 address.  If value '*' is
               specified, all IGMP snooping source-group tables
               are cleared.";
          }
        }
      } // action clear-igmp-snooping-groups
    } // igmp-snooping-instance
  } // augment

  augment "/rt:routing/rt:control-plane-protocols"
        + "/rt:control-plane-protocol" {
    when 'derived-from-or-self(rt:type, "ims:mld-snooping")' {
      description
        "This container is only valid for MLD snooping.";
    }
    description
      "MLD snooping augmentation to control-plane protocol
       configuration and state.";
    container mld-snooping-instance {
      if-feature "mld-snooping";
      description
        "MLD snooping instance to configure mld-snooping.";
      leaf l2-service-type {
        type l2-service-type;
        default "bridge";
        description
          "It indicates bridge or other services.";
      }
      uses instance-config-attributes-igmp-mld-snooping;
      leaf mld-version {
        type uint8 {
          range "1..2";
        }
        default "2";
        description
          "MLD version.";
      }
      leaf querier-source {
        type inet:ipv6-address;
        description
          "The source address of MLD General Query message, which
           is sent out by this switch.";
      }
      list static-l2-multicast-group {
        if-feature "static-l2-multicast-group";
        key "group source-addr";
        description
          "A static multicast route, (*,G) or (S,G).";
        leaf group {
          type rt-types:ipv6-multicast-group-address;
          description
            "Multicast group IPv6 address.";
        }
        leaf source-addr {
          type rt-types:ipv6-multicast-source-address;
          description
            "Multicast source IPv6 address.";
        }
        leaf-list bridge-outgoing-interface {
          when 'derived-from-or-self(../../l2-service-type,
                "ims:bridge")';
          type if:interface-ref;
          description
            "Outgoing interface in bridge forwarding.";
        }
      } // static-l2-multicast-group
      uses instance-state-attributes-igmp-mld-snooping;
      list group {
        key "address";
        config false;
        description
          "MLD snooping statistics information.";
        leaf address {
          type rt-types:ipv6-multicast-group-address;
          description
            "Multicast group IPv6 address.";
        }
        uses instance-state-group-attributes-igmp-mld-snooping;
        leaf last-reporter {
          type inet:ipv6-address;
          description
            "Address of the last host that has sent report
             to join the multicast group.";
        }
        list source {
          key "address";
          description
            "Source IPv6 address for multicast stream.";
          leaf address {
            type rt-types:ipv6-multicast-source-address;
            description
              "Source IPv6 address for multicast stream.";
          }
          uses instance-state-source-attributes-igmp-mld-snooping;
          leaf last-reporter {
            type inet:ipv6-address;
            description
              "Address of the last host that has sent report
               to join the multicast group.";
          }
          list host {
            if-feature "explicit-tracking";
            key "address";
            description
              "List of multicast membership hosts
               of the specific multicast source group.";
            leaf address {
              type inet:ipv6-address;
              description
                "Multicast membership host address.";
            }
            leaf filter-mode {
              type filter-mode-type;
              mandatory true;
              description
                "Filter mode for a multicast membership
                 host may be either include or exclude.";
            }
          } // list host
        } // list source
      } // list group
      container interfaces {
        config false;
        description
          "Contains the interfaces associated with the MLD snooping
           instance.";
        list interface {
          key "name";
          description
            "A list of interfaces associated with the MLD snooping
             instance.";
          leaf name {
            type if:interface-ref;
            description
              "The name of the interface.";
          }
          container statistics {
            description
              "The interface statistics for MLD snooping.";
            leaf discontinuity-time {
              type yang:date-and-time;
              description
                "The time on the most recent occasion at which
                 any one or more of the statistic counters suffered
                 a discontinuity.  If no such discontinuities have
                 occurred since the last re-initialization of the
                 local management subsystem, then this node contains
                 the time the local management subsystem
                 re-initialized itself.";
            }
            container received {
              description
                "Number of received snooped MLD packets.";
              uses mld-snooping-statistics;
            }
            container sent {
              description
                "Number of sent snooped MLD packets.";
              uses mld-snooping-statistics;
            }
          }
        }
      }
      action clear-mld-snooping-groups {
        if-feature "action-clear-groups";
        description
          "Clear MLD snooping cache tables.";
        input {
          leaf group {
            type union {
              type enumeration {
                enum all-groups {
                  description
                    "All multicast group addresses.";
                }
              }
              type rt-types:ipv6-multicast-group-address;
            }
            mandatory true;
            description
              "Multicast group IPv6 address.  If value 'all-groups'
               is specified, all MLD snooping group entries are
               cleared for the specified source address.";
          }
          leaf source {
            type rt-types:ipv6-multicast-source-address;
            mandatory true;
            description
              "Multicast source IPv6 address.  If value '*' is
               specified, all MLD snooping source-group tables
               are cleared.";
          }
        }
      } // action clear-mld-snooping-groups
    } // mld-snooping-instance
  } // augment

  augment "/dot1q:bridges/dot1q:bridge" {
    description
      "Use IGMP or MLD snooping instance in bridge.";
    leaf igmp-snooping-instance {
      type igmp-mld-snooping-instance-ref;
      description
        "Configure IGMP snooping instance under bridge view.";
    }
    leaf mld-snooping-instance {
      type igmp-mld-snooping-instance-ref;
      description
        "Configure MLD snooping instance under bridge view.";
    }
  }

  augment "/dot1q:bridges/dot1q:bridge"
        + "/dot1q:component/dot1q:bridge-vlan/dot1q:vlan" {
    description
      "Use IGMP or MLD snooping instance in a certain VLAN
       of bridge.";
    leaf igmp-snooping-instance {
      type igmp-mld-snooping-instance-ref;
      description
        "Configure IGMP snooping instance under VLAN view.";
    }
    leaf mld-snooping-instance {
      type igmp-mld-snooping-instance-ref;
      description
        "Configure MLD snooping instance under VLAN view.";
    }
  }
}
