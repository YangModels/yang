submodule ietf-snmp-target {

  belongs-to ietf-snmp {
    prefix snmp;
  }

  import ietf-inet-types {
    prefix inet;
  }

  include ietf-snmp-common;

  organization
    &quot;IETF NETMOD (NETCONF Data Modeling Language) Working Group&quot;;

  contact
    &quot;WG Web:   &lt;<a href="https://tools.ietf.org/wg/netmod/">http://tools.ietf.org/wg/netmod/</a>&gt;
     WG List:  &lt;mailto:<a href="mailto:netmod@ietf.org">netmod@ietf.org</a>&gt;

     WG Chair: Thomas Nadeau
               &lt;mailto:<a href="mailto:tnadeau@lucidvision.com">tnadeau@lucidvision.com</a>&gt;

     WG Chair: Juergen Schoenwaelder
               &lt;mailto:<a href="mailto:j.schoenwaelder@jacobs-university.de">j.schoenwaelder@jacobs-university.de</a>&gt;

     Editor:   Martin Bjorklund
               &lt;mailto:<a href="mailto:mbj@tail-f.com">mbj@tail-f.com</a>&gt;

     Editor:   Juergen Schoenwaelder
               &lt;mailto:<a href="mailto:j.schoenwaelder@jacobs-university.de">j.schoenwaelder@jacobs-university.de</a>&gt;&quot;;

  description
    &quot;This submodule contains a collection of YANG definitions
     for configuring SNMP targets.

     Copyright (c) 2014 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).
<span class="grey"><a href="/doc/html/rfc7407">RFC 7407</a>         YANG Data Model for SNMP Configuration    December 2014</span>

        This version of this YANG module is part of <a href="/doc/html/rfc7407">RFC 7407</a>; see
        the RFC itself for full legal notices.&quot;;

     reference
       &quot;<a href="/doc/html/rfc3413">RFC 3413</a>: Simple Network Management Protocol (SNMP)
          Applications&quot;;

     revision 2014-12-10 {
       description
         &quot;Initial revision.&quot;;
       reference
         &quot;<a href="/doc/html/rfc7407">RFC 7407</a>: A YANG Data Model for SNMP Configuration&quot;;
     }

     augment /snmp:snmp {

       list target {
         key name;
         description
           &quot;List of targets.&quot;;
         reference
           &quot;<a href="/doc/html/rfc3413">RFC 3413</a>: Simple Network Management Protocol (SNMP)
              Applications.
              SNMP-TARGET-MIB.snmpTargetAddrTable&quot;;

         leaf name {
           type snmp:identifier;
           description
             &quot;Identifies the target.&quot;;
           reference
             &quot;<a href="/doc/html/rfc3413">RFC 3413</a>: Simple Network Management Protocol (SNMP)
                Applications.
                SNMP-TARGET-MIB.snmpTargetAddrName&quot;;
         }
         choice transport {
           mandatory true;
           description
             &quot;Transport address of the target.

              The snmpTargetAddrTDomain and snmpTargetAddrTAddress
              objects are mapped to transport-specific YANG nodes.  Each
              transport is configured as a separate case in this
              choice.  Submodules providing configuration for additional
              transports are expected to augment this choice.&quot;;

<span class="grey"><a href="/doc/html/rfc7407">RFC 7407</a>         YANG Data Model for SNMP Configuration    December 2014</span>

           reference
             &quot;<a href="/doc/html/rfc3413">RFC 3413</a>: Simple Network Management Protocol (SNMP)
                Applications.
                SNMP-TARGET-MIB.snmpTargetAddrTDomain
                SNMP-TARGET-MIB.snmpTargetAddrTAddress&quot;;
           case udp {
             reference
              &quot;<a href="/doc/html/rfc3417">RFC 3417</a>: Transport Mappings for the Simple Network
                 Management Protocol (SNMP).
                 SNMPv2-TM.snmpUDPDomain
               <a href="/doc/html/rfc3419">RFC 3419</a>: Textual Conventions for Transport Addresses.
                 TRANSPORT-ADDRESS-MIB.transportDomainUdpIpv4
                 TRANSPORT-ADDRESS-MIB.transportDomainUdpIpv4z
                 TRANSPORT-ADDRESS-MIB.transportDomainUdpIpv6
                 TRANSPORT-ADDRESS-MIB.transportDomainUdpIpv6z&quot;;
             container udp {
               leaf ip {
                 type inet:ip-address;
                 mandatory true;
                 reference
                   &quot;<a href="/doc/html/rfc3413">RFC 3413</a>: Simple Network Management Protocol (SNMP).
                      SNMP-TARGET-MIB.snmpTargetAddrTAddress&quot;;
               }
               leaf port {
                 type inet:port-number;
                 default 162;
                 description
                   &quot;UDP port number.&quot;;
                 reference
                   &quot;<a href="/doc/html/rfc3413">RFC 3413</a>: Simple Network Management Protocol (SNMP).
                      SNMP-TARGET-MIB.snmpTargetAddrTAddress&quot;;
               }
               leaf prefix-length {
                 type uint8;
                 description
                   &quot;The value of this leaf must match the value of
                    ../snmp:ip.  If ../snmp:ip contains an IPv4 address,
                    this leaf must be less than or equal to 32.  If it
                    contains an IPv6 address, it must be less than or
                    equal to 128.

                    Note that the prefix-length is currently only used
                    by the Community-based Security Model to filter
                    incoming messages.  Furthermore, the prefix-length
                    filtering does not cover all possible filters
                    supported by the corresponding MIB object.&quot;;

<span class="grey"><a href="/doc/html/rfc7407">RFC 7407</a>         YANG Data Model for SNMP Configuration    December 2014</span>

                 reference
                   &quot;<a href="/doc/html/rfc3584">RFC 3584</a>: Coexistence between Version 1, Version 2,
                      and Version 3 of the Internet-standard
                      Network Management Framework.
                      SNMP-COMMUNITY-MIB.snmpTargetAddrTMask&quot;;
               }
             }
           }
         }
         leaf-list tag {
           type snmp:tag-value;
           description
             &quot;List of tag values used to select target addresses.&quot;;
           reference
             &quot;<a href="/doc/html/rfc3413">RFC 3413</a>: Simple Network Management Protocol (SNMP).
                Applications.
                SNMP-TARGET-MIB.snmpTargetAddrTagList&quot;;
         }
         leaf timeout {
           type uint32;
           units &quot;0.01 seconds&quot;;
           default 1500;
           description
             &quot;Needed only if this target can receive
              InformRequest-PDUs.&quot;;
           reference
             &quot;<a href="/doc/html/rfc3413">RFC 3413</a>: Simple Network Management Protocol (SNMP).
                Applications.
                SNMP-TARGET-MIB.snmpTargetAddrTimeout&quot;;
         }
         leaf retries {
           type uint8;
           default 3;
           description
             &quot;Needed only if this target can receive
              InformRequest-PDUs.&quot;;
           reference
             &quot;<a href="/doc/html/rfc3413">RFC 3413</a>: Simple Network Management Protocol (SNMP).
                Applications.
                SNMP-TARGET-MIB.snmpTargetAddrRetryCount&quot;;
         }
         leaf target-params {
           type snmp:identifier;
           mandatory true;
           reference
             &quot;<a href="/doc/html/rfc3413">RFC 3413</a>: Simple Network Management Protocol (SNMP).
                Applications.
                SNMP-TARGET-MIB.snmpTargetAddrParams&quot;;
<span class="grey"><a href="/doc/html/rfc7407">RFC 7407</a>         YANG Data Model for SNMP Configuration    December 2014</span>

         }
       }

       list target-params {
         key name;
         description
           &quot;List of target parameters.&quot;;
         reference
           &quot;<a href="/doc/html/rfc3413">RFC 3413</a>: Simple Network Management Protocol (SNMP).
              Applications.
              SNMP-TARGET-MIB.snmpTargetParamsTable&quot;;

         leaf name {
           type snmp:identifier;
         }
         choice params {
           description
             &quot;This choice is augmented with case nodes containing
              configuration parameters specific to the security model.&quot;;
         }
       }
     }
   }
