module ietf-vrrp {
  yang-version 1.1;
  namespace &quot;urn:ietf:params:xml:ns:yang:ietf-vrrp&quot;;
  prefix &quot;vrrp&quot;;

  import ietf-inet-types {
    prefix &quot;inet&quot;;
  }

  import ietf-yang-types {
    prefix &quot;yang&quot;;
  }

  import ietf-interfaces {
    prefix &quot;if&quot;;
  }

  import ietf-ip {
    prefix &quot;ip&quot;;
  }

  organization
    &quot;IETF Routing Area Working Group (RTGWG)&quot;;
  contact
    &quot;WG Web:   &lt;<a href="https://datatracker.ietf.org/wg/rtgwg/">https://datatracker.ietf.org/wg/rtgwg/</a>&gt;
     WG List:  &lt;mailto:<a href="mailto:rtgwg@ietf.org">rtgwg@ietf.org</a>&gt;

     Editor:   Xufeng Liu
               &lt;mailto:<a href="mailto:xufeng.liu.ietf@gmail.com">xufeng.liu.ietf@gmail.com</a>&gt;

     Editor:   Athanasios Kyparlis
               &lt;mailto:<a href="mailto:Athanasios_Kyparlis@jabil.com">Athanasios_Kyparlis@jabil.com</a>&gt;
     Editor:   Ravi Parikh
               &lt;mailto:<a href="mailto:parikhr@vmware.com">parikhr@vmware.com</a>&gt;

     Editor:   Acee Lindem
               &lt;mailto:<a href="mailto:acee@cisco.com">acee@cisco.com</a>&gt;

     Editor:   Mingui Zhang
               &lt;mailto:<a href="mailto:zhangmingui@huawei.com">zhangmingui@huawei.com</a>&gt;&quot;;

<span class="grey"><a href="/doc/html/rfc8347">RFC 8347</a>                        YANG VRRP                     March 2018</span>

     description
       &quot;This YANG module defines a model for managing Virtual Router
        Redundancy Protocol (VRRP) versions 2 and 3.

        Copyright (c) 2018 IETF Trust and the persons identified as
        authors of the code.  All rights reserved.

        Redistribution and use in source and binary forms, with or
        without modification, is permitted pursuant to, and subject to
        the license terms contained in, the Simplified BSD License set
        forth in <a href="#section-4">Section 4</a>.c of the IETF Trust&#x27;s Legal Provisions
        Relating to IETF Documents
        (<a href="https://trustee.ietf.org/license-info">https://trustee.ietf.org/license-info</a>).

        This version of this YANG module is part of <a href="/doc/html/rfc8347">RFC 8347</a>; see the
        RFC itself for full legal notices.&quot;;

     revision 2018-03-13 {
       description
         &quot;Initial revision.&quot;;
       reference
         &quot;<a href="/doc/html/rfc8347">RFC 8347</a>: A YANG Data Model for the Virtual Router Redundancy
                    Protocol (VRRP)
          <a href="/doc/html/rfc2787">RFC 2787</a>: Definitions of Managed Objects for the Virtual
                    Router Redundancy Protocol
          <a href="/doc/html/rfc3768">RFC 3768</a>: Virtual Router Redundancy Protocol (VRRP)
          <a href="/doc/html/rfc5798">RFC 5798</a>: Virtual Router Redundancy Protocol (VRRP)
                    Version 3 for IPv4 and IPv6
          <a href="/doc/html/rfc6527">RFC 6527</a>: Definitions of Managed Objects for the Virtual
                    Router Redundancy Protocol Version 3 (VRRPv3)&quot;;
     }

     /*
      * Features
      */

     feature validate-interval-errors {
       description
         &quot;This feature indicates that the system validates that the
          advertisement interval from advertisement packets received
          is the same as the interval configured for the local
          VRRP router.&quot;;
     }

     feature validate-address-list-errors {
       description
         &quot;This feature indicates that the system validates that
          the address list from received packets matches the
<span class="grey"><a href="/doc/html/rfc8347">RFC 8347</a>                        YANG VRRP                     March 2018</span>

          locally configured list for the VRRP router.&quot;;
     }

     /*
      * Typedefs
      */

     typedef new-master-reason-type {
       type enumeration {
         enum not-master {
           description
             &quot;The virtual router has never transitioned to master
              state.&quot;;
         }
         enum priority {
           description
             &quot;Priority was higher.&quot;;
         }
         enum preempted {
           description
             &quot;The master was preempted.&quot;;
         }
         enum no-response {
           description
             &quot;Previous master did not respond.&quot;;
         }
       }
       description
         &quot;Indicates why the virtual router has transitioned to
          master state.&quot;;
     } // new-master-reason-type

     /*
      * Identities
      */

     /* vrrp-event-type identity and its derivatives. */
     identity vrrp-event-type {
       description
         &quot;Indicates the type of a VRRP protocol event.&quot;;
     }
     identity vrrp-event-none {
       base vrrp-event-type;
       description
         &quot;Indicates a non-meaningful event.&quot;;
     }
     identity vrrp-event-startup {
       base vrrp-event-type;
<span class="grey"><a href="/doc/html/rfc8347">RFC 8347</a>                        YANG VRRP                     March 2018</span>

       description
         &quot;Indicates that a VRRP router has initiated the protocol.&quot;;
     }
     identity vrrp-event-shutdown {
       base vrrp-event-type;
       description
         &quot;Indicates that a VRRP router has closed down the protocol.&quot;;
     }
     identity vrrp-event-higher-priority-backup {
       base vrrp-event-type;
       description
         &quot;Indicates that a backup router has a higher priority than
          the current master.&quot;;
     }
     identity vrrp-event-master-timeout {
       base vrrp-event-type;
       description
         &quot;Indicates that the current master has not sent an
          advertisement within the limit of master-down-interval.&quot;;
     }
     identity vrrp-event-interface-up {
       base vrrp-event-type;
       description
         &quot;Indicates that the VRRP-enabled interface has become
          &#x27;operational up&#x27;.&quot;;
     }
     identity vrrp-event-interface-down {
       base vrrp-event-type;
       description
         &quot;Indicates that the VRRP-enabled interface has become
          &#x27;operational down&#x27;.&quot;;
     }
     identity vrrp-event-no-primary-ip-address {
       base vrrp-event-type;
       description
         &quot;Indicates that the primary IP address on the VRRP-enabled
          interface has become unavailable.&quot;;
     }
     identity vrrp-event-primary-ip-address {
       base vrrp-event-type;
       description
         &quot;Indicates that the primary IP address on the VRRP-enabled
          interface has become available.&quot;;
     }
     identity vrrp-event-no-virtual-ip-addresses {
       base vrrp-event-type;
       description
         &quot;Indicates that there are no virtual IP addresses on the
<span class="grey"><a href="/doc/html/rfc8347">RFC 8347</a>                        YANG VRRP                     March 2018</span>

          virtual router.&quot;;
     }
     identity vrrp-event-virtual-ip-addresses {
       base vrrp-event-type;
       description
         &quot;Indicates that there are virtual IP addresses on the
          virtual router.&quot;;
     }
     identity vrrp-event-preempt-hold-timeout {
       base vrrp-event-type;
       description
         &quot;Indicates that the configured preemption hold time has
          passed.&quot;;
     }
     identity vrrp-event-lower-priority-master {
       base vrrp-event-type;
       description
         &quot;Indicates that there is a lower-priority VRRP master.&quot;;
     }
     identity vrrp-event-owner-preempt {
       base vrrp-event-type;
       description
         &quot;Indicates that the owner has preempted another router to
          become the master.&quot;;
     }

     /* vrrp-error-global identity and its derivatives. */
     identity vrrp-error-global {
       description
         &quot;Indicates the type of a VRRP error that occurred
          for a packet before it reaches a VRRP router.&quot;;
     }
     identity checksum-error {
       base vrrp-error-global;
       description
         &quot;A packet has been received with an invalid VRRP checksum
          value.&quot;;
     }
     identity ip-ttl-error {
       base vrrp-error-global;
       description
         &quot;A packet has been received with IP TTL (Time-To-Live)
          not equal to 255.&quot;;
     }
     identity version-error {
       base vrrp-error-global;
       description
         &quot;A packet has been received with an unknown or unsupported
<span class="grey"><a href="/doc/html/rfc8347">RFC 8347</a>                        YANG VRRP                     March 2018</span>

          version number.&quot;;
     }
     identity vrid-error {
       base vrrp-error-global;
       description
         &quot;A packet has been received with a Virtual Router Identifier
          (VRID) that is not valid for any virtual router on this
          router.&quot;;
     }

     /* vrrp-error-virtual-router identity and its derivatives. */
     identity vrrp-error-virtual-router {
       description
         &quot;Indicates the type of a VRRP error that occurred
          after a packet reaches a VRRP router.&quot;;
     }
     identity address-list-error {
       base vrrp-error-virtual-router;
       description
         &quot;A packet has been received with an address list that
          does not match the locally configured address list for
          the virtual router.&quot;;
     }
     identity interval-error {
       base vrrp-error-virtual-router;
       description
         &quot;A packet has been received with an advertisement interval
          different than the interval configured for the local
          virtual router.&quot;;
     }
     identity packet-length-error {
       base vrrp-error-virtual-router;
       description
         &quot;A packet has been received with a packet length less
          than the length of the VRRP header.&quot;;
     }

     /* vrrp-state-type identity and its derivatives. */
     identity vrrp-state-type {
       description
         &quot;Indicates the state of a virtual router.&quot;;
     }
     identity initialize {
       base vrrp-state-type;
       description
         &quot;Indicates that the virtual router is waiting
          for a startup event.&quot;;
     }
<span class="grey"><a href="/doc/html/rfc8347">RFC 8347</a>                        YANG VRRP                     March 2018</span>

     identity backup {
       base vrrp-state-type;
       description
         &quot;Indicates that the virtual router is monitoring the
          availability of the master router.&quot;;
     }
     identity master {
       base vrrp-state-type;
       description
         &quot;Indicates that the virtual router is forwarding
          packets for IP addresses that are associated with
          this virtual router.&quot;;
     }

     /* vrrp-version identity and its derivatives. */
     identity vrrp-version {
       description
         &quot;The version of VRRP.&quot;;
     }
     identity vrrp-v2 {
       base vrrp-version;
       description
         &quot;Indicates version 2 of VRRP.&quot;;
     }
     identity vrrp-v3 {
       base vrrp-version;
       description
         &quot;Indicates version 3 of VRRP.&quot;;
     }

     /*
      * Groupings
      */

     grouping vrrp-common-attributes {
       description
         &quot;Group of VRRP attributes common to versions 2 and 3.&quot;;

       leaf vrid {
         type uint8 {
           range &quot;1..255&quot;;
         }
         description
           &quot;Virtual Router ID (i.e., VRID).&quot;;
       }

       leaf version {
         type identityref {
<span class="grey"><a href="/doc/html/rfc8347">RFC 8347</a>                        YANG VRRP                     March 2018</span>

           base vrrp:vrrp-version;
         }
         mandatory true;
         description
           &quot;Version 2 or 3 of VRRP.&quot;;
       }

       leaf log-state-change {
         type boolean;
         default &quot;false&quot;;
         description
           &quot;Generates VRRP state change messages each time the
            VRRP instance changes state (from &#x27;up&#x27; to &#x27;down&#x27;
            or &#x27;down&#x27; to &#x27;up&#x27;).&quot;;
       }

       container preempt {
         description
           &quot;Enables a higher-priority VRRP backup router to preempt a
            lower-priority VRRP master.&quot;;
         leaf enabled {
           type boolean;
           default &quot;true&quot;;
           description
             &quot;&#x27;true&#x27; if preemption is enabled.&quot;;
         }
         leaf hold-time {
           type uint16;
           units seconds;
           default 0;
           description
             &quot;Hold time, in seconds, for which a higher-priority VRRP
              backup router must wait before preempting a lower-priority
              VRRP master.&quot;;
         }
       }

       leaf priority {
         type uint8 {
           range &quot;1..254&quot;;
         }
         default 100;
         description
           &quot;Configures the VRRP election priority for the backup
            virtual router.&quot;;
       }

       leaf accept-mode {
<span class="grey"><a href="/doc/html/rfc8347">RFC 8347</a>                        YANG VRRP                     March 2018</span>

         when &quot;derived-from-or-self(current()/../version, &#x27;vrrp-v3&#x27;)&quot; {
           description
             &quot;Applicable only to version 3.&quot;;
         }
         type boolean;
         default &quot;false&quot;;
         description
           &quot;Controls whether a virtual router in master state will
            accept packets addressed to the address owner&#x27;s IPvX address
            as its own if it is not the IPvX address owner.  The default
            is &#x27;false&#x27;.  Deployments that rely on, for example, pinging
            the address owner&#x27;s IPvX address may wish to configure
            accept-mode to &#x27;true&#x27;.

            Note: IPv6 Neighbor Solicitations and Neighbor
            Advertisements MUST NOT be dropped when accept-mode
            is &#x27;false&#x27;.&quot;;
       }
     } // vrrp-common-attributes

     grouping vrrp-ipv4-attributes {
       description
         &quot;Group of VRRP attributes for IPv4.&quot;;

       uses vrrp-common-attributes;

       choice advertise-interval-choice {
         description
           &quot;The options for the advertisement interval at which VRRPv2
            or VRRPv3 advertisements are sent from the specified
            interface.&quot;;

         case v2 {
           when &quot;derived-from-or-self(version, &#x27;vrrp-v2&#x27;)&quot; {
             description
               &quot;Applicable only to version 2.&quot;;
           }
           leaf advertise-interval-sec {
             type uint8 {
               range &quot;1..254&quot;;
             }
             units seconds;
             default 1;
             description
               &quot;Configures the interval that VRRPv2 advertisements
                are sent from the specified interface.&quot;;
           }
         }
<span class="grey"><a href="/doc/html/rfc8347">RFC 8347</a>                        YANG VRRP                     March 2018</span>

         case v3 {
           when &quot;derived-from-or-self(version, &#x27;vrrp-v3&#x27;)&quot; {
             description
               &quot;Applicable only to version 3.&quot;;
           }
           leaf advertise-interval-centi-sec {
             type uint16 {
               range &quot;1..4095&quot;;
             }
             units centiseconds;
             default 100;
             description
               &quot;Configures the interval that VRRPv3 advertisements
                are sent from the specified interface.&quot;;
           }
         }
       } // advertise-interval-choice

       container track {
         description
           &quot;Enables the specified VRRP instance to track interfaces
            or networks.&quot;;
         container interfaces {
           description
             &quot;Enables the specified VRRPv2 or VRRPv3 instance to track
              interfaces.  Interface tracking prevents traffic loss by
              detecting the availability of interfaces.  The operational
              states of other interfaces are associated with the
              priority of a VRRP router.  When a tracked interface
              becomes unavailable (or &#x27;operational down&#x27;), the priority
              of the VRRP router decrements.  When an unavailable
              interface becomes available again, the priority of the
              VRRP router is incremented by the same amount.&quot;;

           list interface {
             key &quot;interface&quot;;
             description
               &quot;Interface to track.&quot;;
             leaf interface {
               type if:interface-ref;
               must &quot;/if:interfaces/if:interface[if:name=current()]/&quot;
                  + &quot;ip:ipv4&quot; {
                 description
                   &quot;Interface is IPv4.&quot;;
               }
               description
                 &quot;Interface to track.&quot;;
             }
<span class="grey"><a href="/doc/html/rfc8347">RFC 8347</a>                        YANG VRRP                     March 2018</span>

             leaf priority-decrement {
               type uint8 {
                 range &quot;1..254&quot;;
               }
               default 10;
               description
                 &quot;Specifies how much to decrement the priority of the
                  VRRP instance if the interface goes down.&quot;;
             }
           } // interface
         } // interfaces

         container networks {
           description
             &quot;Enables the VRRPv2 or VRRPv3 router instance to track the
              specified networks through their IPv4 network prefixes.
              Network tracking prevents traffic loss by detecting
              network connectivity failure.  The states of
              connectivity to some networks are associated with the
              priority of a VRRP router.  When connectivity to a
              tracked network represented by its prefix is lost, the
              priority of the VRRP router decrements.  When an
              unavailable network is again reachable, the priority of
              the VRRP router is incremented by the same amount.&quot;;
           list network {
             key &quot;prefix&quot;;
             description
               &quot;Enables the specified VRRPv2 or VRRPv3 instance to
                track an IPv4 network by specifying the prefix of the
                IPv4 network.&quot;;

             leaf prefix {
               type inet:ipv4-prefix;
               description
                 &quot;The IPv4 prefix of the network to track.&quot;;
             }

             leaf priority-decrement {
               type uint8 {
                 range &quot;1..254&quot;;
               }
               default 10;
               description
                 &quot;Specifies how much to decrement the priority of the
                  VRRP router if there is a failure in the IPv4
                  network.&quot;;
             }
           } // network
<span class="grey"><a href="/doc/html/rfc8347">RFC 8347</a>                        YANG VRRP                     March 2018</span>

         } // networks
       } // track

       container virtual-ipv4-addresses {
         description
           &quot;Configures the virtual IPv4 address for the
            VRRP interface.&quot;;

         list virtual-ipv4-address {
           key &quot;ipv4-address&quot;;
           max-elements 16;
           description
             &quot;Virtual IPv4 addresses for a single VRRP instance.  For a
              VRRP owner router, the virtual address must match one
              of the IPv4 addresses configured on the interface
              corresponding to the virtual router.&quot;;

           leaf ipv4-address {
             type inet:ipv4-address;
             description
               &quot;An IPv4 address associated with a virtual router.&quot;;
             reference
               &quot;<a href="/doc/html/rfc5798">RFC 5798</a>: Virtual Router Redundancy Protocol (VRRP)
                          Version 3 for IPv4 and IPv6.  <a href="#section-1.2">Section 1.2</a>&quot;;
           }
         } // virtual-ipv4-address
       } // virtual-ipv4-addresses
     } // vrrp-ipv4-attributes

     grouping vrrp-ipv6-attributes {
       description
         &quot;Group of VRRP attributes for IPv6.&quot;;

       uses vrrp-common-attributes;

       leaf advertise-interval-centi-sec {
         type uint16 {
           range &quot;1..4095&quot;;
         }
         units centiseconds;
         default 100;
         description
           &quot;Configures the interval that VRRPv3 advertisements
            are sent from the specified interface.&quot;;
       }

       container track {
         description
<span class="grey"><a href="/doc/html/rfc8347">RFC 8347</a>                        YANG VRRP                     March 2018</span>

           &quot;Enables the specified VRRP instance to track interfaces
            or networks.&quot;;
         container interfaces {
           description
             &quot;Enables the specified VRRPv2 or VRRPv3 instance to track
              interfaces.  Interface tracking prevents traffic loss by
              detecting the availability of interfaces.  The operational
              states of other interfaces are associated with the
              priority of a VRRP router.  When a tracked interface
              becomes unavailable (or &#x27;operational down&#x27;), the priority
              of the VRRP router decrements.  When an unavailable
              interface becomes available again, the priority of the
              VRRP router is incremented by the same amount.&quot;;
           list interface {
             key &quot;interface&quot;;
             description
               &quot;Interface to track.&quot;;

             leaf interface {
               type if:interface-ref;
               must &quot;/if:interfaces/if:interface[if:name=current()]/&quot;
                  + &quot;ip:ipv6&quot; {
                 description
                   &quot;Interface is IPv6.&quot;;
               }
               description
                 &quot;Interface to track.&quot;;
             }

             leaf priority-decrement {
               type uint8 {
                 range &quot;1..254&quot;;
               }
               default 10;
               description
                 &quot;Specifies how much to decrement the priority of the
                  VRRP instance if the interface goes down.&quot;;
             }
           } // interface
         } // interfaces

         container networks {
           description
             &quot;Enables the VRRPv2 or VRRPv3 router instance to track the
              specified networks through their IPv6 network prefixes.
              Network tracking prevents traffic loss by detecting
              network connectivity failure.  The states of
              connectivity to some networks are associated with the
<span class="grey"><a href="/doc/html/rfc8347">RFC 8347</a>                        YANG VRRP                     March 2018</span>

              priority of a VRRP router.  When connectivity to a
              tracked network represented by its prefix is lost, the
              priority of the VRRP router decrements.  When an
              unavailable network is again reachable, the priority of
              the VRRP router is incremented by the same amount.&quot;;
           list network {
             key &quot;prefix&quot;;
             description
               &quot;Enables the specified VRRPv2 or VRRPv3 instance to
                track an IPv6 network by specifying the prefix of the
                IPv6 network.&quot;;

             leaf prefix {
               type inet:ipv6-prefix;
               description
                 &quot;The IPv6 prefix of the network to track.&quot;;
             }

             leaf priority-decrement {
               type uint8 {
                 range &quot;1..254&quot;;
               }
               default 10;
               description
                 &quot;Specifies how much to decrement the priority of the
                  VRRP router if there is a failure in the IPv6
                  network.&quot;;
             }
           } // network
         } // networks
       } // track

       container virtual-ipv6-addresses {
         description
           &quot;Configures the virtual IPv6 address for the
            VRRP interface.&quot;;
         list virtual-ipv6-address {
           key &quot;ipv6-address&quot;;
           max-elements 2;
           description
             &quot;Two IPv6 addresses are allowed.  The first address must
              be a link-local address.  The second address can be a
              link-local or global address.&quot;;

           leaf ipv6-address {
             type inet:ipv6-address;
             description
               &quot;An IPv6 address associated with a virtual router.&quot;;
<span class="grey"><a href="/doc/html/rfc8347">RFC 8347</a>                        YANG VRRP                     March 2018</span>

             reference
               &quot;<a href="/doc/html/rfc5798">RFC 5798</a>: Virtual Router Redundancy Protocol (VRRP)
                          Version 3 for IPv4 and IPv6.  <a href="#section-1.3">Section 1.3</a>&quot;;
           }
         } // virtual-ipv6-address
       } // virtual-ipv6-addresses
     } // vrrp-ipv6-attributes

     grouping vrrp-state-attributes {
       description
         &quot;Group of VRRP state attributes.&quot;;

       leaf state {
         type identityref {
           base vrrp:vrrp-state-type;
         }
         config false;
         description
           &quot;Operational state.&quot;;
       }

       leaf is-owner {
         type boolean;
         config false;
         description
           &quot;Set to &#x27;true&#x27; if this virtual router is the owner.&quot;;
       }

       leaf last-adv-source {
         type inet:ip-address;
         config false;
         description
           &quot;Last advertised IPv4/IPv6 source address.&quot;;
       }

       leaf up-datetime {
         type yang:date-and-time;
         config false;
         description
           &quot;The date and time when this virtual router
            transitioned out of &#x27;init&#x27; state.&quot;;
       }

       leaf master-down-interval {
         type uint32;
         units centiseconds;
         config false;
         description
<span class="grey"><a href="/doc/html/rfc8347">RFC 8347</a>                        YANG VRRP                     March 2018</span>

           &quot;Time interval for the backup virtual router to declare
            &#x27;master down&#x27;.&quot;;
       }

       leaf skew-time {
         type uint32;
         units microseconds;
         config false;
         description
           &quot;Calculated based on the priority and advertisement
            interval configuration command parameters.  See <a href="/doc/html/rfc3768">RFC 3768</a>.&quot;;
       }

       leaf last-event {
         type identityref {
           base vrrp:vrrp-event-type;
         }
         config false;
         description
           &quot;Last reported event.&quot;;
       }

       leaf new-master-reason {
         type new-master-reason-type;
         config false;
         description
           &quot;Indicates why the virtual router has transitioned to
            master state.&quot;;
       }

       container statistics {
         config false;
         description
           &quot;VRRP statistics.&quot;;

         leaf discontinuity-datetime {
           type yang:date-and-time;
           description
             &quot;The time on the most recent occasion at which any one or
              more of the VRRP statistics counters suffered a
              discontinuity.  If no such discontinuities have occurred
              since the last re-initialization of the local management
              subsystem, then this node contains the time that the
              local management subsystem re-initialized itself.&quot;;
         }

         leaf master-transitions {
           type yang:counter32;
<span class="grey"><a href="/doc/html/rfc8347">RFC 8347</a>                        YANG VRRP                     March 2018</span>

           description
             &quot;The total number of times that this virtual router&#x27;s
              state has transitioned to &#x27;master&#x27;.&quot;;
         }

         leaf advertisement-rcvd {
           type yang:counter64;
           description
             &quot;The total number of VRRP advertisements received by
              this virtual router.&quot;;
         }

         leaf advertisement-sent {
           type yang:counter64;
           description
             &quot;The total number of VRRP advertisements sent by
              this virtual router.&quot;;
         }

         leaf interval-errors {
           if-feature validate-interval-errors;
           type yang:counter64;
           description
             &quot;The total number of VRRP advertisement packets received
              with an advertisement interval different than the
              interval configured for the local virtual router.&quot;;
         }

         leaf priority-zero-pkts-rcvd {
           type yang:counter64;
           description
             &quot;The total number of VRRP packets received by the
              virtual router with a priority of 0.&quot;;
         }

         leaf priority-zero-pkts-sent {
           type yang:counter64;
           description
             &quot;The total number of VRRP packets sent by the
              virtual router with a priority of 0.&quot;;
         }

         leaf invalid-type-pkts-rcvd {
           type yang:counter64;
           description
             &quot;The number of VRRP packets received by the virtual
              router with an invalid value in the &#x27;type&#x27; field.&quot;;
         }
<span class="grey"><a href="/doc/html/rfc8347">RFC 8347</a>                        YANG VRRP                     March 2018</span>

         leaf address-list-errors {
           if-feature validate-address-list-errors;
           type yang:counter64;
           description
             &quot;The total number of packets received with an
              address list that does not match the locally
              configured address list for the virtual router.&quot;;
         }

         leaf packet-length-errors {
           type yang:counter64;
           description
             &quot;The total number of packets received with a packet
              length less than the length of the VRRP header.&quot;;
         }
       } // statistics
     } // vrrp-state-attributes

     grouping vrrp-global-state-attributes {
       description
         &quot;Group of VRRP global state attributes.&quot;;

       leaf virtual-routers {
         type uint32;
         description
           &quot;Number of configured virtual routers.&quot;;
       }

       leaf interfaces {
         type uint32;
         description
           &quot;Number of interfaces with VRRP configured.&quot;;
       }

       container statistics {
         description
           &quot;VRRP global statistics.&quot;;

         leaf discontinuity-datetime {
           type yang:date-and-time;
           description
             &quot;The time on the most recent occasion at which any
              one or more of checksum-errors, version-errors,
              vrid-errors, or ip-ttl-errors suffered a
              discontinuity.

              If no such discontinuities have occurred since the last
              re-initialization of the local management subsystem,
<span class="grey"><a href="/doc/html/rfc8347">RFC 8347</a>                        YANG VRRP                     March 2018</span>

              then this node contains the time that the local management
              subsystem re-initialized itself.&quot;;
         }

         leaf checksum-errors {
           type yang:counter64;
           description
             &quot;The total number of VRRP packets received with an invalid
              VRRP checksum value.&quot;;
           reference
             &quot;<a href="/doc/html/rfc5798">RFC 5798</a>: Virtual Router Redundancy Protocol (VRRP)
                        Version 3 for IPv4 and IPv6.  <a href="#section-5.2.8">Section 5.2.8</a>&quot;;
         }

         leaf version-errors {
           type yang:counter64;
           description
             &quot;The total number of VRRP packets received with an unknown
              or unsupported version number.&quot;;
           reference
             &quot;<a href="/doc/html/rfc5798">RFC 5798</a>: Virtual Router Redundancy Protocol (VRRP)
                        Version 3 for IPv4 and IPv6.  <a href="#section-5.2.1">Section 5.2.1</a>&quot;;
         }

         leaf vrid-errors {
           type yang:counter64;
           description
             &quot;The total number of VRRP packets received with a VRID that
              is not valid for any virtual router on this router.&quot;;
           reference
             &quot;<a href="/doc/html/rfc5798">RFC 5798</a>: Virtual Router Redundancy Protocol (VRRP)
                        Version 3 for IPv4 and IPv6.  <a href="#section-5.2.3">Section 5.2.3</a>&quot;;
         }

         leaf ip-ttl-errors {
           type yang:counter64;
           description
             &quot;The total number of VRRP packets received by the
              virtual router with IP TTL (IPv4) or Hop Limit (IPv6)
              not equal to 255.&quot;;
           reference
             &quot;<a href="/doc/html/rfc5798">RFC 5798</a>: Virtual Router Redundancy Protocol (VRRP)
                        Version 3 for IPv4 and IPv6.
                        Sections <a href="#section-5.1.1.3">5.1.1.3</a> and <a href="#section-5.1.2.3">5.1.2.3</a>&quot;;
         }
       } // statistics
     } // vrrp-global-state-attributes

<span class="grey"><a href="/doc/html/rfc8347">RFC 8347</a>                        YANG VRRP                     March 2018</span>

     /*
      * Configuration data and operational state data nodes
      */

     augment &quot;/if:interfaces/if:interface/ip:ipv4&quot; {
       description
         &quot;Augments IPv4 interface.&quot;;

       container vrrp {
         description
           &quot;Configures VRRP version 2 or 3 for IPv4.&quot;;

         list vrrp-instance {
           key &quot;vrid&quot;;
           description
             &quot;Defines a virtual router, identified by a VRID, within the
              IPv4 address space.&quot;;

           uses vrrp-ipv4-attributes;
           uses vrrp-state-attributes;
         }
       }
     } // augments ipv4

     augment &quot;/if:interfaces/if:interface/ip:ipv6&quot; {
       description
         &quot;Augments IPv6 interface.&quot;;

       container vrrp {
         description
           &quot;Configures VRRP version 3 for IPv6.&quot;;

         list vrrp-instance {
           must &quot;derived-from-or-self(version, &#x27;vrrp-v3&#x27;)&quot; {
             description
               &quot;IPv6 is only supported by version 3.&quot;;
           }
           key &quot;vrid&quot;;
           description
             &quot;Defines a virtual router, identified by a VRID, within the
              IPv6 address space.&quot;;

           uses vrrp-ipv6-attributes;
           uses vrrp-state-attributes;
         }
       }
     } // augments ipv6

<span class="grey"><a href="/doc/html/rfc8347">RFC 8347</a>                        YANG VRRP                     March 2018</span>

     container vrrp {
       config false;
       description
         &quot;VRRP data at the global level.&quot;;

       uses vrrp-global-state-attributes;
     }

     /*
      * Notifications
      */

     notification vrrp-new-master-event {
       description
         &quot;Notification event for the election of a new VRRP master.&quot;;
       leaf master-ip-address {
         type inet:ip-address;
         mandatory true;
         description
           &quot;IPv4 or IPv6 address of the new master.&quot;;
       }
       leaf new-master-reason {
         type new-master-reason-type;
         mandatory true;
         description
           &quot;Indicates why the virtual router has transitioned to
            master state.&quot;;
       }
     }

     notification vrrp-protocol-error-event {
       description
         &quot;Notification event for a VRRP protocol error.&quot;;
       leaf protocol-error-reason {
         type identityref {
           base vrrp:vrrp-error-global;
         }
         mandatory true;
         description
           &quot;Indicates the reason for the protocol error.&quot;;
       }
     }

     notification vrrp-virtual-router-error-event {
       description
         &quot;Notification event for an error that happened on a
          virtual router.&quot;;
       leaf interface {
<span class="grey"><a href="/doc/html/rfc8347">RFC 8347</a>                        YANG VRRP                     March 2018</span>

         type if:interface-ref;
         mandatory true;
         description
           &quot;Indicates the interface on which the event has occurred.&quot;;
       }

       choice ip-version {
         mandatory true;
         description
           &quot;The error may have happened on either an IPv4 virtual
            router or an IPv6 virtual router.  The information
            related to a specific IP version is provided by one of
            the following cases.&quot;;
         case ipv4 {
           description
             &quot;IPv4.&quot;;
           container ipv4 {
             description
               &quot;Error information for IPv4.&quot;;
             leaf vrid {
               type leafref {
                 path &quot;/if:interfaces/if:interface&quot;
                   + &quot;[if:name = current()/../../vrrp:interface]/&quot;
                   + &quot;ip:ipv4/vrrp:vrrp/vrrp:vrrp-instance/vrrp:vrid&quot;;
               }
               mandatory true;
               description
                 &quot;Indicates the virtual router on which the event has
                  occurred.&quot;;
             }
           }
         }
         case ipv6 {
           description
             &quot;IPv6.&quot;;
           container ipv6 {
             description
               &quot;Error information for IPv6.&quot;;
             leaf vrid {
               type leafref {
                 path &quot;/if:interfaces/if:interface&quot;
                   + &quot;[if:name = current()/../../vrrp:interface]/&quot;
                   + &quot;ip:ipv6/vrrp:vrrp/vrrp:vrrp-instance/vrrp:vrid&quot;;
               }
               mandatory true;
               description
                 &quot;Indicates the virtual router on which the event has
                  occurred.&quot;;
<span class="grey"><a href="/doc/html/rfc8347">RFC 8347</a>                        YANG VRRP                     March 2018</span>

             }
           }
         }
       }

       leaf virtual-router-error-reason {
         type identityref {
           base vrrp:vrrp-error-virtual-router;
         }
         mandatory true;
         description
           &quot;Indicates the reason for the virtual router error.&quot;;
       }
     }
   }
