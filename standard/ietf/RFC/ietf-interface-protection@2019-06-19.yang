module ietf-interface-protection {
  yang-version 1.1;
  namespace &quot;urn:ietf:params:xml:ns:yang:ietf-interface-protection&quot;;
  prefix ifprot;

  import ietf-interfaces {
    prefix if;
    reference
      &quot;<a href="/doc/html/rfc8343">RFC 8343</a>&quot;;
  }

  organization
    &quot;Internet Engineering Task Force (IETF) CCAMP WG&quot;;
  contact
    &quot;WG List: &lt;mailto:<a href="mailto:ccamp@ietf.org">ccamp@ietf.org</a>&gt;

     Editors:
      Jonas Ahlberg (<a href="mailto:jonas.ahlberg@ericsson.com">jonas.ahlberg@ericsson.com</a>)
      Min Ye (<a href="mailto:amy.yemin@huawei.com">amy.yemin@huawei.com</a>)
      Xi Li (<a href="mailto:Xi.Li@neclab.eu">Xi.Li@neclab.eu</a>)
      Daniela Spreafico (<a href="mailto:daniela.spreafico@nokia.com">daniela.spreafico@nokia.com</a>)
      Marko Vaupotic (<a href="mailto:Marko.Vaupotic@aviatnet.com">Marko.Vaupotic@aviatnet.com</a>)&quot;;
  description
    &quot;This is a module for the entities in
     a generic interface protection mechanism.

     Copyright (c) 2019 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).

<span class="grey"><a href="/doc/html/rfc8561">RFC 8561</a>          Microwave Radio Link YANG Data Model         June 2019</span>

        This version of this YANG module is part of <a href="/doc/html/rfc8561">RFC 8561</a>; see
        the RFC itself for full legal notices.&quot;;

     revision 2019-06-19 {
       description
         &quot;Initial revision.&quot;;
       reference
         &quot;<a href="/doc/html/rfc8561">RFC 8561</a>: A YANG Data Model for Microwave Radio Link&quot;;
     }

     /*
      * Protection architecture type identities
      */

     identity protection-architecture-type {
       description
         &quot;protection architecture type&quot;;
       reference
         &quot;ITU-T G.808.1&quot;;
     }

     identity one-plus-one-type {
       base protection-architecture-type;
       description
         &quot;1+1; one interface protects
          another one interface.&quot;;
       reference
         &quot;ITU-T G.808.1&quot;;
     }

     identity one-to-n-type {
       base protection-architecture-type;
       description
         &quot;1:N; one interface protects
          n other interfaces.&quot;;
       reference
         &quot;ITU-T G.808.1&quot;;
     }

     /*
      * Protection states identities
      */

     identity protection-states {
       description
         &quot;Identities describing the status of the protection
          in a group of interfaces configured in
          a protection mode.&quot;;
<span class="grey"><a href="/doc/html/rfc8561">RFC 8561</a>          Microwave Radio Link YANG Data Model         June 2019</span>

     }

     identity unprotected {
       base protection-states;
       description
         &quot;Not protected.&quot;;
     }

     identity protected {
       base protection-states;
       description
         &quot;Protected.&quot;;
     }

     identity unable-to-protect {
       base protection-states;
       description
         &quot;Unable to protect.&quot;;
     }

     /*
      * Protection Groups
      */

     grouping protection-groups {
       description
         &quot;Configuration of protected groups of interfaces
          providing protection for each other.  More than one
          protected group per higher-layer interface is allowed.&quot;;
       list protection-group {
         key &quot;name&quot;;
         description
           &quot;List of protected groups of interfaces
            in a higher-layer interface.&quot;;
         leaf name {
           type string;
           description
             &quot;Name used for identification of the protection group.&quot;;
         }
         leaf protection-architecture-type {
           type identityref {
             base protection-architecture-type;
           }
           default &quot;ifprot:one-plus-one-type&quot;;
           description
             &quot;The type of protection architecture used, e.g., one
              interface protecting one or several other interfaces.&quot;;

<span class="grey"><a href="/doc/html/rfc8561">RFC 8561</a>          Microwave Radio Link YANG Data Model         June 2019</span>

           reference
             &quot;ITU-T G.808.1&quot;;
         }
         leaf-list members {
           type if:interface-ref;
           min-elements 2;
           description
             &quot;Association to a group of interfaces configured for
              protection and used by a higher-layer interface.&quot;;
         }
         leaf operation-type {
           type enumeration {
             enum non-revertive {
               description
                 &quot;In non-revertive operation, the traffic does not
                  return to the working interface if the switch requests
                  are terminated.&quot;;
               reference
                 &quot;ITU-T G.808.1&quot;;
             }
             enum revertive {
               description
                 &quot;In revertive operation, the traffic always
                  returns to (or remains on) the working interface
                  if the switch requests are terminated.&quot;;
               reference
                 &quot;ITU-T G.808.1&quot;;
             }
           }
           default &quot;non-revertive&quot;;
           description
             &quot;The type of protection operation, i.e., revertive
              or non-revertive operation.&quot;;
         }
         leaf-list working-entity {
           when &quot;../operation-type = &#x27;revertive&#x27;&quot;;
           type if:interface-ref;
           min-elements 1;
           description
             &quot;The interfaces that the traffic normally should
              be transported over when there is no need to use the
              protecting interface.&quot;;
         }
         leaf revertive-wait-to-restore {
           when &quot;../operation-type = &#x27;revertive&#x27;&quot;;
           type uint16;
           units &quot;seconds&quot;;
           default &quot;0&quot;;
<span class="grey"><a href="/doc/html/rfc8561">RFC 8561</a>          Microwave Radio Link YANG Data Model         June 2019</span>

           description
             &quot;The time to wait before switching back to the working
              interface if operation-type is revertive.&quot;;
           reference
             &quot;ITU-T G.808.1&quot;;
         }
         leaf hold-off-timer {
           type uint16;
           units &quot;milliseconds&quot;;
           default &quot;0&quot;;
           description
             &quot;Time interval after the detection of a fault and its
              confirmation as a condition requiring the protection-
              switching procedure.&quot;;
           reference
             &quot;ITU-T G.808.1&quot;;
         }
         leaf status {
           type identityref {
             base protection-states;
           }
           config false;
           description
             &quot;Status of the protection in a group of interfaces
              configured in a protection mode.&quot;;
           reference
             &quot;ITU-T G.808.1&quot;;
         }
         action manual-switch-working {
           description
             &quot;A switch action initiated by an operator command.
              It switches a normal traffic signal to the working
              transport entity.&quot;;
           reference
             &quot;ITU-T G.808.1&quot;;
         }
         action manual-switch-protection {
           description
             &quot;A switch action initiated by an operator command.
              It switches a normal traffic signal to the protection
              transport entity.&quot;;
           reference
             &quot;ITU-T G.808.1&quot;;
         }
         action forced-switch {
           description
             &quot;A switch action initiated by an operator command.
              It switches a normal traffic signal to the protection
<span class="grey"><a href="/doc/html/rfc8561">RFC 8561</a>          Microwave Radio Link YANG Data Model         June 2019</span>

              transport entity and forces it to remain on that
              entity even when criteria for switching back to
              the original entity are fulfilled.&quot;;
           reference
             &quot;ITU-T G.808.1&quot;;
         }
         action lockout-of-protection {
           description
             &quot;A switch action temporarily disables access to the
              protection transport entity for all signals.&quot;;
           reference
             &quot;ITU-T G.808.1&quot;;
         }
         action freeze {
           description
             &quot;A switch action temporarily prevents any switch action
              to be taken and, as such, freezes the current state.
              Until the freeze is cleared, additional near-end external
              commands are rejected, and fault condition changes and
              received Automatic Protection-Switching (APS) messages
              are ignored.&quot;;
           reference
             &quot;ITU-T G.808.1&quot;;
         }
         action exercise {
           description
             &quot;A switch action to test if the APS communication is
              operating correctly.  It is lower priority than any &#x27;real&#x27;
              switch request.&quot;;
           reference
             &quot;ITU-T G.808.1&quot;;
         }
         action clear {
           description
             &quot;An action clears all switch commands.&quot;;
           reference
             &quot;ITU-T G.808.1&quot;;
         }
       }
     }
   }
