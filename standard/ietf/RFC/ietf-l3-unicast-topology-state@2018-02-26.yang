module ietf-l3-unicast-topology-state {
  yang-version 1.1;
  namespace
    &quot;urn:ietf:params:xml:ns:yang:ietf-l3-unicast-topology-state&quot;;
  prefix &quot;l3t-s&quot;;
  import ietf-network-state {
    prefix &quot;nw-s&quot;;
<span class="grey"><a href="/doc/html/rfc8346">RFC 8346</a>            YANG Data Model for L3 Topologies         March 2018</span>

     }
     import ietf-network-topology-state {
       prefix &quot;nt-s&quot;;
     }
     import ietf-l3-unicast-topology {
       prefix &quot;l3t&quot;;
     }
     organization
       &quot;IETF I2RS (Interface to the Routing System) Working Group&quot;;
     contact
       &quot;WG Web:    &lt;<a href="https://datatracker.ietf.org/wg/i2rs/">https://datatracker.ietf.org/wg/i2rs/</a>&gt;
        WG List:   &lt;mailto:<a href="mailto:i2rs@ietf.org">i2rs@ietf.org</a>&gt;
        Editor:    Alexander Clemm
                   &lt;mailto:<a href="mailto:ludwig@clemm.org">ludwig@clemm.org</a>&gt;
        Editor:    Jan Medved
                   &lt;mailto:<a href="mailto:jmedved@cisco.com">jmedved@cisco.com</a>&gt;
        Editor:    Robert Varga
                   &lt;mailto:<a href="mailto:robert.varga@pantheon.tech">robert.varga@pantheon.tech</a>&gt;
        Editor:    Xufeng Liu
                   &lt;mailto:<a href="mailto:xufeng.liu.ietf@gmail.com">xufeng.liu.ietf@gmail.com</a>&gt;
        Editor:    Nitin Bahadur
                   &lt;mailto:<a href="mailto:nitin_bahadur@yahoo.com">nitin_bahadur@yahoo.com</a>&gt;
        Editor:    Hariharan Ananthakrishnan
                   &lt;mailto:<a href="mailto:hari@packetdesign.com">hari@packetdesign.com</a>&gt;&quot;;
     description
       &quot;This module defines a model for Layer 3 Unicast topology
        state, representing topology that either is learned or
        results from applying topology that has been configured per
        the &#x27;ietf-l3-unicast-topology&#x27; model, mirroring the
        corresponding data nodes in this model.

        This model mirrors &#x27;ietf-l3-unicast-topology&#x27; but contains only
        read-only state data.  The model is not needed when the
        underlying implementation infrastructure supports the Network
        Management Datastore Architecture (NMDA).

        Copyright (c) 2018 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">https://trustee.ietf.org/license-info</a>).

        This version of this YANG module is part of <a href="/doc/html/rfc8346">RFC 8346</a>;
        see the RFC itself for full legal notices.&quot;;
<span class="grey"><a href="/doc/html/rfc8346">RFC 8346</a>            YANG Data Model for L3 Topologies         March 2018</span>

     revision &quot;2018-02-26&quot; {
       description
         &quot;Initial revision.&quot;;
       reference
         &quot;<a href="/doc/html/rfc8346">RFC 8346</a>: A YANG Data Model for Layer 3 Topologies&quot;;
     }
     augment &quot;/nw-s:networks/nw-s:network/nw-s:network-types&quot; {
       description
         &quot;Introduce new network type for L3 Unicast topology&quot;;
       uses l3t:l3-unicast-topology-type;
     }
     augment &quot;/nw-s:networks/nw-s:network&quot; {
       when &quot;nw-s:network-types/l3t-s:l3-unicast-topology&quot; {
         description
           &quot;Augmentation parameters apply only for networks with
           L3 Unicast topology&quot;;
       }
       description
           &quot;L3 Unicast for the network as a whole&quot;;
       uses l3t:l3-topology-attributes;
     }
     augment &quot;/nw-s:networks/nw-s:network/nw-s:node&quot; {
       when &quot;../nw-s:network-types/l3t-s:l3-unicast-topology&quot; {
         description
           &quot;Augmentation parameters apply only for networks with
           L3 Unicast topology&quot;;
       }
       description
           &quot;L3 Unicast node-level attributes &quot;;
       uses l3t:l3-node-attributes;
     }
     augment &quot;/nw-s:networks/nw-s:network/nt-s:link&quot; {
       when &quot;../nw-s:network-types/l3t-s:l3-unicast-topology&quot; {
         description
           &quot;Augmentation parameters apply only for networks with
           L3 Unicast topology&quot;;
       }
       description
         &quot;Augments topology link attributes&quot;;
       uses l3t:l3-link-attributes;
     }
     augment &quot;/nw-s:networks/nw-s:network/nw-s:node/&quot;
            +&quot;nt-s:termination-point&quot; {
       when &quot;../../nw-s:network-types/l3t-s:l3-unicast-topology&quot; {
         description
           &quot;Augmentation parameters apply only for networks with
           L3 Unicast topology&quot;;
       }
<span class="grey"><a href="/doc/html/rfc8346">RFC 8346</a>            YANG Data Model for L3 Topologies         March 2018</span>

       description &quot;Augments topology termination point configuration&quot;;
       uses l3t:l3-termination-point-attributes;
     }
     notification l3-node-event {
       description
         &quot;Notification event for L3 node&quot;;
       leaf l3-event-type {
         type l3t:l3-event-type;
         description
           &quot;Event type&quot;;
       }
       uses nw-s:node-ref;
       uses l3t:l3-unicast-topology-type;
       uses l3t:l3-node-attributes;
     }
     notification l3-link-event {
       description
         &quot;Notification event for L3 link&quot;;
       leaf l3-event-type {
         type l3t:l3-event-type;
         description
           &quot;Event type&quot;;
       }
       uses nt-s:link-ref;
       uses l3t:l3-unicast-topology-type;
       uses l3t:l3-link-attributes;
     }
     notification l3-prefix-event {
       description
         &quot;Notification event for L3 prefix&quot;;
       leaf l3-event-type {
         type l3t:l3-event-type;
         description
           &quot;Event type&quot;;
       }
       uses nw-s:node-ref;
       uses l3t:l3-unicast-topology-type;
       container prefix {
         description
           &quot;Contains L3 prefix attributes&quot;;
         uses l3t:l3-prefix-attributes;
       }
     }
     notification termination-point-event {
       description
         &quot;Notification event for L3 termination point&quot;;
       leaf l3-event-type {
         type l3t:l3-event-type;
<span class="grey"><a href="/doc/html/rfc8346">RFC 8346</a>            YANG Data Model for L3 Topologies         March 2018</span>

         description
           &quot;Event type&quot;;
       }
       uses nt-s:tp-ref;
       uses l3t:l3-unicast-topology-type;
       uses l3t:l3-termination-point-attributes;
     }
   }
