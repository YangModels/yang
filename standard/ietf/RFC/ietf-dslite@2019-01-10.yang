module ietf-dslite {
 yang-version 1.1;
 namespace &quot;urn:ietf:params:xml:ns:yang:ietf-dslite&quot;;
 prefix dslite;

 import ietf-inet-types {
   prefix inet;
   reference
     &quot;<a href="/doc/html/rfc6991#section-4">Section&amp;nbsp;4 of RFC 6991</a>&quot;;
 }
 import ietf-interfaces {
   prefix if;
   reference
     &quot;<a href="/doc/html/rfc8343">RFC 8343</a>: A YANG Data Model for Interface Management&quot;;
 }
 import iana-if-type {
   prefix ianaift;
   reference
     &quot;<a href="/doc/html/rfc7224">RFC 7224</a>: IANA Interface Type YANG Module&quot;;
 }
 import ietf-nat {
   prefix nat;
   reference
     &quot;<a href="/doc/html/rfc8512">RFC 8512</a>: A YANG Module for Network Address Translation (NAT)
                and Network Prefix Translation (NPT)&quot;;
 }
 import ietf-yang-types {
   prefix yang;
   reference
     &quot;<a href="/doc/html/rfc6991#section-3">Section&amp;nbsp;3 of RFC 6991</a>&quot;;
 }

 organization
   &quot;IETF Softwire Working Group&quot;;
 contact
   &quot;WG Web:   &lt;<a href="https://datatracker.ietf.org/wg/softwire/">https://datatracker.ietf.org/wg/softwire/</a>&gt;
    WG List:  &lt;mailto:<a href="mailto:softwires@ietf.org">softwires@ietf.org</a>&gt;

    Editor:  Mohamed Boucadair
             &lt;mailto:<a href="mailto:mohamed.boucadair@orange.com">mohamed.boucadair@orange.com</a>&gt;

<span class="grey"><a href="/doc/html/rfc8513">RFC 8513</a>                   DS-Lite YANG Module              January 2019</span>

      Author:  Christian Jacquenet
               &lt;mailto:<a href="mailto:christian.jacquenet@orange.com">christian.jacquenet@orange.com</a>&gt;

      Author:  Senthil Sivakumar
               &lt;mailto:<a href="mailto:ssenthil@cisco.com">ssenthil@cisco.com</a>&gt;&quot;;

   description
     &quot;This module is a YANG module for DS-Lite AFTR and B4
      implementations.

      Copyright (c) 2018 IETF Trust and the persons identified as
      authors of the code.  All rights reserved.

      Redistribution and use in source and binary forms, with or
      without modification, is permitted pursuant to, and subject
      to the license terms contained in, the Simplified BSD License
      set forth in <a href="#section-4">Section 4</a>.c of the IETF Trust&#x27;s Legal Provisions
      Relating to IETF Documents
      (<a href="https://trustee.ietf.org/license-info">http://trustee.ietf.org/license-info</a>).

      This version of this YANG module is part of <a href="/doc/html/rfc8513">RFC 8513</a>; see
      the RFC itself for full legal notices.&quot;;

   revision 2019-01-10 {
     description
       &quot;Initial revision.&quot;;
     reference
       &quot;<a href="/doc/html/rfc8513">RFC 8513</a>: A YANG Data Model for Dual-Stack Lite (DS-Lite)&quot;;
   }

   identity dslite {
     base ianaift:tunnel;
     description
       &quot;DS-Lite tunnel.&quot;;
   }

   /*
    * Features
    */

   feature b4 {
     description
       &quot;The B4 element is a function implemented on a dual-stack-capable
        node, either a directly connected device or Customer Premises
        Equipment (CPE), that creates a tunnel to an AFTR.&quot;;
     reference
       &quot;<a href="/doc/html/rfc6333#section-5">Section&amp;nbsp;5 of RFC 6333</a>&quot;;
   }
<span class="grey"><a href="/doc/html/rfc8513">RFC 8513</a>                   DS-Lite YANG Module              January 2019</span>

   feature aftr {
     description
       &quot;An AFTR element is the combination of an IPv4-in-IPv6 tunnel
        endpoint and an IPv4-IPv4 NAT implemented on the same node.&quot;;
     reference
       &quot;<a href="/doc/html/rfc6333#section-6">Section&amp;nbsp;6 of RFC 6333</a>&quot;;
   }

   /*
    * Augments
    */

   augment &quot;/if:interfaces/if:interface&quot; {
     when &#x27;derived-from(if:type, &quot;dslite&quot;)&#x27;;
     description
       &quot;Augments Interface module with DS-Lite parameters.

        IANA interface types are maintained at this registry:
        &lt;<a href="https://www.iana.org/assignments/ianaiftype-mib/">https://www.iana.org/assignments/ianaiftype-mib/</a>&gt;.

        tunnel (131),       -- Encapsulation interface&quot;;
     leaf ipv6-address {
       type inet:ipv6-address;
       description
         &quot;IPv6 address of the local DS-Lite endpoint (AFTR or B4).&quot;;
       reference
         &quot;<a href="/doc/html/rfc6333">RFC 6333</a>: Dual-Stack Lite Broadband Deployments Following
                    IPv4 Exhaustion&quot;;
     }
     leaf ipv4-address {
       type inet:ipv4-address;
       description
         &quot;IPv4 address of the local DS-Lite AFTR or B4.

          192.0.0.1 is reserved for the AFTR element, while
          192.0.0.0/29 is reserved for the B4 element.

          This address can be used to report ICMP problems and will
          appear in traceroute outputs.&quot;;
       reference
         &quot;<a href="/doc/html/rfc6333">RFC 6333</a>: Dual-Stack Lite Broadband Deployments Following
                    IPv4 Exhaustion&quot;;
     }
     leaf aftr-ipv6-addr {
       if-feature &quot;b4&quot;;
       type inet:ipv6-address;
       description
         &quot;Indicates the AFTR&#x27;s IPv6 address to be used by a B4
<span class="grey"><a href="/doc/html/rfc8513">RFC 8513</a>                   DS-Lite YANG Module              January 2019</span>

          element.&quot;;
       reference
         &quot;<a href="/doc/html/rfc6333">RFC 6333</a>: Dual-Stack Lite Broadband Deployments Following
                    IPv4 Exhaustion&quot;;
     }
     leaf tunnel-mtu {
       type uint16;
       description
         &quot;Configures a tunnel MTU.

          <a href="/doc/html/rfc6908">RFC 6908</a> specifies that since fragmentation and reassembly
          are not optimal, the operator should do everything possible
          to eliminate the need for them.  If the operator uses simple
          IPv4-in-IPv6 softwire, it is recommended that the MTU size
          of the IPv6 network between the B4 and the AFTR account
          for the additional overhead (40 bytes).&quot;;
       reference
         &quot;<a href="/doc/html/rfc6908">RFC 6908</a>: Deployment Considerations for Dual-Stack Lite&quot;;
     }
     leaf v6-v4-dscp-preservation {
       type boolean;
       description
         &quot;Copies the DSCP value from the IPv6 header, and vice versa.

          According to <a href="/doc/html/rfc6908#section-2.10">Section&amp;nbsp;2.10 of RFC 6908</a>, operators should
          use the uniform model by provisioning the network such
          that the AFTR/B4 copies the DSCP value in the IPv4 header
          to the Traffic Class field in the IPv6 header, after the
          IPv4-in-IPv6 encapsulation.&quot;;
       reference
         &quot;<a href="/doc/html/rfc6908#section-2.10">Section&amp;nbsp;2.10 of RFC 6908</a>&quot;;
     }
   }

   augment &quot;/nat:nat/nat:instances/nat:instance/nat:policy&quot; {
     when &quot;derived-from-or-self(/nat:nat/nat:instances/nat:instance&quot;
        + &quot;/nat:type, &#x27;nat:napt44&#x27;)&quot;
        + &quot; and /nat:nat/nat:instances/nat:instance/&quot;
        + &quot;nat:per-interface-binding=&#x27;dslite&#x27;&quot;;
     if-feature &quot;aftr&quot;;
     description
       &quot;Augments the NAPT44 module with AFTR parameters.&quot;;
     leaf max-softwires-per-subscriber {
       type uint8;
       default &quot;1&quot;;
       description
         &quot;Configures the maximum softwires per subscriber feature.

<span class="grey"><a href="/doc/html/rfc8513">RFC 8513</a>                   DS-Lite YANG Module              January 2019</span>

          A subscriber is uniquely identified by means
          of a subscriber-mask (subscriber-mask-v6).

          This policy aims to prevent a misbehaving subscriber from
          mounting several DS-Lite softwires that would consume
          additional AFTR resources (e.g., get more external ports
          if the quota was enforced on a per-softwire basis and
          consume extra processing due to a large number of active
          softwires).&quot;;
       reference
         &quot;<a href="/doc/html/rfc7785#section-4">Section&amp;nbsp;4 of RFC 7785</a>&quot;;
     }
     leaf state-migrate {
       type boolean;
       default &quot;true&quot;;
       description
         &quot;State migration is enabled by default.

          In the event a new IPv6 address is assigned to the B4 element,
          the AFTR should migrate existing state to be bound to the new
          IPv6 address.  This operation ensures that traffic destined to
          the previous B4&#x27;s IPv6 address will be redirected to the newer
          B4&#x27;s IPv6 address.  The destination IPv6 address for tunneling
          return traffic from the AFTR should be the last seen as the
          B4&#x27;s IPv6 source address from the user device (e.g., CPE).

          The AFTR uses the subscriber-mask-v6 to determine whether two
          IPv6 addresses belong to the same CPE (e.g., if the
          subscriber-mask-v6 is set to 56, the AFTR concludes that
          2001:db8:100:100::1 and 2001:db8:100:100::2 belong to the same
          CPE assigned with 2001:db8:100:100::/56).&quot;;
       reference
         &quot;<a href="/doc/html/rfc7785">RFC 7785</a>: Recommendations for Prefix Binding in the Context
                    of Softwire Dual-Stack Lite&quot;;
     }
     leaf b4-address-change-limit {
       type uint32;
       units &quot;seconds&quot;;
       default &quot;1800&quot;;
       description
         &quot;Minimum number of seconds between a successive B4&#x27;s IPv6
          address change from the same prefix.

          Changing the source B4&#x27;s IPv6 address may be used as an attack
          vector.  Packets with a new B4&#x27;s IPv6 address from the same
          prefix should be rate-limited.

          It is recommended that this rate limit be set to 30 minutes;
<span class="grey"><a href="/doc/html/rfc8513">RFC 8513</a>                   DS-Lite YANG Module              January 2019</span>

          other values can be set on a per-deployment basis.&quot;;
       reference
         &quot;<a href="/doc/html/rfc7785">RFC 7785</a>: Recommendations for Prefix Binding in the Context
                    of Softwire Dual-Stack Lite&quot;;
     }
     container mss-clamping {
       description
         &quot;MSS rewriting configuration to avoid IPv6 fragmentation.&quot;;
       leaf enable {
         type boolean;
         description
           &quot;Enable/disable MSS rewriting feature.&quot;;
       }
       leaf mss-value {
         type uint16;
         units &quot;octets&quot;;
         description
           &quot;Sets the MSS value to be used for MSS rewriting.&quot;;
       }
     }
   }

   augment &quot;/nat:nat/nat:instances/nat:instance&quot;
         + &quot;/nat:mapping-table/nat:mapping-entry&quot; {
     when &quot;derived-from-or-self(/nat:nat/nat:instances/nat:instance&quot;
        + &quot;/nat:type, &#x27;nat:napt44&#x27;)&quot;
        + &quot;and /nat:nat/nat:instances/nat:instance&quot;
        + &quot;/nat:per-interface-binding=&#x27;dslite&#x27;&quot;;
     if-feature &quot;aftr&quot;;
     description
       &quot;Augments the NAPT44 mapping table with DS-Lite specifics.&quot;;
     container b4-ipv6-address {
       description
         &quot;Records the IPv6 address used by a B4 element and the last
          time that address changed.&quot;;
       leaf address {
         type inet:ipv6-address;
         description
           &quot;Corresponds to the IPv6 address used by a B4 element.&quot;;
         reference
           &quot;<a href="/doc/html/rfc6333">RFC 6333</a>: Dual-Stack Lite Broadband Deployments Following
                      IPv4 Exhaustion&quot;;
       }
       leaf last-address-change {
         type yang:date-and-time;
         description
           &quot;Records the last time that the address changed.&quot;;
       }
<span class="grey"><a href="/doc/html/rfc8513">RFC 8513</a>                   DS-Lite YANG Module              January 2019</span>

     }
     leaf v6-dscp {
       when &quot;/if:interfaces/if:interface&quot;
          + &quot;/dslite:v6-v4-dscp-preservation = &#x27;true&#x27;&quot;;
       type inet:dscp;
       description
         &quot;DSCP value used at the softwire level (i.e., IPv6 header).&quot;;
     }
     leaf internal-v4-dscp {
       when &quot;/if:interfaces/if:interface&quot;
          + &quot;/dslite:v6-v4-dscp-preservation = &#x27;true&#x27;&quot;;
       type inet:dscp;
       description
         &quot;DSCP value of the encapsulated IPv4 packet.&quot;;
     }
     leaf external-v4-dscp {
       when &quot;/if:interfaces/if:interface&quot;
          + &quot;/dslite:v6-v4-dscp-preservation = &#x27;true&#x27;&quot;;
       type inet:dscp;
       description
         &quot;DSCP value of the translated IPv4 packet as marked by
          the AFTR.&quot;;
     }
   }

   augment &quot;/nat:nat/nat:instances/nat:instance&quot;
         + &quot;/nat:statistics/nat:mappings-statistics&quot; {
     if-feature &quot;aftr&quot;;
     description
       &quot;Indicates the number of active softwires.&quot;;
     leaf active-softwires {
       type yang:gauge32;
       description
         &quot;The number of currently active softwires on the AFTR
          instance.&quot;;
     }
   }

   /*
    * Notifications
    */

   notification b4-address-change-limit-policy-violation {
     if-feature &quot;aftr&quot;;
     description
       &quot;Generates notifications when a B4 unsuccessfully attempts
        to change the IPv6 address in a time shorter than the value
        of b4-address-change-limit.
<span class="grey"><a href="/doc/html/rfc8513">RFC 8513</a>                   DS-Lite YANG Module              January 2019</span>

        Notifications are rate-limited (notify-interval).&quot;;
     leaf id {
       type leafref {
         path &quot;/nat:nat/nat:instances/nat:instance/nat:id&quot;;
       }
       mandatory true;
       description
         &quot;NAT instance identifier.&quot;;
     }
     leaf policy-id {
       type leafref {
         path &quot;/nat:nat/nat:instances/nat:instance/nat:policy/nat:id&quot;;
       }
       mandatory true;
       description
         &quot;Policy identifier.&quot;;
     }
     leaf address {
       type inet:ipv6-address;
       mandatory true;
       description
         &quot;B4&#x27;s IPv6 address.&quot;;
     }
   }
  }
