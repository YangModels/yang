module ietf-logical-network-element {
  yang-version 1.1;

  // namespace

  namespace &quot;urn:ietf:params:xml:ns:yang:ietf-logical-network-element&quot;;
  prefix lne;

  // import some basic types

  import ietf-interfaces {
    prefix if;
    reference
      &quot;<a href="/doc/html/rfc8343">RFC 8343</a>: A YANG Data Model for Interface Management&quot;;
  }
  import ietf-yang-schema-mount {
    prefix yangmnt;
    reference
      &quot;<a href="/doc/html/rfc8528">RFC 8528</a>: YANG Schema Mount&quot;;
  }

<span class="grey"><a href="/doc/html/rfc8530">RFC 8530</a>                        YANG LNEs                     March 2019</span>

   organization
     &quot;IETF Routing Area (rtgwg) Working Group&quot;;
   contact
     &quot;WG Web:   &lt;<a href="https://datatracker.ietf.org/wg/rtgwg/">https://datatracker.ietf.org/wg/rtgwg/</a>&gt;
      WG List:  &lt;mailto:<a href="mailto:rtgwg@ietf.org">rtgwg@ietf.org</a>&gt;

      Author:   Lou Berger
                &lt;mailto:<a href="mailto:lberger@labn.net">lberger@labn.net</a>&gt;

      Author:   Christian Hopps
                &lt;mailto:<a href="mailto:chopps@chopps.org">chopps@chopps.org</a>&gt;

      Author:   Acee Lindem
                &lt;mailto:<a href="mailto:acee@cisco.com">acee@cisco.com</a>&gt;

      Author:   Dean Bogdanovic
                &lt;mailto:<a href="mailto:ivandean@gmail.com">ivandean@gmail.com</a>&gt;&quot;;
   description
     &quot;This module is used to support multiple logical network
      elements on a single physical or virtual system.

      Copyright (c) 2019 IETF Trust and the persons identified as
      authors of the code.  All rights reserved.

      Redistribution and use in source and binary forms, with or
      without modification, is permitted pursuant to, and subject
      to the license terms contained in, the Simplified BSD License
      set forth in <a href="#section-4">Section 4</a>.c of the IETF Trust&#x27;s Legal Provisions
      Relating to IETF Documents
      (<a href="https://trustee.ietf.org/license-info">http://trustee.ietf.org/license-info</a>).

      This version of this YANG module is part of <a href="/doc/html/rfc8530">RFC 8530</a>; see
      the RFC itself for full legal notices.&quot;;

   revision 2019-01-25 {
     description
       &quot;Initial revision.&quot;;
     reference
       &quot;<a href="/doc/html/rfc8530">RFC 8530</a>: YANG Model for Logical Network Elements&quot;;
   }

   // top level device definition statements

   container logical-network-elements {
     description
       &quot;Allows a network device to support multiple logical
        network element (device) instances.&quot;;
     list logical-network-element {
<span class="grey"><a href="/doc/html/rfc8530">RFC 8530</a>                        YANG LNEs                     March 2019</span>

       key &quot;name&quot;;
       description
         &quot;List of logical network elements.&quot;;
       leaf name {
         type string;
         description
           &quot;Device-wide unique identifier for the
            logical network element.&quot;;
       }
       leaf managed {
         type boolean;
         default &quot;true&quot;;
         description
           &quot;True if the host can access LNE information
            using the root mount point.  This value
            may not be modifiable in all implementations.&quot;;
       }
       leaf description {
         type string;
         description
           &quot;Description of the logical network element.&quot;;
       }
       container root {
         description
           &quot;Container for mount point.&quot;;
         yangmnt:mount-point &quot;root&quot; {
           description
             &quot;Root for models supported per logical
              network element.  This mount point may or may not
              be inline based on the server implementation.  It
              SHALL always contain a YANG library and interfaces
              instance.

              When the associated &#x27;managed&#x27; leaf is &#x27;false&#x27;, any
              operation that attempts to access information below
              the root SHALL fail with an error-tag of
              &#x27;access-denied&#x27; and an error-app-tag of
              &#x27;lne-not-managed&#x27;.&quot;;
         }
       }
     }
   }

   // augment statements

   augment &quot;/if:interfaces/if:interface&quot; {
     description
       &quot;Add a node for the identification of the logical network
<span class="grey"><a href="/doc/html/rfc8530">RFC 8530</a>                        YANG LNEs                     March 2019</span>

        element associated with an interface.  Applies to
        interfaces that can be assigned per logical network
        element.

        Note that a standard error will be returned if the
        identified leafref isn&#x27;t present.  If an interface
        cannot be assigned for any other reason, the operation
        SHALL fail with an error-tag of &#x27;operation-failed&#x27; and an
        error-app-tag of &#x27;lne-assignment-failed&#x27;.  A meaningful
        error-info that indicates the source of the assignment
        failure SHOULD also be provided.&quot;;
     leaf bind-lne-name {
       type leafref {
         path &quot;/logical-network-elements/logical-network-element/name&quot;;
       }
       description
         &quot;Logical network element ID to which the interface is
          bound.&quot;;
     }
   }

   // notification statements

   notification bind-lne-name-failed {
     description
       &quot;Indicates an error in the association of an interface to an
        LNE.  Only generated after success is initially returned
        when bind-lne-name is set.&quot;;
     leaf name {
       type leafref {
         path &quot;/if:interfaces/if:interface/if:name&quot;;
       }
       mandatory true;
       description
         &quot;Contains the interface name associated with the
          failure.&quot;;
     }
     leaf bind-lne-name {
       type leafref {
         path &quot;/if:interfaces/if:interface/lne:bind-lne-name&quot;;
       }
       mandatory true;
       description
         &quot;Contains the bind-lne-name associated with the
          failure.&quot;;
     }
     leaf error-info {
       type string;
<span class="grey"><a href="/doc/html/rfc8530">RFC 8530</a>                        YANG LNEs                     March 2019</span>

       description
         &quot;Optionally, indicates the source of the assignment
          failure.&quot;;
     }
   }
 }
