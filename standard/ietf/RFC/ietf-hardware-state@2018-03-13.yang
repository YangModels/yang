module ietf-hardware-state {
  yang-version 1.1;
  namespace &quot;urn:ietf:params:xml:ns:yang:ietf-hardware-state&quot;;
  prefix hw-state;

  import ietf-inet-types {
    prefix inet;
  }
  import ietf-yang-types {
    prefix yang;
  }
  import iana-hardware {
    prefix ianahw;
  }
  import ietf-hardware {
    prefix hw;
  }

  organization
    &quot;IETF NETMOD (Network Modeling) Working Group&quot;;

  contact
    &quot;WG Web:   &lt;<a href="https://datatracker.ietf.org/wg/netmod/">https://datatracker.ietf.org/wg/netmod/</a>&gt;
     WG List:  &lt;mailto:<a href="mailto:netmod@ietf.org">netmod@ietf.org</a>&gt;

     Editor:   Andy Bierman
               &lt;mailto:<a href="mailto:andy@yumaworks.com">andy@yumaworks.com</a>&gt;

     Editor:   Martin Bjorklund
               &lt;mailto:<a href="mailto:mbj@tail-f.com">mbj@tail-f.com</a>&gt;

     Editor:   Jie Dong
               &lt;mailto:<a href="mailto:jie.dong@huawei.com">jie.dong@huawei.com</a>&gt;
<span class="grey"><a href="/doc/html/rfc8348">RFC 8348</a>                YANG Hardware Management              March 2018</span>

        Editor:   Dan Romascanu
                  &lt;mailto:<a href="mailto:dromasca@gmail.com">dromasca@gmail.com</a>&gt;&quot;;

     description
       &quot;This module contains a collection of YANG definitions for
        monitoring hardware.

        This data model is designed as a temporary solution for
        implementations that do not yet support the Network Management
        Datastore Architecture (NMDA) defined in <a href="/doc/html/rfc8342">RFC 8342</a>.  Such an
        implementation cannot implement the module &#x27;ietf-hardware&#x27;
        properly, since without NMDA support, it is not possible to
        distinguish between instances of nodes in the running
        configuration and operational states.

        The data model in this module is the same as the data model in
        &#x27;ietf-hardware&#x27;, except all nodes are marked as &#x27;config false&#x27;.

        If a server that implements this module but doesn&#x27;t support NMDA
        also supports configuration of hardware components, it SHOULD
        also implement the module &#x27;ietf-hardware&#x27; in the configuration
        datastores.  The corresponding state data is found in the
        &#x27;/hw-state:hardware&#x27; subtree.

        Copyright (c) 2018 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">https://trustee.ietf.org/license-info</a>).

        This version of this YANG module is part of <a href="/doc/html/rfc8348">RFC 8348</a>; see
        the RFC itself for full legal notices.&quot;;

     revision 2018-03-13 {
       description
         &quot;Initial revision.&quot;;
       reference
         &quot;<a href="/doc/html/rfc8348">RFC 8348</a>: A YANG Data Model for Hardware Management&quot;;
     }

     /*
      * Features
      */

<span class="grey"><a href="/doc/html/rfc8348">RFC 8348</a>                YANG Hardware Management              March 2018</span>

     feature entity-mib {
       status deprecated;
       description
         &quot;This feature indicates that the device implements
          the ENTITY-MIB.&quot;;
       reference
         &quot;<a href="/doc/html/rfc6933">RFC 6933</a>: Entity MIB (Version 4)&quot;;
     }

     feature hardware-state {
       status deprecated;
       description
         &quot;Indicates that ENTITY-STATE-MIB objects are supported&quot;;
       reference
         &quot;<a href="/doc/html/rfc4268">RFC 4268</a>: Entity State MIB&quot;;
     }

     feature hardware-sensor {
       status deprecated;
       description
         &quot;Indicates that ENTITY-SENSOR-MIB objects are supported&quot;;
       reference
         &quot;<a href="/doc/html/rfc3433">RFC 3433</a>: Entity Sensor Management Information Base&quot;;
     }

     /*
      * Data nodes
      */

     container hardware {
       config false;
       status deprecated;
       description
         &quot;Data nodes representing components.&quot;;

       leaf last-change {
         type yang:date-and-time;
         status deprecated;
         description
           &quot;The time the &#x27;/hardware/component&#x27; list changed in the
            operational state.&quot;;
       }

       list component {
         key name;
         status deprecated;
         description
           &quot;List of components.
<span class="grey"><a href="/doc/html/rfc8348">RFC 8348</a>                YANG Hardware Management              March 2018</span>

            When the server detects a new hardware component, it
            initializes a list entry in the operational state.

            If the server does not support configuration of hardware
            components, list entries in the operational state are
            initialized with values for all nodes as detected by the
            implementation.

            Otherwise, this procedure is followed:

              1. If there is an entry in the &#x27;/hardware/component&#x27; list
                 in the intended configuration with values for the nodes
                 &#x27;class&#x27;, &#x27;parent&#x27;, and &#x27;parent-rel-pos&#x27; that are equal
                 to the detected values, then:

              1a. If the configured entry has a value for &#x27;mfg-name&#x27;
                  that is equal to the detected value or if the
                  &#x27;mfg-name&#x27; value cannot be detected, then the list
                  entry in the operational state is initialized with the
                  configured values for all configured nodes, including
                  the &#x27;name&#x27;.

                  Otherwise, the list entry in the operational state is
                  initialized with values for all nodes as detected by
                  the implementation.  The implementation may raise an
                  alarm that informs about the &#x27;mfg-name&#x27; mismatch
                  condition.  How this is done is outside the scope of
                  this document.

              1b. Otherwise (i.e., there is no matching configuration
                  entry), the list entry in the operational state is
                  initialized with values for all nodes as detected by
                  the implementation.

            If the &#x27;/hardware/component&#x27; list in the intended
            configuration is modified, then the system MUST behave as if
            it re-initializes itself and follow the procedure in (1).&quot;;
         reference
           &quot;<a href="/doc/html/rfc6933">RFC 6933</a>: Entity MIB (Version 4) - entPhysicalEntry&quot;;

         leaf name {
           type string;
           status deprecated;
           description
             &quot;The name assigned to this component.

              This name is not required to be the same as
              entPhysicalName.&quot;;
<span class="grey"><a href="/doc/html/rfc8348">RFC 8348</a>                YANG Hardware Management              March 2018</span>

         }

         leaf class {
           type identityref {
             base ianahw:hardware-class;
           }
           mandatory true;
           status deprecated;
           description
             &quot;An indication of the general hardware type of the
              component.&quot;;
           reference
             &quot;<a href="/doc/html/rfc6933">RFC 6933</a>: Entity MIB (Version 4) - entPhysicalClass&quot;;
         }

         leaf physical-index {
           if-feature entity-mib;
           type int32 {
             range &quot;1..2147483647&quot;;
           }
           status deprecated;
           description
             &quot;The entPhysicalIndex for the entPhysicalEntry represented
              by this list entry.&quot;;
           reference
             &quot;<a href="/doc/html/rfc6933">RFC 6933</a>: Entity MIB (Version 4) - entPhysicalIndex&quot;;
         }

         leaf description {
           type string;
           status deprecated;
           description
             &quot;A textual description of the component.  This node should
              contain a string that identifies the manufacturer&#x27;s name
              for the component and should be set to a distinct value
              for each version or model of the component.&quot;;
           reference
             &quot;<a href="/doc/html/rfc6933">RFC 6933</a>: Entity MIB (Version 4) - entPhysicalDescr&quot;;
         }

         leaf parent {
           type leafref {
             path &quot;../../component/name&quot;;
             require-instance false;
           }
           status deprecated;

<span class="grey"><a href="/doc/html/rfc8348">RFC 8348</a>                YANG Hardware Management              March 2018</span>

           description
             &quot;The name of the component that physically contains this
              component.

              If this leaf is not instantiated, it indicates that this
              component is not contained in any other component.

              In the event that a physical component is contained by
              more than one physical component (e.g., double-wide
              modules), this node contains the name of one of these
              components.  An implementation MUST use the same name
              every time this node is instantiated.&quot;;
           reference
             &quot;<a href="/doc/html/rfc6933">RFC 6933</a>: Entity MIB (Version 4) -
                        entPhysicalContainedIn&quot;;
         }

         leaf parent-rel-pos {
           type int32 {
             range &quot;0 .. 2147483647&quot;;
           }
           status deprecated;
           description
             &quot;An indication of the relative position of this child
              component among all its sibling components.  Sibling
              components are defined as components that:

                o share the same value of the &#x27;parent&#x27; node and

                o share a common base identity for the &#x27;class&#x27; node.

              Note that the last rule gives implementations flexibility
              in how components are numbered.  For example, some
              implementations might have a single number series for all
              components derived from &#x27;ianahw:port&#x27;, while some others
              might have different number series for different
              components with identities derived from &#x27;ianahw:port&#x27; (for
              example, one for RJ45 and one for SFP).&quot;;

           reference
             &quot;<a href="/doc/html/rfc6933">RFC 6933</a>: Entity MIB (Version 4) -
                        entPhysicalParentRelPos&quot;;
         }

         leaf-list contains-child {
           type leafref {
             path &quot;../../component/name&quot;;
           }
<span class="grey"><a href="/doc/html/rfc8348">RFC 8348</a>                YANG Hardware Management              March 2018</span>

           status deprecated;
           description
             &quot;The name of the contained component.&quot;;
           reference
             &quot;<a href="/doc/html/rfc6933">RFC 6933</a>: Entity MIB (Version 4) - entPhysicalChildIndex&quot;;
         }

         leaf hardware-rev {
           type string;
           status deprecated;
           description
             &quot;The vendor-specific hardware revision string for the
              component.  The preferred value is the hardware revision
              identifier actually printed on the component itself (if
              present).&quot;;
           reference
             &quot;<a href="/doc/html/rfc6933">RFC 6933</a>: Entity MIB (Version 4) -
                        entPhysicalHardwareRev&quot;;
         }

         leaf firmware-rev {
           type string;
           status deprecated;
           description
             &quot;The vendor-specific firmware revision string for the
              component.&quot;;
           reference
             &quot;<a href="/doc/html/rfc6933">RFC 6933</a>: Entity MIB (Version 4) -
                        entPhysicalFirmwareRev&quot;;
         }

         leaf software-rev {
           type string;
           status deprecated;
           description
             &quot;The vendor-specific software revision string for the
              component.&quot;;
           reference
             &quot;<a href="/doc/html/rfc6933">RFC 6933</a>: Entity MIB (Version 4) -
                        entPhysicalSoftwareRev&quot;;
         }

         leaf serial-num {
           type string;
           status deprecated;

<span class="grey"><a href="/doc/html/rfc8348">RFC 8348</a>                YANG Hardware Management              March 2018</span>

           description
             &quot;The vendor-specific serial number string for the
              component.  The preferred value is the serial number
              string actually printed on the component itself (if
              present).&quot;;
           reference
             &quot;<a href="/doc/html/rfc6933">RFC 6933</a>: Entity MIB (Version 4) - entPhysicalSerialNum&quot;;
         }

         leaf mfg-name {
           type string;
           status deprecated;
           description
             &quot;The name of the manufacturer of this physical component.
              The preferred value is the manufacturer name string
              actually printed on the component itself (if present).

              Note that comparisons between instances of the
              &#x27;model-name&#x27;, &#x27;firmware-rev&#x27;, &#x27;software-rev&#x27;, and
              &#x27;serial-num&#x27; nodes are only meaningful amongst components
              with the same value of &#x27;mfg-name&#x27;.

              If the manufacturer name string associated with the
              physical component is unknown to the server, then this
              node is not instantiated.&quot;;
           reference
             &quot;<a href="/doc/html/rfc6933">RFC 6933</a>: Entity MIB (Version 4) - entPhysicalMfgName&quot;;
         }

         leaf model-name {
           type string;
           status deprecated;
           description
             &quot;The vendor-specific model name identifier string
              associated with this physical component.  The preferred
              value is the customer-visible part number, which may be
              printed on the component itself.

              If the model name string associated with the physical
              component is unknown to the server, then this node is not
              instantiated.&quot;;
           reference
             &quot;<a href="/doc/html/rfc6933">RFC 6933</a>: Entity MIB (Version 4) - entPhysicalModelName&quot;;
         }

         leaf alias {
           type string;
           status deprecated;
<span class="grey"><a href="/doc/html/rfc8348">RFC 8348</a>                YANG Hardware Management              March 2018</span>

           description
             &quot;An &#x27;alias&#x27; name for the component, as specified by a
              network manager, that provides a non-volatile &#x27;handle&#x27; for
              the component.

              If no configured value exists, the server MAY set the
              value of this node to a locally unique value in the
              operational state.

              A server implementation MAY map this leaf to the
              entPhysicalAlias MIB object.  Such an implementation needs
              to use some mechanism to handle the differences in size
              and characters allowed between this leaf and
              entPhysicalAlias.  The definition of such a mechanism is
              outside the scope of this document.&quot;;
           reference
             &quot;<a href="/doc/html/rfc6933">RFC 6933</a>: Entity MIB (Version 4) - entPhysicalAlias&quot;;
         }

         leaf asset-id {
           type string;
           status deprecated;
           description
             &quot;This node is a user-assigned asset tracking identifier for
              the component.

              A server implementation MAY map this leaf to the
              entPhysicalAssetID MIB object.  Such an implementation
              needs to use some mechanism to handle the differences in
              size and characters allowed between this leaf and
              entPhysicalAssetID.  The definition of such a mechanism is
              outside the scope of this document.&quot;;
           reference
             &quot;<a href="/doc/html/rfc6933">RFC 6933</a>: Entity MIB (Version 4) - entPhysicalAssetID&quot;;
         }

         leaf is-fru {
           type boolean;
           status deprecated;
           description
             &quot;This node indicates whether or not this component is
              considered a &#x27;field-replaceable unit&#x27; by the vendor.  If
              this node contains the value &#x27;true&#x27;, then this component
              identifies a field-replaceable unit.  For all components
              that are permanently contained within a field-replaceable
              unit, the value &#x27;false&#x27; should be returned for this
              node.&quot;;

<span class="grey"><a href="/doc/html/rfc8348">RFC 8348</a>                YANG Hardware Management              March 2018</span>

           reference
             &quot;<a href="/doc/html/rfc6933">RFC 6933</a>: Entity MIB (Version 4) - entPhysicalIsFRU&quot;;
         }

         leaf mfg-date {
           type yang:date-and-time;
           status deprecated;
           description
             &quot;The date of manufacturing of the managed component.&quot;;
           reference
             &quot;<a href="/doc/html/rfc6933">RFC 6933</a>: Entity MIB (Version 4) - entPhysicalMfgDate&quot;;
         }

         leaf-list uri {
           type inet:uri;
           status deprecated;
           description
             &quot;This node contains identification information about the
              component.&quot;;
           reference
             &quot;<a href="/doc/html/rfc6933">RFC 6933</a>: Entity MIB (Version 4) - entPhysicalUris&quot;;
         }

         leaf uuid {
           type yang:uuid;
           status deprecated;
           description
             &quot;A Universally Unique Identifier of the component.&quot;;
           reference
             &quot;<a href="/doc/html/rfc6933">RFC 6933</a>: Entity MIB (Version 4) - entPhysicalUUID&quot;;
         }

         container state {
           if-feature hardware-state;
           status deprecated;
           description
             &quot;State-related nodes&quot;;
           reference
             &quot;<a href="/doc/html/rfc4268">RFC 4268</a>: Entity State MIB&quot;;

           leaf state-last-changed {
             type yang:date-and-time;
             status deprecated;
             description
               &quot;The date and time when the value of any of the
                admin-state, oper-state, usage-state, alarm-state, or
                standby-state changed for this component.

<span class="grey"><a href="/doc/html/rfc8348">RFC 8348</a>                YANG Hardware Management              March 2018</span>

                If there has been no change since the last
                re-initialization of the local system, this node
                contains the date and time of local system
                initialization.  If there has been no change since the
                component was added to the local system, this node
                contains the date and time of the insertion.&quot;;
             reference
               &quot;<a href="/doc/html/rfc4268">RFC 4268</a>: Entity State MIB - entStateLastChanged&quot;;
           }

           leaf admin-state {
             type hw:admin-state;
             status deprecated;
             description
               &quot;The administrative state for this component.

                This node refers to a component&#x27;s administrative
                permission to service both other components within its
                containment hierarchy as well as other users of its
                services defined by means outside the scope of this
                module.

                Some components exhibit only a subset of the remaining
                administrative state values.  Some components cannot be
                locked; hence, this node exhibits only the &#x27;unlocked&#x27;
                state.  Other components cannot be shut down gracefully;
                hence, this node does not exhibit the &#x27;shutting-down&#x27;
                state.&quot;;
             reference
               &quot;<a href="/doc/html/rfc4268">RFC 4268</a>: Entity State MIB - entStateAdmin&quot;;
           }

           leaf oper-state {
             type hw:oper-state;
             status deprecated;
             description
               &quot;The operational state for this component.

                Note that this node does not follow the administrative
                state.  An administrative state of &#x27;down&#x27; does not
                predict an operational state of &#x27;disabled&#x27;.

                Note that some implementations may not be able to
                accurately report oper-state while the admin-state node
                has a value other than &#x27;unlocked&#x27;.  In these cases, this
                node MUST have a value of &#x27;unknown&#x27;.&quot;;
             reference
               &quot;<a href="/doc/html/rfc4268">RFC 4268</a>: Entity State MIB - entStateOper&quot;;
<span class="grey"><a href="/doc/html/rfc8348">RFC 8348</a>                YANG Hardware Management              March 2018</span>

           }

           leaf usage-state {
             type hw:usage-state;
             status deprecated;
             description
               &quot;The usage state for this component.

                This node refers to a component&#x27;s ability to service
                more components in a containment hierarchy.

                Some components will exhibit only a subset of the usage
                state values.  Components that are unable to ever
                service any components within a containment hierarchy
                will always have a usage state of &#x27;busy&#x27;.  In some
                cases, a component will be able to support only one
                other component within its containment hierarchy and
                will therefore only exhibit values of &#x27;idle&#x27; and
                &#x27;busy&#x27;.&quot;;
             reference
               &quot;<a href="/doc/html/rfc4268">RFC 4268</a>: Entity State MIB - entStateUsage&quot;;
           }

           leaf alarm-state {
             type hw:alarm-state;
             status deprecated;
             description
               &quot;The alarm state for this component.  It does not
                include the alarms raised on child components within its
                containment hierarchy.&quot;;
             reference
               &quot;<a href="/doc/html/rfc4268">RFC 4268</a>: Entity State MIB - entStateAlarm&quot;;
           }

           leaf standby-state {
             type hw:standby-state;
             status deprecated;
             description
               &quot;The standby state for this component.

                Some components will exhibit only a subset of the
                remaining standby state values.  If this component
                cannot operate in a standby role, the value of this node
                will always be &#x27;providing-service&#x27;.&quot;;
             reference
               &quot;<a href="/doc/html/rfc4268">RFC 4268</a>: Entity State MIB - entStateStandby&quot;;
           }
         }
<span class="grey"><a href="/doc/html/rfc8348">RFC 8348</a>                YANG Hardware Management              March 2018</span>

         container sensor-data {
           when &#x27;derived-from-or-self(../class,
                                      &quot;ianahw:sensor&quot;)&#x27; {
             description
               &quot;Sensor data nodes present for any component of type
                &#x27;sensor&#x27;&quot;;
           }
           if-feature hardware-sensor;
           status deprecated;

           description
             &quot;Sensor-related nodes.&quot;;
           reference
             &quot;<a href="/doc/html/rfc3433">RFC 3433</a>: Entity Sensor Management Information Base&quot;;

           leaf value {
             type hw:sensor-value;
             status deprecated;
             description
               &quot;The most recent measurement obtained by the server
                for this sensor.

                A client that periodically fetches this node should also
                fetch the nodes &#x27;value-type&#x27;, &#x27;value-scale&#x27;, and
                &#x27;value-precision&#x27;, since they may change when the value
                is changed.&quot;;
             reference
               &quot;<a href="/doc/html/rfc3433">RFC 3433</a>: Entity Sensor Management Information Base -
                          entPhySensorValue&quot;;
           }

           leaf value-type {
             type hw:sensor-value-type;
             status deprecated;
             description
               &quot;The type of data units associated with the
                sensor value&quot;;
             reference
               &quot;<a href="/doc/html/rfc3433">RFC 3433</a>: Entity Sensor Management Information Base -
                          entPhySensorType&quot;;
           }

           leaf value-scale {
             type hw:sensor-value-scale;
             status deprecated;
             description
               &quot;The (power of 10) scaling factor associated
                with the sensor value&quot;;
<span class="grey"><a href="/doc/html/rfc8348">RFC 8348</a>                YANG Hardware Management              March 2018</span>

             reference
               &quot;<a href="/doc/html/rfc3433">RFC 3433</a>: Entity Sensor Management Information Base -
                          entPhySensorScale&quot;;
           }

           leaf value-precision {
             type hw:sensor-value-precision;
             status deprecated;
             description
               &quot;The number of decimal places of precision
                associated with the sensor value&quot;;
             reference
               &quot;<a href="/doc/html/rfc3433">RFC 3433</a>: Entity Sensor Management Information Base -
                          entPhySensorPrecision&quot;;
           }

           leaf oper-status {
             type hw:sensor-status;
             status deprecated;
             description
               &quot;The operational status of the sensor.&quot;;
             reference
               &quot;<a href="/doc/html/rfc3433">RFC 3433</a>: Entity Sensor Management Information Base -
                          entPhySensorOperStatus&quot;;
           }

           leaf units-display {
             type string;
             status deprecated;
             description
               &quot;A textual description of the data units that should be
                used in the display of the sensor value.&quot;;
             reference
               &quot;<a href="/doc/html/rfc3433">RFC 3433</a>: Entity Sensor Management Information Base -
                          entPhySensorUnitsDisplay&quot;;
           }

           leaf value-timestamp {
             type yang:date-and-time;
             status deprecated;
             description
               &quot;The time the status and/or value of this sensor was last
                obtained by the server.&quot;;
             reference
               &quot;<a href="/doc/html/rfc3433">RFC 3433</a>: Entity Sensor Management Information Base -
                          entPhySensorValueTimeStamp&quot;;
           }

<span class="grey"><a href="/doc/html/rfc8348">RFC 8348</a>                YANG Hardware Management              March 2018</span>

           leaf value-update-rate {
             type uint32;
             units &quot;milliseconds&quot;;
             status deprecated;
             description
               &quot;An indication of the frequency that the server updates
                the associated &#x27;value&#x27; node, represented in
                milliseconds.  The value zero indicates:

                 - the sensor value is updated on demand (e.g.,
                   when polled by the server for a get-request),

                 - the sensor value is updated when the sensor
                   value changes (event-driven), or

                 - the server does not know the update rate.&quot;;
             reference
               &quot;<a href="/doc/html/rfc3433">RFC 3433</a>: Entity Sensor Management Information Base -
                          entPhySensorValueUpdateRate&quot;;
           }
         }
       }
     }

     /*
      * Notifications
      */

     notification hardware-state-change {
       status deprecated;
       description
         &quot;A hardware-state-change notification is generated when the
          value of /hardware/last-change changes in the operational
          state.&quot;;
       reference
         &quot;<a href="/doc/html/rfc6933">RFC 6933</a>: Entity MIB (Version 4) - entConfigChange&quot;;
     }

     notification hardware-state-oper-enabled {
       if-feature hardware-state;
       status deprecated;
       description
         &quot;A hardware-state-oper-enabled notification signifies that a
          component has transitioned into the &#x27;enabled&#x27; state.&quot;;

       leaf name {
         type leafref {
           path &quot;/hardware/component/name&quot;;
<span class="grey"><a href="/doc/html/rfc8348">RFC 8348</a>                YANG Hardware Management              March 2018</span>

         }
         status deprecated;
         description
           &quot;The name of the component that has transitioned into the
            &#x27;enabled&#x27; state.&quot;;
       }
       leaf admin-state {
         type leafref {
           path &quot;/hardware/component/state/admin-state&quot;;
         }
         status deprecated;
         description
           &quot;The administrative state for the component.&quot;;
       }
       leaf alarm-state {
         type leafref {
           path &quot;/hardware/component/state/alarm-state&quot;;
         }
         status deprecated;
         description
           &quot;The alarm state for the component.&quot;;
       }
       reference
         &quot;<a href="/doc/html/rfc4268">RFC 4268</a>: Entity State MIB - entStateOperEnabled&quot;;
     }

     notification hardware-state-oper-disabled {
       if-feature hardware-state;
       status deprecated;
       description
         &quot;A hardware-state-oper-disabled notification signifies that a
          component has transitioned into the &#x27;disabled&#x27; state.&quot;;

       leaf name {
         type leafref {
           path &quot;/hardware/component/name&quot;;
         }
         status deprecated;
         description
           &quot;The name of the component that has transitioned into the
            &#x27;disabled&#x27; state.&quot;;
       }
       leaf admin-state {
         type leafref {
           path &quot;/hardware/component/state/admin-state&quot;;
         }
         status deprecated;

<span class="grey"><a href="/doc/html/rfc8348">RFC 8348</a>                YANG Hardware Management              March 2018</span>

         description
           &quot;The administrative state for the component.&quot;;
       }
       leaf alarm-state {
         type leafref {
           path &quot;/hardware/component/state/alarm-state&quot;;
         }
         status deprecated;
         description
           &quot;The alarm state for the component.&quot;;
       }
       reference
         &quot;<a href="/doc/html/rfc4268">RFC 4268</a>: Entity State MIB - entStateOperDisabled&quot;;
     }

   }
