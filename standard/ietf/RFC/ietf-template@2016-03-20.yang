module ietf-template {
  yang-version 1.1;

  // replace this string with a unique namespace URN value

  namespace &quot;urn:ietf:params:xml:ns:yang:ietf-template&quot;;

  // replace this string, and try to pick a unique prefix

  prefix temp;

  // import statements here: e.g.,
  // import ietf-yang-types { prefix yang; }
  // import ietf-inet-types { prefix inet; }
  // identify the IETF working group if applicable

  organization
    &quot;IETF NETMOD (NETCONF Data Modeling Language) Working Group&quot;;

  // update this contact statement with your info

  contact
    &quot;WG Web:   &lt;<a href="https://datatracker.ietf.org/wg/your-wg-name/">http://datatracker.ietf.org/wg/your-wg-name/</a>&gt;
     WG List:  &lt;mailto:<a href="mailto:your-wg-name@ietf.org">your-wg-name@ietf.org</a>&gt;

     Editor:   your-name
               &lt;mailto:<a href="mailto:your-email@example.com">your-email@example.com</a>&gt;&quot;;

  // replace the first sentence in this description statement.
  // replace the copyright notice with the most recent
  // version, if it has been updated since the publication
  // of this document

  description
    &quot;This module defines a template for other YANG modules.

     Copyright (c) &lt;insert year&gt; IETF Trust and the persons
     identified as authors of the code.  All rights reserved.

     Redistribution and use in source and binary forms, with or
     without modification, is permitted pursuant to, and subject
     to the license terms contained in, the Simplified BSD License
     set forth in <a href="#section-4">Section 4</a>.c of the IETF Trust&#x27;s Legal Provisions

<span class="grey"><a href="/doc/html/rfc8407">RFC 8407</a>              Guidelines for YANG Documents         October 2018</span>

        Relating to IETF Documents
        (<a href="https://trustee.ietf.org/license-info">http://trustee.ietf.org/license-info</a>).

        This version of this YANG module is part of RFC XXXX; see
        the RFC itself for full legal notices.&quot;;

     // RFC Ed.: replace XXXX with actual RFC number and remove
     // this note

     // replace &#x27;2016-03-20&#x27; with the module publication date
     // the format is (year-month-day)

     revision 2016-03-20 {
       description
         &quot;what changed in this revision&quot;;
       reference &quot;RFC XXXX: &lt;Replace With Document Title&gt;&quot;;
     }

     // extension statements
     // feature statements
     // identity statements
     // typedef statements
     // grouping statements
     // data definition statements
     // augment statements
     // rpc statements
     // notification statements
     // DO NOT put deviation statements in a published module
   }
