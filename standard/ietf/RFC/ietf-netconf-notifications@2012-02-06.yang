module ietf-netconf-notifications {

   namespace
     &quot;urn:ietf:params:xml:ns:yang:ietf-netconf-notifications&quot;;

   prefix ncn;

   import ietf-inet-types { prefix inet; }
   import ietf-netconf { prefix nc; }

   organization
     &quot;IETF NETCONF (Network Configuration Protocol) Working Group&quot;;

   contact
     &quot;WG Web:   &lt;<a href="https://tools.ietf.org/wg/netconf/">http://tools.ietf.org/wg/netconf/</a>&gt;
      WG List:  &lt;mailto:<a href="mailto:netconf@ietf.org">netconf@ietf.org</a>&gt;

      WG Chair: Bert Wijnen
                &lt;mailto:<a href="mailto:bertietf@bwijnen.net">bertietf@bwijnen.net</a>&gt;

      WG Chair: Mehmet Ersue
                &lt;mailto:<a href="mailto:mehmet.ersue@nsn.com">mehmet.ersue@nsn.com</a>&gt;

      Editor:   Andy Bierman
                &lt;mailto:<a href="mailto:andy@netconfcentral.org">andy@netconfcentral.org</a>&gt;&quot;;

   description
     &quot;This module defines a YANG data model for use with the
      NETCONF protocol that allows the NETCONF client to
      receive common NETCONF base event notifications.

      Copyright (c) 2012 IETF Trust and the persons identified as
      the document authors.  All rights reserved.

      Redistribution and use in source and binary forms, with or
      without modification, is permitted pursuant to, and subject
      to the license terms contained in, the Simplified BSD License

<span class="grey"><a href="/doc/html/rfc6470">RFC 6470</a>               NETCONF Base Notifications          February 2012</span>

         set forth in <a href="#section-4">Section 4</a>.c of the IETF Trust&#x27;s Legal Provisions
         Relating to IETF Documents
         (<a href="https://trustee.ietf.org/license-info">http://trustee.ietf.org/license-info</a>).

         This version of this YANG module is part of <a href="/doc/html/rfc6470">RFC 6470</a>; see
         the RFC itself for full legal notices.&quot;;

      revision &quot;2012-02-06&quot; {
        description
          &quot;Initial version.&quot;;
        reference
          &quot;<a href="/doc/html/rfc6470">RFC 6470</a>: NETCONF Base Notifications&quot;;
      }

     grouping common-session-parms {
       description
         &quot;Common session parameters to identify a
          management session.&quot;;

       leaf username {
         type string;
         mandatory true;
         description
           &quot;Name of the user for the session.&quot;;
       }

       leaf session-id {
         type nc:session-id-or-zero-type;
         mandatory true;
         description
           &quot;Identifier of the session.
            A NETCONF session MUST be identified by a non-zero value.
            A non-NETCONF session MAY be identified by the value zero.&quot;;
       }

       leaf source-host {
         type inet:ip-address;
         description
           &quot;Address of the remote host for the session.&quot;;
       }
     }

<span class="grey"><a href="/doc/html/rfc6470">RFC 6470</a>               NETCONF Base Notifications          February 2012</span>

      grouping changed-by-parms {
       description
         &quot;Common parameters to identify the source
          of a change event, such as a configuration
          or capability change.&quot;;

       container changed-by {
         description
           &quot;Indicates the source of the change.
            If caused by internal action, then the
            empty leaf &#x27;server&#x27; will be present.
            If caused by a management session, then
            the name, remote host address, and session ID
            of the session that made the change will be reported.&quot;;
         choice server-or-user {
           mandatory true;
           leaf server {
             type empty;
             description
               &quot;If present, the change was caused
                by the server.&quot;;
           }

           case by-user {
             uses common-session-parms;
           }
         } // choice server-or-user
       } // container changed-by-parms
     }

     notification netconf-config-change {
       description
         &quot;Generated when the NETCONF server detects that the
          &lt;running&gt; or &lt;startup&gt; configuration datastore
          has been changed by a management session.
          The notification summarizes the edits that
          have been detected.

          The server MAY choose to also generate this
          notification while loading a datastore during the
          boot process for the device.&quot;;

       uses changed-by-parms;

<span class="grey"><a href="/doc/html/rfc6470">RFC 6470</a>               NETCONF Base Notifications          February 2012</span>

       leaf datastore {
         type enumeration {
           enum running {
             description &quot;The &lt;running&gt; datastore has changed.&quot;;
           }
           enum startup {
             description &quot;The &lt;startup&gt; datastore has changed&quot;;
           }
         }
         default &quot;running&quot;;
         description
           &quot;Indicates which configuration datastore has changed.&quot;;
       }

       list edit {
         description
           &quot;An edit record SHOULD be present for each distinct
            edit operation that the server has detected on
            the target datastore.  This list MAY be omitted
            if the detailed edit operations are not known.
            The server MAY report entries in this list for
            changes not made by a NETCONF session (e.g., CLI).&quot;;

         leaf target {
           type instance-identifier;
           description
             &quot;Topmost node associated with the configuration change.
              A server SHOULD set this object to the node within
              the datastore that is being altered.  A server MAY
              set this object to one of the ancestors of the actual
              node that was changed, or omit this object, if the
              exact node is not known.&quot;;
         }

         leaf operation {
           type nc:edit-operation-type;
           description
             &quot;Type of edit operation performed.
              A server MUST set this object to the NETCONF edit
              operation performed on the target datastore.&quot;;
         }
       } // list edit
     } // notification netconf-config-change

<span class="grey"><a href="/doc/html/rfc6470">RFC 6470</a>               NETCONF Base Notifications          February 2012</span>

     notification netconf-capability-change {
       description
         &quot;Generated when the NETCONF server detects that
          the server capabilities have changed.
          Indicates which capabilities have been added, deleted,
          and/or modified.  The manner in which a server
          capability is changed is outside the scope of this
          document.&quot;;

       uses changed-by-parms;

       leaf-list added-capability {
         type inet:uri;
         description
           &quot;List of capabilities that have just been added.&quot;;
       }

       leaf-list deleted-capability {
         type inet:uri;
         description
           &quot;List of capabilities that have just been deleted.&quot;;
       }

       leaf-list modified-capability {
         type inet:uri;
         description
           &quot;List of capabilities that have just been modified.
            A capability is considered to be modified if the
            base URI for the capability has not changed, but
            one or more of the parameters encoded at the end of
            the capability URI have changed.
            The new modified value of the complete URI is returned.&quot;;
       }
     } // notification netconf-capability-change

     notification netconf-session-start {
       description
         &quot;Generated when a NETCONF server detects that a
          NETCONF session has started.  A server MAY generate
          this event for non-NETCONF management sessions.
          Indicates the identity of the user that started
          the session.&quot;;
       uses common-session-parms;
     } // notification netconf-session-start

<span class="grey"><a href="/doc/html/rfc6470">RFC 6470</a>               NETCONF Base Notifications          February 2012</span>

     notification netconf-session-end {
       description
         &quot;Generated when a NETCONF server detects that a
          NETCONF session has terminated.
          A server MAY optionally generate this event for
          non-NETCONF management sessions.  Indicates the
          identity of the user that owned the session,
          and why the session was terminated.&quot;;

       uses common-session-parms;

       leaf killed-by {
         when &quot;../termination-reason = &#x27;killed&#x27;&quot;;
         type nc:session-id-type;
         description
           &quot;The ID of the session that directly caused this session
            to be abnormally terminated.  If this session was abnormally
            terminated by a non-NETCONF session unknown to the server,
            then this leaf will not be present.&quot;;
       }

       leaf termination-reason {
         type enumeration {
           enum &quot;closed&quot; {
             description
               &quot;The session was terminated by the client in normal
                fashion, e.g., by the NETCONF &lt;close-session&gt;
                protocol operation.&quot;;
           }
           enum &quot;killed&quot; {
             description
               &quot;The session was terminated in abnormal
                fashion, e.g., by the NETCONF &lt;kill-session&gt;
                protocol operation.&quot;;
           }
           enum &quot;dropped&quot; {
             description
               &quot;The session was terminated because the transport layer
                connection was unexpectedly closed.&quot;;
           }
           enum &quot;timeout&quot; {
             description
               &quot;The session was terminated because of inactivity,
                e.g., waiting for the &lt;hello&gt; message or &lt;rpc&gt;
                messages.&quot;;
           }

<span class="grey"><a href="/doc/html/rfc6470">RFC 6470</a>               NETCONF Base Notifications          February 2012</span>

           enum &quot;bad-hello&quot; {
             description
               &quot;The client&#x27;s &lt;hello&gt; message was invalid.&quot;;
           }
           enum &quot;other&quot; {
             description
               &quot;The session was terminated for some other reason.&quot;;
           }
         }
         mandatory true;
         description
           &quot;Reason the session was terminated.&quot;;
       }
     } // notification netconf-session-end

     notification netconf-confirmed-commit {
       description
         &quot;Generated when a NETCONF server detects that a
          confirmed-commit event has occurred.  Indicates the event
          and the current state of the confirmed-commit procedure
          in progress.&quot;;
       reference
         &quot;<a href="/doc/html/rfc6241#section-8.4">RFC 6241, Section&amp;nbsp;8.4</a>&quot;;

       uses common-session-parms {
         when &quot;../confirm-event != &#x27;timeout&#x27;&quot;;
       }

       leaf confirm-event {
         type enumeration {
           enum &quot;start&quot; {
             description
               &quot;The confirmed-commit procedure has started.&quot;;
           }
           enum &quot;cancel&quot; {
             description
               &quot;The confirmed-commit procedure has been canceled,
                e.g., due to the session being terminated, or an
                explicit &lt;cancel-commit&gt; operation.&quot;;
           }
           enum &quot;timeout&quot; {
             description
               &quot;The confirmed-commit procedure has been canceled
                due to the confirm-timeout interval expiring.
                The common session parameters will not be present
                in this sub-mode.&quot;;
           }
<span class="grey"><a href="/doc/html/rfc6470">RFC 6470</a>               NETCONF Base Notifications          February 2012</span>

           enum &quot;extend&quot; {
             description
               &quot;The confirmed-commit timeout has been extended,
                e.g., by a new &lt;confirmed-commit&gt; operation.&quot;;
           }
           enum &quot;complete&quot; {
             description
               &quot;The confirmed-commit procedure has been completed.&quot;;
           }
         }
         mandatory true;
         description
           &quot;Indicates the event that caused the notification.&quot;;
       }

       leaf timeout {
         when
           &quot;../confirm-event = &#x27;start&#x27; or ../confirm-event = &#x27;extend&#x27;&quot;;
         type uint32;
         units &quot;seconds&quot;;
         description
           &quot;The configured timeout value if the event type
            is &#x27;start&#x27; or &#x27;extend&#x27;.  This value represents
            the approximate number of seconds from the event
            time when the &#x27;timeout&#x27; event might occur.&quot;;
       }
     } // notification netconf-confirmed-commit

   }
