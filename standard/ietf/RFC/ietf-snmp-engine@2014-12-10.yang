submodule ietf-snmp-engine {

  belongs-to ietf-snmp {
    prefix snmp;
  }

  import ietf-inet-types {
    prefix inet;
  }

  include ietf-snmp-common;

  organization
    &quot;IETF NETMOD (NETCONF Data Modeling Language) Working Group&quot;;

  contact
    &quot;WG Web:   &lt;<a href="https://tools.ietf.org/wg/netmod/">http://tools.ietf.org/wg/netmod/</a>&gt;
<span class="grey"><a href="/doc/html/rfc7407">RFC 7407</a>         YANG Data Model for SNMP Configuration    December 2014</span>

        WG List:  &lt;mailto:<a href="mailto:netmod@ietf.org">netmod@ietf.org</a>&gt;

        WG Chair: Thomas Nadeau
                  &lt;mailto:<a href="mailto:tnadeau@lucidvision.com">tnadeau@lucidvision.com</a>&gt;

        WG Chair: Juergen Schoenwaelder
                  &lt;mailto:<a href="mailto:j.schoenwaelder@jacobs-university.de">j.schoenwaelder@jacobs-university.de</a>&gt;

        Editor:   Martin Bjorklund
                  &lt;mailto:<a href="mailto:mbj@tail-f.com">mbj@tail-f.com</a>&gt;

        Editor:   Juergen Schoenwaelder
                  &lt;mailto:<a href="mailto:j.schoenwaelder@jacobs-university.de">j.schoenwaelder@jacobs-university.de</a>&gt;&quot;;

     description
       &quot;This submodule contains a collection of YANG definitions
        for configuring SNMP engines.

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).
        This version of this YANG module is part of <a href="/doc/html/rfc7407">RFC 7407</a>; see
        the RFC itself for full legal notices.&quot;;

     revision 2014-12-10 {
       description
         &quot;Initial revision.&quot;;
       reference
         &quot;<a href="/doc/html/rfc7407">RFC 7407</a>: A YANG Data Model for SNMP Configuration&quot;;
     }

     augment /snmp:snmp {

       container engine {

         description
           &quot;Configuration of the SNMP engine.&quot;;

         leaf enabled {
           type boolean;
           default &quot;false&quot;;
           description
<span class="grey"><a href="/doc/html/rfc7407">RFC 7407</a>         YANG Data Model for SNMP Configuration    December 2014</span>

             &quot;Enables the SNMP engine.&quot;;
         }

         list listen {
           key &quot;name&quot;;
           description
             &quot;Configuration of the transport endpoints on which the
              engine listens.&quot;;

           leaf name {
             type snmp:identifier;
             description
               &quot;An arbitrary name for the list entry.&quot;;
           }

           choice transport {
             mandatory true;
             description
               &quot;The transport-protocol-specific parameters for this
                endpoint.  Submodules providing configuration for
                additional transports are expected to augment this
                choice.&quot;;
             case udp {
               container udp {
                 leaf ip {
                   type inet:ip-address;
                   mandatory true;
                   description
                     &quot;The IPv4 or IPv6 address on which the engine
                      listens.&quot;;
                 }
                 leaf port {
                   type inet:port-number;
                   description
                     &quot;The UDP port on which the engine listens.

                      If the port is not configured, an engine that
                      acts as a Command Responder uses port 161, and
                      an engine that acts as a Notification Receiver
                      uses port 162.&quot;;
                 }
               }
             }
           }
         }

<span class="grey"><a href="/doc/html/rfc7407">RFC 7407</a>         YANG Data Model for SNMP Configuration    December 2014</span>

         container version {
           description
             &quot;SNMP version used by the engine.&quot;;
           leaf v1 {
             type empty;
           }
           leaf v2c {
             type empty;
           }
           leaf v3 {
             type empty;
           }
         }

         leaf engine-id {
           type snmp:engine-id;
           description
             &quot;The local SNMP engine&#x27;s administratively assigned unique
              identifier.

              If this leaf is not set, the device automatically
              calculates an engine ID, as described in <a href="/doc/html/rfc3411">RFC 3411</a>.  A
              server MAY initialize this leaf with the automatically
              created value.&quot;;
           reference
             &quot;<a href="/doc/html/rfc3411">RFC 3411</a>: An Architecture for Describing Simple Network
                Management Protocol (SNMP) Management
                Frameworks.
                SNMP-FRAMEWORK-MIB.snmpEngineID&quot;;
         }

         leaf enable-authen-traps {
           type boolean;
           description
             &quot;Indicates whether the SNMP entity is permitted to
              generate authenticationFailure traps.&quot;;
           reference
             &quot;<a href="/doc/html/rfc3418">RFC 3418</a>: Management Information Base (MIB) for the
                Simple Network Management Protocol (SNMP)
                SNMPv2-MIB.snmpEnableAuthenTraps&quot;;
         }
       }
     }
   }
