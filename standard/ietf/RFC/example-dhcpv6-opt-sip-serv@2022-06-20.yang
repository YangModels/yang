module example-dhcpv6-opt-sip-serv {
  yang-version 1.1;
  namespace "https://example.com/ns/"
          + "example-dhcpv6-opt-sip-serv";
  prefix sip-srv;

  import ietf-inet-types {
    prefix inet;
  }
  import ietf-dhcpv6-server {
    prefix dhc6-srv;
  }

  organization
    "IETF Dynamic Host Configuration (DHC) Working Group";
  contact
    "WG Web:   <https://datatracker.ietf.org/wg/dhc/>
     WG List:  <mailto:dhcwg@ietf.org>
     Author:   Yong Cui <yong@csnet1.cs.tsinghua.edu.cn>
     Author:   Linhui Sun <lh.sunlinh@gmail.com>
     Editor:   Ian Farrer <ian.farrer@telekom.de>
     Author:   Sladjana Zeichlin <sladjana.zechlin@telekom.de>
     Author:   Zihao He <hezihao9512@gmail.com>
     Author:   Michal Nowikowski <godfryd@isc.org>";
  description
    "This YANG module contains DHCPv6 options defined in RFC 8415
     that can be used by DHCPv6 servers.

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC 9243
     (https://www.rfc-editor.org/info/rfc9243); see the RFC itself
     for full legal notices.";

  revision 2022-06-20 {
    description
      "Initial revision.";
    reference
      "RFC 9243: A YANG Data Model for DHCPv6 Configuration";
  }

  /*
   * Groupings
   */

  grouping sip-server-domain-name-list-option-group {
    description
      "OPTION_SIP_SERVER_D (21) SIP Servers Domain-Name List.";
    reference
      "RFC 3319: Dynamic Host Configuration Protocol
       (DHCPv6) Options for Session Initiation Protocol (SIP)
       Servers";
    container sip-server-domain-name-list-option {
      description
        "OPTION_SIP_SERVER_D (21) SIP Servers Domain Name List
         Option.";
      list sip-server {
        key "sip-serv-id";
        description
          "SIP server information.";
        leaf sip-serv-id {
          type uint8;
          description
            "SIP server list identifier.";
        }
        leaf sip-serv-domain-name {
          type inet:domain-name;
          description
            "SIP server domain name.";
        }
      }
    }
  }

  grouping sip-server-address-list-option-group {
    description
      "OPTION_SIP_SERVER_A (22) SIP Servers IPv6 Address List.";
    reference
      "RFC 3319: Dynamic Host Configuration Protocol
       (DHCPv6) Options for Session Initiation Protocol (SIP)
       Servers";
    container sip-server-address-list-option {
      description
        "OPTION_SIP_SERVER_A (22) SIP Servers IPv6 Address List
         Option.";
      list sip-server {
        key "sip-serv-id";
        description
          "SIP server information.";
        leaf sip-serv-id {
          type uint8;
          description
            "SIP server list entry identifier.";
        }
        leaf sip-serv-addr {
          type inet:ipv6-address;
          description
            "SIP server IPv6 address.";
        }
      }
    }
  }

  /*
   * Augmentations
   */

  augment "/dhc6-srv:dhcpv6-server/dhc6-srv:option-sets/"
        + "dhc6-srv:option-set" {
    description
      "Augment the option definition groupings to the server
       module.";
    uses sip-server-domain-name-list-option-group;
    uses sip-server-address-list-option-group;
  }
}
