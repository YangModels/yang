module ietf-connectionless-oam {
  yang-version 1.1;
  namespace &quot;urn:ietf:params:xml:ns:yang:ietf-connectionless-oam&quot;;
  prefix cl-oam;

  import ietf-yang-schema-mount {
    prefix yangmnt;
  }
  import ietf-network {
    prefix nd;
  }
  import ietf-yang-types {
    prefix yang;
  }
  import ietf-interfaces {
    prefix if;
  }
  import ietf-inet-types {
    prefix inet;
  }
  import ietf-network-instance {
    prefix ni;
  }
  import ietf-routing-types {
    prefix rt;
  }
<span class="grey"><a href="/doc/html/rfc8532">RFC 8532</a>           Connectionless OAM YANG Data Model         April 2019</span>

  import ietf-lime-time-types {
    prefix lime;
  }

  organization
    &quot;IETF LIME Working Group&quot;;
  contact
    &quot;WG Web:   &lt;<a href="https://datatracker.ietf.org/wg/lime">https://datatracker.ietf.org/wg/lime</a>&gt;
     WG List:  &lt;mailto:<a href="mailto:lmap@ietf.org">lmap@ietf.org</a>&gt;

     Deepak Kumar &lt;<a href="mailto:dekumar@cisco.com">dekumar@cisco.com</a>&gt;
     Qin Wu &lt;<a href="mailto:bill.wu@huawei.com">bill.wu@huawei.com</a>&gt;
     Srihari Raghavan &lt;<a href="mailto:srihari@cisco.com">srihari@cisco.com</a>&gt;
     Michael Wang &lt;<a href="mailto:wangzitao@huawei.com">wangzitao@huawei.com</a>&gt;
     Reshad Rahman &lt;<a href="mailto:rrahman@cisco.com">rrahman@cisco.com</a>&gt;&quot;;
  description
    &quot;This YANG module defines the generic configuration,
     data model, and statistics for OAM protocols using
     connectionless communications, described in a
     protocol independent manner.  It is assumed that each
     protocol maps corresponding abstracts to its native
     format.  Each protocol may extend the YANG data model defined
     here to include protocol specific extensions.

     Copyright (c) 2019 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).

     This version of this YANG module is part of <a href="/doc/html/rfc8532">RFC 8532</a>; see
     the RFC itself for full legal notices.&quot;;

  revision 2019-04-16 {
    description
      &quot;Base model for Connectionless Operations, Administration,
       and Maintenance (OAM).&quot;;
    reference
      &quot;<a href="/doc/html/rfc8532">RFC 8532</a>: Generic YANG Data Model for the Management of
       Operations, Administration, and Maintenance (OAM) Protocols
       That Use Connectionless Communications&quot;;
  }

  feature connectionless {
<span class="grey"><a href="/doc/html/rfc8532">RFC 8532</a>           Connectionless OAM YANG Data Model         April 2019</span>

    description
      &quot;This feature indicates that the OAM solution is connectionless.&quot;;
  }

  feature continuity-check {
    description
      &quot;This feature indicates that the server supports
       executing a Continuity Check OAM command and
       returning a response.  Servers that do not advertise
       this feature will not support executing
       Continuity Check commands or the RPC operation model for
       Continuity Check commands.&quot;;
  }

  feature path-discovery {
    description
      &quot;This feature indicates that the server supports
       executing a path discovery OAM command and
       returning a response.  Servers that do not advertise
       this feature will not support executing
       path discovery commands or the RPC operation model for
       path discovery commands.&quot;;
  }

  feature ptp-long-format {
    description
      &quot;This feature indicates that the timestamp is PTP long format.&quot;;
  }

  feature ntp-short-format {
    description
      &quot;This feature indicates that the timestamp is NTP short format.&quot;;
  }

  feature icmp-timestamp {
    description
      &quot;This feature indicates that the timestamp is ICMP timestamp.&quot;;
  }

  identity traffic-type {
    description
      &quot;This is the base identity of the traffic type,
       which includes IPv4, IPv6, etc.&quot;;
  }

  identity ipv4 {
    base traffic-type;
    description
<span class="grey"><a href="/doc/html/rfc8532">RFC 8532</a>           Connectionless OAM YANG Data Model         April 2019</span>

      &quot;identity for IPv4 traffic type.&quot;;
  }

  identity ipv6 {
    base traffic-type;
    description
      &quot;identity for IPv6 traffic type.&quot;;
  }

  identity address-attribute-types {
    description
      &quot;This is the base identity of the address attribute types, which
       are Generic IPv4/IPv6 Prefix, BGP Labeled IPv4/IPv6 Prefix,
       Tunnel ID, PW ID, VPLS VE ID, etc. (See <a href="/doc/html/rfc8029">RFC 8029</a> for details.)&quot;;
  }

  typedef address-attribute-type {
    type identityref {
      base address-attribute-types;
    }
    description
      &quot;Target address attribute type.&quot;;
  }

  typedef percentage {
    type decimal64 {
      fraction-digits 5;
      range &quot;0..100&quot;;
    }
    description
      &quot;Percentage.&quot;;
  }

  typedef routing-instance-ref {
    type leafref {
      path &quot;/ni:network-instances/ni:network-instance/ni:name&quot;;
    }
    description
      &quot;This type is used for leafs that reference a routing instance
       configuration.&quot;;
  }

  grouping cc-session-statistics {
    description
      &quot;Grouping for session statistics.&quot;;
    container cc-session-statistics {
      description
        &quot;CC session counters.&quot;;
<span class="grey"><a href="/doc/html/rfc8532">RFC 8532</a>           Connectionless OAM YANG Data Model         April 2019</span>

      leaf session-count {
        type uint32;
        default &quot;0&quot;;
        description
          &quot;Number of Continuity Check sessions.
           A value of zero indicates that no session
           count is sent.&quot;;
      }
      leaf session-up-count {
        type uint32;
        default &quot;0&quot;;
        description
          &quot;Number of sessions that are up.
           A value of zero indicates that no up
           session count is sent.&quot;;
      }
      leaf session-down-count {
        type uint32;
        default &quot;0&quot;;
        description
          &quot;Number of sessions that are down.
           A value of zero indicates that no down
           session count is sent.&quot;;
      }
      leaf session-admin-down-count {
        type uint32;
        default &quot;0&quot;;
        description
          &quot;Number of sessions that are admin-down.
           A value of zero indicates that no admin-
           down session count is sent.&quot;;
      }
    }
  }

  grouping session-packet-statistics {
    description
      &quot;Grouping for statistics per session packet.&quot;;
    container session-packet-statistics {
      description
        &quot;Statistics per session packet.&quot;;
      leaf rx-packet-count {
        type uint32 {
          range &quot;0..4294967295&quot;;
        }
        default &quot;0&quot;;
        description
          &quot;Total count of received OAM packets.
<span class="grey"><a href="/doc/html/rfc8532">RFC 8532</a>           Connectionless OAM YANG Data Model         April 2019</span>

           The value of count will be set to zero (0)
           on creation and will thereafter increase
           monotonically until it reaches a maximum value
           of 2^32-1 (4294967295 decimal), when it wraps
           around and starts increasing again from zero.&quot;;
      }
      leaf tx-packet-count {
        type uint32 {
          range &quot;0..4294967295&quot;;
        }
        default &quot;0&quot;;
        description
          &quot;Total count of transmitted OAM packets.
           The value of count will be set to zero (0)
           on creation and will thereafter increase
           monotonically until it reaches a maximum value
           of 2^32-1 (4294967295 decimal), when it wraps
           around and starts increasing again from zero.&quot;;
      }
      leaf rx-bad-packet {
        type uint32 {
          range &quot;0..4294967295&quot;;
        }
        default &quot;0&quot;;
        description
          &quot;Total number of received bad OAM packets.
           The value of count will be set to zero (0)
           on creation and will thereafter increase
           monotonically until it reaches a maximum value
           of 2^32-1 (4294967295 decimal), when it wraps
           around and starts increasing again from zero.&quot;;
      }
      leaf tx-packet-failed {
        type uint32 {
          range &quot;0..4294967295&quot;;
        }
        default &quot;0&quot;;
        description
          &quot;Total number of OAM packets that failed when sent.
           The value of count will be set to zero (0)
           on creation and will thereafter increase
           monotonically until it reaches a maximum value
           of 2^32-1 (4294967295 decimal), when it wraps
           around and starts increasing again from zero.&quot;;
      }
    }
  }

<span class="grey"><a href="/doc/html/rfc8532">RFC 8532</a>           Connectionless OAM YANG Data Model         April 2019</span>

  grouping cc-per-session-statistics {
    description
      &quot;Grouping for per-session statistics.&quot;;
    container cc-per-session-statistics {
      description
        &quot;Per-session statistics.&quot;;
      leaf create-time {
        type yang:date-and-time;
        description
          &quot;Time and date when session is created.&quot;;
      }
      leaf last-down-time {
        type yang:date-and-time;
        description
          &quot;Time and date of the last time session was down.&quot;;
      }
      leaf last-up-time {
        type yang:date-and-time;
        description
          &quot;Time and date of the last time session was up.&quot;;
      }
      leaf down-count {
        type uint32 {
          range &quot;0..4294967295&quot;;
        }
        default &quot;0&quot;;
        description
          &quot;Total count of Continuity Check sessions down.
           The value of count will be set to zero (0)
           on creation and will thereafter increase
           monotonically until it reaches a maximum value
           of 2^32-1 (4294967295 decimal), when it wraps
           around and starts increasing again from zero.&quot;;
      }
      leaf admin-down-count {
        type uint32 {
          range &quot;0..4294967295&quot;;
        }
        default &quot;0&quot;;
        description
          &quot;Total count of Continuity Check sessions admin down.
           The value of count will be set to zero (0)
           on creation and will thereafter increase
           monotonically until it reaches a maximum value
           of 2^32-1 (4294967295 decimal), when it wraps
           around and starts increasing again from zero.&quot;;
      }
      uses session-packet-statistics;
<span class="grey"><a href="/doc/html/rfc8532">RFC 8532</a>           Connectionless OAM YANG Data Model         April 2019</span>

    }
  }

  grouping session-error-statistics {
    description
      &quot;Grouping for per-session error statistics.&quot;;
    container session-error-statistics {
      description
        &quot;Per-session error statistics.&quot;;
      leaf packet-loss-count {
        type uint32 {
          range &quot;0..4294967295&quot;;
        }
        default &quot;0&quot;;
        description
          &quot;Total count of received packet drops.
           The value of count will be set to zero (0)
           on creation and will thereafter increase
           monotonically until it reaches a maximum value
           of 2^32-1 (4294967295 decimal), when it wraps
           around and starts increasing again from zero.&quot;;
      }
      leaf loss-ratio {
        type percentage;
        description
          &quot;Loss ratio of the packets.  Expressed as percentage
           of packets lost with respect to packets sent.&quot;;
      }
      leaf packet-reorder-count {
        type uint32 {
          range &quot;0..4294967295&quot;;
        }
        default &quot;0&quot;;
        description
          &quot;Total count of received packets that were reordered.
           The value of count will be set to zero (0)
           on creation and will thereafter increase
           monotonically until it reaches a maximum value
           of 2^32-1 (4294967295 decimal), when it wraps
           around and starts increasing again from zero.&quot;;
      }
      leaf packets-out-of-seq-count {
        type uint32 {
          range &quot;0..4294967295&quot;;
        }
        description
          &quot;Total count of packets received out of sequence.
           The value of count will be set to zero (0)
<span class="grey"><a href="/doc/html/rfc8532">RFC 8532</a>           Connectionless OAM YANG Data Model         April 2019</span>

           on creation and will thereafter increase
           monotonically until it reaches a maximum value
           of 2^32-1 (4294967295 decimal), when it wraps
           around and starts increasing again from zero.&quot;;
      }
      leaf packets-dup-count {
        type uint32 {
          range &quot;0..4294967295&quot;;
        }
        description
          &quot;Total count of received packet duplicates.
           The value of count will be set to zero (0)
           on creation and will thereafter increase
           monotonically until it reaches a maximum value
           of 2^32-1 (4294967295 decimal), when it wraps
           around and starts increasing again from zero.&quot;;
      }
    }
  }

  grouping session-delay-statistics {
    description
      &quot;Grouping for delay statistics per session.&quot;;
    container session-delay-statistics {
      description
        &quot;Session delay summarized information.  By default, a
         one-way measurement protocol (e.g., OWAMP) is used
         to measure delay.  When a two-way measurement protocol
         (e.g., TWAMP) is used instead, it can be indicated
         using the protocol-id defined in RPC operation of
         retrieval methods for connectionless OAM (<a href="/doc/html/rfc8533">RFC 8533</a>),
         i.e., set protocol-id as OWAMP.  Note that only one
         measurement protocol for delay is specified for
         interoperability reasons.&quot;;
      leaf time-unit-value {
        type identityref {
          base lime:time-unit-type;
        }
        default &quot;lime:milliseconds&quot;;
        description
          &quot;Time units, where the options are s, ms, ns, etc.&quot;;
      }
      leaf min-delay-value {
        type uint32;
        description
          &quot;Minimum delay value observed.&quot;;
      }
      leaf max-delay-value {
<span class="grey"><a href="/doc/html/rfc8532">RFC 8532</a>           Connectionless OAM YANG Data Model         April 2019</span>

        type uint32;
        description
          &quot;Maximum delay value observed.&quot;;
      }
      leaf average-delay-value {
        type uint32;
        description
          &quot;Average delay value observed.&quot;;
      }
    }
  }

  grouping session-jitter-statistics {
    description
      &quot;Grouping for per session jitter statistics.&quot;;
    container session-jitter-statistics {
      description
        &quot;Summarized information about session jitter.  By default,
         jitter is measured using IP Packet Delay Variation
         (IPDV) as defined in <a href="/doc/html/rfc3393">RFC 3393</a>.  When the other measurement
         method is used instead (e.g., Packet Delay Variation used
         in ITU-T Recommendation Y.1540, it can be indicated using
         protocol-id-meta-data defined in RPC operation of
         retrieval methods for connectionless OAM (<a href="/doc/html/rfc8533">RFC 8533</a>).
         Note that only one measurement method for jitter is
         specified for interoperability reasons.&quot;;
      leaf unit-value {
        type identityref {
          base lime:time-unit-type;
        }
        default &quot;lime:milliseconds&quot;;
        description
          &quot;Time units, where the options are s, ms, ns, etc.&quot;;
      }
      leaf min-jitter-value {
        type uint32;
        description
          &quot;Minimum jitter value observed.&quot;;
      }
      leaf max-jitter-value {
        type uint32;
        description
          &quot;Maximum jitter value observed.&quot;;
      }
      leaf average-jitter-value {
        type uint32;
        description
          &quot;Average jitter value observed.&quot;;
<span class="grey"><a href="/doc/html/rfc8532">RFC 8532</a>           Connectionless OAM YANG Data Model         April 2019</span>

      }
    }
  }

  grouping session-path-verification-statistics {
    description
      &quot;Grouping for path verification statistics per session.&quot;;
    container session-path-verification-statistics {
      description
        &quot;OAM path verification statistics per session.&quot;;
      leaf verified-count {
        type uint32 {
          range &quot;0..4294967295&quot;;
        }
        description
          &quot;Total number of OAM packets that
           went through a path as intended.
           The value of count will be set to zero (0)
           on creation and will thereafter increase
           monotonically until it reaches a maximum value
           of 2^32-1 (4294967295 decimal), when it wraps
           around and starts increasing again from zero.&quot;;
      }
      leaf failed-count {
        type uint32 {
          range &quot;0..4294967295&quot;;
        }
        description
          &quot;Total number of OAM packets that
           went through an unintended path.
           The value of count will be set to zero (0)
           on creation and will thereafter increase
           monotonically until it reaches a maximum value
           of 2^32-1 (4294967295 decimal), when it wraps
           around and starts increasing again from zero.&quot;;
      }
    }
  }

  grouping session-type {
    description
      &quot;This object indicates which kind of activation will
       be used by the current session.&quot;;
    leaf session-type {
      type enumeration {
        enum proactive {
          description
            &quot;The current session is a proactive session.&quot;;
<span class="grey"><a href="/doc/html/rfc8532">RFC 8532</a>           Connectionless OAM YANG Data Model         April 2019</span>

        }
        enum on-demand {
          description
            &quot;The current session is an on-demand session.&quot;;
        }
      }
      default &quot;on-demand&quot;;
      description
        &quot;Indicate which kind of activation will be used
         by the current session.&quot;;
    }
  }

  identity tp-address-technology-type {
    description
      &quot;Test point address type.&quot;;
  }

  identity mac-address-type {
    base tp-address-technology-type;
    description
      &quot;MAC address type.&quot;;
  }

  identity ipv4-address-type {
    base tp-address-technology-type;
    description
      &quot;IPv4 address type.&quot;;
  }

  identity ipv6-address-type {
    base tp-address-technology-type;
    description
      &quot;IPv6 address type.&quot;;
  }

  identity tp-attribute-type {
    base tp-address-technology-type;
    description
      &quot;Test point attribute type.&quot;;
  }

  identity router-id-address-type {
    base tp-address-technology-type;
    description
      &quot;System ID address type.&quot;;
  }

<span class="grey"><a href="/doc/html/rfc8532">RFC 8532</a>           Connectionless OAM YANG Data Model         April 2019</span>

  identity as-number-address-type {
    base tp-address-technology-type;
    description
      &quot;AS number address type.&quot;;
  }

  identity route-distinguisher-address-type {
    base tp-address-technology-type;
    description
      &quot;Route Distinguisher address type.&quot;;
  }

  grouping tp-address {
    leaf tp-location-type {
      type identityref {
        base tp-address-technology-type;
      }
      mandatory true;
      description
        &quot;Test point address type.&quot;;
    }
    container mac-address {
      when &quot;derived-from-or-self(../tp-location-type,&quot;
         + &quot;&#x27;cl-oam:mac-address-type&#x27;)&quot; {
        description
          &quot;MAC address type.&quot;;
      }
      leaf mac-address {
        type yang:mac-address;
        mandatory true;
        description
          &quot;MAC address.&quot;;
      }
      description
        &quot;MAC address based TP addressing.&quot;;
    }
    container ipv4-address {
      when &quot;derived-from-or-self(../tp-location-type,&quot;
         + &quot;&#x27;cl-oam:ipv4-address-type&#x27;)&quot; {
        description
          &quot;IPv4 address type.&quot;;
      }
      leaf ipv4-address {
        type inet:ipv4-address;
        mandatory true;
        description
          &quot;IPv4 address.&quot;;
      }
<span class="grey"><a href="/doc/html/rfc8532">RFC 8532</a>           Connectionless OAM YANG Data Model         April 2019</span>

      description
        &quot;IP address based TP addressing.&quot;;
    }
    container ipv6-address {
      when &quot;derived-from-or-self(../tp-location-type,&quot;
         + &quot;&#x27;cl-oam:ipv6-address-type&#x27;)&quot; {
        description
          &quot;IPv6 address type.&quot;;
      }
      leaf ipv6-address {
        type inet:ipv6-address;
        mandatory true;
        description
          &quot;IPv6 address.&quot;;
      }
      description
        &quot;IPv6 address based TP addressing.&quot;;
    }
    container tp-attribute {
      when &quot;derived-from-or-self(../tp-location-type,&quot;
         + &quot;&#x27;cl-oam:tp-attribute-type&#x27;)&quot; {
        description
          &quot;Test point attribute type.&quot;;
      }
      leaf tp-attribute-type {
        type address-attribute-type;
        description
          &quot;Test point type.&quot;;
      }
      choice tp-attribute-value {
        description
          &quot;Test point value.&quot;;
        case ip-prefix {
          leaf ip-prefix {
            type inet:ip-prefix;
            description
              &quot;Generic IPv4/IPv6 prefix.  See Sections <a href="#section-3.2.13">3.2.13</a> and
               3.2.14 of <a href="/doc/html/rfc8029">RFC 8029</a>.&quot;;
            reference
              &quot;<a href="/doc/html/rfc8029">RFC 8029</a>: Detecting Multiprotocol Label
               Switched (MPLS) Data-Plane Failures&quot;;
          }
        }
        case bgp {
          leaf bgp {
            type inet:ip-prefix;
            description
              &quot;BGP Labeled IPv4/IPv6 Prefix.  See Sections
<span class="grey"><a href="/doc/html/rfc8532">RFC 8532</a>           Connectionless OAM YANG Data Model         April 2019</span>

               3.2.11 and 3.2.12 of <a href="/doc/html/rfc8029">RFC 8029</a> for details.&quot;;
            reference
              &quot;<a href="/doc/html/rfc8029">RFC 8029</a>: Detecting Multiprotocol Label
               Switched (MPLS) Data-Plane Failures&quot;;
          }
        }
        case tunnel {
          leaf tunnel-interface {
            type uint32;
            description
              &quot;Basic IPv4/IPv6 Tunnel ID.  See Sections <a href="#section-3.2.3">3.2.3</a>
               and 3.2.4 of <a href="/doc/html/rfc8029">RFC 8029</a> for details.&quot;;
            reference
              &quot;<a href="/doc/html/rfc8029">RFC 8029</a>: Detecting Multiprotocol Label
               Switched (MPLS) Data-Plane Failures.&quot;;
          }
        }
        case pw {
          leaf remote-pe-address {
            type inet:ip-address;
            description
              &quot;Remote PE address.  See <a href="/doc/html/rfc8029#section-3.2.8">Section&amp;nbsp;3.2.8
               of RFC 8029</a> for details.&quot;;
            reference
              &quot;<a href="/doc/html/rfc8029">RFC 8029</a>: Detecting Multiprotocol Label
               Switched (MPLS) Data-Plane Failures&quot;;
          }
          leaf pw-id {
            type uint32;
            description
              &quot;Pseudowire ID is a non-zero 32-bit ID.  See Sections
               3.2.8 and 3.2.9 of <a href="/doc/html/rfc8029">RFC 8029</a> for details.&quot;;
            reference
              &quot;<a href="/doc/html/rfc8029">RFC 8029</a>: Detecting Multiprotocol Label
               Switched (MPLS) Data-Plane Failures&quot;;
          }
        }
        case vpls {
          leaf route-distinguisher {
            type rt:route-distinguisher;
            description
              &quot;Route Distinguisher is an 8-octet identifier
               used to distinguish information about various
               L2VPNs advertised by a node.&quot;;
            reference
              &quot;<a href="/doc/html/rfc8029">RFC 8029</a>: Detecting Multiprotocol Label
               Switched (MPLS) Data-Plane Failures&quot;;
          }
<span class="grey"><a href="/doc/html/rfc8532">RFC 8532</a>           Connectionless OAM YANG Data Model         April 2019</span>

          leaf sender-ve-id {
            type uint16;
            description
              &quot;Sender&#x27;s VE ID.  The VE ID (VPLS Edge Identifier)
               is a 2-octet identifier.&quot;;
            reference
              &quot;<a href="/doc/html/rfc8029">RFC 8029</a>: Detecting Multiprotocol Label
               Switched (MPLS) Data-Plane Failures&quot;;
          }
          leaf receiver-ve-id {
            type uint16;
            description
              &quot;Receiver&#x27;s VE ID.  The VE ID (VPLS Edge Identifier)
               is a 2-octet identifier.&quot;;
            reference
              &quot;<a href="/doc/html/rfc8029">RFC 8029</a>: Detecting Multiprotocol Label
               Switched (MPLS) Data-Plane Failures&quot;;
          }
        }
        case mpls-mldp {
          choice root-address {
            description
              &quot;Root address choice.&quot;;
            case ip-address {
              leaf source-address {
                type inet:ip-address;
                description
                  &quot;IP address.&quot;;
              }
              leaf group-ip-address {
                type inet:ip-address;
                description
                  &quot;Group IP address.&quot;;
              }
            }
            case vpn {
              leaf as-number {
                type inet:as-number;
                description
                  &quot;The AS number that identifies an Autonomous
                   System.&quot;;
              }
            }
            case global-id {
              leaf lsp-id {
                type string;
                description
                  &quot;LSP ID is an identifier of a LSP
<span class="grey"><a href="/doc/html/rfc8532">RFC 8532</a>           Connectionless OAM YANG Data Model         April 2019</span>

                   within a MPLS network.&quot;;
                reference
                  &quot;<a href="/doc/html/rfc8029">RFC 8029</a>: Detecting Multiprotocol Label
                   Switched (MPLS) Data-Plane Failures&quot;;
              }
            }
          }
        }
      }
      description
        &quot;Test Point Attribute Container.&quot;;
    }
    container system-info {
      when &quot;derived-from-or-self(../tp-location-type,&quot;
         + &quot;&#x27;cl-oam:router-id-address-type&#x27;)&quot; {
        description
          &quot;System ID address type.&quot;;
      }
      leaf router-id {
        type rt:router-id;
        description
          &quot;Router ID assigned to this node.&quot;;
      }
      description
        &quot;Router ID container.&quot;;
    }
    description
      &quot;TP Address.&quot;;
  }

  grouping tp-address-ni {
    description
      &quot;Test point address with VRF.&quot;;
    leaf ni {
      type routing-instance-ref;
      description
        &quot;The ni is used to describe virtual resource partitioning
         that may be present on a network device.  An example of a
         common industry term for virtual resource partitioning is
         &#x27;VRF instance&#x27;.&quot;;
    }
    uses tp-address;
  }

  grouping connectionless-oam-tps {
    list oam-neighboring-tps {
      key &quot;index&quot;;
      leaf index {
<span class="grey"><a href="/doc/html/rfc8532">RFC 8532</a>           Connectionless OAM YANG Data Model         April 2019</span>

        type uint16 {
          range &quot;0..65535&quot;;
        }
        description
          &quot;Index of a list of neighboring test points
           in layers up and down the stack for
           the same interface that are related to the
           current test point.&quot;;
      }
      leaf position {
        type int8 {
          range &quot;-1..1&quot;;
        }
        default &quot;0&quot;;
        description
          &quot;The position of the neighboring test point relative to
           the current test point.  Level 0 indicates a test point
           corresponding to a specific index in the same layer as
           the current test point.  -1 means there is a test point
           corresponding to a specific index in the test point down
           the stack, and +1 means there is a test point corresponding
           to a specific index in the test point up the stack.&quot;;
      }
      choice tp-location {
        case mac-address {
          leaf mac-address-location {
            type yang:mac-address;
            description
              &quot;MAC address.&quot;;
          }
          description
            &quot;MAC address based TP addressing.&quot;;
        }
        case ipv4-address {
          leaf ipv4-address-location {
            type inet:ipv4-address;
            description
              &quot;IPv4 address.&quot;;
          }
          description
            &quot;IP address based TP addressing.&quot;;
        }
        case ipv6-address {
          leaf ipv6-address-location {
            type inet:ipv6-address;
            description
              &quot;IPv6 address.&quot;;
          }
<span class="grey"><a href="/doc/html/rfc8532">RFC 8532</a>           Connectionless OAM YANG Data Model         April 2019</span>

          description
            &quot;IPv6 address based TP addressing.&quot;;
        }
        case as-number {
          leaf as-number-location {
            type inet:as-number;
            description
              &quot;AS number location.&quot;;
          }
          description
            &quot;AS number for point-to-multipoint OAM.&quot;;
        }
        case router-id {
          leaf router-id-location {
            type rt:router-id;
            description
              &quot;System ID location.&quot;;
          }
          description
            &quot;System ID.&quot;;
        }
        description
          &quot;TP location.&quot;;
      }
      description
        &quot;List of neighboring test points in the same layer that are
         related to current test point.  If the neighboring test point
         is placed after the current test point, the position is
         specified as +1.  If the neighboring test point is placed
         before the current test point, the position is specified
         as -1; if no neighboring test points are placed before or
         after the current test point in the same layer, the
         position is specified as 0.&quot;;
    }
    description
      &quot;List of neighboring test points related to connectionless OAM.&quot;;
  }

  grouping tp-technology {
    choice technology {
      default &quot;technology-null&quot;;
      case technology-null {
        description
          &quot;This is a placeholder when no technology is needed.&quot;;
        leaf tech-null {
          type empty;
          description
            &quot;There is no technology to be defined.&quot;;
<span class="grey"><a href="/doc/html/rfc8532">RFC 8532</a>           Connectionless OAM YANG Data Model         April 2019</span>

        }
      }
      description
        &quot;Technology choice.&quot;;
    }
    description
      &quot;OAM technology.&quot;;
  }

  grouping tp-tools {
    description
      &quot;Test point OAM toolset.&quot;;
    container tp-tools {
      leaf continuity-check {
        type boolean;
        mandatory true;
        description
          &quot;A flag indicating whether or not the
           Continuity Check function is supported.&quot;;
        reference
          &quot;<a href="/doc/html/rfc792">RFC 792</a>: INTERNET CONTROL MESSAGE PROTOCOL
           <a href="/doc/html/rfc4443">RFC 4443</a>: Internet Control Message Protocol (ICMPv6)
               for the Internet Protocol Version 6 (IPv6) Specification
           <a href="/doc/html/rfc5880">RFC 5880</a>: Bidirectional Forwarding Detection
           <a href="/doc/html/rfc5881">RFC 5881</a>: BFD for IPv4 and IPv6
           <a href="/doc/html/rfc5883">RFC 5883</a>: BFD for Multihop Paths
           <a href="/doc/html/rfc5884">RFC 5884</a>: BFD for MPLS Label Switched Paths
           <a href="/doc/html/rfc5885">RFC 5885</a>: BFD for PW VCCV
           <a href="/doc/html/rfc6450">RFC 6450</a>: Multicast Ping Protocol
           <a href="/doc/html/rfc8029">RFC 8029</a>: Detecting Multiprotocol Label Switched (MPLS)
               Data-Plane Failures&quot;;
      }
      leaf path-discovery {
        type boolean;
        mandatory true;
        description
          &quot;A flag indicating whether or not the
           path discovery function is supported.&quot;;
        reference
          &quot;<a href="/doc/html/rfc792">RFC 792</a>: INTERNET CONTROL MESSAGE PROTOCOL
           <a href="/doc/html/rfc4443">RFC 4443</a>: Internet Control Message Protocol (ICMPv6)
               for the Internet Protocol Version 6 (IPv6) Specification
           <a href="/doc/html/rfc4884">RFC 4884</a>: Extended ICMP to Support Multi-Part Messages
           <a href="/doc/html/rfc5837">RFC 5837</a>: Extending ICMP for Interface and Next-Hop
               Identification
           <a href="/doc/html/rfc8029">RFC 8029</a>: Detecting Multiprotocol Label Switched (MPLS)
               Data-Plane Failures&quot;;
      }
<span class="grey"><a href="/doc/html/rfc8532">RFC 8532</a>           Connectionless OAM YANG Data Model         April 2019</span>

      description
        &quot;Container for test point OAM toolset.&quot;;
    }
  }

  grouping test-point-location-info {
    uses tp-technology;
    uses tp-tools;
    anydata root {
      yangmnt:mount-point &quot;root&quot;;
      description
        &quot;Root for models supported per test point.&quot;;
    }
    uses connectionless-oam-tps;
    description
      &quot;Test point location.&quot;;
  }

  grouping test-point-locations {
    description
      &quot;Group of test point locations.&quot;;
    leaf tp-location-type {
      type identityref {
        base tp-address-technology-type;
      }
      description
        &quot;Test point location type.&quot;;
    }
    container ipv4-location-type {
      when &quot;derived-from-or-self(../tp-location-type,&quot;
         + &quot;&#x27;cl-oam:ipv4-address-type&#x27;)&quot; {
        description
          &quot;When test point location type is equal to IPv4 address.&quot;;
      }
      container test-point-ipv4-location-list {
        list test-point-locations {
          key &quot;ipv4-location ni&quot;;
          leaf ipv4-location {
            type inet:ipv4-address;
            description
              &quot;IPv4 address.&quot;;
          }
          leaf ni {
            type routing-instance-ref;
            description
              &quot;The ni is used to describe the
               corresponding network instance&quot;;
          }
<span class="grey"><a href="/doc/html/rfc8532">RFC 8532</a>           Connectionless OAM YANG Data Model         April 2019</span>

          uses test-point-location-info;
          description
            &quot;List of test point locations.&quot;;
        }
        description
          &quot;Serves as top-level container
           for test point location list.&quot;;
      }
      description
        &quot;Container for IPv4 location types.&quot;;
    }
    container ipv6-location-type {
      when &quot;derived-from-or-self(../tp-location-type,&quot;
         + &quot;&#x27;cl-oam:ipv6-address-type&#x27;)&quot; {
        description
          &quot;When test point location is equal to IPv6 address.&quot;;
      }
      container test-point-ipv6-location-list {
        list test-point-locations {
          key &quot;ipv6-location ni&quot;;
          leaf ipv6-location {
            type inet:ipv6-address;
            description
              &quot;IPv6 address.&quot;;
          }
          leaf ni {
            type routing-instance-ref;
            description
              &quot;The ni is used to describe the
               corresponding network instance.&quot;;
          }
          uses test-point-location-info;
          description
            &quot;List of test point locations.&quot;;
        }
        description
          &quot;Serves as top-level container
           for test point location list.&quot;;
      }
      description
        &quot;ipv6 location type container.&quot;;
    }
    container mac-location-type {
      when &quot;derived-from-or-self(../tp-location-type,&quot;
         + &quot;&#x27;cl-oam:mac-address-type&#x27;)&quot; {
        description
          &quot;When test point location type is equal to MAC address.&quot;;
      }
<span class="grey"><a href="/doc/html/rfc8532">RFC 8532</a>           Connectionless OAM YANG Data Model         April 2019</span>

      container test-point-mac-address-location-list {
        list test-point-locations {
          key &quot;mac-address-location&quot;;
          leaf mac-address-location {
            type yang:mac-address;
            description
              &quot;MAC address.&quot;;
          }
          uses test-point-location-info;
          description
            &quot;List of test point locations.&quot;;
        }
        description
          &quot;Serves as top-level container
           for test point location list.&quot;;
      }
      description
        &quot;Container for MAC address location types.&quot;;
    }
    container group-as-number-location-type {
      when &quot;derived-from-or-self(../tp-location-type,&quot;
         + &quot;&#x27;cl-oam:as-number-address-type&#x27;)&quot; {
        description
          &quot;When test point location type is equal to AS number.&quot;;
      }
      container test-point-as-number-location-list {
        list test-point-locations {
          key &quot;as-number-location&quot;;
          leaf as-number-location {
            type inet:as-number;
            description
              &quot;AS number for point-to-multipoint OAM.&quot;;
          }
          leaf ni {
            type routing-instance-ref;
            description
              &quot;The ni is used to describe the
               corresponding network instance.&quot;;
          }
          uses test-point-location-info;
          description
            &quot;List of test point locations.&quot;;
        }
        description
          &quot;Serves as top-level container
           for test point location list.&quot;;
      }
      description
<span class="grey"><a href="/doc/html/rfc8532">RFC 8532</a>           Connectionless OAM YANG Data Model         April 2019</span>

        &quot;Container for AS number location types.&quot;;
    }
    container group-router-id-location-type {
      when &quot;derived-from-or-self(../tp-location-type,&quot;
         + &quot;&#x27;cl-oam:router-id-address-type&#x27;)&quot; {
        description
          &quot;When test point location type is equal to system-info.&quot;;
      }
      container test-point-system-info-location-list {
        list test-point-locations {
          key &quot;router-id-location&quot;;
          leaf router-id-location {
            type rt:router-id;
            description
              &quot;System ID.&quot;;
          }
          leaf ni {
            type routing-instance-ref;
            description
              &quot;The ni is used to describe the
               corresponding network instance.&quot;;
          }
          uses test-point-location-info;
          description
            &quot;List of test point locations.&quot;;
        }
        description
          &quot;Serves as top-level container for
           test point location list.&quot;;
      }
      description
        &quot;Container for system ID location types.&quot;;
    }
  }

  augment &quot;/nd:networks/nd:network/nd:node&quot; {
    description
      &quot;Augments the /networks/network/node path defined in the
       ietf-network module (<a href="/doc/html/rfc8345">RFC 8345</a>) with test-point-locations
       grouping.&quot;;
    uses test-point-locations;
  }

  grouping timestamp {
    description
      &quot;Grouping for timestamp.&quot;;
    leaf timestamp-type {
      type identityref {
<span class="grey"><a href="/doc/html/rfc8532">RFC 8532</a>           Connectionless OAM YANG Data Model         April 2019</span>

        base lime:timestamp-type;
      }
      description
        &quot;Type of timestamp, such as Truncated PTP or NTP.&quot;;
    }
    container timestamp-64bit {
      when &quot;derived-from-or-self(../timestamp-type,&quot;
         + &quot;&#x27;lime:truncated-ptp&#x27;)&quot;
         + &quot;or derived-from-or-self(../timestamp-type,&quot;
         + &quot;&#x27;lime:ntp64&#x27;)&quot; {
        description
          &quot;Only applies when PTP truncated or 64-bit NTP timestamp.&quot;;
      }
      leaf timestamp-sec {
        type uint32;
        description
          &quot;Absolute timestamp in seconds as per IEEE 1588v2
           or seconds part in 64-bit NTP timestamp.&quot;;
      }
      leaf timestamp-nanosec {
        type uint32;
        description
          &quot;Fractional part in nanoseconds as per IEEE 1588v2
           or fractional part in 64-bit NTP timestamp.&quot;;
      }
      description
        &quot;Container for 64-bit timestamp.  The Network Time Protocol
         (NTP) 64-bit timestamp format is defined in <a href="/doc/html/rfc5905">RFC 5905</a>.  The
         PTP truncated timestamp format is defined in IEEE 1588v1.&quot;;
      reference
        &quot;<a href="/doc/html/rfc5905">RFC 5905</a>: Network Time Protocol Version 4: Protocol and
             Algorithms Specification
         IEEE 1588v1: IEEE Standard for a Precision Clock
             Synchronization Protocol for Networked Measurement and
             Control Systems Version 1&quot;;
    }
    container timestamp-80bit {
      when &quot;derived-from-or-self(../timestamp-type, &#x27;lime:ptp80&#x27;)&quot; {
        description
          &quot;Only applies when 80-bit PTP timestamp.&quot;;
      }
      if-feature &quot;ptp-long-format&quot;;
      leaf timestamp-sec {
        type uint64 {
          range &quot;0..281474976710655&quot;;
        }
        description
          &quot;48-bit timestamp in seconds as per IEEE 1588v2.&quot;;
<span class="grey"><a href="/doc/html/rfc8532">RFC 8532</a>           Connectionless OAM YANG Data Model         April 2019</span>

      }
      leaf timestamp-nanosec {
        type uint32;
        description
          &quot;Fractional part in nanoseconds as per IEEE 1588v2.&quot;;
      }
      description
        &quot;Container for 80-bit timestamp.&quot;;
    }
    container ntp-timestamp-32bit {
      when &quot;derived-from-or-self(../timestamp-type,&quot;
         + &quot;&#x27;lime:truncated-ntp&#x27;)&quot; {
        description
          &quot;Only applies when 32-bit NTP short-format timestamp.&quot;;
      }
      if-feature &quot;ntp-short-format&quot;;
      leaf timestamp-sec {
        type uint16;
        description
          &quot;Timestamp in seconds as per short-format NTP.&quot;;
      }
      leaf timestamp-nanosec {
        type uint16;
        description
          &quot;Truncated fractional part in 16-bit NTP timestamp.&quot;;
      }
      description
        &quot;Container for 32-bit timestamp <a href="/doc/html/rfc5905">RFC5905</a>.&quot;;
      reference
        &quot;<a href="/doc/html/rfc5905">RFC 5905</a>: Network Time Protocol Version 4: Protocol and
         Algorithms Specification.&quot;;
    }
    container icmp-timestamp-32bit {
      when &quot;derived-from-or-self(../timestamp-type, &#x27;lime:icmp&#x27;)&quot; {
        description
          &quot;Only applies when ICMP timestamp.&quot;;
      }
      if-feature &quot;icmp-timestamp&quot;;
      leaf timestamp-millisec {
        type uint32;
        description
          &quot;Timestamp in milliseconds for ICMP timestamp.&quot;;
      }
      description
        &quot;Container for 32-bit timestamp.  See <a href="/doc/html/rfc792">RFC 792</a> for ICMP
         timestamp format.&quot;;
    }
  }
<span class="grey"><a href="/doc/html/rfc8532">RFC 8532</a>           Connectionless OAM YANG Data Model         April 2019</span>

  grouping path-discovery-data {
    description
      &quot;Data output from nodes related to path discovery.&quot;;
    container src-test-point {
      description
        &quot;Source test point.&quot;;
      uses tp-address-ni;
    }
    container dest-test-point {
      description
        &quot;Destination test point.&quot;;
      uses tp-address-ni;
    }
    leaf sequence-number {
      type uint64;
      default &quot;0&quot;;
      description
        &quot;Sequence number in data packets.  A value of
         zero indicates that no sequence number is sent.&quot;;
    }
    leaf hop-cnt {
      type uint8;
      default &quot;0&quot;;
      description
        &quot;Hop count.  A value of zero indicates
         that no hop count is sent.&quot;;
    }
    uses session-packet-statistics;
    uses session-error-statistics;
    uses session-delay-statistics;
    uses session-jitter-statistics;
    container path-verification {
      description
        &quot;Optional information related to path verification.&quot;;
      leaf flow-info {
        type string;
        description
          &quot;Information that refers to the flow.&quot;;
      }
      uses session-path-verification-statistics;
    }
    container path-trace-info {
      description
        &quot;Optional per-hop path trace information about test points.
         The path trace information list typically has a single
         element for per-hop cases such as path-discovery RPC operation
         but allows a list of hop-related information for other types of
         data retrieval methods.&quot;;
<span class="grey"><a href="/doc/html/rfc8532">RFC 8532</a>           Connectionless OAM YANG Data Model         April 2019</span>

      list path-trace-info-list {
        key &quot;index&quot;;
        description
          &quot;Path trace information list.&quot;;
        leaf index {
          type uint32;
          description
            &quot;Trace information index.&quot;;
        }
        uses tp-address-ni;
        uses timestamp;
        leaf ingress-intf-name {
          type if:interface-ref;
          description
            &quot;Ingress interface name.&quot;;
        }
        leaf egress-intf-name {
          type if:interface-ref;
          description
            &quot;Egress interface name.&quot;;
        }
        leaf queue-depth {
          type uint32;
          description
            &quot;Length of the queue of the interface from where
             the packet is forwarded out.  The queue depth could
             be the current number of memory buffers used by the
             queue, and a packet can consume one or more memory buffers,
             thus constituting device-level information.&quot;;
        }
        leaf transit-delay {
          type uint32;
          description
            &quot;Time in nanoseconds that the packet spent transiting a
             node.&quot;;
        }
        leaf app-meta-data {
          type uint64;
          description
            &quot;Application-specific data added by node.&quot;;
        }
      }
    }
  }

  grouping continuity-check-data {
    description
      &quot;Continuity Check data output from nodes.&quot;;
<span class="grey"><a href="/doc/html/rfc8532">RFC 8532</a>           Connectionless OAM YANG Data Model         April 2019</span>

    container src-test-point {
      description
        &quot;Source test point.&quot;;
      uses tp-address-ni;
      leaf egress-intf-name {
        type if:interface-ref;
        description
          &quot;Egress interface name.&quot;;
      }
    }
    container dest-test-point {
      description
        &quot;Destination test point.&quot;;
      uses tp-address-ni;
      leaf ingress-intf-name {
        type if:interface-ref;
        description
          &quot;Ingress interface name.&quot;;
      }
    }
    leaf sequence-number {
      type uint64;
      default &quot;0&quot;;
      description
        &quot;Sequence number in data packets.  A value of
         zero indicates that no sequence number is sent.&quot;;
    }
    leaf hop-cnt {
      type uint8;
      default &quot;0&quot;;
      description
        &quot;Hop count.  A value of zero indicates
         that no hop count is sent.&quot;;
    }
    uses session-packet-statistics;
    uses session-error-statistics;
    uses session-delay-statistics;
    uses session-jitter-statistics;
  }

  container cc-session-statistics-data {
    if-feature &quot;continuity-check&quot;;
    config false;
    list cc-session-statistics {
      key &quot;type&quot;;
      leaf type {
        type identityref {
          base traffic-type;
<span class="grey"><a href="/doc/html/rfc8532">RFC 8532</a>           Connectionless OAM YANG Data Model         April 2019</span>

        }
        description
          &quot;Type of traffic.&quot;;
      }
      container cc-ipv4-sessions-statistics {
        when &quot;../type = &#x27;ipv4&#x27;&quot; {
          description
            &quot;Only applies when traffic type is IPv4.&quot;;
        }
        description
          &quot;CC ipv4 sessions.&quot;;
        uses cc-session-statistics;
      }
      container cc-ipv6-sessions-statistics {
        when &quot;../type = &#x27;ipv6&#x27;&quot; {
          description
            &quot;Only applies when traffic type is IPv6.&quot;;
        }
        description
          &quot;CC IPv6 sessions.&quot;;
        uses cc-session-statistics;
      }
      description
        &quot;List of CC session statistics data.&quot;;
    }
    description
      &quot;CC operational information.&quot;;
  }
}
