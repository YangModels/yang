module ietf-yang-push {
  yang-version 1.1;
  namespace &quot;urn:ietf:params:xml:ns:yang:ietf-yang-push&quot;;
  prefix yp;

  import ietf-yang-types {
    prefix yang;
    reference
      &quot;<a href="/doc/html/rfc6991">RFC 6991</a>: Common YANG Data Types&quot;;
  }
  import ietf-subscribed-notifications {
    prefix sn;
    reference
      &quot;<a href="/doc/html/rfc8639">RFC 8639</a>: Subscription to YANG Notifications&quot;;
  }
  import ietf-datastores {
    prefix ds;
    reference
      &quot;<a href="/doc/html/rfc8342">RFC 8342</a>: Network Management Datastore Architecture (NMDA)&quot;;
  }
  import ietf-restconf {
    prefix rc;
    reference
      &quot;<a href="/doc/html/rfc8040">RFC 8040</a>: RESTCONF Protocol&quot;;
  }
  import ietf-yang-patch {
    prefix ypatch;
    reference
      &quot;<a href="/doc/html/rfc8072">RFC 8072</a>: YANG Patch Media Type&quot;;
  }

  organization
    &quot;IETF NETCONF (Network Configuration) Working Group&quot;;
  contact
    &quot;WG Web:  &lt;https:/datatracker.ietf.org/wg/netconf/&gt;
     WG List: &lt;mailto:<a href="mailto:netconf@ietf.org">netconf@ietf.org</a>&gt;

     Author:  Alexander Clemm
<span class="grey"><a href="/doc/html/rfc8641">RFC 8641</a>                        YANG-Push                 September 2019</span>

                 &lt;mailto:<a href="mailto:ludwig@clemm.org">ludwig@clemm.org</a>&gt;

        Author:  Eric Voit
                 &lt;mailto:<a href="mailto:evoit@cisco.com">evoit@cisco.com</a>&gt;&quot;;

     description
       &quot;This module contains YANG specifications for YANG-Push.

        The key words &#x27;MUST&#x27;, &#x27;MUST NOT&#x27;, &#x27;REQUIRED&#x27;, &#x27;SHALL&#x27;, &#x27;SHALL
        NOT&#x27;, &#x27;SHOULD&#x27;, &#x27;SHOULD NOT&#x27;, &#x27;RECOMMENDED&#x27;, &#x27;NOT RECOMMENDED&#x27;,
        &#x27;MAY&#x27;, and &#x27;OPTIONAL&#x27; in this document are to be interpreted as
        described in <a href="/doc/html/bcp14">BCP 14</a> (<a href="/doc/html/rfc2119">RFC 2119</a>) (<a href="/doc/html/rfc8174">RFC 8174</a>) when, and only when,
        they appear in all capitals, as shown here.

        Copyright (c) 2019 IETF Trust and the persons identified as
        authors of the code.  All rights reserved.

        Redistribution and use in source and binary forms, with or
        without modification, is permitted pursuant to, and subject to
        the license terms contained in, the Simplified BSD License set
        forth in <a href="#section-4">Section 4</a>.c of the IETF Trust&#x27;s Legal Provisions
        Relating to IETF Documents
        (<a href="https://trustee.ietf.org/license-info">https://trustee.ietf.org/license-info</a>).

        This version of this YANG module is part of <a href="/doc/html/rfc8641">RFC 8641</a>; see the
        RFC itself for full legal notices.&quot;;

     revision 2019-09-09 {
       description
         &quot;Initial revision.&quot;;
       reference
         &quot;<a href="/doc/html/rfc8641">RFC 8641</a>: Subscriptions to YANG Datastores&quot;;
     }

     /*
      * FEATURES
      */

     feature on-change {
       description
         &quot;This feature indicates that on-change triggered subscriptions
          are supported.&quot;;
     }

     /*
      * IDENTITIES
      */

<span class="grey"><a href="/doc/html/rfc8641">RFC 8641</a>                        YANG-Push                 September 2019</span>

     /* Error type identities for datastore subscription */

     identity resync-subscription-error {
       description
         &quot;Problem found while attempting to fulfill a
          &#x27;resync-subscription&#x27; RPC request.&quot;;
     }

     identity cant-exclude {
       base sn:establish-subscription-error;
       description
         &quot;Unable to remove the set of &#x27;excluded-change&#x27; parameters.
          This means that the publisher is unable to restrict
          &#x27;push-change-update&#x27; notifications to just the change types
          requested for this subscription.&quot;;
     }

     identity datastore-not-subscribable {
       base sn:establish-subscription-error;
       base sn:subscription-terminated-reason;
       description
         &quot;This is not a subscribable datastore.&quot;;
     }

     identity no-such-subscription-resync {
       base resync-subscription-error;
       description
         &quot;The referenced subscription doesn&#x27;t exist.  This may be as a
          result of a nonexistent subscription ID, an ID that belongs to
          another subscriber, or an ID for a configured subscription.&quot;;
     }

     identity on-change-unsupported {
       base sn:establish-subscription-error;
       description
         &quot;On-change is not supported for any objects that are
          selectable by this filter.&quot;;
     }

     identity on-change-sync-unsupported {
       base sn:establish-subscription-error;
       description
         &quot;Neither &#x27;sync-on-start&#x27; nor resynchronization is supported for
          this subscription.  This error will be used for two reasons:
          (1) if an &#x27;establish-subscription&#x27; RPC includes
          &#x27;sync-on-start&#x27; but the publisher can&#x27;t support sending a
          &#x27;push-update&#x27; for this subscription for reasons other than
          &#x27;on-change-unsupported&#x27; or &#x27;sync-too-big&#x27;
<span class="grey"><a href="/doc/html/rfc8641">RFC 8641</a>                        YANG-Push                 September 2019</span>

          (2) if the &#x27;resync-subscription&#x27; RPC is invoked for either an
          existing periodic subscription or an on-change subscription
          that can&#x27;t support resynchronization.&quot;;
     }

     identity period-unsupported {
       base sn:establish-subscription-error;
       base sn:modify-subscription-error;
       base sn:subscription-suspended-reason;
       description
         &quot;The requested time period or &#x27;dampening-period&#x27; is too short.
          This can be for both periodic and on-change subscriptions
          (with or without dampening).  Hints suggesting alternative
          periods may be returned as supplemental information.&quot;;
     }

     identity update-too-big {
       base sn:establish-subscription-error;
       base sn:modify-subscription-error;
       base sn:subscription-suspended-reason;
       description
         &quot;Periodic or on-change push update data trees exceed a maximum
          size limit.  Hints on the estimated size of what was too big
          may be returned as supplemental information.&quot;;
     }

     identity sync-too-big {
       base sn:establish-subscription-error;
       base sn:modify-subscription-error;
       base resync-subscription-error;
       base sn:subscription-suspended-reason;
       description
         &quot;The &#x27;sync-on-start&#x27; or resynchronization data tree exceeds a
          maximum size limit.  Hints on the estimated size of what was
          too big may be returned as supplemental information.&quot;;
     }

     identity unchanging-selection {
       base sn:establish-subscription-error;
       base sn:modify-subscription-error;
       base sn:subscription-terminated-reason;
       description
         &quot;The selection filter is unlikely to ever select data tree
          nodes.  This means that based on the subscriber&#x27;s current
          access rights, the publisher recognizes that the selection
          filter is unlikely to ever select data tree nodes that change.
          Examples for this might be that the node or subtree doesn&#x27;t
          exist, read access is not permitted for a receiver, or static
<span class="grey"><a href="/doc/html/rfc8641">RFC 8641</a>                        YANG-Push                 September 2019</span>

          objects that only change at reboot have been chosen.&quot;;
     }

     /*
      * TYPE DEFINITIONS
      */

     typedef change-type {
       type enumeration {
         enum create {
           description
             &quot;A change that refers to the creation of a new
              datastore node.&quot;;
         }
         enum delete {
           description
             &quot;A change that refers to the deletion of a
              datastore node.&quot;;
         }
         enum insert {
           description
             &quot;A change that refers to the insertion of a new
              user-ordered datastore node.&quot;;
         }
         enum move {
           description
             &quot;A change that refers to a reordering of the target
              datastore node.&quot;;
         }
         enum replace {
           description
             &quot;A change that refers to a replacement of the target
              datastore node&#x27;s value.&quot;;
         }
       }
       description
         &quot;Specifies different types of datastore changes.

          This type is based on the edit operations defined for
          YANG Patch, with the difference that it is valid for a
          receiver to process an update record that performs a
          &#x27;create&#x27; operation on a datastore node the receiver believes
          exists or to process a delete on a datastore node the
          receiver believes is missing.&quot;;
       reference
         &quot;<a href="/doc/html/rfc8072">RFC 8072</a>: YANG Patch Media Type, <a href="#section-2.5">Section 2.5</a>&quot;;
     }

<span class="grey"><a href="/doc/html/rfc8641">RFC 8641</a>                        YANG-Push                 September 2019</span>

     typedef selection-filter-ref {
       type leafref {
         path &quot;/sn:filters/yp:selection-filter/yp:filter-id&quot;;
       }
       description
         &quot;This type is used to reference a selection filter.&quot;;
     }

     typedef centiseconds {
       type uint32;
       description
         &quot;A period of time, measured in units of 0.01 seconds.&quot;;
     }

     /*
      * GROUP DEFINITIONS
      */

     grouping datastore-criteria {
       description
         &quot;A grouping to define criteria for which selected objects from
          a targeted datastore should be included in push updates.&quot;;
       leaf datastore {
         type identityref {
           base ds:datastore;
         }
         mandatory true;
         description
           &quot;Datastore from which to retrieve data.&quot;;
       }
       uses selection-filter-objects;
     }

     grouping selection-filter-types {
       description
         &quot;This grouping defines the types of selectors for objects
          from a datastore.&quot;;
       choice filter-spec {
         description
           &quot;The content filter specification for this request.&quot;;
         anydata datastore-subtree-filter {
           if-feature &quot;sn:subtree&quot;;
           description
             &quot;This parameter identifies the portions of the
              target datastore to retrieve.&quot;;
           reference
             &quot;<a href="/doc/html/rfc6241">RFC 6241</a>: Network Configuration Protocol (NETCONF),
                        <a href="#section-6">Section 6</a>&quot;;
<span class="grey"><a href="/doc/html/rfc8641">RFC 8641</a>                        YANG-Push                 September 2019</span>

         }
         leaf datastore-xpath-filter {
           if-feature &quot;sn:xpath&quot;;
           type yang:xpath1.0;
           description
             &quot;This parameter contains an XPath expression identifying
              the portions of the target datastore to retrieve.

              If the expression returns a node set, all nodes in the
              node set are selected by the filter.  Otherwise, if the
              expression does not return a node set, the filter
              doesn&#x27;t select any nodes.

              The expression is evaluated in the following XPath
              context:

              o  The set of namespace declarations is the set of prefix
                 and namespace pairs for all YANG modules implemented
                 by the server, where the prefix is the YANG module
                 name and the namespace is as defined by the
                 &#x27;namespace&#x27; statement in the YANG module.

                 If the leaf is encoded in XML, all namespace
                 declarations in scope on the &#x27;stream-xpath-filter&#x27;
                 leaf element are added to the set of namespace
                 declarations.  If a prefix found in the XML is
                 already present in the set of namespace declarations,
                 the namespace in the XML is used.

              o  The set of variable bindings is empty.

              o  The function library is comprised of the core
                 function library and the XPath functions defined in
                 <a href="/doc/html/rfc7950#section-10">Section&amp;nbsp;10 in RFC 7950</a>.

              o  The context node is the root node of the target
                 datastore.&quot;;
           reference
             &quot;XML Path Language (XPath) Version 1.0
              (<a href="https://www.w3.org/TR/1999/REC-xpath-19991116">https://www.w3.org/TR/1999/REC-xpath-19991116</a>)
              <a href="/doc/html/rfc7950">RFC 7950</a>: The YANG 1.1 Data Modeling Language,
                        <a href="#section-10">Section 10</a>&quot;;
         }
       }
     }

     grouping selection-filter-objects {
       description
<span class="grey"><a href="/doc/html/rfc8641">RFC 8641</a>                        YANG-Push                 September 2019</span>

         &quot;This grouping defines a selector for objects from a
          datastore.&quot;;
       choice selection-filter {
         description
           &quot;The source of the selection filter applied to the
            subscription.  This will either (1) come referenced from a
            global list or (2) be provided in the subscription itself.&quot;;
         case by-reference {
           description
             &quot;Incorporates a filter that has been configured
              separately.&quot;;
           leaf selection-filter-ref {
             type selection-filter-ref;
             mandatory true;
             description
               &quot;References an existing selection filter that is to be
                applied to the subscription.&quot;;
           }
         }
         case within-subscription {
           description
             &quot;A local definition allows a filter to have the same
              lifecycle as the subscription.&quot;;
           uses selection-filter-types;
         }
       }
     }

     grouping update-policy-modifiable {
       description
         &quot;This grouping describes the datastore-specific subscription
          conditions that can be changed during the lifetime of the
          subscription.&quot;;
       choice update-trigger {
         description
           &quot;Defines necessary conditions for sending an event record to
            the subscriber.&quot;;
         case periodic {
           container periodic {
             presence &quot;indicates a periodic subscription&quot;;
             description
               &quot;The publisher is requested to periodically notify the
                receiver regarding the current values of the datastore
                as defined by the selection filter.&quot;;
             leaf period {
               type centiseconds;
               mandatory true;
               description
<span class="grey"><a href="/doc/html/rfc8641">RFC 8641</a>                        YANG-Push                 September 2019</span>

                 &quot;Duration of time that should occur between periodic
                  push updates, in units of 0.01 seconds.&quot;;
             }
             leaf anchor-time {
               type yang:date-and-time;
               description
                 &quot;Designates a timestamp before or after which a series
                  of periodic push updates are determined.  The next
                  update will take place at a point in time that is a
                  multiple of a period from the &#x27;anchor-time&#x27;.
                  For example, for an &#x27;anchor-time&#x27; that is set for the
                  top of a particular minute and a period interval of a
                  minute, updates will be sent at the top of every
                  minute that this subscription is active.&quot;;
             }
           }
         }
         case on-change {
           if-feature &quot;on-change&quot;;
           container on-change {
             presence &quot;indicates an on-change subscription&quot;;
             description
               &quot;The publisher is requested to notify the receiver
                regarding changes in values in the datastore subset as
                defined by a selection filter.&quot;;
             leaf dampening-period {
               type centiseconds;
               default &quot;0&quot;;
               description
                 &quot;Specifies the minimum interval between the assembly of
                  successive update records for a single receiver of a
                  subscription.  Whenever subscribed objects change and
                  a dampening-period interval (which may be zero) has
                  elapsed since the previous update record creation for
                  a receiver, any subscribed objects and properties
                  that have changed since the previous update record
                  will have their current values marshalled and placed
                  in a new update record.&quot;;
             }
           }
         }
       }
     }

     grouping update-policy {
       description
         &quot;This grouping describes the datastore-specific subscription
          conditions of a subscription.&quot;;
<span class="grey"><a href="/doc/html/rfc8641">RFC 8641</a>                        YANG-Push                 September 2019</span>

       uses update-policy-modifiable {
         augment &quot;update-trigger/on-change/on-change&quot; {
           description
             &quot;Includes objects that are not modifiable once a
              subscription is established.&quot;;
           leaf sync-on-start {
             type boolean;
             default &quot;true&quot;;
             description
               &quot;When this object is set to &#x27;false&#x27;, (1) it restricts an
                on-change subscription from sending &#x27;push-update&#x27;
                notifications and (2) pushing a full selection per the
                terms of the selection filter MUST NOT be done for
                this subscription.  Only updates about changes
                (i.e., only &#x27;push-change-update&#x27; notifications)
                are sent.  When set to &#x27;true&#x27; (the default behavior),
                in order to facilitate a receiver&#x27;s synchronization,
                a full update is sent, via a &#x27;push-update&#x27; notification,
                when the subscription starts.  After that,
                &#x27;push-change-update&#x27; notifications are exclusively sent,
                unless the publisher chooses to resync the subscription
                via a new &#x27;push-update&#x27; notification.&quot;;
           }
           leaf-list excluded-change {
             type change-type;
             description
               &quot;Used to restrict which changes trigger an update.  For
                example, if a &#x27;replace&#x27; operation is excluded, only the
                creation and deletion of objects are reported.&quot;;
           }
         }
       }
     }

     grouping hints {
       description
         &quot;Parameters associated with an error for a subscription
          made upon a datastore.&quot;;
       leaf period-hint {
         type centiseconds;
         description
           &quot;Returned when the requested time period is too short.  This
            hint can assert a viable period for either a periodic push
            cadence or an on-change dampening interval.&quot;;
       }
       leaf filter-failure-hint {
         type string;
         description
<span class="grey"><a href="/doc/html/rfc8641">RFC 8641</a>                        YANG-Push                 September 2019</span>

           &quot;Information describing where and/or why a provided filter
            was unsupportable for a subscription.&quot;;
       }
       leaf object-count-estimate {
         type uint32;
         description
           &quot;If there are too many objects that could potentially be
            returned by the selection filter, this identifies the
            estimate of the number of objects that the filter would
            potentially pass.&quot;;
       }
       leaf object-count-limit {
         type uint32;
         description
           &quot;If there are too many objects that could be returned by
            the selection filter, this identifies the upper limit of
            the publisher&#x27;s ability to service this subscription.&quot;;
       }
       leaf kilobytes-estimate {
         type uint32;
         description
           &quot;If the returned information could be beyond the capacity
            of the publisher, this would identify the estimated
            data size that could result from this selection filter.&quot;;
       }
       leaf kilobytes-limit {
         type uint32;
         description
           &quot;If the returned information would be beyond the capacity
            of the publisher, this identifies the upper limit of the
            publisher&#x27;s ability to service this subscription.&quot;;
       }
     }

     /*
      * RPCs
      */

     rpc resync-subscription {
       if-feature &quot;on-change&quot;;
       description
         &quot;This RPC allows a subscriber of an active on-change
          subscription to request a full push of objects.

          A successful invocation results in a &#x27;push-update&#x27; of all
          datastore nodes that the subscriber is permitted to access.
          This RPC can only be invoked on the same session on which the
          subscription is currently active.  In the case of an error, a
<span class="grey"><a href="/doc/html/rfc8641">RFC 8641</a>                        YANG-Push                 September 2019</span>

          &#x27;resync-subscription-error&#x27; is sent as part of an error
          response.&quot;;
       input {
         leaf id {
           type sn:subscription-id;
           mandatory true;
           description
             &quot;Identifier of the subscription that is to be resynced.&quot;;
         }
       }
     }

     rc:yang-data resync-subscription-error {
       container resync-subscription-error {
         description
           &quot;If a &#x27;resync-subscription&#x27; RPC fails, the subscription is
            not resynced and the RPC error response MUST indicate the
            reason for this failure.  This yang-data MAY be inserted as
            structured data in a subscription&#x27;s RPC error response
            to indicate the reason for the failure.&quot;;
         leaf reason {
           type identityref {
             base resync-subscription-error;
           }
           mandatory true;
           description
             &quot;Indicates the reason why the publisher has declined a
              request for subscription resynchronization.&quot;;
         }
         uses hints;
       }
     }

     augment &quot;/sn:establish-subscription/sn:input&quot; {
       description
         &quot;This augmentation adds additional subscription parameters
          that apply specifically to datastore updates to RPC input.&quot;;
       uses update-policy;
     }

     augment &quot;/sn:establish-subscription/sn:input/sn:target&quot; {
       description
         &quot;This augmentation adds the datastore as a valid target
          for the subscription to RPC input.&quot;;
       case datastore {
         description
           &quot;Information specifying the parameters of a request for a
            datastore subscription.&quot;;
<span class="grey"><a href="/doc/html/rfc8641">RFC 8641</a>                        YANG-Push                 September 2019</span>

         uses datastore-criteria;
       }
     }

     rc:yang-data establish-subscription-datastore-error-info {
       container establish-subscription-datastore-error-info {
         description
           &quot;If any &#x27;establish-subscription&#x27; RPC parameters are
            unsupportable against the datastore, a subscription is not
            created and the RPC error response MUST indicate the reason
            why the subscription failed to be created.  This yang-data
            MAY be inserted as structured data in a subscription&#x27;s
            RPC error response to indicate the reason for the failure.
            This yang-data MUST be inserted if hints are to be provided
            back to the subscriber.&quot;;
         leaf reason {
           type identityref {
             base sn:establish-subscription-error;
           }
           description
             &quot;Indicates the reason why the subscription has failed to
              be created to a targeted datastore.&quot;;
         }
         uses hints;
       }
     }

     augment &quot;/sn:modify-subscription/sn:input&quot; {
       description
         &quot;This augmentation adds additional subscription parameters
          specific to datastore updates.&quot;;
       uses update-policy-modifiable;
     }

     augment &quot;/sn:modify-subscription/sn:input/sn:target&quot; {
       description
         &quot;This augmentation adds the datastore as a valid target
          for the subscription to RPC input.&quot;;
       case datastore {
         description
           &quot;Information specifying the parameters of a request for a
            datastore subscription.&quot;;
         uses datastore-criteria;
       }
     }

     rc:yang-data modify-subscription-datastore-error-info {
       container modify-subscription-datastore-error-info {
<span class="grey"><a href="/doc/html/rfc8641">RFC 8641</a>                        YANG-Push                 September 2019</span>

         description
           &quot;This yang-data MAY be provided as part of a subscription&#x27;s
            RPC error response when there is a failure of a
            &#x27;modify-subscription&#x27; RPC that has been made against a
            datastore.  This yang-data MUST be used if hints are to be
            provided back to the subscriber.&quot;;
         leaf reason {
           type identityref {
             base sn:modify-subscription-error;
           }
           description
             &quot;Indicates the reason why the subscription has failed to
              be modified.&quot;;
         }
         uses hints;
       }
     }

     /*
      * NOTIFICATIONS
      */

     notification push-update {
       description
         &quot;This notification contains a push update that in turn contains
          data subscribed to via a subscription.  In the case of a
          periodic subscription, this notification is sent for periodic
          updates.  It can also be used for synchronization updates of
          an on-change subscription.  This notification shall only be
          sent to receivers of a subscription.  It does not constitute
          a general-purpose notification that would be subscribable as
          part of the NETCONF event stream by any receiver.&quot;;
       leaf id {
         type sn:subscription-id;
         description
           &quot;This references the subscription that drove the
            notification to be sent.&quot;;
       }
       anydata datastore-contents {
         description
           &quot;This contains the updated data.  It constitutes a snapshot
            at the time of update of the set of data that has been
            subscribed to.  The snapshot corresponds to the same
            snapshot that would be returned in a corresponding &#x27;get&#x27;
            operation with the same selection filter parameters
            applied.&quot;;
       }
       leaf incomplete-update {
<span class="grey"><a href="/doc/html/rfc8641">RFC 8641</a>                        YANG-Push                 September 2019</span>

         type empty;
         description
           &quot;This is a flag that indicates that not all datastore
            nodes subscribed to are included with this update.  In
            other words, the publisher has failed to fulfill its full
            subscription obligations and, despite its best efforts, is
            providing an incomplete set of objects.&quot;;
       }
     }

     notification push-change-update {
       if-feature &quot;on-change&quot;;
       description
         &quot;This notification contains an on-change push update.  This
          notification shall only be sent to the receivers of a
          subscription.  It does not constitute a general-purpose
          notification that would be subscribable as part of the
          NETCONF event stream by any receiver.&quot;;
       leaf id {
         type sn:subscription-id;
         description
           &quot;This references the subscription that drove the
            notification to be sent.&quot;;
       }
       container datastore-changes {
         description
           &quot;This contains the set of datastore changes of the target
            datastore, starting at the time of the previous update, per
            the terms of the subscription.&quot;;
         uses ypatch:yang-patch;
       }
       leaf incomplete-update {
         type empty;
         description
           &quot;The presence of this object indicates that not all changes
            that have occurred since the last update are included with
            this update.  In other words, the publisher has failed to
            fulfill its full subscription obligations -- for example,
            in cases where it was not able to keep up with a burst of
            changes.&quot;;
       }
     }

     augment &quot;/sn:subscription-started&quot; {
       description
         &quot;This augmentation adds datastore-specific objects to
          the notification that a subscription has started.&quot;;
       uses update-policy;
<span class="grey"><a href="/doc/html/rfc8641">RFC 8641</a>                        YANG-Push                 September 2019</span>

     }

     augment &quot;/sn:subscription-started/sn:target&quot; {
       description
         &quot;This augmentation allows the datastore to be included as
          part of the notification that a subscription has started.&quot;;
       case datastore {
         uses datastore-criteria {
           refine &quot;selection-filter/within-subscription&quot; {
             description
               &quot;Specifies the selection filter and where it originated
                from.  If the &#x27;selection-filter-ref&#x27; is populated, the
                filter in the subscription came from the &#x27;filters&#x27;
                container.  Otherwise, it is populated in-line as part
                of the subscription itself.&quot;;
           }
         }
       }
     }

     augment &quot;/sn:subscription-modified&quot; {
       description
         &quot;This augmentation adds datastore-specific objects to
          the notification that a subscription has been modified.&quot;;
       uses update-policy;
     }

     augment &quot;/sn:subscription-modified/sn:target&quot; {
       description
         &quot;This augmentation allows the datastore to be included as
          part of the notification that a subscription has been
          modified.&quot;;
       case datastore {
         uses datastore-criteria {
           refine &quot;selection-filter/within-subscription&quot; {
             description
               &quot;Specifies the selection filter and where it originated
                from.  If the &#x27;selection-filter-ref&#x27; is populated, the
                filter in the subscription came from the &#x27;filters&#x27;
                container.  Otherwise, it is populated in-line as part
                of the subscription itself.&quot;;
           }
         }
       }
     }

     /*
      * DATA NODES
<span class="grey"><a href="/doc/html/rfc8641">RFC 8641</a>                        YANG-Push                 September 2019</span>

      */

     augment &quot;/sn:filters&quot; {
       description
         &quot;This augmentation allows the datastore to be included as part
          of the selection-filtering criteria for a subscription.&quot;;
       list selection-filter {
         key &quot;filter-id&quot;;
         description
           &quot;A list of preconfigured filters that can be applied
            to datastore subscriptions.&quot;;
         leaf filter-id {
           type string;
           description
             &quot;An identifier to differentiate between selection
              filters.&quot;;
         }
         uses selection-filter-types;
       }
     }

     augment &quot;/sn:subscriptions/sn:subscription&quot; {
       when &#x27;yp:datastore&#x27;;
       description
         &quot;This augmentation adds objects to a subscription that are
          specific to a datastore subscription, i.e., a subscription to
          a stream of datastore node updates.&quot;;
       uses update-policy;
     }

     augment &quot;/sn:subscriptions/sn:subscription/sn:target&quot; {
       description
         &quot;This augmentation allows the datastore to be included as
          part of the selection-filtering criteria for a subscription.&quot;;
       case datastore {
         uses datastore-criteria;
       }
     }
   }
