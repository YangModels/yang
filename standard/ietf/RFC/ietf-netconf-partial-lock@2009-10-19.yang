module ietf-netconf-partial-lock {

  namespace urn:ietf:params:xml:ns:netconf:partial-lock:1.0;
  prefix pl;

  organization &quot;IETF Network Configuration (netconf) Working Group&quot;;

  contact
   &quot;Netconf Working Group
    Mailing list: <a href="mailto:netconf@ietf.org">netconf@ietf.org</a>
    Web: <a href="https://www.ietf.org/html.charters/netconf-charter.html">http://www.ietf.org/html.charters/netconf-charter.html</a>

    Balazs Lengyel
    Ericsson
    <a href="mailto:balazs.lengyel@ericsson.com">balazs.lengyel@ericsson.com</a>&quot;;

  description
   &quot;This YANG module defines the &lt;partial-lock&gt; and
    &lt;partial-unlock&gt; operations.&quot;;

  revision 2009-10-19 {
    description
     &quot;Initial version, published as <a href="/doc/html/rfc5717">RFC 5717</a>.&quot;;
  }

  typedef lock-id-type {
    type uint32;
    description
     &quot;A number identifying a specific partial-lock granted to a session.
      It is allocated by the system, and SHOULD be used in the
      partial-unlock operation.&quot;;
  }

  rpc partial-lock {
    description
     &quot;A NETCONF operation that locks parts of the running datastore.&quot;;
    input {
      leaf-list select {
        type string;
        min-elements 1;
        description
<span class="grey"><a href="/doc/html/rfc5717">RFC 5717</a>              Partial Lock RPC for NETCONF         December 2009</span>

         &quot;XPath expression that specifies the scope of the lock.
          An Instance Identifier expression MUST be used unless the
          :xpath capability is supported, in which case any XPath 1.0
          expression is allowed.&quot;;
      }
    }
    output {
      leaf lock-id {
        type lock-id-type;
        description
         &quot;Identifies the lock, if granted.  The lock-id SHOULD be
          used in the partial-unlock rpc.&quot;;
      }
      leaf-list locked-node {
        type instance-identifier;
        min-elements 1;
        description
         &quot;List of locked nodes in the running datastore&quot;;
      }
    }
  }

  rpc partial-unlock {
    description
     &quot;A NETCONF operation that releases a previously acquired
      partial-lock.&quot;;
    input {
      leaf lock-id {
        type lock-id-type;
        description
         &quot;Identifies the lock to be released.  MUST be the value
          received in the response to a partial-lock operation.&quot;;
      }
    }
  }
}
