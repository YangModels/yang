module ietf-lmap-report {

  yang-version 1.1;
  namespace &quot;urn:ietf:params:xml:ns:yang:ietf-lmap-report&quot;;
  prefix &quot;lmapr&quot;;

  import ietf-yang-types {
    prefix yang;
  }
  import ietf-lmap-common {
    prefix lmap;
  }

  organization
    &quot;IETF Large-Scale Measurement of Broadband Performance
     Working Group&quot;;

  contact
    &quot;WG Web:   &lt;<a href="https://datatracker.ietf.org/wg/lmap">https://datatracker.ietf.org/wg/lmap</a>&gt;
     WG List:  &lt;mailto:<a href="mailto:lmap@ietf.org">lmap@ietf.org</a>&gt;

     Editor:   Juergen Schoenwaelder
               &lt;<a href="mailto:j.schoenwaelder@jacobs-university.de">j.schoenwaelder@jacobs-university.de</a>&gt;

     Editor:   Vaibhav Bajpai
               &lt;<a href="mailto:bajpaiv@in.tum.de">bajpaiv@in.tum.de</a>&gt;&quot;;

  description
    &quot;This module defines a data model for reporting results from
     Measurement Agents, which are part of a Large-Scale Measurement
     Platform (LMAP), to result data Collectors.  This data model is
     expected to be implemented by a Collector.&quot;;

  revision &quot;2017-08-08&quot; {
    description
      &quot;Initial version&quot;;
<span class="grey"><a href="/doc/html/rfc8194">RFC 8194</a>                YANG Data Model for LMAP             August 2017</span>

       reference
         &quot;<a href="/doc/html/rfc8194">RFC 8194</a>: A YANG Data Model for LMAP Measurement Agents&quot;;
     }

     rpc report {
       description
         &quot;The report operation is used by a Measurement Agent to
          submit measurement results produced by Measurement Tasks to
          a Collector.&quot;;

       input {

         leaf date {
           type yang:date-and-time;
           mandatory true;
           description
             &quot;The date and time when this result report was sent to
              a Collector.&quot;;
         }

         leaf agent-id {
           type yang:uuid;
           description
             &quot;The agent-id of the agent from which this
              report originates.&quot;;
         }

         leaf group-id {
           type string;
           description
             &quot;The group-id of the agent from which this
              report originates.&quot;;
         }

         leaf measurement-point {
           type string;
           description
             &quot;The measurement-point of the agent from which this
              report originates.&quot;;
         }

         list result {
           description
             &quot;The list of Tasks for which results are reported.&quot;;

           leaf schedule {
             type lmap:identifier;

<span class="grey"><a href="/doc/html/rfc8194">RFC 8194</a>                YANG Data Model for LMAP             August 2017</span>

             description
               &quot;The name of the Schedule that produced the result.&quot;;
           }

           leaf action {
             type lmap:identifier;
             description
               &quot;The name of the Action in the Schedule that produced
                the result.&quot;;
           }

           leaf task {
             type lmap:identifier;
             description
               &quot;The name of the Task that produced the result.&quot;;
           }

           container parameters {
             description
               &quot;This container is a placeholder for runtime
                parameters defined in Task-specific data models
                augmenting the base LMAP report data model.&quot;;

             choice extension {
               description
                 &quot;This choice is provided to augment in different
                  sets of parameters.&quot;;
             }
           }

           uses lmap:options-grouping {
             description
               &quot;The list of options there were in use when the
                measurement was performed.  This list must include
                both the Task-specific options as well as the
                Action-specific options.&quot;;
           }

           leaf-list tag {
             type lmap:tag;
             description
               &quot;A tag contains additional information that is passed
                with the result record to the Collector.  This is the
                joined set of tags defined for the Task object, the
                Schedule object, and the Action object.  A tag can be
                used to carry the Measurement Cycle ID.&quot;;
           }

<span class="grey"><a href="/doc/html/rfc8194">RFC 8194</a>                YANG Data Model for LMAP             August 2017</span>

           leaf event {
             type yang:date-and-time;
             description
               &quot;The date and time of the event that triggered the
                Schedule of the Action that produced the reported
                result values.  The date and time does not include
                any added randomization.&quot;;
           }

           leaf start {
             type yang:date-and-time;
             mandatory true;
             description
               &quot;The date and time when the Task producing
                this result started.&quot;;
           }

           leaf end {
             type yang:date-and-time;
             description
               &quot;The date and time when the Task producing
                this result finished.&quot;;
           }

           leaf cycle-number {
             type lmap:cycle-number;
             description
               &quot;The optional cycle number is the time closest to
                the time reported in the event leaf that is a multiple
                of the cycle-interval of the event that triggered the
                execution of the Schedule.  The value is only present
                if the event that triggered the execution of the
                Schedule has a defined cycle-interval.&quot;;
           }

           leaf status {
             type lmap:status-code;
             mandatory true;
             description
               &quot;The status code returned by the execution of this
                Action.&quot;;
           }

           list conflict {
             description
               &quot;The names of Tasks overlapping with the execution
                of the Task that has produced this result.&quot;;

<span class="grey"><a href="/doc/html/rfc8194">RFC 8194</a>                YANG Data Model for LMAP             August 2017</span>

             leaf schedule-name {
               type lmap:identifier;
               description
                 &quot;The name of a Schedule that might have impacted
                  the execution of the Task that has produced this
                  result.&quot;;
             }

             leaf action-name {
               type lmap:identifier;
               description
                 &quot;The name of an Action within the Schedule that
                  might have impacted the execution of the Task that
                  has produced this result.&quot;;
             }

             leaf task-name {
               type lmap:identifier;
               description
                 &quot;The name of the Task executed by an Action within
                  the Schedule that might have impacted the execution
                  of the Task that has produced this result.&quot;;
             }
           }

           list table {
             description
               &quot;A list of result tables.&quot;;

             uses lmap:registry-grouping;

             leaf-list column {
               type string;
               description
                 &quot;An ordered list of column labels.  The order is
                  determined by the system and must match the order
                  of the columns in the result rows.&quot;;
             }

             list row {
               description
                 &quot;The rows of a result table.&quot;;

               leaf-list value {
                 type string;
                 description
                   &quot;The value of a cell in the result row.&quot;;
               }
<span class="grey"><a href="/doc/html/rfc8194">RFC 8194</a>                YANG Data Model for LMAP             August 2017</span>

             }
           }
         }
       }
     }
   }
