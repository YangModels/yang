module ietf-ipsec-iptfs {
  yang-version 1.1;
  namespace "urn:ietf:params:xml:ns:yang:ietf-ipsec-iptfs";
  prefix iptfs;

  import ietf-i2nsf-ike {
    prefix nsfike;
    reference
      "RFC 9061: A YANG Data Model for IPsec Flow Protection Based on
       Software-Defined Networking (SDN), Section 5.2";
  }
  import ietf-i2nsf-ikeless {
    prefix nsfikels;
    reference
      "RFC 9061: A YANG Data Model for IPsec Flow Protection Based on
       Software-Defined Networking (SDN), Section 5.3";
  }
  import ietf-yang-types {
    prefix yang;
    reference
      "RFC 6991: Common YANG Data Types";
  }

  organization
    "IETF IPSECME Working Group (IPSECME)";
  contact
    "WG Web:  <https://datatracker.ietf.org/wg/ipsecme/>
     WG List: <mailto:ipsecme@ietf.org>

     Author: Don Fedyk
             <mailto:dfedyk@labn.net>

     Author: Christian Hopps
             <mailto:chopps@chopps.org>";

  description
    "This module defines the configuration and operational state for
     managing the IP Traffic Flow Security functionality (RFC 9348).

     Copyright (c) 2023 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC 9348; see
     the RFC itself for full legal notices.";

  revision 2023-01-31 {
    description
      "Initial revision";
    reference
      "RFC 9348: A YANG Data Model for IP Traffic Flow Security";
  }

  feature ipsec-stats {
    description
      "This feature indicates the device supports
       per-SA IPsec statistics.";
  }

  feature iptfs-stats {
    description
      "This feature indicates the device supports
       per-SA IP Traffic Flow Security statistics.";
  }

  /*--------------------*/
  /*   groupings        */
  /*--------------------*/

  grouping ipsec-tx-stat-grouping {
    description
      "IPsec outbound statistics";
    leaf tx-pkts {
      type yang:counter64;
      config false;
      description
        "Outbound Packet count";
    }
    leaf tx-octets {
      type yang:counter64;
      config false;
      description
        "Outbound Packet bytes";
    }
    leaf tx-drop-pkts {
      type yang:counter64;
      config false;
      description
        "Outbound dropped packets count";
    }
  }

  grouping ipsec-rx-stat-grouping {
    description
      "IPsec inbound statistics";
    leaf rx-pkts {
      type yang:counter64;
      config false;
      description
        "Inbound Packet count";
    }
    leaf rx-octets {
      type yang:counter64;
      config false;
      description
        "Inbound Packet bytes";
    }
    leaf rx-drop-pkts {
      type yang:counter64;
      config false;
      description
        "Inbound dropped packets count";
    }
  }

  grouping iptfs-inner-tx-stat-grouping {
    description
      "IP-TFS outbound inner packet statistics";
    leaf tx-pkts {
      type yang:counter64;
      config false;
      description
        "Total number of IP-TFS inner packets sent.  This
         count is whole packets only.  A fragmented packet
         counts as one packet.";
      reference
        "RFC 9347: Aggregation and Fragmentation Mode for
         Encapsulating Security Payload (ESP) and Its Use for
         IP Traffic Flow Security (IP-TFS)";
    }
    leaf tx-octets {
      type yang:counter64;
      config false;
      description
        "Total number of IP-TFS inner octets sent.  This is
         inner packet octets only. It does not count padding.";
      reference
        "RFC 9347: Aggregation and Fragmentation Mode for
         Encapsulating Security Payload (ESP) and Its Use for
         IP Traffic Flow Security (IP-TFS)";
    }
  }

  grouping iptfs-outer-tx-stat-grouping {
    description
      "IP-TFS outbound inner packet statistics";
    leaf tx-all-pad-pkts {
      type yang:counter64;
      config false;
      description
        "Total number of transmitted IP-TFS packets that
         were all padding with no inner packet data.";
      reference
        "RFC 9347: Aggregation and Fragmentation Mode for
         Encapsulating Security Payload (ESP) and Its Use for
         IP Traffic Flow Security (IP-TFS), Section 2.2.3";
    }
    leaf tx-all-pad-octets {
      type yang:counter64;
      config false;
      description
        "Total number transmitted octets of padding added to
         IP-TFS packets with no inner packet data.";
      reference
        "RFC 9347: Aggregation and Fragmentation Mode for
         Encapsulating Security Payload (ESP) and Its Use for
         IP Traffic Flow Security (IP-TFS), Section 2.2.3";
    }
    leaf tx-extra-pad-pkts {
      type yang:counter64;
      config false;
      description
        "Total number of transmitted outer IP-TFS packets
         that included some padding.";
      reference
        "RFC 9347: Aggregation and Fragmentation Mode for
         Encapsulating Security Payload (ESP) and Its Use for
         IP Traffic Flow Security (IP-TFS), Section 2.2.3.1";
    }
    leaf tx-extra-pad-octets {
      type yang:counter64;
      config false;
      description
        "Total number of transmitted octets of padding added
         to outer IP-TFS packets with data.";
      reference
        "RFC 9347: Aggregation and Fragmentation Mode for
         Encapsulating Security Payload (ESP) and Its Use for
         IP Traffic Flow Security (IP-TFS), Section 2.2.3.1";
    }
  }

  grouping iptfs-inner-rx-stat-grouping {
    description
      "IP-TFS inner packet inbound statistics";
    leaf rx-pkts {
      type yang:counter64;
      config false;
      description
        "Total number of IP-TFS inner packets received.";
      reference
        "RFC 9347: Aggregation and Fragmentation Mode for
         Encapsulating Security Payload (ESP) and Its Use for
         IP Traffic Flow Security (IP-TFS), Section 2.2";
    }
    leaf rx-octets {
      type yang:counter64;
      config false;
      description
        "Total number of IP-TFS inner octets received.  It does
         not include padding or overhead.";
      reference
        "RFC 9347: Aggregation and Fragmentation Mode for
         Encapsulating Security Payload (ESP) and Its Use for
         IP Traffic Flow Security (IP-TFS), Section 2.2";
    }
    leaf rx-incomplete-pkts {
      type yang:counter64;
      config false;
      description
        "Total number of IP-TFS inner packets that were
         incomplete.  Usually this is due to fragments that are
         not received.  Also, this may be due to misordering or
         errors in received outer packets.";
      reference
        "RFC 9347: Aggregation and Fragmentation Mode for
         Encapsulating Security Payload (ESP) and Its Use for
         IP Traffic Flow Security (IP-TFS)";
    }
  }

  grouping iptfs-outer-rx-stat-grouping {
    description
      "IP-TFS outer packet inbound statistics";
    leaf rx-all-pad-pkts {
      type yang:counter64;
      config false;
      description
        "Total number of received IP-TFS packets that were
         all padding with no inner packet data.";
      reference
        "RFC 9347: Aggregation and Fragmentation Mode for
         Encapsulating Security Payload (ESP) and Its Use for
         IP Traffic Flow Security (IP-TFS), Section 2.2.3";
    }
    leaf rx-all-pad-octets {
      type yang:counter64;
      config false;
      description
        "Total number of received octets of padding added to
         IP-TFS packets with no inner packet data.";
      reference
        "RFC 9347: Aggregation and Fragmentation Mode for
         Encapsulating Security Payload (ESP) and Its Use for
         IP Traffic Flow Security (IP-TFS), Section 2.2.3";
    }
    leaf rx-extra-pad-pkts {
      type yang:counter64;
      config false;
      description
        "Total number of received outer IP-TFS packets that
         included some padding.";
      reference
        "RFC 9347: Aggregation and Fragmentation Mode for
         Encapsulating Security Payload (ESP) and Its Use for
         IP Traffic Flow Security (IP-TFS), Section 2.2.3.1";
    }
    leaf rx-extra-pad-octets {
      type yang:counter64;
      config false;
      description
        "Total number of received octets of padding added to
         outer IP-TFS packets with data.";
      reference
        "RFC 9347: Aggregation and Fragmentation Mode for
         Encapsulating Security Payload (ESP) and Its Use for
         IP Traffic Flow Security (IP-TFS), Section 2.2.3.1";
    }
    leaf rx-errored-pkts {
      type yang:counter64;
      config false;
      description
        "Total number of IP-TFS outer packets dropped due to
         errors.";
      reference
        "RFC 9347: Aggregation and Fragmentation Mode for
         Encapsulating Security Payload (ESP) and Its Use for
         IP Traffic Flow Security (IP-TFS)";
    }
    leaf rx-missed-pkts {
      type yang:counter64;
      config false;
      description
        "Total number of IP-TFS outer packets missing,
         indicated by a missing sequence number.";
      reference
        "RFC 9347: Aggregation and Fragmentation Mode for
         Encapsulating Security Payload (ESP) and Its Use for
         IP Traffic Flow Security (IP-TFS)";
    }
  }

  grouping iptfs-config {
    description
      "This is the grouping for IP-TFS configuration.";
    container traffic-flow-security {
      description
        "Configure the IPsec TFS in the Security
         Association Database (SAD).";
      leaf congestion-control {
        type boolean;
        default "true";
        description
          "When set to true, the default, this enables the
           congestion control on-the-wire exchange of data that is
           required by congestion control algorithms, as defined by
           RFC 5348.  When set to false, IP-TFS sends fixed-size
           packets over an IP-TFS tunnel at a constant rate.";
        reference
          "RFC 9347: Aggregation and Fragmentation Mode for
           Encapsulating Security Payload (ESP) and Its Use for
           IP Traffic Flow Security (IP-TFS), Section 2.4.2;
           RFC 5348: TCP Friendly Rate Control (TFRC): Protocol
           Specification";
      }
      container packet-size {
        description
          "Packet size is either auto-discovered or manually
           configured.";
        leaf use-path-mtu-discovery {
          type boolean;
          default "true";
          description
            "Utilize path MTU discovery to determine maximum
             IP-TFS packet size.  If the packet size is explicitly
             configured, then it will only be adjusted downward if
             use-path-mtu-discovery is set.";
          reference
            "RFC 9347: Aggregation and Fragmentation Mode for
             Encapsulating Security Payload (ESP) and Its Use for
             IP Traffic Flow Security (IP-TFS), Section 4.2";
        }
        leaf outer-packet-size {
          type uint16;
          units "bytes";
          description
            "On transmission, the size of the outer encapsulating
             tunnel packet (i.e., the IP packet containing
             Encapsulating Security Payload (ESP)).";
          reference
            "RFC 9347: Aggregation and Fragmentation Mode for
             Encapsulating Security Payload (ESP) and Its Use for
             IP Traffic Flow Security (IP-TFS), Section 4.2";
        }
      }
      choice tunnel-rate {
        description
          "The TFS bit rate may be specified at layer 2 wire
           rate or layer 3 packet rate.";
        leaf l2-fixed-rate {
          type yang:gauge64;
          units "bits/second";
          description
            "On transmission, target bandwidth/bit rate in
             bits/second for IP-TFS tunnel.  This fixed rate is the
             nominal timing for the fixed-size packet.  If
             congestion control is enabled, the rate may be
             adjusted down (or up if unset).";
          reference
            "RFC 9347: Aggregation and Fragmentation Mode for
             Encapsulating Security Payload (ESP) and Its Use for
             IP Traffic Flow Security (IP-TFS), Section 4.1";
        }
        leaf l3-fixed-rate {
          type yang:gauge64;
          units "bits/second";
          description
            "On transmission, target bandwidth/bit rate in
             bits/second for IP-TFS tunnel.  This fixed rate is the
             nominal timing for the fixed-size packet.  If
             congestion control is enabled, the rate may be
             adjusted down (or up if unset).";
          reference
            "RFC 9347: Aggregation and Fragmentation Mode for
             Encapsulating Security Payload (ESP) and Its Use for
             IP Traffic Flow Security (IP-TFS), Section 4.1";
        }
      }
      leaf dont-fragment {
        type boolean;
        default "false";
        description
          "On transmission, disable packet fragmentation across
           consecutive IP-TFS tunnel packets; inner packets larger
           than what can be transmitted in outer packets will be
           dropped.";
        reference
          "RFC 9347: Aggregation and Fragmentation Mode for
           Encapsulating Security Payload (ESP) and Its Use for
           IP Traffic Flow Security (IP-TFS), Section 2.2.4 and
           6.1.4";
      }
      leaf max-aggregation-time {
        type decimal64 {
          fraction-digits 6;
        }
        units "milliseconds";
        description
          "On transmission, maximum aggregation time is the
           maximum length of time a received inner packet can be
           held prior to transmission in the IP-TFS tunnel.  Inner
           packets that would be held longer than this time, based
           on the current tunnel configuration, will be dropped
           rather than be queued for transmission.  Maximum
           aggregation time is configurable in milliseconds or
           fractional milliseconds down to 1 nanosecond.";
      }
      leaf window-size {
        type uint16 {
          range "0..65535";
        }
        description
          "On reception, the maximum number of out-of-order
           packets that will be reordered by an IP-TFS receiver
           while performing the reordering operation.  The value 0
           disables any reordering.";
        reference
          "RFC 9347: Aggregation and Fragmentation Mode for
           Encapsulating Security Payload (ESP) and Its Use for
           IP Traffic Flow Security (IP-TFS), Section 2.2.3";
      }
      leaf send-immediately {
        type boolean;
        default "false";
        description
          "On reception, send inner packets as soon as possible; do
           not wait for lost or misordered outer packets.
           Selecting this option reduces the inner (user) packet
           delay but can amplify out-of-order delivery of the
           inner packet stream in the presence of packet
           aggregation and any reordering.";
        reference
          "RFC 9347: Aggregation and Fragmentation Mode for
           Encapsulating Security Payload (ESP) and Its Use for
           IP Traffic Flow Security (IP-TFS), Section 2.5";
      }
      leaf lost-packet-timer-interval {
        type decimal64 {
          fraction-digits 6;
        }
        units "milliseconds";
        description
          "On reception, this interval defines the length of time
           an IP-TFS receiver will wait for a missing packet before
           considering it lost.  If not using send-immediately,
           then each lost packet will delay inner (user) packets
           until this timer expires.  Setting this value too low
           can impact reordering and reassembly.  The value is
           configurable in milliseconds or fractional milliseconds
           down to 1 nanosecond.";
        reference
          "RFC 9347: Aggregation and Fragmentation Mode for
           Encapsulating Security Payload (ESP) and Its Use for
           IP Traffic Flow Security (IP-TFS), Section 2.2.3";
      }
    }
  }

  /*
   * IP-TFS ike configuration
   */

  augment "/nsfike:ipsec-ike/nsfike:conn-entry/nsfike:spd/"
        + "nsfike:spd-entry/"
        + "nsfike:ipsec-policy-config/"
        + "nsfike:processing-info/"
        + "nsfike:ipsec-sa-cfg" {
    description
      "IP-TFS configuration for this policy.";
    uses iptfs-config;
  }

  augment "/nsfike:ipsec-ike/nsfike:conn-entry/"
        + "nsfike:child-sa-info" {
    description
      "IP-TFS configured on this SA.";
    uses iptfs-config {
      refine "traffic-flow-security" {
        config false;
      }
    }
  }

  /*
   * IP-TFS ikeless configuration
   */

  augment "/nsfikels:ipsec-ikeless/nsfikels:spd/"
        + "nsfikels:spd-entry/"
        + "nsfikels:ipsec-policy-config/"
        + "nsfikels:processing-info/"
        + "nsfikels:ipsec-sa-cfg" {
    description
      "IP-TFS configuration for this policy.";
    uses iptfs-config;
  }

  augment "/nsfikels:ipsec-ikeless/nsfikels:sad/"
        + "nsfikels:sad-entry" {
    description
      "IP-TFS configured on this SA.";
    uses iptfs-config {
      refine "traffic-flow-security" {
        config false;
      }
    }
  }

  /*
   * packet counters
   */

  augment "/nsfike:ipsec-ike/nsfike:conn-entry/"
        + "nsfike:child-sa-info" {
    description
      "Per-SA counters";
    container ipsec-stats {
      if-feature "ipsec-stats";
      config false;
      description
        "IPsec per-SA packet counters.
         tx = outbound, rx = inbound";
      uses ipsec-tx-stat-grouping;
      uses ipsec-rx-stat-grouping;
    }
    container iptfs-inner-pkt-stats {
      if-feature "iptfs-stats";
      config false;
      description
        "IP-TFS per-SA inner packet counters.
         tx = outbound, rx = inbound";
      uses iptfs-inner-tx-stat-grouping;
      uses iptfs-inner-rx-stat-grouping;
    }
    container iptfs-outer-pkt-stats {
      if-feature "iptfs-stats";
      config false;
      description
        "IP-TFS per-SA outer packets counters.
         tx = outbound, rx = inbound";
      uses iptfs-outer-tx-stat-grouping;
      uses iptfs-outer-rx-stat-grouping;
    }
  }

  /*
   * packet counters
   */

  augment "/nsfikels:ipsec-ikeless/nsfikels:sad/"
        + "nsfikels:sad-entry" {
    description
      "Per-SA counters";
    container ipsec-stats {
      if-feature "ipsec-stats";
      config false;
      description
        "IPsec per-SA packet counters.
         tx = outbound, rx = inbound";
      uses ipsec-tx-stat-grouping;
      uses ipsec-rx-stat-grouping;
    }
    container iptfs-inner-pkt-stats {
      if-feature "iptfs-stats";
      config false;
      description
        "IP-TFS per-SA inner packet counters.
         tx = outbound, rx = inbound";
      uses iptfs-inner-tx-stat-grouping;
      uses iptfs-inner-rx-stat-grouping;
    }
    container iptfs-outer-pkt-stats {
      if-feature "iptfs-stats";
      config false;
      description
        "IP-TFS per-SA outer packets counters.
         tx = outbound, rx = inbound";
      uses iptfs-outer-tx-stat-grouping;
      uses iptfs-outer-rx-stat-grouping;
    }
  }
}
