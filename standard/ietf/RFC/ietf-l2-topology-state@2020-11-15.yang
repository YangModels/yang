module ietf-l2-topology-state {
  yang-version 1.1;
  namespace "urn:ietf:params:xml:ns:yang:ietf-l2-topology-state";
  prefix l2t-s;

  import ietf-network-state {
    prefix nw-s;
    reference
      "RFC 8345: A YANG Data Model for Network Topologies";
  }
  import ietf-network-topology-state {
    prefix nt-s;
    reference
      "RFC 8345: A YANG Data Model for Network Topologies";
  }
  import ietf-l2-topology {
    prefix l2t;
    reference
      "RFC 8944: A YANG Data Model for Layer 2 Network Topologies";
  }

  organization
    "IETF I2RS (Interface to the Routing System) Working Group";
  contact
    "WG Web:   &lt;http://tools.ietf.org/wg/i2rs/&gt;
     WG List:  &lt;mailto:i2rs@ietf.org&gt;

     Editor:    Jie Dong
               &lt;mailto:jie.dong@huawei.com&gt;
     Editor:    Xiugang Wei
               &lt;mailto:weixiugang@huawei.com&gt;
     Editor:    Qin Wu
               &lt;mailto:bill.wu@huawei.com&gt;
     Editor:    Mohamed Boucadair
               &lt;mailto:mohamed.boucadair@orange.com&gt;
     Editor:   Anders Liu
               &lt;andersliu@tencent.com&gt;";
  description
    "This module defines a model for Layer 2 Network Topology
     state, representing topology that either is learned or
     results from applying topology that has been configured per
     the 'ietf-l2-topology' model, mirroring the
     corresponding data nodes in this model.

     This model mirrors 'ietf-l2-topology' but contains only
     read-only state data.  The model is not needed when the
     underlying implementation infrastructure supports the
     Network Management Datastore Architecture (NMDA).

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 8944; see
     the RFC itself for full legal notices.";

  revision 2020-11-15 {
    description
      "Initial revision.";
    reference
      "RFC 8944: A YANG Data Model for Layer 2 Network Topologies";
  }

  /*
   * Data nodes
   */

  augment "/nw-s:networks/nw-s:network/nw-s:network-types" {
    description
      "Introduces a new network type for L2 topology.";
    uses l2t:l2-network-type;
  }

  augment "/nw-s:networks/nw-s:network" {
    when 'nw-s:network-types/l2t-s:l2-topology' {
      description
        "Augmentation parameters apply only for networks
         with L2 topology.";
    }
    description
      "Configuration parameters for the L2 network
       as a whole.";
    uses l2t:l2-topology-attributes;
  }

  augment "/nw-s:networks/nw-s:network/nw-s:node" {
    when '../nw-s:network-types/l2t-s:l2-topology' {
      description
        "Augmentation parameters apply only for networks
         with L2 topology.";
    }
    description
      "Configuration parameters for L2 at the node
       level.";
    uses l2t:l2-node-attributes;
  }

  augment "/nw-s:networks/nw-s:network/nt-s:link" {
    when '../nw-s:network-types/l2t-s:l2-topology' {
      description
        "Augmentation parameters apply only for networks
         with L2 topology.";
    }
    description
      "Augments L2 topology link information.";
    uses l2t:l2-link-attributes;
  }

  augment "/nw-s:networks/nw-s:network/nw-s:node/"
        + "nt-s:termination-point" {
    when '../../nw-s:network-types/l2t-s:l2-topology' {
      description
        "Augmentation parameters apply only for networks
         with L2 topology.";
    }
    description
      "Augments L2 topology termination point information.";
    uses l2t:l2-termination-point-attributes;
  }

  /*
   * Notifications
   */

  notification l2-node-event {
    description
      "Notification event for L2 node.";
    leaf event-type {
      type l2t:l2-network-event-type;
      description
        "Event type.";
    }
    uses nw-s:node-ref;
    uses l2t:l2-network-type;
    uses l2t:l2-node-attributes;
  }

  notification l2-link-event {
    description
      "Notification event for an L2 link.";
    leaf event-type {
      type l2t:l2-network-event-type;
      description
        "Event type.";
    }
    uses nt-s:link-ref;
    uses l2t:l2-network-type;
    uses l2t:l2-link-attributes;
  }

  notification l2-termination-point-event {
    description
      "Notification event for L2 termination point.";
    leaf event-type {
      type l2t:l2-network-event-type;
      description
        "Event type.";
    }
    uses nt-s:tp-ref;
    uses l2t:l2-network-type;
    uses l2t:l2-termination-point-attributes;
  }
}
