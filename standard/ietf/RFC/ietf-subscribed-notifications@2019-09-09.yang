module ietf-subscribed-notifications {
  yang-version 1.1;
  namespace &quot;urn:ietf:params:xml:ns:yang:ietf-subscribed-notifications&quot;;
  prefix sn;

  import ietf-inet-types {
    prefix inet;
    reference
      &quot;<a href="/doc/html/rfc6991">RFC 6991</a>: Common YANG Data Types&quot;;
  }
  import ietf-interfaces {
    prefix if;
    reference
      &quot;<a href="/doc/html/rfc8343">RFC 8343</a>: A YANG Data Model for Interface Management&quot;;
<span class="grey"><a href="/doc/html/rfc8639">RFC 8639</a>                Subscribed Notifications          September 2019</span>

  }
  import ietf-netconf-acm {
    prefix nacm;
    reference
      &quot;<a href="/doc/html/rfc8341">RFC 8341</a>: Network Configuration Access Control Model&quot;;
  }
  import ietf-network-instance {
    prefix ni;
    reference
      &quot;<a href="/doc/html/rfc8529">RFC 8529</a>: YANG Data Model for Network Instances&quot;;
  }
  import ietf-restconf {
    prefix rc;
    reference
      &quot;<a href="/doc/html/rfc8040">RFC 8040</a>: RESTCONF Protocol&quot;;
  }
  import ietf-yang-types {
    prefix yang;
    reference
      &quot;<a href="/doc/html/rfc6991">RFC 6991</a>: Common YANG Data Types&quot;;
  }

  organization
    &quot;IETF NETCONF (Network Configuration) Working Group&quot;;
  contact
    &quot;WG Web:  &lt;https:/datatracker.ietf.org/wg/netconf/&gt;
     WG List: &lt;mailto:<a href="mailto:netconf@ietf.org">netconf@ietf.org</a>&gt;

     Author:  Alexander Clemm
              &lt;mailto:<a href="mailto:ludwig@clemm.org">ludwig@clemm.org</a>&gt;

     Author:  Eric Voit
              &lt;mailto:<a href="mailto:evoit@cisco.com">evoit@cisco.com</a>&gt;

     Author:  Alberto Gonzalez Prieto
              &lt;mailto:<a href="mailto:alberto.gonzalez@microsoft.com">alberto.gonzalez@microsoft.com</a>&gt;

     Author:  Einar Nilsen-Nygaard
              &lt;mailto:<a href="mailto:einarnn@cisco.com">einarnn@cisco.com</a>&gt;

     Author:  Ambika Prasad Tripathy
              &lt;mailto:<a href="mailto:ambtripa@cisco.com">ambtripa@cisco.com</a>&gt;&quot;;
  description
    &quot;This module defines a YANG data model for subscribing to event
     records and receiving matching content in notification messages.

     The key words &#x27;MUST&#x27;, &#x27;MUST NOT&#x27;, &#x27;REQUIRED&#x27;, &#x27;SHALL&#x27;, &#x27;SHALL
     NOT&#x27;, &#x27;SHOULD&#x27;, &#x27;SHOULD NOT&#x27;, &#x27;RECOMMENDED&#x27;, &#x27;NOT RECOMMENDED&#x27;,
<span class="grey"><a href="/doc/html/rfc8639">RFC 8639</a>                Subscribed Notifications          September 2019</span>

     &#x27;MAY&#x27;, and &#x27;OPTIONAL&#x27; in this document are to be interpreted as
     described in <a href="/doc/html/bcp14">BCP 14</a> (<a href="/doc/html/rfc2119">RFC 2119</a>) (<a href="/doc/html/rfc8174">RFC 8174</a>) when, and only when,
     they appear in all capitals, as shown here.

     Copyright (c) 2019 IETF Trust and the persons identified as
     authors of the code.  All rights reserved.

     Redistribution and use in source and binary forms, with or
     without modification, is permitted pursuant to, and subject to
     the license terms contained in, the Simplified BSD License set
     forth in <a href="#section-4">Section 4</a>.c of the IETF Trust&#x27;s Legal Provisions
     Relating to IETF Documents
     (<a href="https://trustee.ietf.org/license-info">https://trustee.ietf.org/license-info</a>).

     This version of this YANG module is part of <a href="/doc/html/rfc8639">RFC 8639</a>; see the
     RFC itself for full legal notices.&quot;;

  revision 2019-09-09 {
    description
      &quot;Initial version.&quot;;
    reference
      &quot;<a href="/doc/html/rfc8639">RFC 8639</a>: A YANG Data Model for Subscriptions to
                 Event Notifications&quot;;
  }

  /*
   * FEATURES
   */

  feature configured {
    description
      &quot;This feature indicates that configuration of subscriptions is
       supported.&quot;;
  }

  feature dscp {
    description
      &quot;This feature indicates that a publisher supports the ability
       to set the Differentiated Services Code Point (DSCP) value in
       outgoing packets.&quot;;
  }

  feature encode-json {
    description
      &quot;This feature indicates that JSON encoding of notification
       messages is supported.&quot;;
  }

<span class="grey"><a href="/doc/html/rfc8639">RFC 8639</a>                Subscribed Notifications          September 2019</span>

  feature encode-xml {
    description
      &quot;This feature indicates that XML encoding of notification
       messages is supported.&quot;;
  }

  feature interface-designation {
    description
      &quot;This feature indicates that a publisher supports sourcing all
       receiver interactions for a configured subscription from a
       single designated egress interface.&quot;;
  }

  feature qos {
    description
      &quot;This feature indicates that a publisher supports absolute
       dependencies of one subscription&#x27;s traffic over another
       as well as weighted bandwidth sharing between subscriptions.
       Both of these are Quality of Service (QoS) features that allow
       differentiated treatment of notification messages between a
       publisher and a specific receiver.&quot;;
  }

  feature replay {
    description
      &quot;This feature indicates that historical event record replay is
       supported.  With replay, it is possible for past event records
       to be streamed in chronological order.&quot;;
  }

  feature subtree {
    description
      &quot;This feature indicates support for YANG subtree filtering.&quot;;
    reference
      &quot;<a href="/doc/html/rfc6241">RFC 6241</a>: Network Configuration Protocol (NETCONF),
                 <a href="#section-6">Section 6</a>&quot;;
  }

  feature supports-vrf {
    description
      &quot;This feature indicates that a publisher supports VRF
       configuration for configured subscriptions.  VRF support for
       dynamic subscriptions does not require this feature.&quot;;
    reference
      &quot;<a href="/doc/html/rfc8529">RFC 8529</a>: YANG Data Model for Network Instances,
                 <a href="#section-6">Section 6</a>&quot;;
  }

<span class="grey"><a href="/doc/html/rfc8639">RFC 8639</a>                Subscribed Notifications          September 2019</span>

  feature xpath {
    description
      &quot;This feature indicates support for XPath filtering.&quot;;
    reference
      &quot;XML Path Language (XPath) Version 1.0
       (<a href="https://www.w3.org/TR/1999/REC-xpath-19991116">https://www.w3.org/TR/1999/REC-xpath-19991116</a>)&quot;;
  }

  /*
   * EXTENSIONS
   */

  extension subscription-state-notification {
    description
      &quot;This statement applies only to notifications.  It indicates
       that the notification is a subscription state change
       notification.  Therefore, it does not participate in a regular
       event stream and does not need to be specifically subscribed
       to in order to be received.  This statement can only occur as
       a substatement of the YANG &#x27;notification&#x27; statement.  This
       statement is not for use outside of this YANG module.&quot;;
  }

  /*
   * IDENTITIES
   */
  /* Identities for RPC and notification errors */

  identity delete-subscription-error {
    description
      &quot;Base identity for the problem found while attempting to
       fulfill either a &#x27;delete-subscription&#x27; RPC request or a
       &#x27;kill-subscription&#x27; RPC request.&quot;;
  }

  identity establish-subscription-error {
    description
      &quot;Base identity for the problem found while attempting to
       fulfill an &#x27;establish-subscription&#x27; RPC request.&quot;;
  }

  identity modify-subscription-error {
    description
      &quot;Base identity for the problem found while attempting to
       fulfill a &#x27;modify-subscription&#x27; RPC request.&quot;;
  }

  identity subscription-suspended-reason {
<span class="grey"><a href="/doc/html/rfc8639">RFC 8639</a>                Subscribed Notifications          September 2019</span>

    description
      &quot;Base identity for the problem condition communicated to a
       receiver as part of a &#x27;subscription-suspended&#x27;
       notification.&quot;;
  }

  identity subscription-terminated-reason {
    description
      &quot;Base identity for the problem condition communicated to a
       receiver as part of a &#x27;subscription-terminated&#x27;
       notification.&quot;;
  }

  identity dscp-unavailable {
    base establish-subscription-error;
    if-feature &quot;dscp&quot;;
    description
      &quot;The publisher is unable to mark notification messages with
       prioritization information in a way that will be respected
       during network transit.&quot;;
  }

  identity encoding-unsupported {
    base establish-subscription-error;
    description
      &quot;Unable to encode notification messages in the desired
       format.&quot;;
  }

  identity filter-unavailable {
    base subscription-terminated-reason;
    description
      &quot;Referenced filter does not exist.  This means a receiver is
       referencing a filter that doesn&#x27;t exist or to which it
       does not have access permissions.&quot;;
  }

  identity filter-unsupported {
    base establish-subscription-error;
    base modify-subscription-error;
    description
      &quot;Cannot parse syntax in the filter.  This failure can be from
       a syntax error or a syntax too complex to be processed by the
       publisher.&quot;;
  }

  identity insufficient-resources {
    base establish-subscription-error;
<span class="grey"><a href="/doc/html/rfc8639">RFC 8639</a>                Subscribed Notifications          September 2019</span>

    base modify-subscription-error;
    base subscription-suspended-reason;
    description
      &quot;The publisher does not have sufficient resources to support
       the requested subscription.  An example might be that
       allocated CPU is too limited to generate the desired set of
       notification messages.&quot;;
  }

  identity no-such-subscription {
    base modify-subscription-error;
    base delete-subscription-error;
    base subscription-terminated-reason;
    description
      &quot;Referenced subscription doesn&#x27;t exist.  This may be as a
       result of a nonexistent subscription ID, an ID that belongs to
       another subscriber, or an ID for a configured subscription.&quot;;
  }

  identity replay-unsupported {
    base establish-subscription-error;
    if-feature &quot;replay&quot;;
    description
      &quot;Replay cannot be performed for this subscription.  This means
       the publisher will not provide the requested historic
       information from the event stream via replay to this
       receiver.&quot;;
  }

  identity stream-unavailable {
    base subscription-terminated-reason;
    description
      &quot;Not a subscribable event stream.  This means the referenced
       event stream is not available for subscription by the
       receiver.&quot;;
  }

  identity suspension-timeout {
    base subscription-terminated-reason;
    description
      &quot;Termination of a previously suspended subscription.  The
       publisher has eliminated the subscription, as it exceeded a
       time limit for suspension.&quot;;
  }

  identity unsupportable-volume {
    base subscription-suspended-reason;
    description
<span class="grey"><a href="/doc/html/rfc8639">RFC 8639</a>                Subscribed Notifications          September 2019</span>

      &quot;The publisher does not have the network bandwidth needed to
       get the volume of generated information intended for a
       receiver.&quot;;
  }

  /* Identities for encodings */

  identity configurable-encoding {
    description
      &quot;If a transport identity derives from this identity, it means
       that it supports configurable encodings.  An example of a
       configurable encoding might be a new identity such as
       &#x27;encode-cbor&#x27;.  Such an identity could use
       &#x27;configurable-encoding&#x27; as its base.  This would allow a
       dynamic subscription encoded in JSON (<a href="/doc/html/rfc8259">RFC 8259</a>) to request
       that notification messages be encoded via the Concise Binary
       Object Representation (CBOR) (<a href="/doc/html/rfc7049">RFC 7049</a>).  Further details for
       any specific configurable encoding would be explored in a
       transport document based on this specification.&quot;;
    reference
      &quot;<a href="/doc/html/rfc8259">RFC 8259</a>: The JavaScript Object Notation (JSON) Data
                 Interchange Format
       <a href="/doc/html/rfc7049">RFC 7049</a>: Concise Binary Object Representation (CBOR)&quot;;
  }

  identity encoding {
    description
      &quot;Base identity to represent data encodings.&quot;;
  }

  identity encode-xml {
    base encoding;
    if-feature &quot;encode-xml&quot;;
    description
      &quot;Encode data using XML as described in <a href="/doc/html/rfc7950">RFC 7950</a>.&quot;;
    reference
      &quot;<a href="/doc/html/rfc7950">RFC 7950</a>: The YANG 1.1 Data Modeling Language&quot;;
  }

  identity encode-json {
    base encoding;
    if-feature &quot;encode-json&quot;;
    description
      &quot;Encode data using JSON as described in <a href="/doc/html/rfc7951">RFC 7951</a>.&quot;;
    reference
      &quot;<a href="/doc/html/rfc7951">RFC 7951</a>: JSON Encoding of Data Modeled with YANG&quot;;
  }

<span class="grey"><a href="/doc/html/rfc8639">RFC 8639</a>                Subscribed Notifications          September 2019</span>

  /* Identities for transports */

  identity transport {
    description
      &quot;An identity that represents the underlying mechanism for
       passing notification messages.&quot;;
  }

  /*
   * TYPEDEFs
   */

  typedef encoding {
    type identityref {
      base encoding;
    }
    description
      &quot;Specifies a data encoding, e.g., for a data subscription.&quot;;
  }

  typedef stream-filter-ref {
    type leafref {
      path &quot;/sn:filters/sn:stream-filter/sn:name&quot;;
    }
    description
      &quot;This type is used to reference an event stream filter.&quot;;
  }

  typedef stream-ref {
    type leafref {
      path &quot;/sn:streams/sn:stream/sn:name&quot;;
    }
    description
      &quot;This type is used to reference a system-provided
       event stream.&quot;;
  }

  typedef subscription-id {
    type uint32;
    description
      &quot;A type for subscription identifiers.&quot;;
  }

  typedef transport {
    type identityref {
      base transport;
    }
    description
<span class="grey"><a href="/doc/html/rfc8639">RFC 8639</a>                Subscribed Notifications          September 2019</span>

      &quot;Specifies the transport used to send notification messages
       to a receiver.&quot;;
  }

  /*
   * GROUPINGS
   */

  grouping stream-filter-elements {
    description
      &quot;This grouping defines the base for filters applied to event
       streams.&quot;;
    choice filter-spec {
      description
        &quot;The content filter specification for this request.&quot;;
      anydata stream-subtree-filter {
        if-feature &quot;subtree&quot;;
        description
          &quot;Event stream evaluation criteria encoded in the syntax of
           a subtree filter as defined in <a href="/doc/html/rfc6241#section-6">RFC 6241, Section&amp;nbsp;6</a>.

           The subtree filter is applied to the representation of
           individual, delineated event records as contained in the
           event stream.

           If the subtree filter returns a non-empty node set, the
           filter matches the event record, and the event record is
           included in the notification message sent to the
           receivers.&quot;;
        reference
          &quot;<a href="/doc/html/rfc6241">RFC 6241</a>: Network Configuration Protocol (NETCONF),
                     <a href="#section-6">Section 6</a>&quot;;
      }
      leaf stream-xpath-filter {
        if-feature &quot;xpath&quot;;
        type yang:xpath1.0;
        description
          &quot;Event stream evaluation criteria encoded in the syntax of
           an XPath 1.0 expression.

           The XPath expression is evaluated on the representation of
           individual, delineated event records as contained in
           the event stream.

           The result of the XPath expression is converted to a
           boolean value using the standard XPath 1.0 rules.  If the
           boolean value is &#x27;true&#x27;, the filter matches the event
           record, and the event record is included in the
<span class="grey"><a href="/doc/html/rfc8639">RFC 8639</a>                Subscribed Notifications          September 2019</span>

           notification message sent to the receivers.

           The expression is evaluated in the following XPath
           context:

              o  The set of namespace declarations is the set of
                 prefix and namespace pairs for all YANG modules
                 implemented by the server, where the prefix is the
                 YANG module name and the namespace is as defined by
                 the &#x27;namespace&#x27; statement in the YANG module.

                 If the leaf is encoded in XML, all namespace
                 declarations in scope on the &#x27;stream-xpath-filter&#x27;
                 leaf element are added to the set of namespace
                 declarations.  If a prefix found in the XML is
                 already present in the set of namespace
                 declarations, the namespace in the XML is used.

              o  The set of variable bindings is empty.

              o  The function library is comprised of the core
                 function library and the XPath functions defined in
                 <a href="/doc/html/rfc7950#section-10">Section&amp;nbsp;10 in RFC 7950</a>.

              o  The context node is the root node.&quot;;
        reference
          &quot;XML Path Language (XPath) Version 1.0
           (<a href="https://www.w3.org/TR/1999/REC-xpath-19991116">https://www.w3.org/TR/1999/REC-xpath-19991116</a>)
           <a href="/doc/html/rfc7950">RFC 7950</a>: The YANG 1.1 Data Modeling Language,
                     <a href="#section-10">Section 10</a>&quot;;
      }
    }
  }

  grouping update-qos {
    description
      &quot;This grouping describes QoS information concerning a
       subscription.  This information is passed to lower layers
       for transport prioritization and treatment.&quot;;
    leaf dscp {
      if-feature &quot;dscp&quot;;
      type inet:dscp;
      default &quot;0&quot;;
      description
        &quot;The desired network transport priority level.  This is the
         priority set on notification messages encapsulating the
         results of the subscription.  This transport priority is
         shared for all receivers of a given subscription.&quot;;
<span class="grey"><a href="/doc/html/rfc8639">RFC 8639</a>                Subscribed Notifications          September 2019</span>

    }
    leaf weighting {
      if-feature &quot;qos&quot;;
      type uint8 {
        range &quot;0 .. 255&quot;;
      }
      description
        &quot;Relative weighting for a subscription.  Larger weights get
         more resources.  Allows an underlying transport layer to
         perform informed load-balance allocations between various
         subscriptions.&quot;;
      reference
        &quot;<a href="/doc/html/rfc7540">RFC 7540</a>: Hypertext Transfer Protocol Version 2 (HTTP/2),
                   <a href="#section-5.3.2">Section 5.3.2</a>&quot;;
    }
    leaf dependency {
      if-feature &quot;qos&quot;;
      type subscription-id;
      description
        &quot;Provides the &#x27;subscription-id&#x27; of a parent subscription.
         The parent subscription has absolute precedence should
         that parent have push updates ready to egress the publisher.
         In other words, there should be no streaming of objects from
         the current subscription if the parent has something ready
         to push.

         If a dependency is asserted via configuration or via an RPC
         but the referenced &#x27;subscription-id&#x27; does not exist, the
         dependency is silently discarded.  If a referenced
         subscription is deleted, this dependency is removed.&quot;;
      reference
        &quot;<a href="/doc/html/rfc7540">RFC 7540</a>: Hypertext Transfer Protocol Version 2 (HTTP/2),
                   <a href="#section-5.3.1">Section 5.3.1</a>&quot;;
    }
  }

  grouping subscription-policy-modifiable {
    description
      &quot;This grouping describes all objects that may be changed
       in a subscription.&quot;;
    choice target {
      mandatory true;
      description
        &quot;Identifies the source of information against which a
         subscription is being applied as well as specifics on the
         subset of information desired from that source.&quot;;
      case stream {
        choice stream-filter {
<span class="grey"><a href="/doc/html/rfc8639">RFC 8639</a>                Subscribed Notifications          September 2019</span>

          description
            &quot;An event stream filter can be applied to a subscription.
             That filter will either come referenced from a global
             list or be provided in the subscription itself.&quot;;
          case by-reference {
            description
              &quot;Apply a filter that has been configured separately.&quot;;
            leaf stream-filter-name {
              type stream-filter-ref;
              mandatory true;
              description
                &quot;References an existing event stream filter that is
                 to be applied to an event stream for the
                 subscription.&quot;;
            }
          }
          case within-subscription {
            description
              &quot;A local definition allows a filter to have the same
               lifecycle as the subscription.&quot;;
            uses stream-filter-elements;
          }
        }
      }
    }
    leaf stop-time {
      type yang:date-and-time;
      description
        &quot;Identifies a time after which notification messages for a
         subscription should not be sent.  If &#x27;stop-time&#x27; is not
         present, the notification messages will continue until the
         subscription is terminated.  If &#x27;replay-start-time&#x27; exists,
         &#x27;stop-time&#x27; must be for a subsequent time.  If
         &#x27;replay-start-time&#x27; doesn&#x27;t exist, &#x27;stop-time&#x27;, when
         established, must be for a future time.&quot;;
    }
  }

  grouping subscription-policy-dynamic {
    description
      &quot;This grouping describes the only information concerning a
       subscription that can be passed over the RPCs defined in this
       data model.&quot;;
    uses subscription-policy-modifiable {
      augment &quot;target/stream&quot; {
        description
          &quot;Adds additional objects that can be modified by an RPC.&quot;;
        leaf stream {
<span class="grey"><a href="/doc/html/rfc8639">RFC 8639</a>                Subscribed Notifications          September 2019</span>

          type stream-ref {
            require-instance false;
          }
          mandatory true;
          description
            &quot;Indicates the event stream to be considered for
             this subscription.&quot;;
        }
        leaf replay-start-time {
          if-feature &quot;replay&quot;;
          type yang:date-and-time;
          config false;
          description
            &quot;Used to trigger the &#x27;replay&#x27; feature for a dynamic
             subscription, where event records that are selected
             need to be at or after the specified starting time.  If
             &#x27;replay-start-time&#x27; is not present, this is not a replay
             subscription and event record push should start
             immediately.  It is never valid to specify start times
             that are later than or equal to the current time.&quot;;
        }
      }
    }
    uses update-qos;
  }

  grouping subscription-policy {
    description
      &quot;This grouping describes the full set of policy information
       concerning both dynamic and configured subscriptions, with the
       exclusion of both receivers and networking information
       specific to the publisher, such as what interface should be
       used to transmit notification messages.&quot;;
    uses subscription-policy-dynamic;
    leaf transport {
      if-feature &quot;configured&quot;;
      type transport;
      description
        &quot;For a configured subscription, this leaf specifies the
         transport used to deliver messages destined for all
         receivers of that subscription.&quot;;
    }
    leaf encoding {
      when &#x27;not(../transport) or derived-from(../transport,
      &quot;sn:configurable-encoding&quot;)&#x27;;
      type encoding;
      description
        &quot;The type of encoding for notification messages.  For a
<span class="grey"><a href="/doc/html/rfc8639">RFC 8639</a>                Subscribed Notifications          September 2019</span>

         dynamic subscription, if not included as part of an
         &#x27;establish-subscription&#x27; RPC, the encoding will be populated
         with the encoding used by that RPC.  For a configured
         subscription, if not explicitly configured, the encoding
         will be the default encoding for an underlying transport.&quot;;
    }
    leaf purpose {
      if-feature &quot;configured&quot;;
      type string;
      description
        &quot;Open text allowing a configuring entity to embed the
         originator or other specifics of this subscription.&quot;;
    }
  }

  /*
   * RPCs
   */

  rpc establish-subscription {
    description
      &quot;This RPC allows a subscriber to create (and possibly
       negotiate) a subscription on its own behalf.  If successful,
       the subscription remains in effect for the duration of the
       subscriber&#x27;s association with the publisher or until the
       subscription is terminated.  If an error occurs or the
       publisher cannot meet the terms of a subscription, an RPC
       error is returned, and the subscription is not created.
       In that case, the RPC reply&#x27;s &#x27;error-info&#x27; MAY include
       suggested parameter settings that would have a higher
       likelihood of succeeding in a subsequent
       &#x27;establish-subscription&#x27; request.&quot;;
    input {
      uses subscription-policy-dynamic;
      leaf encoding {
        type encoding;
        description
          &quot;The type of encoding for the subscribed data.  If not
           included as part of the RPC, the encoding MUST be set by
           the publisher to be the encoding used by this RPC.&quot;;
      }
    }
    output {
      leaf id {
        type subscription-id;
        mandatory true;
        description
          &quot;Identifier used for this subscription.&quot;;
<span class="grey"><a href="/doc/html/rfc8639">RFC 8639</a>                Subscribed Notifications          September 2019</span>

      }
      leaf replay-start-time-revision {
        if-feature &quot;replay&quot;;
        type yang:date-and-time;
        description
          &quot;If a replay has been requested, this object represents
           the earliest time covered by the event buffer for the
           requested event stream.  The value of this object is the
           &#x27;replay-log-aged-time&#x27; if it exists.  Otherwise, it is
           the &#x27;replay-log-creation-time&#x27;.  All buffered event
           records after this time will be replayed to a receiver.
           This object will only be sent if the starting time has
           been revised to be later than the time requested by the
           subscriber.&quot;;
      }
    }
  }

  rc:yang-data establish-subscription-stream-error-info {
    container establish-subscription-stream-error-info {
      description
        &quot;If any &#x27;establish-subscription&#x27; RPC parameters are
         unsupportable against the event stream, a subscription
         is not created and the RPC error response MUST indicate the
         reason why the subscription failed to be created.  This
         yang-data MAY be inserted as structured data in a
         subscription&#x27;s RPC error response to indicate the reason for
         the failure.  This yang-data MUST be inserted if hints are
         to be provided back to the subscriber.&quot;;
      leaf reason {
        type identityref {
          base establish-subscription-error;
        }
        description
          &quot;Indicates the reason why the subscription has failed to
           be created to a targeted event stream.&quot;;
      }
      leaf filter-failure-hint {
        type string;
        description
          &quot;Information describing where and/or why a provided
           filter was unsupportable for a subscription.  The
           syntax and semantics of this hint are
           implementation specific.&quot;;
      }
    }
  }

<span class="grey"><a href="/doc/html/rfc8639">RFC 8639</a>                Subscribed Notifications          September 2019</span>

  rpc modify-subscription {
    description
      &quot;This RPC allows a subscriber to modify a dynamic
       subscription&#x27;s parameters.  If successful, the changed
       subscription parameters remain in effect for the duration of
       the subscription, until the subscription is again modified, or
       until the subscription is terminated.  In the case of an error
       or an inability to meet the modified parameters, the
       subscription is not modified and the original subscription
       parameters remain in effect.  In that case, the RPC error MAY
       include &#x27;error-info&#x27; suggested parameter hints that would have
       a high likelihood of succeeding in a subsequent
       &#x27;modify-subscription&#x27; request.  A successful
       &#x27;modify-subscription&#x27; will return a suspended subscription to
       the &#x27;active&#x27; state.&quot;;
    input {
      leaf id {
        type subscription-id;
        mandatory true;
        description
          &quot;Identifier to use for this subscription.&quot;;
      }
      uses subscription-policy-modifiable;
    }
  }

  rc:yang-data modify-subscription-stream-error-info {
    container modify-subscription-stream-error-info {
      description
        &quot;This yang-data MAY be provided as part of a subscription&#x27;s
         RPC error response when there is a failure of a
         &#x27;modify-subscription&#x27; RPC that has been made against an
         event stream.  This yang-data MUST be used if hints are to
         be provided back to the subscriber.&quot;;
      leaf reason {
        type identityref {
          base modify-subscription-error;
        }
        description
          &quot;Information in a &#x27;modify-subscription&#x27; RPC error response
           that indicates the reason why the subscription to an event
           stream has failed to be modified.&quot;;
      }
      leaf filter-failure-hint {
        type string;
        description
          &quot;Information describing where and/or why a provided
           filter was unsupportable for a subscription.  The syntax
<span class="grey"><a href="/doc/html/rfc8639">RFC 8639</a>                Subscribed Notifications          September 2019</span>

           and semantics of this hint are
           implementation specific.&quot;;
      }
    }
  }

  rpc delete-subscription {
    description
      &quot;This RPC allows a subscriber to delete a subscription that
       was previously created by that same subscriber using the
       &#x27;establish-subscription&#x27; RPC.

       If an error occurs, the server replies with an &#x27;rpc-error&#x27;
       where the &#x27;error-info&#x27; field MAY contain a
       &#x27;delete-subscription-error-info&#x27; structure.&quot;;
    input {
      leaf id {
        type subscription-id;
        mandatory true;
        description
          &quot;Identifier of the subscription that is to be deleted.
           Only subscriptions that were created using
           &#x27;establish-subscription&#x27; from the same origin as this RPC
           can be deleted via this RPC.&quot;;
      }
    }
  }

  rpc kill-subscription {
    nacm:default-deny-all;
    description
      &quot;This RPC allows an operator to delete a dynamic subscription
       without restrictions on the originating subscriber or
       underlying transport session.

       If an error occurs, the server replies with an &#x27;rpc-error&#x27;
       where the &#x27;error-info&#x27; field MAY contain a
       &#x27;delete-subscription-error-info&#x27; structure.&quot;;
    input {
      leaf id {
        type subscription-id;
        mandatory true;
        description
          &quot;Identifier of the subscription that is to be deleted.
           Only subscriptions that were created using
           &#x27;establish-subscription&#x27; can be deleted via this RPC.&quot;;
      }
    }
<span class="grey"><a href="/doc/html/rfc8639">RFC 8639</a>                Subscribed Notifications          September 2019</span>

  }

  rc:yang-data delete-subscription-error-info {
    container delete-subscription-error-info {
      description
        &quot;If a &#x27;delete-subscription&#x27; RPC or a &#x27;kill-subscription&#x27; RPC
         fails, the subscription is not deleted and the RPC error
         response MUST indicate the reason for this failure.  This
         yang-data MAY be inserted as structured data in a
         subscription&#x27;s RPC error response to indicate the reason
         for the failure.&quot;;
      leaf reason {
        type identityref {
          base delete-subscription-error;
        }
        mandatory true;
        description
          &quot;Indicates the reason why the subscription has failed to be
           deleted.&quot;;
      }
    }
  }

  /*
   * NOTIFICATIONS
   */

  notification replay-completed {
    sn:subscription-state-notification;
    if-feature &quot;replay&quot;;
    description
      &quot;This notification is sent to indicate that all of the replay
       notifications have been sent.&quot;;
    leaf id {
      type subscription-id;
      mandatory true;
      description
        &quot;This references the affected subscription.&quot;;
    }
  }

  notification subscription-completed {
    sn:subscription-state-notification;
    if-feature &quot;configured&quot;;
    description
      &quot;This notification is sent to indicate that a subscription has
       finished passing event records, as the &#x27;stop-time&#x27; has been
       reached.&quot;;
<span class="grey"><a href="/doc/html/rfc8639">RFC 8639</a>                Subscribed Notifications          September 2019</span>

    leaf id {
      type subscription-id;
      mandatory true;
      description
        &quot;This references the gracefully completed subscription.&quot;;
    }
  }

  notification subscription-modified {
    sn:subscription-state-notification;
    description
      &quot;This notification indicates that a subscription has been
       modified.  Notification messages sent from this point on will
       conform to the modified terms of the subscription.  For
       completeness, this subscription state change notification
       includes both modified and unmodified aspects of a
       subscription.&quot;;
    leaf id {
      type subscription-id;
      mandatory true;
      description
        &quot;This references the affected subscription.&quot;;
    }
    uses subscription-policy {
      refine &quot;target/stream/stream-filter/within-subscription&quot; {
        description
          &quot;Filter applied to the subscription.  If the
           &#x27;stream-filter-name&#x27; is populated, the filter in the
           subscription came from the &#x27;filters&#x27; container.
           Otherwise, it is populated in-line as part of the
           subscription.&quot;;
      }
    }
  }

  notification subscription-resumed {
    sn:subscription-state-notification;
    description
      &quot;This notification indicates that a subscription that had
       previously been suspended has resumed.  Notifications will
       once again be sent.  In addition, a &#x27;subscription-resumed&#x27;
       indicates that no modification of parameters has occurred
       since the last time event records have been sent.&quot;;
    leaf id {
      type subscription-id;
      mandatory true;
      description
        &quot;This references the affected subscription.&quot;;
<span class="grey"><a href="/doc/html/rfc8639">RFC 8639</a>                Subscribed Notifications          September 2019</span>

    }
  }

  notification subscription-started {
    sn:subscription-state-notification;
    if-feature &quot;configured&quot;;
    description
      &quot;This notification indicates that a subscription has started
       and notifications will now be sent.&quot;;
    leaf id {
      type subscription-id;
      mandatory true;
      description
        &quot;This references the affected subscription.&quot;;
    }
    uses subscription-policy {
      refine &quot;target/stream/replay-start-time&quot; {
        description
          &quot;Indicates the time that a replay is using for the
           streaming of buffered event records.  This will be
           populated with the most recent of the following:
           the event time of the previous event record sent to a
           receiver, the &#x27;replay-log-creation-time&#x27;, the
           &#x27;replay-log-aged-time&#x27;, or the most recent publisher
           boot time.&quot;;
      }
      refine &quot;target/stream/stream-filter/within-subscription&quot; {
        description
          &quot;Filter applied to the subscription.  If the
           &#x27;stream-filter-name&#x27; is populated, the filter in the
           subscription came from the &#x27;filters&#x27; container.
           Otherwise, it is populated in-line as part of the
           subscription.&quot;;
      }
      augment &quot;target/stream&quot; {
        description
          &quot;This augmentation adds additional parameters specific to a
           &#x27;subscription-started&#x27; notification.&quot;;
        leaf replay-previous-event-time {
          when &#x27;../replay-start-time&#x27;;
          if-feature &quot;replay&quot;;
          type yang:date-and-time;
          description
            &quot;If there is at least one event in the replay buffer
             prior to &#x27;replay-start-time&#x27;, this gives the time of
             the event generated immediately prior to the
             &#x27;replay-start-time&#x27;.

<span class="grey"><a href="/doc/html/rfc8639">RFC 8639</a>                Subscribed Notifications          September 2019</span>

             If a receiver previously received event records for
             this configured subscription, it can compare this time
             to the last event record previously received.  If the
             two are not the same (perhaps due to a reboot), then a
             dynamic replay can be initiated to acquire any missing
             event records.&quot;;
        }
      }
    }
  }

  notification subscription-suspended {
    sn:subscription-state-notification;
    description
      &quot;This notification indicates that a suspension of the
       subscription by the publisher has occurred.  No further
       notifications will be sent until the subscription resumes.
       This notification shall only be sent to receivers of a
       subscription; it does not constitute a general-purpose
       notification.&quot;;
    leaf id {
      type subscription-id;
      mandatory true;
      description
        &quot;This references the affected subscription.&quot;;
    }
    leaf reason {
      type identityref {
        base subscription-suspended-reason;
      }
      mandatory true;
      description
        &quot;Identifies the condition that resulted in the suspension.&quot;;
    }
  }

  notification subscription-terminated {
    sn:subscription-state-notification;
    description
      &quot;This notification indicates that a subscription has been
       terminated.&quot;;
    leaf id {
      type subscription-id;
      mandatory true;
      description
        &quot;This references the affected subscription.&quot;;
    }
    leaf reason {
<span class="grey"><a href="/doc/html/rfc8639">RFC 8639</a>                Subscribed Notifications          September 2019</span>

      type identityref {
        base subscription-terminated-reason;
      }
      mandatory true;
      description
        &quot;Identifies the condition that resulted in the termination.&quot;;
    }
  }

  /*
   * DATA NODES
   */

  container streams {
    config false;
    description
      &quot;Contains information on the built-in event streams provided by
       the publisher.&quot;;
    list stream {
      key &quot;name&quot;;
      description
        &quot;Identifies the built-in event streams that are supported by
         the publisher.&quot;;
      leaf name {
        type string;
        description
          &quot;A handle for a system-provided event stream made up of a
           sequential set of event records, each of which is
           characterized by its own domain and semantics.&quot;;
      }
      leaf description {
        type string;
        description
          &quot;A description of the event stream, including such
           information as the type of event records that are
           available in this event stream.&quot;;
      }
      leaf replay-support {
        if-feature &quot;replay&quot;;
        type empty;
        description
          &quot;Indicates that event record replay is available on this
           event stream.&quot;;
      }
      leaf replay-log-creation-time {
        when &#x27;../replay-support&#x27;;
        if-feature &quot;replay&quot;;
        type yang:date-and-time;
<span class="grey"><a href="/doc/html/rfc8639">RFC 8639</a>                Subscribed Notifications          September 2019</span>

        mandatory true;
        description
          &quot;The timestamp of the creation of the log used to support
           the replay function on this event stream.  This time
           might be earlier than the earliest available information
           contained in the log.  This object is updated if the log
           resets for some reason.&quot;;
      }
      leaf replay-log-aged-time {
        when &#x27;../replay-support&#x27;;
        if-feature &quot;replay&quot;;
        type yang:date-and-time;
        description
          &quot;The timestamp associated with the last event record that
           has been aged out of the log.  This timestamp identifies
           how far back in history this replay log extends, if it
           doesn&#x27;t extend back to the &#x27;replay-log-creation-time&#x27;.
           This object MUST be present if replay is supported and any
           event records have been aged out of the log.&quot;;
      }
    }
  }
  container filters {
    description
      &quot;Contains a list of configurable filters that can be applied to
       subscriptions.  This facilitates the reuse of complex filters
       once defined.&quot;;
    list stream-filter {
      key &quot;name&quot;;
      description
        &quot;A list of preconfigured filters that can be applied to
         subscriptions.&quot;;
      leaf name {
        type string;
        description
          &quot;A name to differentiate between filters.&quot;;
      }
      uses stream-filter-elements;
    }
  }
  container subscriptions {
    description
      &quot;Contains the list of currently active subscriptions, i.e.,
       subscriptions that are currently in effect, used for
       subscription management and monitoring purposes.  This
       includes subscriptions that have been set up via
       RPC primitives as well as subscriptions that have been
       established via configuration.&quot;;
<span class="grey"><a href="/doc/html/rfc8639">RFC 8639</a>                Subscribed Notifications          September 2019</span>

    list subscription {
      key &quot;id&quot;;
      description
        &quot;The identity and specific parameters of a subscription.
         Subscriptions in this list can be created using a control
         channel or RPC or can be established through configuration.

         If the &#x27;kill-subscription&#x27; RPC or configuration operations
         are used to delete a subscription, a
         &#x27;subscription-terminated&#x27; message is sent to any active or
         suspended receivers.&quot;;
      leaf id {
        type subscription-id;
        description
          &quot;Identifier of a subscription; unique in a given
           publisher.&quot;;
      }
      uses subscription-policy {
        refine &quot;target/stream/stream&quot; {
          description
            &quot;Indicates the event stream to be considered for this
             subscription.  If an event stream has been removed
             and can no longer be referenced by an active
             subscription, send a &#x27;subscription-terminated&#x27;
             notification with &#x27;stream-unavailable&#x27; as the reason.
             If a configured subscription refers to a nonexistent
             event stream, move that subscription to the
             &#x27;invalid&#x27; state.&quot;;
        }
        refine &quot;transport&quot; {
          description
            &quot;For a configured subscription, this leaf specifies the
             transport used to deliver messages destined for all
             receivers of that subscription.  This object is
             mandatory for subscriptions in the configuration
             datastore.  This object (1) is not mandatory for dynamic
             subscriptions in the operational state datastore and
             (2) should not be present for other types of dynamic
             subscriptions.&quot;;
        }
        augment &quot;target/stream&quot; {
          description
            &quot;Enables objects to be added to a configured stream
             subscription.&quot;;
          leaf configured-replay {
            if-feature &quot;configured&quot;;
            if-feature &quot;replay&quot;;
            type empty;
<span class="grey"><a href="/doc/html/rfc8639">RFC 8639</a>                Subscribed Notifications          September 2019</span>

            description
              &quot;The presence of this leaf indicates that replay for
               the configured subscription should start at the
               earliest time in the event log or at the publisher
               boot time, whichever is later.&quot;;
          }
        }
      }
      choice notification-message-origin {
        if-feature &quot;configured&quot;;
        description
          &quot;Identifies the egress interface on the publisher
           from which notification messages are to be sent.&quot;;
        case interface-originated {
          description
            &quot;When notification messages are to egress a specific,
             designated interface on the publisher.&quot;;
          leaf source-interface {
            if-feature &quot;interface-designation&quot;;
            type if:interface-ref;
            description
              &quot;References the interface for notification messages.&quot;;
          }
        }
        case address-originated {
          description
            &quot;When notification messages are to depart from a
             publisher using a specific originating address and/or
             routing context information.&quot;;
          leaf source-vrf {
            if-feature &quot;supports-vrf&quot;;
            type leafref {
              path &quot;/ni:network-instances/ni:network-instance/ni:name&quot;;
            }
            description
              &quot;VRF from which notification messages should egress a
               publisher.&quot;;
          }
          leaf source-address {
            type inet:ip-address-no-zone;
            description
              &quot;The source address for the notification messages.
               If a source VRF exists but this object doesn&#x27;t, a
               publisher&#x27;s default address for that VRF must
               be used.&quot;;
          }
        }
      }
<span class="grey"><a href="/doc/html/rfc8639">RFC 8639</a>                Subscribed Notifications          September 2019</span>

      leaf configured-subscription-state {
        if-feature &quot;configured&quot;;
        type enumeration {
          enum valid {
            value 1;
            description
              &quot;The subscription is supportable with its current
               parameters.&quot;;
          }
          enum invalid {
            value 2;
            description
              &quot;The subscription as a whole is unsupportable with its
               current parameters.&quot;;
          }
          enum concluded {
            value 3;
            description
              &quot;A subscription is inactive, as it has hit a
               stop time.  It no longer has receivers in the
               &#x27;active&#x27; or &#x27;suspended&#x27; state, but the subscription
               has not yet been removed from configuration.&quot;;
          }
        }
        config false;
        description
          &quot;The presence of this leaf indicates that the subscription
           originated from configuration, not through a control
           channel or RPC.  The value indicates the state of the
           subscription as established by the publisher.&quot;;
      }
      container receivers {
        description
          &quot;Set of receivers in a subscription.&quot;;
        list receiver {
          key &quot;name&quot;;
          min-elements 1;
          description
            &quot;A host intended as a recipient for the notification
             messages of a subscription.  For configured
             subscriptions, transport-specific network parameters
             (or a leafref to those parameters) may be augmented to a
             specific receiver in this list.&quot;;
          leaf name {
            type string;
            description
              &quot;Identifies a unique receiver for a subscription.&quot;;
          }
<span class="grey"><a href="/doc/html/rfc8639">RFC 8639</a>                Subscribed Notifications          September 2019</span>

          leaf sent-event-records {
            type yang:zero-based-counter64;
            config false;
            description
              &quot;The number of event records sent to the receiver.  The
               count is initialized when a dynamic subscription is
               established or when a configured receiver
               transitions to the &#x27;valid&#x27; state.&quot;;
          }
          leaf excluded-event-records {
            type yang:zero-based-counter64;
            config false;
            description
              &quot;The number of event records explicitly removed via
               either an event stream filter or an access control
               filter so that they are not passed to a receiver.
               This count is set to zero each time
               &#x27;sent-event-records&#x27; is initialized.&quot;;
          }
          leaf state {
            type enumeration {
              enum active {
                value 1;
                description
                  &quot;The receiver is currently being sent any
                   applicable notification messages for the
                   subscription.&quot;;
              }
              enum suspended {
                value 2;
                description
                  &quot;The receiver state is &#x27;suspended&#x27;, so the
                   publisher is currently unable to provide
                   notification messages for the subscription.&quot;;
              }
              enum connecting {
                value 3;
                if-feature &quot;configured&quot;;
                description
                  &quot;A subscription has been configured, but a
                   &#x27;subscription-started&#x27; subscription state change
                   notification needs to be successfully received
                   before notification messages are sent.

                   If the &#x27;reset&#x27; action is invoked for a receiver of
                   an active configured subscription, the state
                   must be moved to &#x27;connecting&#x27;.&quot;;
              }
<span class="grey"><a href="/doc/html/rfc8639">RFC 8639</a>                Subscribed Notifications          September 2019</span>

              enum disconnected {
                value 4;
                if-feature &quot;configured&quot;;
                description
                  &quot;A subscription has failed to send a
                   &#x27;subscription-started&#x27; state change to the
                   receiver.  Additional connection attempts are not
                   currently being made.&quot;;
              }
            }
            config false;
            mandatory true;
            description
              &quot;Specifies the state of a subscription from the
               perspective of a particular receiver.  With this
               information, it is possible to determine whether a
               publisher is currently generating notification
               messages intended for that receiver.&quot;;
          }
          action reset {
            if-feature &quot;configured&quot;;
            description
              &quot;Allows the reset of this configured subscription&#x27;s
               receiver to the &#x27;connecting&#x27; state.  This enables the
               connection process to be reinitiated.&quot;;
            output {
              leaf time {
                type yang:date-and-time;
                mandatory true;
                description
                  &quot;Time at which a publisher returned the receiver to
                   the &#x27;connecting&#x27; state.&quot;;
              }
            }
          }
        }
      }
    }
  }
}
