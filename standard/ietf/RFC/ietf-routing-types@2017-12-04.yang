module ietf-routing-types {
  namespace &quot;urn:ietf:params:xml:ns:yang:ietf-routing-types&quot;;
  prefix rt-types;

  import ietf-yang-types {
    prefix yang;
  }
  import ietf-inet-types {
    prefix inet;
  }

  organization
    &quot;IETF RTGWG - Routing Area Working Group&quot;;
  contact
    &quot;WG Web:   &lt;<a href="https://datatracker.ietf.org/wg/rtgwg/">https://datatracker.ietf.org/wg/rtgwg/</a>&gt;
     WG List:  &lt;mailto:<a href="mailto:rtgwg@ietf.org">rtgwg@ietf.org</a>&gt;

     Editors:  Xufeng Liu
               &lt;mailto:<a href="mailto:Xufeng_Liu@jabail.com">Xufeng_Liu@jabail.com</a>&gt;
               Yingzhen Qu
               &lt;mailto:<a href="mailto:yingzhen.qu@huawei.com">yingzhen.qu@huawei.com</a>&gt;
               Acee Lindem
               &lt;mailto:<a href="mailto:acee@cisco.com">acee@cisco.com</a>&gt;
               Christian Hopps
               &lt;mailto:<a href="mailto:chopps@chopps.org">chopps@chopps.org</a>&gt;
               Lou Berger
               &lt;mailto:<a href="mailto:lberger@labn.com">lberger@labn.com</a>&gt;&quot;;

  description
    &quot;This module contains a collection of YANG data types
     considered generally useful for routing protocols.

     Copyright (c) 2017 IETF Trust and the persons
     identified as authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">https://trustee.ietf.org/license-info</a>).

     This version of this YANG module is part of <a href="/doc/html/rfc8294">RFC 8294</a>; see
     the RFC itself for full legal notices.&quot;;
<span class="grey"><a href="/doc/html/rfc8294">RFC 8294</a>                 Routing Area YANG Types           December 2017</span>

      revision 2017-12-04 {
        description &quot;Initial revision.&quot;;
        reference
          &quot;<a href="/doc/html/rfc8294">RFC 8294</a>: Common YANG Data Types for the Routing Area.
           <a href="#section-3">Section 3</a>.&quot;;
     }

     /*** Identities related to MPLS/GMPLS ***/

     identity mpls-label-special-purpose-value {
       description
         &quot;Base identity for deriving identities describing
          special-purpose Multiprotocol Label Switching (MPLS) label
          values.&quot;;
       reference
         &quot;<a href="/doc/html/rfc7274">RFC 7274</a>: Allocating and Retiring Special-Purpose MPLS
          Labels.&quot;;
     }

     identity ipv4-explicit-null-label {
       base mpls-label-special-purpose-value;
       description
         &quot;This identity represents the IPv4 Explicit NULL Label.&quot;;
       reference
         &quot;<a href="/doc/html/rfc3032">RFC 3032</a>: MPLS Label Stack Encoding.  <a href="#section-2.1">Section 2.1</a>.&quot;;
     }

     identity router-alert-label {
       base mpls-label-special-purpose-value;
       description
         &quot;This identity represents the Router Alert Label.&quot;;
       reference
         &quot;<a href="/doc/html/rfc3032">RFC 3032</a>: MPLS Label Stack Encoding.  <a href="#section-2.1">Section 2.1</a>.&quot;;
     }

     identity ipv6-explicit-null-label {
       base mpls-label-special-purpose-value;
       description
         &quot;This identity represents the IPv6 Explicit NULL Label.&quot;;
       reference
         &quot;<a href="/doc/html/rfc3032">RFC 3032</a>: MPLS Label Stack Encoding.  <a href="#section-2.1">Section 2.1</a>.&quot;;
     }

<span class="grey"><a href="/doc/html/rfc8294">RFC 8294</a>                 Routing Area YANG Types           December 2017</span>

     identity implicit-null-label {
       base mpls-label-special-purpose-value;
       description
         &quot;This identity represents the Implicit NULL Label.&quot;;
       reference
         &quot;<a href="/doc/html/rfc3032">RFC 3032</a>: MPLS Label Stack Encoding.  <a href="#section-2.1">Section 2.1</a>.&quot;;
     }

     identity entropy-label-indicator {
       base mpls-label-special-purpose-value;
       description
         &quot;This identity represents the Entropy Label Indicator.&quot;;
       reference
         &quot;<a href="/doc/html/rfc6790">RFC 6790</a>: The Use of Entropy Labels in MPLS Forwarding.
          Sections <a href="#section-3">3</a> and <a href="#section-10.1">10.1</a>.&quot;;
     }

     identity gal-label {
       base mpls-label-special-purpose-value;
       description
         &quot;This identity represents the Generic Associated Channel
          (G-ACh) Label (GAL).&quot;;
       reference
         &quot;<a href="/doc/html/rfc5586">RFC 5586</a>: MPLS Generic Associated Channel.
          Sections <a href="#section-4">4</a> and <a href="#section-10">10</a>.&quot;;
     }

     identity oam-alert-label {
       base mpls-label-special-purpose-value;
       description
         &quot;This identity represents the OAM Alert Label.&quot;;
       reference
         &quot;<a href="/doc/html/rfc3429">RFC 3429</a>: Assignment of the &#x27;OAM Alert Label&#x27; for
          Multiprotocol Label Switching Architecture (MPLS)
          Operation and Maintenance (OAM) Functions.
          Sections <a href="#section-3">3</a> and <a href="#section-6">6</a>.&quot;;
     }

     identity extension-label {
       base mpls-label-special-purpose-value;
       description
         &quot;This identity represents the Extension Label.&quot;;
       reference
         &quot;<a href="/doc/html/rfc7274">RFC 7274</a>: Allocating and Retiring Special-Purpose MPLS
          Labels.  Sections <a href="#section-3.1">3.1</a> and <a href="#section-5">5</a>.&quot;;
     }

<span class="grey"><a href="/doc/html/rfc8294">RFC 8294</a>                 Routing Area YANG Types           December 2017</span>

     /*** Collection of types related to routing ***/

     typedef router-id {
       type yang:dotted-quad;
       description
         &quot;A 32-bit number in the dotted-quad format assigned to each
          router.  This number uniquely identifies the router within
          an Autonomous System.&quot;;
     }

     /*** Collection of types related to VPNs ***/

     typedef route-target {
       type string {
         pattern
           &#x27;(0:(6553[0-5]|655[0-2][0-9]|65[0-4][0-9]{2}|&#x27;
         +     &#x27;6[0-4][0-9]{3}|&#x27;
         +     &#x27;[1-5][0-9]{4}|[1-9][0-9]{0,3}|0):(429496729[0-5]|&#x27;
         +     &#x27;42949672[0-8][0-9]|&#x27;
         +     &#x27;4294967[01][0-9]{2}|429496[0-6][0-9]{3}|&#x27;
         +     &#x27;42949[0-5][0-9]{4}|&#x27;
         +     &#x27;4294[0-8][0-9]{5}|429[0-3][0-9]{6}|&#x27;
         +     &#x27;42[0-8][0-9]{7}|4[01][0-9]{8}|&#x27;
         +     &#x27;[1-3][0-9]{9}|[1-9][0-9]{0,8}|0))|&#x27;
         + &#x27;(1:((([0-9]|[1-9][0-9]|1[0-9]{2}|2[0-4][0-9]|&#x27;
         +     &#x27;25[0-5])\.){3}([0-9]|[1-9][0-9]|&#x27;
         +     &#x27;1[0-9]{2}|2[0-4][0-9]|25[0-5])):(6553[0-5]|&#x27;
         +     &#x27;655[0-2][0-9]|&#x27;
         +     &#x27;65[0-4][0-9]{2}|6[0-4][0-9]{3}|&#x27;
         +     &#x27;[1-5][0-9]{4}|[1-9][0-9]{0,3}|0))|&#x27;
         + &#x27;(2:(429496729[0-5]|42949672[0-8][0-9]|&#x27;
         +     &#x27;4294967[01][0-9]{2}|&#x27;
         +     &#x27;429496[0-6][0-9]{3}|42949[0-5][0-9]{4}|&#x27;
         +     &#x27;4294[0-8][0-9]{5}|&#x27;
         +     &#x27;429[0-3][0-9]{6}|42[0-8][0-9]{7}|4[01][0-9]{8}|&#x27;
         +     &#x27;[1-3][0-9]{9}|[1-9][0-9]{0,8}|0):&#x27;
         +     &#x27;(6553[0-5]|655[0-2][0-9]|65[0-4][0-9]{2}|&#x27;
         +     &#x27;6[0-4][0-9]{3}|&#x27;
         +     &#x27;[1-5][0-9]{4}|[1-9][0-9]{0,3}|0))|&#x27;
         + &#x27;(6(:[a-fA-F0-9]{2}){6})|&#x27;
         + &#x27;(([3-57-9a-fA-F]|[1-9a-fA-F][0-9a-fA-F]{1,3}):&#x27;
         +     &#x27;[0-9a-fA-F]{1,12})&#x27;;
       }

<span class="grey"><a href="/doc/html/rfc8294">RFC 8294</a>                 Routing Area YANG Types           December 2017</span>

       description
         &quot;A Route Target is an 8-octet BGP extended community
          initially identifying a set of sites in a BGP VPN
          (<a href="/doc/html/rfc4364">RFC 4364</a>).  However, it has since taken on a more general
          role in BGP route filtering.  A Route Target consists of two
          or three fields: a 2-octet Type field, an administrator
          field, and, optionally, an assigned number field.

          According to the data formats for types 0, 1, 2, and 6 as
          defined in <a href="/doc/html/rfc4360">RFC 4360</a>, <a href="/doc/html/rfc5668">RFC 5668</a>, and <a href="/doc/html/rfc7432">RFC 7432</a>, the encoding
          pattern is defined as:

          0:2-octet-asn:4-octet-number
          1:4-octet-ipv4addr:2-octet-number
          2:4-octet-asn:2-octet-number
          6:6-octet-mac-address

          Additionally, a generic pattern is defined for future
          Route Target types:

          2-octet-other-hex-number:6-octet-hex-number

          Some valid examples are 0:100:100, 1:1.1.1.1:100,
          2:1234567890:203, and 6:26:00:08:92:78:00.&quot;;
       reference
         &quot;<a href="/doc/html/rfc4360">RFC 4360</a>: BGP Extended Communities Attribute.
          <a href="/doc/html/rfc4364">RFC 4364</a>: BGP/MPLS IP Virtual Private Networks (VPNs).
          <a href="/doc/html/rfc5668">RFC 5668</a>: 4-Octet AS Specific BGP Extended Community.
          <a href="/doc/html/rfc7432">RFC 7432</a>: BGP MPLS-Based Ethernet VPN.&quot;;
     }

<span class="grey"><a href="/doc/html/rfc8294">RFC 8294</a>                 Routing Area YANG Types           December 2017</span>

     typedef ipv6-route-target {
       type string {
         pattern
             &#x27;((:|[0-9a-fA-F]{0,4}):)([0-9a-fA-F]{0,4}:){0,5}&#x27;
             + &#x27;((([0-9a-fA-F]{0,4}:)?(:|[0-9a-fA-F]{0,4}))|&#x27;
             + &#x27;(((25[0-5]|2[0-4][0-9]|1[0-9]{2}|[1-9]?[0-9])\.){3}&#x27;
             + &#x27;(25[0-5]|2[0-4][0-9]|1[0-9]{2}|[1-9]?[0-9])))&#x27;
             + &#x27;:&#x27;
             + &#x27;(6553[0-5]|655[0-2][0-9]|65[0-4][0-9]{2}|&#x27;
             + &#x27;6[0-4][0-9]{3}|&#x27;
             + &#x27;[1-5][0-9]{4}|[1-9][0-9]{0,3}|0)&#x27;;
         pattern &#x27;((([^:]+:){6}(([^:]+:[^:]+)|(.*\..*)))|&#x27;
             + &#x27;((([^:]+:)*[^:]+)?::(([^:]+:)*[^:]+)?))&#x27;
             + &#x27;:&#x27;
             + &#x27;(6553[0-5]|655[0-2][0-9]|65[0-4][0-9]{2}|&#x27;
             + &#x27;6[0-4][0-9]{3}|&#x27;
             + &#x27;[1-5][0-9]{4}|[1-9][0-9]{0,3}|0)&#x27;;
       }
       description
         &quot;An IPv6 Route Target is a 20-octet BGP IPv6 Address
          Specific Extended Community serving the same function
          as a standard 8-octet Route Target, except that it only
          allows an IPv6 address as the global administrator.
          The format is &lt;ipv6-address:2-octet-number&gt;.

          Two valid examples are 2001:db8::1:6544 and
          2001:db8::5eb1:791:6b37:17958.&quot;;
       reference
         &quot;<a href="/doc/html/rfc5701">RFC 5701</a>: IPv6 Address Specific BGP Extended Community
          Attribute.&quot;;
     }

     typedef route-target-type {
       type enumeration {
         enum import {
           value 0;
           description
             &quot;The Route Target applies to route import.&quot;;
         }
         enum export {
           value 1;
           description
             &quot;The Route Target applies to route export.&quot;;
         }

<span class="grey"><a href="/doc/html/rfc8294">RFC 8294</a>                 Routing Area YANG Types           December 2017</span>

         enum both {
           value 2;
           description
             &quot;The Route Target applies to both route import and
              route export.&quot;;
         }
       }
       description
         &quot;Indicates the role a Route Target takes in route filtering.&quot;;
       reference
         &quot;<a href="/doc/html/rfc4364">RFC 4364</a>: BGP/MPLS IP Virtual Private Networks (VPNs).&quot;;
     }

     typedef route-distinguisher {
       type string {
         pattern
           &#x27;(0:(6553[0-5]|655[0-2][0-9]|65[0-4][0-9]{2}|&#x27;
         +     &#x27;6[0-4][0-9]{3}|&#x27;
         +     &#x27;[1-5][0-9]{4}|[1-9][0-9]{0,3}|0):(429496729[0-5]|&#x27;
         +     &#x27;42949672[0-8][0-9]|&#x27;
         +     &#x27;4294967[01][0-9]{2}|429496[0-6][0-9]{3}|&#x27;
         +     &#x27;42949[0-5][0-9]{4}|&#x27;
         +     &#x27;4294[0-8][0-9]{5}|429[0-3][0-9]{6}|&#x27;
         +     &#x27;42[0-8][0-9]{7}|4[01][0-9]{8}|&#x27;
         +     &#x27;[1-3][0-9]{9}|[1-9][0-9]{0,8}|0))|&#x27;
         + &#x27;(1:((([0-9]|[1-9][0-9]|1[0-9]{2}|2[0-4][0-9]|&#x27;
         +     &#x27;25[0-5])\.){3}([0-9]|[1-9][0-9]|&#x27;
         +     &#x27;1[0-9]{2}|2[0-4][0-9]|25[0-5])):(6553[0-5]|&#x27;
         +     &#x27;655[0-2][0-9]|&#x27;
         +     &#x27;65[0-4][0-9]{2}|6[0-4][0-9]{3}|&#x27;
         +     &#x27;[1-5][0-9]{4}|[1-9][0-9]{0,3}|0))|&#x27;
         + &#x27;(2:(429496729[0-5]|42949672[0-8][0-9]|&#x27;
         +     &#x27;4294967[01][0-9]{2}|&#x27;
         +     &#x27;429496[0-6][0-9]{3}|42949[0-5][0-9]{4}|&#x27;
         +     &#x27;4294[0-8][0-9]{5}|&#x27;
         +     &#x27;429[0-3][0-9]{6}|42[0-8][0-9]{7}|4[01][0-9]{8}|&#x27;
         +     &#x27;[1-3][0-9]{9}|[1-9][0-9]{0,8}|0):&#x27;
         +     &#x27;(6553[0-5]|655[0-2][0-9]|65[0-4][0-9]{2}|&#x27;
         +     &#x27;6[0-4][0-9]{3}|&#x27;
         +     &#x27;[1-5][0-9]{4}|[1-9][0-9]{0,3}|0))|&#x27;
         + &#x27;(6(:[a-fA-F0-9]{2}){6})|&#x27;
         + &#x27;(([3-57-9a-fA-F]|[1-9a-fA-F][0-9a-fA-F]{1,3}):&#x27;
         +     &#x27;[0-9a-fA-F]{1,12})&#x27;;
       }

<span class="grey"><a href="/doc/html/rfc8294">RFC 8294</a>                 Routing Area YANG Types           December 2017</span>

       description
         &quot;A Route Distinguisher is an 8-octet value used to
          distinguish routes from different BGP VPNs (<a href="/doc/html/rfc4364">RFC 4364</a>).
          A Route Distinguisher will have the same format as a
          Route Target as per <a href="/doc/html/rfc4360">RFC 4360</a> and will consist of
          two or three fields: a 2-octet Type field, an administrator
          field, and, optionally, an assigned number field.

          According to the data formats for types 0, 1, 2, and 6 as
          defined in <a href="/doc/html/rfc4360">RFC 4360</a>, <a href="/doc/html/rfc5668">RFC 5668</a>, and <a href="/doc/html/rfc7432">RFC 7432</a>, the encoding
          pattern is defined as:

          0:2-octet-asn:4-octet-number
          1:4-octet-ipv4addr:2-octet-number
          2:4-octet-asn:2-octet-number
          6:6-octet-mac-address

          Additionally, a generic pattern is defined for future
          route discriminator types:

          2-octet-other-hex-number:6-octet-hex-number

          Some valid examples are 0:100:100, 1:1.1.1.1:100,
          2:1234567890:203, and 6:26:00:08:92:78:00.&quot;;
       reference
         &quot;<a href="/doc/html/rfc4360">RFC 4360</a>: BGP Extended Communities Attribute.
          <a href="/doc/html/rfc4364">RFC 4364</a>: BGP/MPLS IP Virtual Private Networks (VPNs).
          <a href="/doc/html/rfc5668">RFC 5668</a>: 4-Octet AS Specific BGP Extended Community.
          <a href="/doc/html/rfc7432">RFC 7432</a>: BGP MPLS-Based Ethernet VPN.&quot;;
     }

<span class="grey"><a href="/doc/html/rfc8294">RFC 8294</a>                 Routing Area YANG Types           December 2017</span>

     typedef route-origin {
       type string {
         pattern
           &#x27;(0:(6553[0-5]|655[0-2][0-9]|65[0-4][0-9]{2}|&#x27;
         +     &#x27;6[0-4][0-9]{3}|&#x27;
         +     &#x27;[1-5][0-9]{4}|[1-9][0-9]{0,3}|0):(429496729[0-5]|&#x27;
         +     &#x27;42949672[0-8][0-9]|&#x27;
         +     &#x27;4294967[01][0-9]{2}|429496[0-6][0-9]{3}|&#x27;
         +     &#x27;42949[0-5][0-9]{4}|&#x27;
         +     &#x27;4294[0-8][0-9]{5}|429[0-3][0-9]{6}|&#x27;
         +     &#x27;42[0-8][0-9]{7}|4[01][0-9]{8}|&#x27;
         +     &#x27;[1-3][0-9]{9}|[1-9][0-9]{0,8}|0))|&#x27;
         + &#x27;(1:((([0-9]|[1-9][0-9]|1[0-9]{2}|2[0-4][0-9]|&#x27;
         +     &#x27;25[0-5])\.){3}([0-9]|[1-9][0-9]|&#x27;
         +     &#x27;1[0-9]{2}|2[0-4][0-9]|25[0-5])):(6553[0-5]|&#x27;
         +     &#x27;655[0-2][0-9]|&#x27;
         +     &#x27;65[0-4][0-9]{2}|6[0-4][0-9]{3}|&#x27;
         +     &#x27;[1-5][0-9]{4}|[1-9][0-9]{0,3}|0))|&#x27;
         + &#x27;(2:(429496729[0-5]|42949672[0-8][0-9]|&#x27;
         +     &#x27;4294967[01][0-9]{2}|&#x27;
         +     &#x27;429496[0-6][0-9]{3}|42949[0-5][0-9]{4}|&#x27;
         +     &#x27;4294[0-8][0-9]{5}|&#x27;
         +     &#x27;429[0-3][0-9]{6}|42[0-8][0-9]{7}|4[01][0-9]{8}|&#x27;
         +     &#x27;[1-3][0-9]{9}|[1-9][0-9]{0,8}|0):&#x27;
         +     &#x27;(6553[0-5]|655[0-2][0-9]|65[0-4][0-9]{2}|&#x27;
         +     &#x27;6[0-4][0-9]{3}|&#x27;
         +     &#x27;[1-5][0-9]{4}|[1-9][0-9]{0,3}|0))|&#x27;
         + &#x27;(6(:[a-fA-F0-9]{2}){6})|&#x27;
         + &#x27;(([3-57-9a-fA-F]|[1-9a-fA-F][0-9a-fA-F]{1,3}):&#x27;
         +    &#x27;[0-9a-fA-F]{1,12})&#x27;;
       }
       description
         &quot;A Route Origin is an 8-octet BGP extended community
          identifying the set of sites where the BGP route
          originated (<a href="/doc/html/rfc4364">RFC 4364</a>).  A Route Origin will have the same
          format as a Route Target as per <a href="/doc/html/rfc4360">RFC 4360</a> and will consist
          of two or three fields: a 2-octet Type field, an
          administrator field, and, optionally, an assigned number
          field.

          According to the data formats for types 0, 1, 2, and 6 as
          defined in <a href="/doc/html/rfc4360">RFC 4360</a>, <a href="/doc/html/rfc5668">RFC 5668</a>, and <a href="/doc/html/rfc7432">RFC 7432</a>, the encoding
          pattern is defined as:

          0:2-octet-asn:4-octet-number
          1:4-octet-ipv4addr:2-octet-number
          2:4-octet-asn:2-octet-number
          6:6-octet-mac-address
<span class="grey"><a href="/doc/html/rfc8294">RFC 8294</a>                 Routing Area YANG Types           December 2017</span>

          Additionally, a generic pattern is defined for future
          Route Origin types:

          2-octet-other-hex-number:6-octet-hex-number

          Some valid examples are 0:100:100, 1:1.1.1.1:100,
          2:1234567890:203, and 6:26:00:08:92:78:00.&quot;;
       reference
         &quot;<a href="/doc/html/rfc4360">RFC 4360</a>: BGP Extended Communities Attribute.
          <a href="/doc/html/rfc4364">RFC 4364</a>: BGP/MPLS IP Virtual Private Networks (VPNs).
          <a href="/doc/html/rfc5668">RFC 5668</a>: 4-Octet AS Specific BGP Extended Community.
          <a href="/doc/html/rfc7432">RFC 7432</a>: BGP MPLS-Based Ethernet VPN.&quot;;
     }

     typedef ipv6-route-origin {
       type string {
         pattern
             &#x27;((:|[0-9a-fA-F]{0,4}):)([0-9a-fA-F]{0,4}:){0,5}&#x27;
             + &#x27;((([0-9a-fA-F]{0,4}:)?(:|[0-9a-fA-F]{0,4}))|&#x27;
             + &#x27;(((25[0-5]|2[0-4][0-9]|1[0-9]{2}|[1-9]?[0-9])\.){3}&#x27;
             + &#x27;(25[0-5]|2[0-4][0-9]|1[0-9]{2}|[1-9]?[0-9])))&#x27;
             + &#x27;:&#x27;
             + &#x27;(6553[0-5]|655[0-2][0-9]|65[0-4][0-9]{2}|&#x27;
             + &#x27;6[0-4][0-9]{3}|&#x27;
             + &#x27;[1-5][0-9]{4}|[1-9][0-9]{0,3}|0)&#x27;;
         pattern &#x27;((([^:]+:){6}(([^:]+:[^:]+)|(.*\..*)))|&#x27;
             + &#x27;((([^:]+:)*[^:]+)?::(([^:]+:)*[^:]+)?))&#x27;
             + &#x27;:&#x27;
             + &#x27;(6553[0-5]|655[0-2][0-9]|65[0-4][0-9]{2}|&#x27;
             + &#x27;6[0-4][0-9]{3}|&#x27;
             + &#x27;[1-5][0-9]{4}|[1-9][0-9]{0,3}|0)&#x27;;
       }
       description
         &quot;An IPv6 Route Origin is a 20-octet BGP IPv6 Address
          Specific Extended Community serving the same function
          as a standard 8-octet route, except that it only allows
          an IPv6 address as the global administrator.  The format
          is &lt;ipv6-address:2-octet-number&gt;.

          Two valid examples are 2001:db8::1:6544 and
          2001:db8::5eb1:791:6b37:17958.&quot;;
       reference
         &quot;<a href="/doc/html/rfc5701">RFC 5701</a>: IPv6 Address Specific BGP Extended Community
          Attribute.&quot;;
     }

<span class="grey"><a href="/doc/html/rfc8294">RFC 8294</a>                 Routing Area YANG Types           December 2017</span>

     /*** Collection of types common to multicast ***/

     typedef ipv4-multicast-group-address {
       type inet:ipv4-address {
         pattern &#x27;(2((2[4-9])|(3[0-9]))\.).*&#x27;;
       }
       description
         &quot;This type represents an IPv4 multicast group address,
          which is in the range of 224.0.0.0 to 239.255.255.255.&quot;;
       reference
         &quot;<a href="/doc/html/rfc1112">RFC 1112</a>: Host Extensions for IP Multicasting.&quot;;
     }

     typedef ipv6-multicast-group-address {
       type inet:ipv6-address {
         pattern &#x27;(([fF]{2}[0-9a-fA-F]{2}):).*&#x27;;
       }
       description
         &quot;This type represents an IPv6 multicast group address,
          which is in the range of ff00::/8.&quot;;
       reference
         &quot;<a href="/doc/html/rfc4291">RFC 4291</a>: IP Version 6 Addressing Architecture.  <a href="#section-2.7">Section 2.7</a>.
          <a href="/doc/html/rfc7346">RFC 7346</a>: IPv6 Multicast Address Scopes.&quot;;
     }

     typedef ip-multicast-group-address {
       type union {
         type ipv4-multicast-group-address;
         type ipv6-multicast-group-address;
       }
       description
         &quot;This type represents a version-neutral IP multicast group
          address.  The format of the textual representation implies
          the IP version.&quot;;
     }

<span class="grey"><a href="/doc/html/rfc8294">RFC 8294</a>                 Routing Area YANG Types           December 2017</span>

     typedef ipv4-multicast-source-address {
       type union {
         type enumeration {
           enum * {
             description
               &quot;Any source address.&quot;;
           }
         }
         type inet:ipv4-address;
       }
       description
         &quot;Multicast source IPv4 address type.&quot;;
     }

     typedef ipv6-multicast-source-address {
       type union {
         type enumeration {
           enum * {
             description
               &quot;Any source address.&quot;;
           }
         }
         type inet:ipv6-address;
       }
       description
         &quot;Multicast source IPv6 address type.&quot;;
     }

     /*** Collection of types common to protocols ***/

     typedef bandwidth-ieee-float32 {
       type string {
         pattern
           &#x27;0[xX](0((\.0?)?[pP](\+)?0?|(\.0?))|&#x27;
         + &#x27;1(\.([0-9a-fA-F]{0,5}[02468aAcCeE]?)?)?[pP](\+)?(12[0-7]|&#x27;
         + &#x27;1[01][0-9]|0?[0-9]?[0-9])?)&#x27;;
       }
       description
         &quot;Bandwidth in IEEE 754 floating-point 32-bit binary format:
          (-1)**(S) * 2**(Exponent-127) * (1 + Fraction),
          where Exponent uses 8 bits and Fraction uses 23 bits.
          The units are octets per second.
          The encoding format is the external hexadecimal-significant
          character sequences specified in IEEE 754 and ISO/IEC C99.
          The format is restricted to be normalized, non-negative, and
          non-fraction: 0x1.hhhhhhp{+}d, 0X1.HHHHHHP{+}D, or 0x0p0,
          where &#x27;h&#x27; and &#x27;H&#x27; are hexadecimal digits and &#x27;d&#x27; and &#x27;D&#x27; are
          integers in the range of [0..127].
<span class="grey"><a href="/doc/html/rfc8294">RFC 8294</a>                 Routing Area YANG Types           December 2017</span>

          When six hexadecimal digits are used for &#x27;hhhhhh&#x27; or
          &#x27;HHHHHH&#x27;, the least significant digit must be an even
          number.  &#x27;x&#x27; and &#x27;X&#x27; indicate hexadecimal; &#x27;p&#x27; and &#x27;P&#x27;
          indicate a power of two.  Some examples are 0x0p0, 0x1p10,
          and 0x1.abcde2p+20.&quot;;
       reference
         &quot;IEEE Std 754-2008: IEEE Standard for Floating-Point
          Arithmetic.
          ISO/IEC C99: Information technology - Programming
          Languages - C.&quot;;
     }

     typedef link-access-type {
       type enumeration {
         enum broadcast {
           description
             &quot;Specify broadcast multi-access network.&quot;;
         }
         enum non-broadcast-multiaccess {
           description
             &quot;Specify Non-Broadcast Multi-Access (NBMA) network.&quot;;
         }
         enum point-to-multipoint {
           description
             &quot;Specify point-to-multipoint network.&quot;;
         }
         enum point-to-point {
           description
             &quot;Specify point-to-point network.&quot;;
         }
       }
       description
         &quot;Link access type.&quot;;
     }

     typedef timer-multiplier {
       type uint8;
       description
         &quot;The number of timer value intervals that should be
          interpreted as a failure.&quot;;
     }

<span class="grey"><a href="/doc/html/rfc8294">RFC 8294</a>                 Routing Area YANG Types           December 2017</span>

     typedef timer-value-seconds16 {
       type union {
         type uint16 {
           range &quot;1..65535&quot;;
         }
         type enumeration {
           enum infinity {
             description
               &quot;The timer is set to infinity.&quot;;
           }
           enum not-set {
             description
               &quot;The timer is not set.&quot;;
           }
         }
       }
       units &quot;seconds&quot;;
       description
         &quot;Timer value type, in seconds (16-bit range).&quot;;
     }

     typedef timer-value-seconds32 {
       type union {
         type uint32 {
           range &quot;1..4294967295&quot;;
         }
         type enumeration {
           enum infinity {
             description
               &quot;The timer is set to infinity.&quot;;
           }
           enum not-set {
             description
               &quot;The timer is not set.&quot;;
           }
         }
       }
       units &quot;seconds&quot;;
       description
         &quot;Timer value type, in seconds (32-bit range).&quot;;
     }

<span class="grey"><a href="/doc/html/rfc8294">RFC 8294</a>                 Routing Area YANG Types           December 2017</span>

     typedef timer-value-milliseconds {
       type union {
         type uint32 {
           range &quot;1..4294967295&quot;;
         }
         type enumeration {
           enum infinity {
             description
               &quot;The timer is set to infinity.&quot;;
           }
           enum not-set {
             description
               &quot;The timer is not set.&quot;;
           }
         }
       }
       units &quot;milliseconds&quot;;
       description
         &quot;Timer value type, in milliseconds.&quot;;
     }

     typedef percentage {
       type uint8 {
         range &quot;0..100&quot;;
       }
       description
         &quot;Integer indicating a percentage value.&quot;;
     }

     typedef timeticks64 {
       type uint64;
       description
         &quot;This type is based on the timeticks type defined in
          <a href="/doc/html/rfc6991">RFC 6991</a>, but with 64-bit width.  It represents the time,
          modulo 2^64, in hundredths of a second between two epochs.&quot;;
       reference
         &quot;<a href="/doc/html/rfc6991">RFC 6991</a>: Common YANG Data Types.&quot;;
     }

     typedef uint24 {
       type uint32 {
         range &quot;0..16777215&quot;;
       }
       description
         &quot;24-bit unsigned integer.&quot;;
     }

<span class="grey"><a href="/doc/html/rfc8294">RFC 8294</a>                 Routing Area YANG Types           December 2017</span>

     /*** Collection of types related to MPLS/GMPLS ***/

     typedef generalized-label {
       type binary;
       description
         &quot;Generalized Label.  Nodes sending and receiving the
          Generalized Label are aware of the link-specific
          label context and type.&quot;;
       reference
         &quot;<a href="/doc/html/rfc3471">RFC 3471</a>: Generalized Multi-Protocol Label Switching (GMPLS)
          Signaling Functional Description.  <a href="#section-3.2">Section 3.2</a>.&quot;;
     }

     typedef mpls-label-special-purpose {
       type identityref {
         base mpls-label-special-purpose-value;
       }
       description
         &quot;This type represents the special-purpose MPLS label values.&quot;;
       reference
         &quot;<a href="/doc/html/rfc3032">RFC 3032</a>: MPLS Label Stack Encoding.
          <a href="/doc/html/rfc7274">RFC 7274</a>: Allocating and Retiring Special-Purpose MPLS
          Labels.&quot;;
     }

     typedef mpls-label-general-use {
       type uint32 {
         range &quot;16..1048575&quot;;
       }
       description
         &quot;The 20-bit label value in an MPLS label stack as specified
          in <a href="/doc/html/rfc3032">RFC 3032</a>.  This label value does not include the
          encodings of Traffic Class and TTL (Time to Live).
          The label range specified by this type is for general use,
          with special-purpose MPLS label values excluded.&quot;;
       reference
         &quot;<a href="/doc/html/rfc3032">RFC 3032</a>: MPLS Label Stack Encoding.&quot;;
     }

<span class="grey"><a href="/doc/html/rfc8294">RFC 8294</a>                 Routing Area YANG Types           December 2017</span>

     typedef mpls-label {
       type union {
         type mpls-label-special-purpose;
         type mpls-label-general-use;
       }
       description
         &quot;The 20-bit label value in an MPLS label stack as specified
          in <a href="/doc/html/rfc3032">RFC 3032</a>.  This label value does not include the
          encodings of Traffic Class and TTL.&quot;;
       reference
         &quot;<a href="/doc/html/rfc3032">RFC 3032</a>: MPLS Label Stack Encoding.&quot;;
     }

     /*** Groupings **/

     grouping mpls-label-stack {
       description
         &quot;This grouping specifies an MPLS label stack.  The label
          stack is encoded as a list of label stack entries.  The
          list key is an identifier that indicates the relative
          ordering of each entry, with the lowest-value identifier
          corresponding to the top of the label stack.&quot;;
       container mpls-label-stack {
         description
           &quot;Container for a list of MPLS label stack entries.&quot;;
         list entry {
           key &quot;id&quot;;
           description
             &quot;List of MPLS label stack entries.&quot;;
           leaf id {
             type uint8;
             description
               &quot;Identifies the entry in a sequence of MPLS label
                stack entries.  An entry with a smaller identifier
                value precedes an entry with a larger identifier
                value in the label stack.  The value of this ID has
                no semantic meaning other than relative ordering
                and referencing the entry.&quot;;
           }
           leaf label {
             type rt-types:mpls-label;
             description
               &quot;Label value.&quot;;
           }

<span class="grey"><a href="/doc/html/rfc8294">RFC 8294</a>                 Routing Area YANG Types           December 2017</span>

           leaf ttl {
             type uint8;
             description
               &quot;Time to Live (TTL).&quot;;
             reference
               &quot;<a href="/doc/html/rfc3032">RFC 3032</a>: MPLS Label Stack Encoding.&quot;;
           }
           leaf traffic-class {
             type uint8 {
               range &quot;0..7&quot;;
             }
             description
               &quot;Traffic Class (TC).&quot;;
             reference
               &quot;<a href="/doc/html/rfc5462">RFC 5462</a>: Multiprotocol Label Switching (MPLS) Label
                Stack Entry: &#x27;EXP&#x27; Field Renamed to &#x27;Traffic Class&#x27;
                Field.&quot;;
           }
         }
       }
     }

<span class="grey"><a href="/doc/html/rfc8294">RFC 8294</a>                 Routing Area YANG Types           December 2017</span>

     grouping vpn-route-targets {
       description
         &quot;A grouping that specifies Route Target import-export rules
          used in BGP-enabled VPNs.&quot;;
       reference
         &quot;<a href="/doc/html/rfc4364">RFC 4364</a>: BGP/MPLS IP Virtual Private Networks (VPNs).
          <a href="/doc/html/rfc4664">RFC 4664</a>: Framework for Layer 2 Virtual Private Networks
          (L2VPNs).&quot;;
       list vpn-target {
         key &quot;route-target&quot;;
         description
           &quot;List of Route Targets.&quot;;
         leaf route-target {
           type rt-types:route-target;
           description
             &quot;Route Target value.&quot;;
         }
         leaf route-target-type {
           type rt-types:route-target-type;
           mandatory true;
           description
             &quot;Import/export type of the Route Target.&quot;;
         }
       }
     }
   }
