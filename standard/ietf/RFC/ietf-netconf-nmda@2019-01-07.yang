module ietf-netconf-nmda {
  yang-version 1.1;
  namespace &quot;urn:ietf:params:xml:ns:yang:ietf-netconf-nmda&quot;;
  prefix ncds;

  import ietf-yang-types {
    prefix yang;
    reference
      &quot;<a href="/doc/html/rfc6991">RFC 6991</a>: Common YANG Data Types&quot;;
  }
  import ietf-inet-types {
    prefix inet;
    reference
      &quot;<a href="/doc/html/rfc6991">RFC 6991</a>: Common YANG Data Types&quot;;
  }
  import ietf-datastores {
    prefix ds;
    reference
      &quot;<a href="/doc/html/rfc8342">RFC 8342</a>: Network Management Datastore Architecture
                 (NMDA)&quot;;
  }
  import ietf-origin {
    prefix or;
    reference
      &quot;<a href="/doc/html/rfc8342">RFC 8342</a>: Network Management Datastore Architecture
                 (NMDA)&quot;;
  }
  import ietf-netconf {
    prefix nc;
    reference
      &quot;<a href="/doc/html/rfc6241">RFC 6241</a>: Network Configuration Protocol (NETCONF)&quot;;
  }
  import ietf-netconf-with-defaults {
    prefix ncwd;
    reference
      &quot;<a href="/doc/html/rfc6243">RFC 6243</a>: With-defaults Capability for NETCONF&quot;;
  }

  organization
    &quot;IETF NETCONF Working Group&quot;;

<span class="grey"><a href="/doc/html/rfc8526">RFC 8526</a>             NETCONF Extensions for the NMDA          March 2019</span>

     contact
       &quot;WG Web:   &lt;<a href="https://datatracker.ietf.org/wg/netconf/">https://datatracker.ietf.org/wg/netconf/</a>&gt;

        WG List:  &lt;mailto:<a href="mailto:netconf@ietf.org">netconf@ietf.org</a>&gt;

        Author:   Martin Bjorklund
                  &lt;mailto:<a href="mailto:mbj@tail-f.com">mbj@tail-f.com</a>&gt;

        Author:   Juergen Schoenwaelder
                  &lt;mailto:<a href="mailto:j.schoenwaelder@jacobs-university.de">j.schoenwaelder@jacobs-university.de</a>&gt;

        Author:   Phil Shafer
                  &lt;mailto:<a href="mailto:phil@juniper.net">phil@juniper.net</a>&gt;

        Author:   Kent Watsen
                  &lt;mailto:<a href="mailto:kent%2Bietf@watsen.net">kent+ietf@watsen.net</a>&gt;

        Author:   Robert Wilton
                  &lt;mailto:<a href="mailto:rwilton@cisco.com">rwilton@cisco.com</a>&gt;&quot;;
     description
       &quot;This YANG module defines a set of NETCONF operations to support
        the Network Management Datastore Architecture (NMDA).

        The key words &#x27;MUST&#x27;, &#x27;MUST NOT&#x27;, &#x27;REQUIRED&#x27;, &#x27;SHALL&#x27;, &#x27;SHALL
        NOT&#x27;, &#x27;SHOULD&#x27;, &#x27;SHOULD NOT&#x27;, &#x27;RECOMMENDED&#x27;, &#x27;NOT RECOMMENDED&#x27;,
        &#x27;MAY&#x27;, and &#x27;OPTIONAL&#x27; in this document are to be interpreted as
        described in <a href="/doc/html/bcp14">BCP 14</a> (<a href="/doc/html/rfc2119">RFC 2119</a>) (<a href="/doc/html/rfc8174">RFC 8174</a>) when, and only when,
        they appear in all capitals, as shown here.

        Copyright (c) 2019 IETF Trust and the persons identified as
        authors of the code.  All rights reserved.

        Redistribution and use in source and binary forms, with or
        without modification, is permitted pursuant to, and subject to
        the license terms contained in, the Simplified BSD License set
        forth in <a href="#section-4">Section 4</a>.c of the IETF Trust&#x27;s Legal Provisions
        Relating to IETF Documents
        (<a href="https://trustee.ietf.org/license-info">https://trustee.ietf.org/license-info</a>).

        This version of this YANG module is part of <a href="/doc/html/rfc8526">RFC 8526</a>; see
        the RFC itself for full legal notices.&quot;;

     revision 2019-01-07 {
       description
         &quot;Initial revision.&quot;;
       reference
         &quot;<a href="/doc/html/rfc8526">RFC 8526</a>: NETCONF Extensions to Support the Network Management
                    Datastore Architecture&quot;;
<span class="grey"><a href="/doc/html/rfc8526">RFC 8526</a>             NETCONF Extensions for the NMDA          March 2019</span>

     }

     feature origin {
       description
         &quot;Indicates that the server supports the &#x27;origin&#x27; annotation.&quot;;
       reference
         &quot;<a href="/doc/html/rfc8342">RFC 8342</a>: Network Management Datastore Architecture (NMDA)&quot;;
     }

     feature with-defaults {
       description
         &quot;NETCONF :with-defaults capability.  If the server advertises
          the :with-defaults capability for a session, then this
          feature must also be enabled for that session.  Otherwise,
          this feature must not be enabled.&quot;;
       reference
         &quot;<a href="/doc/html/rfc6243">RFC 6243</a>: With-defaults Capability for NETCONF, <a href="#section-4">Section 4</a>; and
          <a href="/doc/html/rfc8526">RFC 8526</a>: NETCONF Extensions to Support the Network Management
                    Datastore Architecture, <a href="#section-3.1.1.2">Section 3.1.1.2</a>&quot;;
     }

     rpc get-data {
       description
         &quot;Retrieve data from an NMDA datastore.  The content returned
          by get-data must satisfy all filters, i.e., the filter
          criteria are logically ANDed.

          Any ancestor nodes (including list keys) of nodes selected by
          the filters are included in the response.

          The &#x27;with-origin&#x27; parameter is only valid for an operational
          datastore.  If &#x27;with-origin&#x27; is used with an invalid
          datastore, then the server MUST return an &lt;rpc-error&gt; element
          with an &lt;error-tag&gt; value of &#x27;invalid-value&#x27;.

          The &#x27;with-defaults&#x27; parameter only applies to the operational
          datastore if the NETCONF :with-defaults and
          :with-operational-defaults capabilities are both advertised.
          If the &#x27;with-defaults&#x27; parameter is present in a request for
          which it is not supported, then the server MUST return an
          &lt;rpc-error&gt; element with an &lt;error-tag&gt; value of
          &#x27;invalid-value&#x27;.&quot;;
       input {
         leaf datastore {
           type ds:datastore-ref;
           mandatory true;

<span class="grey"><a href="/doc/html/rfc8526">RFC 8526</a>             NETCONF Extensions for the NMDA          March 2019</span>

           description
             &quot;Datastore from which to retrieve data.

              If the datastore is not supported by the server, then the
              server MUST return an &lt;rpc-error&gt; element with an
              &lt;error-tag&gt; value of &#x27;invalid-value&#x27;.&quot;;
         }
         choice filter-spec {
           description
             &quot;The content filter specification for this request.&quot;;
           anydata subtree-filter {
             description
               &quot;This parameter identifies the portions of the
                target datastore to retrieve.&quot;;
             reference
               &quot;<a href="/doc/html/rfc6241">RFC 6241</a>: Network Configuration Protocol (NETCONF),
                          <a href="#section-6">Section 6</a>&quot;;
           }
           leaf xpath-filter {
             if-feature &quot;nc:xpath&quot;;
             type yang:xpath1.0;
             description
               &quot;This parameter contains an XPath expression identifying
                the portions of the target datastore to retrieve.

                If the expression returns a node-set, all nodes in the
                node-set are selected by the filter.  Otherwise, if the
                expression does not return a node-set, then the
                &lt;get-data&gt; operation fails.

                The expression is evaluated in the following XPath
                context:

                  o  The set of namespace declarations are those in
                     scope on the &#x27;xpath-filter&#x27; leaf element.

                  o  The set of variable bindings is empty.

                  o  The function library is the core function library,
                     and the XPath functions are defined in <a href="/doc/html/rfc7950#section-10">Section&amp;nbsp;10
                     of RFC 7950</a>.

                  o  The context node is the root node of the target
                     datastore.&quot;;
           }
         }
         leaf config-filter {
           type boolean;
<span class="grey"><a href="/doc/html/rfc8526">RFC 8526</a>             NETCONF Extensions for the NMDA          March 2019</span>

           description
             &quot;Filter for nodes with the given value for their &#x27;config&#x27;
              property.  When this leaf is set to &#x27;true&#x27;, only &#x27;config
              true&#x27; nodes are selected, and when set to &#x27;false&#x27;, only
              &#x27;config false&#x27; nodes are selected.  If this leaf is not
              present, no nodes are filtered.&quot;;
         }
         choice origin-filters {
           when &#x27;derived-from-or-self(datastore, &quot;ds:operational&quot;)&#x27;;
           if-feature &quot;origin&quot;;
           description
             &quot;Filters configuration nodes based on the &#x27;origin&#x27;
              annotation.  Configuration nodes that do not have an
              &#x27;origin&#x27; annotation are treated as if they have the
              &#x27;origin&#x27; annotation &#x27;or:unknown&#x27;.

              System state nodes are not affected by origin-filters and
              thus not filtered.  Note that system state nodes can be
              filtered with the &#x27;config-filter&#x27; leaf.&quot;;

           leaf-list origin-filter {
             type or:origin-ref;
             description
               &quot;Filter based on the &#x27;origin&#x27; annotation.  A
                configuration node matches the filter if its &#x27;origin&#x27;
                annotation is derived from or equal to any of the given
                filter values.&quot;;
           }
           leaf-list negated-origin-filter {
             type or:origin-ref;
             description
               &quot;Filter based on the &#x27;origin&#x27; annotation.  A
                configuration node matches the filter if its &#x27;origin&#x27;
                annotation is neither derived from nor equal to any of
                the given filter values.&quot;;
           }
         }
         leaf max-depth {
           type union {
             type uint16 {
               range &quot;1..65535&quot;;
             }
             type enumeration {
               enum unbounded {
                 description
                   &quot;All descendant nodes are included.&quot;;
               }
             }
<span class="grey"><a href="/doc/html/rfc8526">RFC 8526</a>             NETCONF Extensions for the NMDA          March 2019</span>

           }
           default &quot;unbounded&quot;;
           description
             &quot;For each node selected by the filters, this parameter
              selects how many conceptual subtree levels should be
              returned in the reply.  If the depth is 1, the reply
              includes just the selected nodes but no children.  If the
              depth is &#x27;unbounded&#x27;, all descendant nodes are included.&quot;;
         }
         leaf with-origin {
           when &#x27;derived-from-or-self(../datastore, &quot;ds:operational&quot;)&#x27;;
           if-feature &quot;origin&quot;;
           type empty;
           description
             &quot;If this parameter is present, the server will return
              the &#x27;origin&#x27; annotation for the nodes that have one.&quot;;
         }
         uses ncwd:with-defaults-parameters {
           if-feature &quot;with-defaults&quot;;
         }
       }
       output {
         anydata data {
           description
             &quot;Copy of the source datastore subset that matched
              the filter criteria (if any).  An empty data
              container indicates that the request did not
              produce any results.&quot;;
         }
       }
     }

     rpc edit-data {
       description
         &quot;Edit data in an NMDA datastore.

          If an error condition occurs such that an error severity
          &lt;rpc-error&gt; element is generated, the server will stop
          processing the &lt;edit-data&gt; operation and restore the
          specified configuration to its complete state at
          the start of this &lt;edit-data&gt; operation.&quot;;
       input {
         leaf datastore {
           type ds:datastore-ref;
           mandatory true;

<span class="grey"><a href="/doc/html/rfc8526">RFC 8526</a>             NETCONF Extensions for the NMDA          March 2019</span>

           description
             &quot;Datastore that is the target of the &lt;edit-data&gt; operation.

              If the target datastore is not writable, or is not
              supported by the server, then the server MUST return an
              &lt;rpc-error&gt; element with an &lt;error-tag&gt; value of
              &#x27;invalid-value&#x27;.&quot;;
         }
         leaf default-operation {
           type enumeration {
             enum merge {
               description
                 &quot;The default operation is merge.&quot;;
             }
             enum replace {
               description
                 &quot;The default operation is replace.&quot;;
             }
             enum none {
               description
                 &quot;There is no default operation.&quot;;
             }
           }
           default &quot;merge&quot;;
           description
             &quot;The default operation to use.&quot;;
         }
         choice edit-content {
           mandatory true;
           description
             &quot;The content for the edit operation.&quot;;
           anydata config {
             description
               &quot;Inline config content.&quot;;
           }
           leaf url {
             if-feature &quot;nc:url&quot;;
             type inet:uri;
             description
               &quot;URL-based config content.&quot;;
           }
         }
       }
     }

     /*
      * Augment the &lt;lock&gt; and &lt;unlock&gt; operations with a
      * &quot;datastore&quot; parameter.
<span class="grey"><a href="/doc/html/rfc8526">RFC 8526</a>             NETCONF Extensions for the NMDA          March 2019</span>

      */

     augment &quot;/nc:lock/nc:input/nc:target/nc:config-target&quot; {
       description
         &quot;Add NMDA datastore as target.&quot;;
       leaf datastore {
         type ds:datastore-ref;
         description
           &quot;Datastore to lock.

            The &lt;lock&gt; operation is only supported on writable
            datastores.

            If the &lt;lock&gt; operation is not supported by the server on
            the specified target datastore, then the server MUST return
            an &lt;rpc-error&gt; element with an &lt;error-tag&gt; value of
            &#x27;invalid-value&#x27;.&quot;;
       }
     }

     augment &quot;/nc:unlock/nc:input/nc:target/nc:config-target&quot; {
       description
         &quot;Add NMDA datastore as target.&quot;;
       leaf datastore {
         type ds:datastore-ref;
         description
           &quot;Datastore to unlock.

            The &lt;unlock&gt; operation is only supported on writable
            datastores.

            If the &lt;unlock&gt; operation is not supported by the server on
            the specified target datastore, then the server MUST return
            an &lt;rpc-error&gt; element with an &lt;error-tag&gt; value of
            &#x27;invalid-value&#x27;.&quot;;
       }
     }

     /*
      * Augment the &lt;validate&gt; operation with a
      * &quot;datastore&quot; parameter.
      */

     augment &quot;/nc:validate/nc:input/nc:source/nc:config-source&quot; {
       description
         &quot;Add NMDA datastore as source.&quot;;
       leaf datastore {
         type ds:datastore-ref;
<span class="grey"><a href="/doc/html/rfc8526">RFC 8526</a>             NETCONF Extensions for the NMDA          March 2019</span>

         description
           &quot;Datastore to validate.

            The &lt;validate&gt; operation is supported only on configuration
            datastores.

            If the &lt;validate&gt; operation is not supported by the server
            on the specified target datastore, then the server MUST
            return an &lt;rpc-error&gt; element with an &lt;error-tag&gt; value of
            &#x27;invalid-value&#x27;.&quot;;
       }
     }
   }
