module ietf-voucher {
  yang-version 1.1;
  namespace &quot;urn:ietf:params:xml:ns:yang:ietf-voucher&quot;;
  prefix vch;

  import ietf-yang-types {
    prefix yang;
    reference &quot;<a href="/doc/html/rfc6991">RFC 6991</a>: Common YANG Data Types&quot;;
  }
  import ietf-restconf {
    prefix rc;
    description
      &quot;This import statement is only present to access
       the yang-data extension defined in <a href="/doc/html/rfc8040">RFC 8040</a>.&quot;;
    reference &quot;<a href="/doc/html/rfc8040">RFC 8040</a>: RESTCONF Protocol&quot;;
  }

  organization
    &quot;IETF ANIMA Working Group&quot;;
  contact
    &quot;WG Web:   &lt;<a href="https://datatracker.ietf.org/wg/anima/">https://datatracker.ietf.org/wg/anima/</a>&gt;
     WG List:  &lt;mailto:<a href="mailto:anima@ietf.org">anima@ietf.org</a>&gt;
     Author:   Kent Watsen
               &lt;mailto:<a href="mailto:kwatsen@juniper.net">kwatsen@juniper.net</a>&gt;
<span class="grey"><a href="/doc/html/rfc8366">RFC 8366</a>                     Voucher Profile                    May 2018</span>

     Author:   Max Pritikin
               &lt;mailto:<a href="mailto:pritikin@cisco.com">pritikin@cisco.com</a>&gt;
     Author:   Michael Richardson
               &lt;mailto:<a href="mailto:mcr%2Bietf@sandelman.ca">mcr+ietf@sandelman.ca</a>&gt;
     Author:   Toerless Eckert
               &lt;mailto:<a href="mailto:tte%2Bietf@cs.fau.de">tte+ietf@cs.fau.de</a>&gt;&quot;;
  description
    &quot;This module defines the format for a voucher, which is produced by
     a pledge&#x27;s manufacturer or delegate (MASA) to securely assign a
     pledge to an &#x27;owner&#x27;, so that the pledge may establish a secure
     connection to the owner&#x27;s network infrastructure.

     The key words &#x27;MUST&#x27;, &#x27;MUST NOT&#x27;, &#x27;REQUIRED&#x27;, &#x27;SHALL&#x27;, &#x27;SHALL
     NOT&#x27;, &#x27;SHOULD&#x27;, &#x27;SHOULD NOT&#x27;, &#x27;RECOMMENDED&#x27;, &#x27;NOT RECOMMENDED&#x27;,
     &#x27;MAY&#x27;, and &#x27;OPTIONAL&#x27; in this document are to be interpreted as
     described in <a href="/doc/html/bcp14">BCP 14</a> (<a href="/doc/html/rfc2119">RFC 2119</a>) (<a href="/doc/html/rfc8174">RFC 8174</a>) when, and only when, they
     appear in all capitals, as shown here.

     Copyright (c) 2018 IETF Trust and the persons identified as
     authors of the code.  All rights reserved.

     Redistribution and use in source and binary forms, with or without
     modification, is permitted pursuant to, and subject to the license
     terms contained in, the Simplified BSD License set forth in <a href="#section-4">Section</a>
     <a href="#section-4">4</a>.c of the IETF Trust&#x27;s Legal Provisions Relating to IETF Documents
     (<a href="https://trustee.ietf.org/license-info">https://trustee.ietf.org/license-info</a>).

     This version of this YANG module is part of <a href="/doc/html/rfc8366">RFC 8366</a>; see the RFC
     itself for full legal notices.&quot;;

  revision 2018-05-09 {
    description
      &quot;Initial version&quot;;
    reference &quot;<a href="/doc/html/rfc8366">RFC 8366</a>: Voucher Profile for Bootstrapping Protocols&quot;;
  }

  // Top-level statement
  rc:yang-data voucher-artifact {
    uses voucher-artifact-grouping;
  }

  // Grouping defined for future augmentations

  grouping voucher-artifact-grouping {
    description
      &quot;Grouping to allow reuse/extensions in future work.&quot;;
    container voucher {

<span class="grey"><a href="/doc/html/rfc8366">RFC 8366</a>                     Voucher Profile                    May 2018</span>

      description
        &quot;A voucher assigns a pledge to an owner (pinned-domain-cert).&quot;;
      leaf created-on {
        type yang:date-and-time;
        mandatory true;
        description
          &quot;A value indicating the date this voucher was created.  This
           node is primarily for human consumption and auditing.  Future
           work MAY create verification requirements based on this
           node.&quot;;
      }
      leaf expires-on {
        type yang:date-and-time;
        must &#x27;not(../nonce)&#x27;;
        description
          &quot;A value indicating when this voucher expires.  The node is
           optional as not all pledges support expirations, such as
           pledges lacking a reliable clock.

           If this field exists, then the pledges MUST ensure that
           the expires-on time has not yet passed.  A pledge without
           an accurate clock cannot meet this requirement.

           The expires-on value MUST NOT exceed the expiration date
           of any of the listed &#x27;pinned-domain-cert&#x27; certificates.&quot;;
      }
      leaf assertion {
        type enumeration {
          enum verified {
            description
              &quot;Indicates that the ownership has been positively
               verified by the MASA (e.g., through sales channel
               integration).&quot;;
          }
          enum logged {
            description
              &quot;Indicates that the voucher has been issued after
               minimal verification of ownership or control.  The
               issuance has been logged for detection of
               potential security issues (e.g., recipients of
               vouchers might verify for themselves that unexpected
               vouchers are not in the log).  This is similar to
               unsecured trust-on-first-use principles but with the
               logging providing a basis for detecting unexpected
               events.&quot;;
          }
          enum proximity {

<span class="grey"><a href="/doc/html/rfc8366">RFC 8366</a>                     Voucher Profile                    May 2018</span>

            description
              &quot;Indicates that the voucher has been issued after
               the MASA verified a proximity proof provided by the
               device and target domain.  The issuance has been logged
               for detection of potential security issues.  This is
               stronger than just logging, because it requires some
               verification that the pledge and owner are
               in communication but is still dependent on analysis of
               the logs to detect unexpected events.&quot;;
          }
        }
        mandatory true;
        description
          &quot;The assertion is a statement from the MASA regarding how
           the owner was verified.  This statement enables pledges
           to support more detailed policy checks.  Pledges MUST
           ensure that the assertion provided is acceptable, per
           local policy, before processing the voucher.&quot;;
      }
      leaf serial-number {
        type string;
        mandatory true;
        description
          &quot;The serial-number of the hardware.  When processing a
           voucher, a pledge MUST ensure that its serial-number
           matches this value.  If no match occurs, then the
           pledge MUST NOT process this voucher.&quot;;
      }
      leaf idevid-issuer {
        type binary;
        description
          &quot;The Authority Key Identifier OCTET STRING (as defined in
           <a href="/doc/html/rfc5280#section-4.2.1.1">Section&amp;nbsp;4.2.1.1 of RFC 5280</a>) from the pledge&#x27;s IDevID
           certificate.  Optional since some serial-numbers are
           already unique within the scope of a MASA.
           Inclusion of the statistically unique key identifier
           ensures statistically unique identification of the hardware.
           When processing a voucher, a pledge MUST ensure that its
           IDevID Authority Key Identifier matches this value.  If no
           match occurs, then the pledge MUST NOT process this voucher.

           When issuing a voucher, the MASA MUST ensure that this field
           is populated for serial-numbers that are not otherwise unique
           within the scope of the MASA.&quot;;
      }
      leaf pinned-domain-cert {
        type binary;
        mandatory true;
<span class="grey"><a href="/doc/html/rfc8366">RFC 8366</a>                     Voucher Profile                    May 2018</span>

        description
          &quot;An X.509 v3 certificate structure, as specified by <a href="/doc/html/rfc5280">RFC 5280</a>,
           using Distinguished Encoding Rules (DER) encoding, as defined
           in ITU-T X.690.

           This certificate is used by a pledge to trust a Public Key
           Infrastructure in order to verify a domain certificate
           supplied to the pledge separately by the bootstrapping
           protocol.  The domain certificate MUST have this certificate
           somewhere in its chain of certificates.  This certificate
           MAY be an end-entity certificate, including a self-signed
           entity.&quot;;
        reference
          &quot;<a href="/doc/html/rfc5280">RFC 5280</a>:
             Internet X.509 Public Key Infrastructure Certificate
             and Certificate Revocation List (CRL) Profile.
           ITU-T X.690:
              Information technology - ASN.1 encoding rules:
              Specification of Basic Encoding Rules (BER),
              Canonical Encoding Rules (CER) and Distinguished
              Encoding Rules (DER).&quot;;
      }
      leaf domain-cert-revocation-checks {
        type boolean;
        description
          &quot;A processing instruction to the pledge that it MUST (true)
           or MUST NOT (false) verify the revocation status for the
           pinned domain certificate.  If this field is not set, then
           normal PKIX behavior applies to validation of the domain
           certificate.&quot;;
      }
      leaf nonce {
        type binary {
          length &quot;8..32&quot;;
        }
        must &#x27;not(../expires-on)&#x27;;
        description
          &quot;A value that can be used by a pledge in some bootstrapping
           protocols to enable anti-replay protection.  This node is
           optional because it is not used by all bootstrapping
           protocols.

           When present, the pledge MUST compare the provided nonce
           value with another value that the pledge randomly generated
           and sent to a bootstrap server in an earlier bootstrapping
           message.  If the values do not match, then the pledge MUST
           NOT process this voucher.&quot;;
      }
<span class="grey"><a href="/doc/html/rfc8366">RFC 8366</a>                     Voucher Profile                    May 2018</span>

      leaf last-renewal-date {
        type yang:date-and-time;
        must &#x27;../expires-on&#x27;;
        description
          &quot;The date that the MASA projects to be the last date it
           will renew a voucher on.  This field is merely informative;
           it is not processed by pledges.

           Circumstances may occur after a voucher is generated that
           may alter a voucher&#x27;s validity period.  For instance, a
           vendor may associate validity periods with support contracts,
           which may be terminated or extended over time.&quot;;
      }
    } // end voucher
  } // end voucher-grouping
}
