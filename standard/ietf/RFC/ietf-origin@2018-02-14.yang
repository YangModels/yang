module ietf-origin {
  yang-version 1.1;
  namespace &quot;urn:ietf:params:xml:ns:yang:ietf-origin&quot;;
  prefix or;

  import ietf-yang-metadata {
    prefix md;
  }

  organization
    &quot;IETF Network Modeling (NETMOD) Working Group&quot;;

  contact
    &quot;WG Web:   &lt;<a href="https://datatracker.ietf.org/wg/netmod/">https://datatracker.ietf.org/wg/netmod/</a>&gt;

     WG List:  &lt;mailto:<a href="mailto:netmod@ietf.org">netmod@ietf.org</a>&gt;

     Author:   Martin Bjorklund
               &lt;mailto:<a href="mailto:mbj@tail-f.com">mbj@tail-f.com</a>&gt;

     Author:   Juergen Schoenwaelder
               &lt;mailto:<a href="mailto:j.schoenwaelder@jacobs-university.de">j.schoenwaelder@jacobs-university.de</a>&gt;

     Author:   Phil Shafer
               &lt;mailto:<a href="mailto:phil@juniper.net">phil@juniper.net</a>&gt;

     Author:   Kent Watsen
               &lt;mailto:<a href="mailto:kwatsen@juniper.net">kwatsen@juniper.net</a>&gt;

     Author:   Rob Wilton
               &lt;<a href="mailto:rwilton@cisco.com">rwilton@cisco.com</a>&gt;&quot;;

  description
    &quot;This YANG module defines an &#x27;origin&#x27; metadata annotation and a
     set of identities for the origin value.

     Copyright (c) 2018 IETF Trust and the persons identified as
     authors of the code.  All rights reserved.

     Redistribution and use in source and binary forms, with or
     without modification, is permitted pursuant to, and subject to
     the license terms contained in, the Simplified BSD License set
     forth in <a href="#section-4">Section 4</a>.c of the IETF Trust&#x27;s Legal Provisions
     Relating to IETF Documents
     (<a href="https://trustee.ietf.org/license-info">https://trustee.ietf.org/license-info</a>).

<span class="grey"><a href="/doc/html/rfc8342">RFC 8342</a>                          NMDA                        March 2018</span>

        This version of this YANG module is part of <a href="/doc/html/rfc8342">RFC 8342</a>
        (<a href="https://www.rfc-editor.org/info/rfc8342">https://www.rfc-editor.org/info/rfc8342</a>); see the RFC itself
        for full legal notices.&quot;;

     revision 2018-02-14 {
       description
         &quot;Initial revision.&quot;;
       reference
         &quot;<a href="/doc/html/rfc8342">RFC 8342</a>: Network Management Datastore Architecture (NMDA)&quot;;
     }

     /*
      * Identities
      */

     identity origin {
       description
         &quot;Abstract base identity for the origin annotation.&quot;;
     }

     identity intended {
       base origin;
       description
         &quot;Denotes configuration from the intended configuration
          datastore.&quot;;
     }

     identity dynamic {
       base origin;
       description
         &quot;Denotes configuration from a dynamic configuration
          datastore.&quot;;
     }

     identity system {
       base origin;
       description
         &quot;Denotes configuration originated by the system itself.

          Examples of system configuration include applied configuration
          for an always-existing loopback interface, or interface
          configuration that is auto-created due to the hardware
          currently present in the device.&quot;;
     }

<span class="grey"><a href="/doc/html/rfc8342">RFC 8342</a>                          NMDA                        March 2018</span>

     identity learned {
       base origin;
       description
         &quot;Denotes configuration learned from protocol interactions with
          other devices, instead of via either the intended
          configuration datastore or any dynamic configuration
          datastore.

          Examples of protocols that provide learned configuration
          include link-layer negotiations, routing protocols, and
          DHCP.&quot;;
     }

     identity default {
       base origin;
       description
         &quot;Denotes configuration that does not have a configured or
          learned value but has a default value in use.  Covers both
          values defined in a &#x27;default&#x27; statement and values defined
          via an explanation in a &#x27;description&#x27; statement.&quot;;
     }

     identity unknown {
       base origin;
       description
         &quot;Denotes configuration for which the system cannot identify the
          origin.&quot;;
     }

     /*
      * Type definitions
      */

     typedef origin-ref {
       type identityref {
         base origin;
       }
       description
         &quot;An origin identity reference.&quot;;
     }

<span class="grey"><a href="/doc/html/rfc8342">RFC 8342</a>                          NMDA                        March 2018</span>

     /*
      * Metadata annotations
      */

     md:annotation origin {
       type origin-ref;
       description
         &quot;The &#x27;origin&#x27; annotation can be present on any configuration
          data node in the operational state datastore.  It specifies
          from where the node originated.  If not specified for a given
          configuration data node, then the origin is the same as the
          origin of its parent node in the data tree.  The origin for
          any top-level configuration data nodes must be specified.&quot;;
     }
   }
