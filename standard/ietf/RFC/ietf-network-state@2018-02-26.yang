module ietf-network-state {
  yang-version 1.1;
  namespace &quot;urn:ietf:params:xml:ns:yang:ietf-network-state&quot;;
  prefix nw-s;

  import ietf-network {
    prefix nw;
    reference
      &quot;<a href="/doc/html/rfc8345">RFC 8345</a>: A YANG Data Model for Network Topologies&quot;;
  }

  organization
    &quot;IETF I2RS (Interface to the Routing System) Working Group&quot;;

  contact
    &quot;WG Web:    &lt;<a href="https://datatracker.ietf.org/wg/i2rs/">https://datatracker.ietf.org/wg/i2rs/</a>&gt;
     WG List:   &lt;mailto:<a href="mailto:i2rs@ietf.org">i2rs@ietf.org</a>&gt;

     Editor:    Alexander Clemm
                &lt;mailto:<a href="mailto:ludwig@clemm.org">ludwig@clemm.org</a>&gt;

     Editor:    Jan Medved
                &lt;mailto:<a href="mailto:jmedved@cisco.com">jmedved@cisco.com</a>&gt;

     Editor:    Robert Varga
                &lt;mailto:<a href="mailto:robert.varga@pantheon.tech">robert.varga@pantheon.tech</a>&gt;

     Editor:    Nitin Bahadur
                &lt;mailto:<a href="mailto:nitin_bahadur@yahoo.com">nitin_bahadur@yahoo.com</a>&gt;
<span class="grey"><a href="/doc/html/rfc8345">RFC 8345</a>         YANG Data Model for Network Topologies       March 2018</span>

     Editor:    Hariharan Ananthakrishnan
                &lt;mailto:<a href="mailto:hari@packetdesign.com">hari@packetdesign.com</a>&gt;

     Editor:    Xufeng Liu
                &lt;mailto:<a href="mailto:xufeng.liu.ietf@gmail.com">xufeng.liu.ietf@gmail.com</a>&gt;&quot;;

  description
    &quot;This module defines a common base data model for a collection
     of nodes in a network.  Node definitions are further used
     in network topologies and inventories.  It represents
     information that either (1) is learned and automatically
     populated or (2) results from applying network information
     that has been configured per the &#x27;ietf-network&#x27; data model,
     mirroring the corresponding data nodes in this data model.

     The data model mirrors &#x27;ietf-network&#x27; but contains only
     read-only state data.  The data model is not needed when the
     underlying implementation infrastructure supports the Network
     Management Datastore Architecture (NMDA).

     Copyright (c) 2018 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">https://trustee.ietf.org/license-info</a>).

     This version of this YANG module is part of <a href="/doc/html/rfc8345">RFC 8345</a>;
     see the RFC itself for full legal notices.&quot;;

  revision 2018-02-26 {
    description
      &quot;Initial revision.&quot;;
    reference
      &quot;<a href="/doc/html/rfc8345">RFC 8345</a>: A YANG Data Model for Network Topologies&quot;;
  }

<span class="grey"><a href="/doc/html/rfc8345">RFC 8345</a>         YANG Data Model for Network Topologies       March 2018</span>

  grouping network-ref {
    description
      &quot;Contains the information necessary to reference a network --
       for example, an underlay network.&quot;;
    leaf network-ref {
      type leafref {
        path &quot;/nw-s:networks/nw-s:network/nw-s:network-id&quot;;
      require-instance false;
      }
      description
        &quot;Used to reference a network -- for example, an underlay
         network.&quot;;
    }
  }

  grouping node-ref {
    description
      &quot;Contains the information necessary to reference a node.&quot;;
    leaf node-ref {
      type leafref {
        path &quot;/nw-s:networks/nw-s:network[nw-s:network-id=current()&quot;+
          &quot;/../network-ref]/nw-s:node/nw-s:node-id&quot;;
        require-instance false;
      }
      description
        &quot;Used to reference a node.
         Nodes are identified relative to the network that
         contains them.&quot;;
    }
    uses network-ref;
  }

<span class="grey"><a href="/doc/html/rfc8345">RFC 8345</a>         YANG Data Model for Network Topologies       March 2018</span>

  container networks {
    config false;
    description
      &quot;Serves as a top-level container for a list of networks.&quot;;
    list network {
      key &quot;network-id&quot;;
      description
        &quot;Describes a network.
         A network typically contains an inventory of nodes,
         topological information (augmented through the
         network-topology data model), and layering information.&quot;;
      container network-types {
        description
          &quot;Serves as an augmentation target.
           The network type is indicated through corresponding
           presence containers augmented into this container.&quot;;
      }
      leaf network-id {
        type nw:network-id;
        description
          &quot;Identifies a network.&quot;;
      }
      list supporting-network {
        key &quot;network-ref&quot;;
        description
          &quot;An underlay network, used to represent layered network
           topologies.&quot;;
        leaf network-ref {
          type leafref {
            path &quot;/nw-s:networks/nw-s:network/nw-s:network-id&quot;;
          require-instance false;
          }
          description
            &quot;References the underlay network.&quot;;
        }
      }

<span class="grey"><a href="/doc/html/rfc8345">RFC 8345</a>         YANG Data Model for Network Topologies       March 2018</span>

      list node {
        key &quot;node-id&quot;;
        description
          &quot;The inventory of nodes of this network.&quot;;
        leaf node-id {
          type nw:node-id;
          description
            &quot;Uniquely identifies a node within the containing
             network.&quot;;
        }
        list supporting-node {
          key &quot;network-ref node-ref&quot;;
          description
            &quot;Represents another node that is in an underlay network
             and that supports this node.  Used to represent layering
             structure.&quot;;
          leaf network-ref {
            type leafref {
              path &quot;../../../nw-s:supporting-network/nw-s:network-ref&quot;;
            require-instance false;
            }
            description
              &quot;References the underlay network of which the
               underlay node is a part.&quot;;
          }
          leaf node-ref {
            type leafref {
              path &quot;/nw-s:networks/nw-s:network/nw-s:node/nw-s:node-id&quot;;
            require-instance false;
            }
            description
              &quot;References the underlay node itself.&quot;;
          }
        }
      }
    }
  }
}
