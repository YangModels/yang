module ietf-network-instance {
  yang-version 1.1;
  namespace &quot;urn:ietf:params:xml:ns:yang:ietf-network-instance&quot;;
  prefix ni;

  // import some basic types

  import ietf-interfaces {
    prefix if;
    reference
      &quot;<a href="/doc/html/rfc8343">RFC 8343</a>: A YANG Data Model for Interface Management&quot;;
  }
  import ietf-ip {
    prefix ip;
    reference
      &quot;<a href="/doc/html/rfc8344">RFC 8344</a>: A YANG Data Model for IP Management&quot;;
  }
  import ietf-yang-schema-mount {
    prefix yangmnt;
    reference
      &quot;<a href="/doc/html/rfc8528">RFC 8528</a>: YANG Schema Mount&quot;;
  }

  organization
    &quot;IETF Routing Area (rtgwg) Working Group&quot;;
  contact
    &quot;WG Web:   &lt;<a href="https://datatracker.ietf.org/wg/rtgwg">https://datatracker.ietf.org/wg/rtgwg</a>&gt;
     WG List:  &lt;mailto:<a href="mailto:rtgwg@ietf.org">rtgwg@ietf.org</a>&gt;

     Author:   Lou Berger
               &lt;mailto:<a href="mailto:lberger@labn.net">lberger@labn.net</a>&gt;
     Author:   Christian Hopps
               &lt;mailto:<a href="mailto:chopps@chopps.org">chopps@chopps.org</a>&gt;
     Author:   Acee Lindem
               &lt;mailto:<a href="mailto:acee@cisco.com">acee@cisco.com</a>&gt;
     Author:   Dean Bogdanovic
               &lt;mailto:<a href="mailto:ivandean@gmail.com">ivandean@gmail.com</a>&gt;&quot;;
  description
    &quot;This module is used to support multiple network instances
     within a single physical or virtual device.  Network
     instances are commonly known as VRFs (VPN Routing and
     Forwarding) and VSIs (Virtual Switching Instances).
<span class="grey"><a href="/doc/html/rfc8529">RFC 8529</a>                        YANG NIs                      March 2019</span>

        The key words &#x27;MUST&#x27;, &#x27;MUST NOT&#x27;, &#x27;REQUIRED&#x27;, &#x27;SHALL&#x27;,
        &#x27;SHALL NOT&#x27;, &#x27;SHOULD&#x27;, &#x27;SHOULD NOT&#x27;, &#x27;RECOMMENDED&#x27;,
        &#x27;NOT RECOMMENDED&#x27;, &#x27;MAY&#x27;, and &#x27;OPTIONAL&#x27; in this document
        are to be interpreted as described in <a href="/doc/html/bcp14">BCP 14</a> (<a href="/doc/html/rfc2119">RFC 2119</a>)
        (<a href="/doc/html/rfc8174">RFC 8174</a>) when, and only when, they appear in all capitals,
         as shown here.

        Copyright (c) 2019 IETF Trust and the persons identified as
        authors of the code.  All rights reserved.

        Redistribution and use in source and binary forms, with or
        without modification, is permitted pursuant to, and subject
        to the license terms contained in, the Simplified BSD
        License set forth in <a href="#section-4">Section 4</a>.c of the IETF Trust&#x27;s Legal
        Provisions Relating to IETF Documents
        (<a href="https://trustee.ietf.org/license-info">https://trustee.ietf.org/license-info</a>).

        This version of this YANG module is part of <a href="/doc/html/rfc8529">RFC 8529</a>; see
        the RFC itself for full legal notices.&quot;;

     revision 2019-01-21 {
       description
         &quot;Initial revision.&quot;;
       reference
         &quot;<a href="/doc/html/rfc8529">RFC 8529</a>&quot;;
     }

     // top-level device definition statements

     container network-instances {
       description
         &quot;Network instances, each of which consists of
          VRFs and/or VSIs.&quot;;
       reference
         &quot;<a href="/doc/html/rfc8349">RFC 8349</a>: A YANG Data Model for Routing Management&quot;;
       list network-instance {
         key &quot;name&quot;;
         description
           &quot;List of network instances.&quot;;
         leaf name {
           type string;
           mandatory true;
           description
             &quot;device-scoped identifier for the network
              instance.&quot;;
         }
         leaf enabled {
           type boolean;
<span class="grey"><a href="/doc/html/rfc8529">RFC 8529</a>                        YANG NIs                      March 2019</span>

           default &quot;true&quot;;
           description
             &quot;Flag indicating whether or not the network
              instance is enabled.&quot;;
         }
         leaf description {
           type string;
           description
             &quot;Description of the network instance
              and its intended purpose.&quot;;
         }
         choice ni-type {
           description
             &quot;This node serves as an anchor point for different types
              of network instances.  Each &#x27;case&#x27; is expected to
              differ in terms of the information needed in the
              parent/core to support the NI and may differ in their
              mounted-schema definition.  When the mounted schema is
              not expected to be the same for a specific type of NI,
              a mount point should be defined.&quot;;
         }
         choice root-type {
           mandatory true;
           description
             &quot;Well-known mount points.&quot;;
           container vrf-root {
             description
               &quot;Container for mount point.&quot;;
             yangmnt:mount-point &quot;vrf-root&quot; {
               description
                 &quot;Root for L3VPN-type models.  This will typically
                  not be an inline-type mount point.&quot;;
             }
           }
           container vsi-root {
             description
               &quot;Container for mount point.&quot;;
             yangmnt:mount-point &quot;vsi-root&quot; {
               description
                 &quot;Root for L2VPN-type models.  This will typically
                  not be an inline-type mount point.&quot;;
             }
           }
           container vv-root {
             description
               &quot;Container for mount point.&quot;;
             yangmnt:mount-point &quot;vv-root&quot; {
               description
<span class="grey"><a href="/doc/html/rfc8529">RFC 8529</a>                        YANG NIs                      March 2019</span>

                 &quot;Root models that support both L2VPN-type bridging
                  and L3VPN-type routing.  This will typically
                  not be an inline-type mount point.&quot;;
             }
           }
         }
       }
     }

     // augment statements

     augment &quot;/if:interfaces/if:interface&quot; {
       description
         &quot;Add a node for the identification of the network
          instance associated with the information configured
          on a interface.

          Note that a standard error will be returned if the
          identified leafref isn&#x27;t present.  If an interface cannot
          be assigned for any other reason, the operation SHALL fail
          with an error-tag of &#x27;operation-failed&#x27; and an
          error-app-tag of &#x27;ni-assignment-failed&#x27;.  A meaningful
          error-info that indicates the source of the assignment
          failure SHOULD also be provided.&quot;;
       leaf bind-ni-name {
         type leafref {
           path &quot;/network-instances/network-instance/name&quot;;
         }
         description
           &quot;Network instance to which an interface is bound.&quot;;
       }
     }
     augment &quot;/if:interfaces/if:interface/ip:ipv4&quot; {
       description
         &quot;Add a node for the identification of the network
          instance associated with the information configured
          on an IPv4 interface.

          Note that a standard error will be returned if the
          identified leafref isn&#x27;t present.  If an interface cannot
          be assigned for any other reason, the operation SHALL fail
          with an error-tag of &#x27;operation-failed&#x27; and an
          error-app-tag of &#x27;ni-assignment-failed&#x27;.  A meaningful
          error-info that indicates the source of the assignment
          failure SHOULD also be provided.&quot;;
       leaf bind-ni-name {
         type leafref {
           path &quot;/network-instances/network-instance/name&quot;;
<span class="grey"><a href="/doc/html/rfc8529">RFC 8529</a>                        YANG NIs                      March 2019</span>

         }
         description
           &quot;Network instance to which IPv4 interface is bound.&quot;;
       }
     }
     augment &quot;/if:interfaces/if:interface/ip:ipv6&quot; {
       description
         &quot;Add a node for the identification of the network
          instance associated with the information configured
          on an IPv6 interface.

          Note that a standard error will be returned if the
          identified leafref isn&#x27;t present.  If an interface cannot
          be assigned for any other reason, the operation SHALL fail
          with an error-tag of &#x27;operation-failed&#x27; and an
          error-app-tag of &#x27;ni-assignment-failed&#x27;.  A meaningful
          error-info that indicates the source of the assignment
          failure SHOULD also be provided.&quot;;
       leaf bind-ni-name {
         type leafref {
           path &quot;/network-instances/network-instance/name&quot;;
         }
         description
           &quot;Network instance to which IPv6 interface is bound.&quot;;
       }
     }

     // notification statements

     notification bind-ni-name-failed {
       description
         &quot;Indicates an error in the association of an interface to an
          NI.  Only generated after success is initially returned when
          bind-ni-name is set.

          Note: Some errors may need to be reported for multiple
          associations, e.g., a single error may need to be reported
          for an IPv4 and an IPv6 bind-ni-name.

          At least one container with a bind-ni-name leaf MUST be
          included in this notification.&quot;;
       leaf name {
         type leafref {
           path &quot;/if:interfaces/if:interface/if:name&quot;;
         }
         mandatory true;
         description
           &quot;Contains the interface name associated with the
<span class="grey"><a href="/doc/html/rfc8529">RFC 8529</a>                        YANG NIs                      March 2019</span>

            failure.&quot;;
       }
       container interface {
         description
           &quot;Generic interface type.&quot;;
         leaf bind-ni-name {
           type leafref {
             path &quot;/if:interfaces/if:interface&quot;
                + &quot;/ni:bind-ni-name&quot;;
           }
           description
             &quot;Contains the bind-ni-name associated with the
              failure.&quot;;
         }
       }
       container ipv4 {
         description
           &quot;IPv4 interface type.&quot;;
         leaf bind-ni-name {
           type leafref {
             path &quot;/if:interfaces/if:interface/ip:ipv4/ni:bind-ni-name&quot;;
           }
           description
             &quot;Contains the bind-ni-name associated with the
              failure.&quot;;
         }
       }
       container ipv6 {
         description
           &quot;IPv6 interface type.&quot;;
         leaf bind-ni-name {
           type leafref {
             path &quot;/if:interfaces/if:interface/ip:ipv6&quot;
                + &quot;/ni:bind-ni-name&quot;;
           }
           description
             &quot;Contains the bind-ni-name associated with the
              failure.&quot;;
         }
       }
       leaf error-info {
         type string;
         description
           &quot;Optionally, indicates the source of the assignment
            failure.&quot;;
       }
     }
   }
