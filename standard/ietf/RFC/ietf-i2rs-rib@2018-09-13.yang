module ietf-i2rs-rib {
  yang-version 1.1;
  namespace &quot;urn:ietf:params:xml:ns:yang:ietf-i2rs-rib&quot;;
  prefix iir;

  import ietf-inet-types {
    prefix inet;
    reference &quot;<a href="/doc/html/rfc6991">RFC 6991</a>&quot;;
  }
  import ietf-interfaces {
    prefix if;
    reference &quot;<a href="/doc/html/rfc8344">RFC 8344</a>&quot;;
  }
  import ietf-yang-types {
    prefix yang;
    reference &quot;<a href="/doc/html/rfc6991">RFC 6991</a>&quot;;
  }

  organization
    &quot;IETF I2RS (Interface to Routing System) Working Group&quot;;
  contact
    &quot;WG Web:   &lt;<a href="https://datatracker.ietf.org/wg/i2rs/">https://datatracker.ietf.org/wg/i2rs/</a>&gt;
     WG List:  &lt;mailto:<a href="mailto:i2rs@ietf.org">i2rs@ietf.org</a>&gt;

     Editor:   Lixing Wang
               &lt;mailto:<a href="mailto:wang_little_star@sina.com">wang_little_star@sina.com</a>&gt;

     Editor:   Mach(Guoyi) Chen
               &lt;mailto:<a href="mailto:mach.chen@huawei.com">mach.chen@huawei.com</a>&gt;

     Editor:   Amit Dass
               &lt;mailto:<a href="mailto:dass.amit@gmail.com">dass.amit@gmail.com</a>&gt;

     Editor:   Hariharan Ananthakrishnan
               &lt;mailto:<a href="mailto:hari@netflix.com">hari@netflix.com</a>&gt;

     Editor:   Sriganesh Kini
               &lt;mailto:<a href="mailto:sriganeshkini@gmail.com">sriganeshkini@gmail.com</a>&gt;

     Editor:   Nitin Bahadur
               &lt;mailto:<a href="mailto:nitin_bahadur@yahoo.com">nitin_bahadur@yahoo.com</a>&gt;&quot;;
<span class="grey"><a href="/doc/html/rfc8431">RFC 8431</a>                     RIB Data Model               September 2018</span>

     description
       &quot;This module defines a YANG data model for
        Routing Information Base (RIB) that aligns
        with the I2RS RIB information model.

        Copyright (c) 2018 IETF Trust and the persons
        identified as authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc8341">RFC 8341</a>; see
        the RFC itself for full legal notices.&quot;;

     revision 2018-09-13 {
       description
         &quot;initial revision&quot;;
       reference &quot;<a href="/doc/html/rfc8431">RFC 8431</a>&quot;;
     }

     //Features

     feature nexthop-tunnel {
       description
         &quot;This feature means that a node supports
          tunnel nexthop capability.&quot;;
     }

     feature nexthop-chain {
       description
         &quot;This feature means that a node supports
          chain nexthop capability.&quot;;
     }

     feature nexthop-protection {
       description
         &quot;This feature means that a node supports
          protection nexthop capability.&quot;;
     }

     feature nexthop-replicate {
       description
         &quot;This feature means that a node supports
          replicate nexthop capability.&quot;;
<span class="grey"><a href="/doc/html/rfc8431">RFC 8431</a>                     RIB Data Model               September 2018</span>

     }

     feature nexthop-load-balance {
       description
         &quot;This feature means that a node supports
          load-balance nexthop capability.&quot;;
     }

     feature ipv4-tunnel {
       description
         &quot;This feature means that a node supports
          IPv4 tunnel encapsulation capability.&quot;;
     }

     feature ipv6-tunnel {
       description
         &quot;This feature means that a node supports
          IPv6 tunnel encapsulation capability.&quot;;
     }

     feature mpls-tunnel {
       description
         &quot;This feature means that a node supports
          MPLS tunnel encapsulation capability.&quot;;
     }

     feature vxlan-tunnel {
       description
         &quot;This feature means that a node supports
          Virtual eXtensible Local Area Network
          (VXLAN) tunnel encapsulation capability.&quot;;
       reference &quot;<a href="/doc/html/rfc7348">RFC 7348</a>&quot;;
     }

     feature gre-tunnel {
       description
         &quot;This feature means that a node supports
          GRE tunnel encapsulation capability.&quot;;
       reference &quot;<a href="/doc/html/rfc2784">RFC 2784</a>&quot;;
     }

     feature nvgre-tunnel {
       description
         &quot;This feature means that a node supports
          Network Virtualization Using GRE (NVGRE)
          tunnel encapsulation capability.&quot;;
       reference &quot;<a href="/doc/html/rfc7637">RFC 7637</a>&quot;;
     }
<span class="grey"><a href="/doc/html/rfc8431">RFC 8431</a>                     RIB Data Model               September 2018</span>

     feature route-vendor-attributes {
       description
         &quot;This feature means that a node supports
          route vendor attributes.&quot;;
     }

     //Identities and Type Definitions

     identity mpls-label-action {
       description
         &quot;Base identity from which all MPLS label
          operations are derived.

          The MPLS label stack operations include:
          push - to add a new label to a label stack
          pop -  to pop the top label from a label stack
          swap - to exchange the top label of a label
                 stack with a new label&quot;;
     }

     identity label-push {
       base mpls-label-action;
       description
         &quot;MPLS label stack operation: push.&quot;;
     }

     identity label-pop {
       base mpls-label-action;
       description
         &quot;MPLS label stack operation: pop.&quot;;
     }

     identity label-swap {
       base mpls-label-action;
       description
         &quot;MPLS label stack operation: swap.&quot;;
     }

     typedef mpls-label-action-definition {
       type identityref {
         base mpls-label-action;
       }
       description
         &quot;MPLS label action definition.&quot;;
     }

     identity tunnel-decapsulation-action {
       description
<span class="grey"><a href="/doc/html/rfc8431">RFC 8431</a>                     RIB Data Model               September 2018</span>

         &quot;Base identity from which all tunnel decapsulation
          actions are derived.
          Tunnel decapsulation actions include
          ipv4-decapsulation (to decapsulate an IPv4 tunnel)
          ipv6-decapsulation (to decapsulate an IPv6 tunnel)&quot;;
     }

     identity ipv4-decapsulation {
       base tunnel-decapsulation-action;
       description
         &quot;IPv4 tunnel decapsulation.&quot;;
     }

     identity ipv6-decapsulation {
       base tunnel-decapsulation-action;
       description
         &quot;IPv6 tunnel decapsulation.&quot;;
     }

     typedef tunnel-decapsulation-action-definition {
       type identityref {
         base tunnel-decapsulation-action;
       }
       description
         &quot;Tunnel decapsulation definition.&quot;;
     }

     identity ttl-action {
       description
         &quot;Base identity from which all TTL
          actions are derived.&quot;;
     }

     identity no-action {
       base ttl-action;
       description
         &quot;Do nothing regarding the TTL.&quot;;
     }

     identity copy-to-inner {
       base ttl-action;
       description
         &quot;Copy the TTL of the outer header
          to the inner header.&quot;;
     }

     identity decrease-and-copy-to-inner {
       base ttl-action;
<span class="grey"><a href="/doc/html/rfc8431">RFC 8431</a>                     RIB Data Model               September 2018</span>

       description
         &quot;Decrease TTL by one and copy the TTL
          to the inner header.&quot;;
     }

     identity decrease-and-copy-to-next {
       base ttl-action;
       description
         &quot;Decrease TTL by one and copy the TTL
          to the next header; for example, when
          MPLS label swapping, decrease the TTL
          of the in_label and copy it to the
          out_label.&quot;;
     }

     typedef ttl-action-definition {
       type identityref {
         base ttl-action;
       }
       description
         &quot;TTL action definition.&quot;;
     }

     identity hop-limit-action {
       description
         &quot;Base identity from which all hop limit
          actions are derived.&quot;;
     }

     identity hop-limit-no-action {
       base hop-limit-action;
       description
         &quot;Do nothing regarding the hop limit.&quot;;
     }

     identity hop-limit-copy-to-inner {
       base hop-limit-action;
       description
         &quot;Copy the hop limit of the outer header
          to the inner header.&quot;;
     }

     typedef hop-limit-action-definition {
       type identityref {
         base hop-limit-action;
       }
       description
         &quot;IPv6 hop limit action definition.&quot;;
<span class="grey"><a href="/doc/html/rfc8431">RFC 8431</a>                     RIB Data Model               September 2018</span>

     }

     identity special-nexthop {
       description
         &quot;Base identity from which all special
          nexthops are derived.&quot;;
     }

     identity discard {
       base special-nexthop;
       description
         &quot;This indicates that the network
          device should drop the packet and
          increment a drop counter.&quot;;
     }

     identity discard-with-error {
       base special-nexthop;
       description
         &quot;This indicates that the network
          device should drop the packet,
          increment a drop counter, and send
          back an appropriate error message
          (like ICMP error).&quot;;
     }

     identity receive {
       base special-nexthop;
       description
         &quot;This indicates that the traffic is
          destined for the network device, e.g.,
          protocol packets or Operations,
          Administration, and Maintenance (OAM) packets.
          All locally destined traffic SHOULD be
          throttled to avoid a denial-of-service
          attack on the router&#x27;s control plane.  An
          optional rate-limiter can be specified
          to indicate how to throttle traffic
          destined for the control plane.&quot;;
     }

     identity cos-value {
       base special-nexthop;
       description
         &quot;Cos-value special nexthop.&quot;;
     }

     typedef special-nexthop-definition {
<span class="grey"><a href="/doc/html/rfc8431">RFC 8431</a>                     RIB Data Model               September 2018</span>

       type identityref {
         base special-nexthop;
       }
       description
         &quot;Special nexthop definition.&quot;;
     }

     identity ip-route-match-type {
       description
         &quot;Base identity from which all route
          match types are derived.
          The route match type could be:
          match source, or
          match destination, or
          match source and destination.&quot;;
     }

     identity match-ip-src {
       base ip-route-match-type;
       description
         &quot;Source route match type.&quot;;
     }

     identity match-ip-dest {
       base ip-route-match-type;
       description
         &quot;Destination route match type&quot;;
     }

     identity match-ip-src-dest {
       base ip-route-match-type;
       description
         &quot;Source and Destination route match type&quot;;
     }

     typedef ip-route-match-type-definition {
       type identityref {
         base ip-route-match-type;
       }
       description
         &quot;IP route match type definition.&quot;;
     }

     identity address-family {
       description
         &quot;Base identity from which all RIB
          address families are derived.&quot;;
     }
<span class="grey"><a href="/doc/html/rfc8431">RFC 8431</a>                     RIB Data Model               September 2018</span>

     identity ipv4-address-family {
       base address-family;
       description
         &quot;IPv4 RIB address family.&quot;;
     }

     identity ipv6-address-family {
       base address-family;
       description
         &quot;IPv6 RIB address family.&quot;;
     }

     identity mpls-address-family {
       base address-family;
       description
         &quot;MPLS RIB address family.&quot;;
     }

     identity ieee-mac-address-family {
       base address-family;
       description
         &quot;MAC RIB address family.&quot;;
     }

     typedef address-family-definition {
       type identityref {
         base address-family;
       }
       description
         &quot;RIB address family definition.&quot;;
     }

     identity route-type {
       description
         &quot;Base identity from which all route types
          are derived.&quot;;
     }

     identity ipv4-route {
       base route-type;
       description
         &quot;IPv4 route type.&quot;;
     }

     identity ipv6-route {
       base route-type;
       description
         &quot;IPv6 route type.&quot;;
<span class="grey"><a href="/doc/html/rfc8431">RFC 8431</a>                     RIB Data Model               September 2018</span>

     }

     identity mpls-route {
       base route-type;
       description
         &quot;MPLS route type.&quot;;
     }

     identity ieee-mac {
       base route-type;
       description
         &quot;MAC route type.&quot;;
     }

     identity interface {
       base route-type;
       description
         &quot;Interface route type.&quot;;
     }

     typedef route-type-definition {
       type identityref {
         base route-type;
       }
       description
         &quot;Route type definition.&quot;;
     }

     identity tunnel-type {
       description
         &quot;Base identity from which all tunnel
          types are derived.&quot;;
     }

     identity ipv4-tunnel {
       base tunnel-type;
       description
         &quot;IPv4 tunnel type&quot;;
     }

     identity ipv6-tunnel {
       base tunnel-type;
       description
         &quot;IPv6 tunnel type&quot;;
     }

     identity mpls-tunnel {
       base tunnel-type;
<span class="grey"><a href="/doc/html/rfc8431">RFC 8431</a>                     RIB Data Model               September 2018</span>

       description
         &quot;MPLS tunnel type&quot;;
     }

     identity gre-tunnel {
       base tunnel-type;
       description
         &quot;GRE tunnel type&quot;;
     }

     identity vxlan-tunnel {
       base tunnel-type;
       description
         &quot;VXLAN tunnel type&quot;;
     }

     identity nvgre-tunnel {
       base tunnel-type;
       description
         &quot;NVGRE tunnel type&quot;;
     }

     typedef tunnel-type-definition {
       type identityref {
         base tunnel-type;
       }
       description
         &quot;Tunnel type definition.&quot;;
     }

     identity route-state {
       description
         &quot;Base identity from which all route
          states are derived.&quot;;
     }

     identity active {
       base route-state;
       description
         &quot;Active state.&quot;;
     }

     identity inactive {
       base route-state;
       description
         &quot;Inactive state.&quot;;
     }

<span class="grey"><a href="/doc/html/rfc8431">RFC 8431</a>                     RIB Data Model               September 2018</span>

     typedef route-state-definition {
       type identityref {
         base route-state;
       }
       description
         &quot;Route state definition.&quot;;
     }

     identity nexthop-state {
       description
         &quot;Base identity from which all nexthop
          states are derived.&quot;;
     }

     identity resolved {
       base nexthop-state;
       description
         &quot;Resolved nexthop state.&quot;;
     }

     identity unresolved {
       base nexthop-state;
       description
         &quot;Unresolved nexthop state.&quot;;
     }

     typedef nexthop-state-definition {
       type identityref {
         base nexthop-state;
       }
       description
         &quot;Nexthop state definition.&quot;;
     }

     identity route-installed-state {
       description
         &quot;Base identity from which all route
          installed states are derived.&quot;;
     }

     identity uninstalled {
       base route-installed-state;
       description
         &quot;Uninstalled state.&quot;;
     }

     identity installed {
       base route-installed-state;
<span class="grey"><a href="/doc/html/rfc8431">RFC 8431</a>                     RIB Data Model               September 2018</span>

       description
         &quot;Installed state.&quot;;
     }

     typedef route-installed-state-definition {
       type identityref {
         base route-installed-state;
       }
       description
         &quot;Route installed state definition.&quot;;
     }

     //Route Change Reason Identities

     identity route-change-reason {
       description
         &quot;Base identity from which all route change
          reasons are derived.&quot;;
     }

     identity lower-route-preference {
       base route-change-reason;
       description
         &quot;This route was installed in the FIB because it had
          a lower route preference value (and thus was more
          preferred) than the route it replaced.&quot;;
     }

     identity higher-route-preference {
       base route-change-reason;
       description
         &quot;This route was uninstalled from the FIB because it had
          a higher route preference value (and thus was less
          preferred) than the route that replaced it.&quot;;
     }

     identity resolved-nexthop {
       base route-change-reason;
       description
         &quot;This route was made active because at least
          one of its nexthops was resolved.&quot;;
     }

     identity unresolved-nexthop {
       base route-change-reason;
       description
         &quot;This route was made inactive because all of
          its nexthops are unresolved.&quot;;
<span class="grey"><a href="/doc/html/rfc8431">RFC 8431</a>                     RIB Data Model               September 2018</span>

     }

     typedef route-change-reason-definition {
       type identityref {
         base route-change-reason;
       }
       description
         &quot;Route change reason definition.&quot;;
     }

     typedef nexthop-preference-definition {
       type uint8 {
         range &quot;1..99&quot;;
       }
       description
         &quot;Nexthop-preference is used for protection schemes.
          It is an integer value between 1 and 99.  Lower
          values are preferred.  To download N
          nexthops to the FIB, the N nexthops with the lowest
          value are selected.  If there are more than N
          nexthops that have the same preference, an
          implementation of the I2RS client should select N
          nexthops and download them.  As for how to select
          the nexthops, this is left to the implementations.&quot;;
     }

     typedef nexthop-lb-weight-definition {
       type uint8 {
         range &quot;1..99&quot;;
       }
       description
         &quot;Nexthop-lb-weight is used for load-balancing.
          Each list member SHOULD be assigned a weight
          between 1 and 99.  The weight determines the
          proportion of traffic to be sent over a nexthop
          used for forwarding as a ratio of the weight of
          this nexthop divided by the sum of the weights
          of all the nexthops of this route that are used
          for forwarding.  To perform equal load-balancing,
          one MAY specify a weight of 0 for all the member
          nexthops.  The value 0 is reserved for equal
          load-balancing and, if applied, MUST be applied
          to all member nexthops.
          Note that the weight of 0 is special because of
          historical reasons.  It&#x27;s typically used in
          hardware devices to signify ECMP.&quot;;
     }

<span class="grey"><a href="/doc/html/rfc8431">RFC 8431</a>                     RIB Data Model               September 2018</span>

     typedef nexthop-ref {
       type leafref {
         path  &quot;/iir:routing-instance&quot; +
               &quot;/iir:rib-list&quot; +
               &quot;/iir:route-list&quot; +
               &quot;/iir:nexthop&quot; +
               &quot;/iir:nexthop-id&quot;;
       }
       description
         &quot;A nexthop reference that provides
          an indirection reference to a nexthop.&quot;;
     }

     //Groupings

     grouping route-prefix {
       description
         &quot;The common attributes used for all types of route prefixes.&quot;;
       leaf route-index {
         type uint64;
         mandatory true;
         description
           &quot;Route index.&quot;;
       }
       container match {
         description
           &quot;The match condition specifies the
            kind of route (IPv4, MPLS, etc.)
            and the set of fields to match on.&quot;;
         choice route-type {
           description
             &quot;Route types: IPv4, IPv6, MPLS, MAC, etc.&quot;;
           case ipv4 {
             description
               &quot;IPv4 route case.&quot;;
             container ipv4 {
               description
                 &quot;IPv4 route match.&quot;;
               choice ip-route-match-type {
                 description
                   &quot;IP route match type options:
                    match source, or
                    match destination, or
                    match source and destination.&quot;;
                 case dest-ipv4-address {
                   leaf dest-ipv4-prefix {
                     type inet:ipv4-prefix;
                     mandatory true;
<span class="grey"><a href="/doc/html/rfc8431">RFC 8431</a>                     RIB Data Model               September 2018</span>

                     description
                       &quot;An IPv4 destination address as the match.&quot;;
                   }
                 }
                 case src-ipv4-address {
                   leaf src-ipv4-prefix {
                     type inet:ipv4-prefix;
                     mandatory true;
                     description
                       &quot;An IPv4 source address as the match.&quot;;
                   }
                 }
                 case dest-src-ipv4-address {
                   container dest-src-ipv4-address {
                     description
                       &quot;A combination of an IPv4 source and
                        an IPv4 destination address as the match.&quot;;
                     leaf dest-ipv4-prefix {
                       type inet:ipv4-prefix;
                       mandatory true;
                       description
                         &quot;The IPv4 destination address of the match.&quot;;
                     }
                     leaf src-ipv4-prefix {
                       type inet:ipv4-prefix;
                       mandatory true;
                       description
                         &quot;The IPv4 source address of the match.&quot;;
                     }
                   }
                 }
               }
             }
           }
           case ipv6 {
             description
               &quot;IPv6 route case.&quot;;
             container ipv6 {
               description
                 &quot;IPv6 route match.&quot;;
               choice ip-route-match-type {
                 description
                   &quot;IP route match type options:
                    match source,
                    match destination, or
                    match source and destination.&quot;;
                 case dest-ipv6-address {
                   leaf dest-ipv6-prefix {
<span class="grey"><a href="/doc/html/rfc8431">RFC 8431</a>                     RIB Data Model               September 2018</span>

                     type inet:ipv6-prefix;
                     mandatory true;
                     description
                       &quot;An IPv6 destination address as the match.&quot;;
                   }
                 }
                 case src-ipv6-address {
                   leaf src-ipv6-prefix {
                     type inet:ipv6-prefix;
                     mandatory true;
                     description
                       &quot;An IPv6 source address as the match.&quot;;
                   }
                 }
                 case dest-src-ipv6-address {
                   container dest-src-ipv6-address {
                     description
                       &quot;A combination of an IPv6 source and
                        an IPv6 destination address as the match.&quot;;
                     leaf dest-ipv6-prefix {
                       type inet:ipv6-prefix;
                       mandatory true;
                       description
                         &quot;The IPv6 destination address of the match.&quot;;
                     }
                     leaf src-ipv6-prefix {
                       type inet:ipv6-prefix;
                       mandatory true;
                       description
                         &quot;The IPv6 source address of the match.&quot;;
                     }
                   }
                 }
               }
             }
           }
           case mpls-route {
             description
               &quot;MPLS route case.&quot;;
             leaf mpls-label {
               type uint32;
               mandatory true;
               description
                 &quot;The label used for matching.&quot;;
             }
           }
           case mac-route {
             description
<span class="grey"><a href="/doc/html/rfc8431">RFC 8431</a>                     RIB Data Model               September 2018</span>

               &quot;MAC route case.&quot;;
             leaf mac-address {
               type yang:mac-address;
               mandatory true;
               description
                 &quot;The MAC address used for matching.&quot;;
             }
           }
           case interface-route {
             description
               &quot;Interface route case.&quot;;
             leaf interface-identifier {
               type if:interface-ref;
               mandatory true;
               description
                 &quot;The interface used for matching.&quot;;
             }
           }
         }
       }
     }

     grouping route {
       description
         &quot;The common attributes used for all types of routes.&quot;;
       uses route-prefix;
       container nexthop {
         description
           &quot;The nexthop of the route.&quot;;
         uses nexthop;
       }
       //In the information model, it is called route-statistic
       container route-status {
         description
           &quot;The status information of the route.&quot;;
         leaf route-state {
           type route-state-definition;
           config false;
           description
             &quot;Indicate a route&#x27;s state: active or inactive.&quot;;
         }
         leaf route-installed-state {
           type route-installed-state-definition;
           config false;
           description
             &quot;Indicate that a route&#x27;s installed states:
              installed or uninstalled.&quot;;
         }
<span class="grey"><a href="/doc/html/rfc8431">RFC 8431</a>                     RIB Data Model               September 2018</span>

         leaf route-reason {
           type route-change-reason-definition;
           config false;
           description
             &quot;Indicate the reason that caused the route change.&quot;;
         }
       }
       container route-attributes {
         description
           &quot;Route attributes.&quot;;
         uses route-attributes;
       }
       container route-vendor-attributes {
         description
           &quot;Route vendor attributes.&quot;;
         uses route-vendor-attributes;
       }
     }

     grouping nexthop-list {
       description
         &quot;A generic nexthop list.&quot;;
       list nexthop-list {
         key &quot;nexthop-member-id&quot;;
         description
           &quot;A list of nexthops.&quot;;
         leaf nexthop-member-id {
           type uint32;
           mandatory true;
           description
             &quot;A nexthop identifier that points
              to a nexthop list member.
              A nexthop list member is a nexthop.&quot;;
         }
       }
     }

     grouping nexthop-list-p {
       description
         &quot;A nexthop list with preference parameter.&quot;;
       list nexthop-list {
         key &quot;nexthop-member-id&quot;;
         description
           &quot;A list of nexthop.&quot;;
         leaf nexthop-member-id {
           type uint32;
           mandatory true;
           description
<span class="grey"><a href="/doc/html/rfc8431">RFC 8431</a>                     RIB Data Model               September 2018</span>

             &quot;A nexthop identifier that points
              to a nexthop list member.
              A nexthop list member is a nexthop.&quot;;
         }
         leaf nexthop-preference {
           type nexthop-preference-definition;
           mandatory true;
           description
             &quot;Nexthop-preference is used for protection schemes.
              It is an integer value between 1 and 99.  Lower
              values are more preferred.  To download a
              primary/standby/tertiary group to the FIB, the
              nexthops that are resolved and are most preferred
              are selected.&quot;;
         }
       }
     }

     grouping nexthop-list-w {
       description
         &quot;A nexthop list with a weight parameter.&quot;;
       list nexthop-list {
         key &quot;nexthop-member-id&quot;;
         description
           &quot;A list of nexthop.&quot;;
         leaf nexthop-member-id {
           type uint32;
           mandatory true;
           description
             &quot;A nexthop identifier that points
              to a nexthop list member.
              A nexthop list member is a nexthop.&quot;;
         }
         leaf nexthop-lb-weight {
           type nexthop-lb-weight-definition;
           mandatory true;
           description
             &quot;The weight of a nexthop of
              the load-balance nexthops.&quot;;
         }
       }
     }

     grouping nexthop {
       description
         &quot;The nexthop structure.&quot;;
       leaf nexthop-id {
         type uint32;
<span class="grey"><a href="/doc/html/rfc8431">RFC 8431</a>                     RIB Data Model               September 2018</span>

         description
           &quot;An identifier that refers to a nexthop.&quot;;
       }
       leaf sharing-flag {
         type boolean;
         description
           &quot;To indicate whether a nexthop is sharable
            or non-sharable:
            true  - sharable (which means the nexthop can be
                    shared with other routes)
            false - non-sharable (which means the nexthop can
                    not be shared with other routes)&quot;;
       }
       choice nexthop-type {
         description
           &quot;Nexthop type options.&quot;;
         case nexthop-base {
           container nexthop-base {
             description
               &quot;The base nexthop.&quot;;
             uses nexthop-base;
           }
         }
         case nexthop-chain {
           if-feature &quot;nexthop-chain&quot;;
           container nexthop-chain {
             description
               &quot;A chain nexthop.&quot;;
             uses nexthop-list;
           }
         }
         case nexthop-replicate {
           if-feature &quot;nexthop-replicate&quot;;
           container nexthop-replicate {
             description
               &quot;A replicate nexthop.&quot;;
             uses nexthop-list;
           }
         }
         case nexthop-protection {
           if-feature &quot;nexthop-protection&quot;;
           container nexthop-protection {
             description
               &quot;A protection nexthop.&quot;;
             uses nexthop-list-p;
           }
         }
         case nexthop-load-balance {
<span class="grey"><a href="/doc/html/rfc8431">RFC 8431</a>                     RIB Data Model               September 2018</span>

           if-feature &quot;nexthop-load-balance&quot;;
           container nexthop-lb {
             description
               &quot;A load-balance nexthop.&quot;;
             uses nexthop-list-w;
           }
         }
       }
     }

     grouping nexthop-base {
       description
         &quot;The base nexthop.&quot;;
       choice nexthop-base-type {
         description
           &quot;Nexthop base type options.&quot;;
         case special-nexthop {
           leaf special {
             type special-nexthop-definition;
             description
               &quot;A special nexthop.&quot;;
           }
         }
         case egress-interface-nexthop {
           leaf outgoing-interface {
             type if:interface-ref;
             mandatory true;
             description
               &quot;The nexthop is an outgoing interface.&quot;;
           }
         }
         case ipv4-address-nexthop {
           leaf ipv4-address {
             type inet:ipv4-address;
             mandatory true;
             description
               &quot;The nexthop is an IPv4 address.&quot;;
           }
         }
         case ipv6-address-nexthop {
           leaf ipv6-address {
             type inet:ipv6-address;
             mandatory true;
             description
               &quot;The nexthop is an IPv6 address.&quot;;
           }
         }
         case egress-interface-ipv4-nexthop {
<span class="grey"><a href="/doc/html/rfc8431">RFC 8431</a>                     RIB Data Model               September 2018</span>

           container egress-interface-ipv4-address {
             leaf outgoing-interface {
               type if:interface-ref;
               mandatory true;
               description
                 &quot;Name of the outgoing interface.&quot;;
             }
             leaf ipv4-address {
               type inet:ipv4-address;
               mandatory true;
               description
                 &quot;The nexthop points to an interface with
                  an IPv4 address.&quot;;
             }
             description
               &quot;The nexthop is an egress-interface and an IP
                address.  This can be used in cases where, e.g.,
                the IP address is a link-local address.&quot;;
           }
         }
         case egress-interface-ipv6-nexthop {
           container egress-interface-ipv6-address {
             leaf outgoing-interface {
               type if:interface-ref;
               mandatory true;
               description
                 &quot;Name of the outgoing interface.&quot;;
             }
             leaf ipv6-address {
               type inet:ipv6-address;
               mandatory true;
               description
                 &quot;The nexthop points to an interface with
                  an IPv6 address.&quot;;
             }
             description
               &quot;The nexthop is an egress-interface and an IP
                address.  This can be used in cases where, e.g.,
                the IP address is a link-local address.&quot;;
           }
         }
         case egress-interface-mac-nexthop {
           container egress-interface-mac-address {
             leaf outgoing-interface {
               type if:interface-ref;
               mandatory true;
               description
                 &quot;Name of the outgoing interface.&quot;;
<span class="grey"><a href="/doc/html/rfc8431">RFC 8431</a>                     RIB Data Model               September 2018</span>

             }
             leaf ieee-mac-address {
               type yang:mac-address;
               mandatory true;
               description
                 &quot;The nexthop points to an interface with
                  a specific MAC address.&quot;;
             }
             description
               &quot;The egress-interface must be an Ethernet
                interface.  Address resolution is not required
                for this nexthop.&quot;;
           }
         }
         case tunnel-encapsulation-nexthop {
           if-feature &quot;nexthop-tunnel&quot;;
           container tunnel-encapsulation {
             uses tunnel-encapsulation;
             description
               &quot;This can be an encapsulation representing an IP
                tunnel, MPLS tunnel, or others as defined in the info
                model.  An optional egress-interface can be chained
                to the tunnel encapsulation to indicate which
                interface to send the packet out on.  The
                egress-interface is useful when the network device
                contains Ethernet interfaces and one needs to
                perform address resolution for the IP packet.&quot;;
           }
         }
         case tunnel-decapsulation-nexthop {
           if-feature &quot;nexthop-tunnel&quot;;
           container tunnel-decapsulation {
             uses tunnel-decapsulation;
             description
               &quot;This is to specify the decapsulation of a tunnel
                header.&quot;;
           }
         }
         case logical-tunnel-nexthop {
           if-feature &quot;nexthop-tunnel&quot;;
           container logical-tunnel {
             uses logical-tunnel;
             description
               &quot;This can be an MPLS Label Switched Path (LSP)
                or a GRE tunnel (or others as defined in this
                document) that is represented by a unique
                identifier (e.g., name).&quot;;
           }
<span class="grey"><a href="/doc/html/rfc8431">RFC 8431</a>                     RIB Data Model               September 2018</span>

         }
         case rib-name-nexthop {
           leaf rib-name {
             type string;
             description
               &quot;A nexthop pointing to a RIB indicates that the
                route lookup needs to continue in the specified
                RIB.  This is a way to perform chained lookups.&quot;;
           }
         }
         case nexthop-identifier {
           leaf nexthop-ref {
             type nexthop-ref;
             mandatory true;
             description
               &quot;A nexthop reference that points to a nexthop.&quot;;
           }
         }
       }
     }

     grouping route-vendor-attributes {
       description
         &quot;Route vendor attributes.&quot;;
     }

     grouping logical-tunnel {
       description
         &quot;A logical tunnel that is identified
          by a type and a tunnel name.&quot;;
       leaf tunnel-type {
         type tunnel-type-definition;
         mandatory true;
         description
           &quot;A tunnel type.&quot;;
       }
       leaf tunnel-name {
         type string;
         mandatory true;
         description
           &quot;A tunnel name that points to a logical tunnel.&quot;;
       }
     }

     grouping ipv4-header {
       description
         &quot;The IPv4 header encapsulation information.&quot;;
       leaf src-ipv4-address {
<span class="grey"><a href="/doc/html/rfc8431">RFC 8431</a>                     RIB Data Model               September 2018</span>

         type inet:ipv4-address;
         mandatory true;
         description
           &quot;The source IP address of the header.&quot;;
       }
       leaf dest-ipv4-address {
         type inet:ipv4-address;
         mandatory true;
         description
           &quot;The destination IP address of the header.&quot;;
       }
       leaf protocol {
         type uint8;
         mandatory true;
         description
           &quot;The protocol id of the header.&quot;;
       }
       leaf ttl {
         type uint8;
         description
           &quot;The TTL of the header.&quot;;
       }
       leaf dscp {
         type uint8;
         description
           &quot;The Differentiated Services Code Point
            (DSCP) field of the header.&quot;;
       }
     }

     grouping ipv6-header {
       description
         &quot;The IPv6 header encapsulation information.&quot;;
       leaf src-ipv6-address {
         type inet:ipv6-address;
         mandatory true;
         description
           &quot;The source IP address of the header.&quot;;
       }
       leaf dest-ipv6-address {
         type inet:ipv6-address;
         mandatory true;
         description
           &quot;The destination IP address of the header.&quot;;
       }
       leaf next-header {
         type uint8;
         mandatory true;
<span class="grey"><a href="/doc/html/rfc8431">RFC 8431</a>                     RIB Data Model               September 2018</span>

         description
           &quot;The next header of the IPv6 header.&quot;;
       }
       leaf traffic-class {
         type uint8;
         description
           &quot;The traffic class value of the header.&quot;;
       }
       leaf flow-label {
         type inet:ipv6-flow-label;
         description
           &quot;The flow label of the header.&quot;;
       }
       leaf hop-limit {
         type uint8 {
           range &quot;1..255&quot;;
         }
         description
           &quot;The hop limit of the header.&quot;;
       }
     }

     grouping nvgre-header {
       description
         &quot;The NVGRE header encapsulation information.&quot;;
       choice nvgre-type {
         description
           &quot;NVGRE can use either an IPv4
            or an IPv6 header for encapsulation.&quot;;
         case ipv4 {
           uses ipv4-header;
         }
         case ipv6 {
           uses ipv6-header;
         }
       }
       leaf virtual-subnet-id {
         type uint32;
         mandatory true;
         description
           &quot;The subnet identifier of the NVGRE header.&quot;;
       }
       leaf flow-id {
         type uint8;
         description
           &quot;The flow identifier of the NVGRE header.&quot;;
       }
     }
<span class="grey"><a href="/doc/html/rfc8431">RFC 8431</a>                     RIB Data Model               September 2018</span>

     grouping vxlan-header {
       description
         &quot;The VXLAN encapsulation header information.&quot;;
       choice vxlan-type {
         description
           &quot;NVGRE can use either an IPv4
            or an IPv6 header for encapsulation.&quot;;
         case ipv4 {
           uses ipv4-header;
         }
         case ipv6 {
           uses ipv6-header;
         }
       }
       leaf vxlan-identifier {
         type uint32;
         mandatory true;
         description
           &quot;The VXLAN identifier of the VXLAN header.&quot;;
       }
     }

     grouping gre-header {
       description
         &quot;The GRE encapsulation header information.&quot;;
       choice dest-address-type {
         description
           &quot;GRE options: IPv4 and IPv6&quot;;
         case ipv4 {
           leaf ipv4-dest {
             type inet:ipv4-address;
             mandatory true;
             description
               &quot;The destination IP address of the GRE header.&quot;;
           }
         }
         case ipv6 {
           leaf ipv6-dest {
             type inet:ipv6-address;
             mandatory true;
             description
               &quot;The destination IP address of the GRE header.&quot;;
           }
         }
       }
       leaf protocol-type {
         type uint16;
         mandatory true;
<span class="grey"><a href="/doc/html/rfc8431">RFC 8431</a>                     RIB Data Model               September 2018</span>

         description
           &quot;The protocol type of the GRE header.&quot;;
       }
       leaf key {
         type uint64;
         description
           &quot;The GRE key of the GRE header.&quot;;
       }
     }

     grouping mpls-header {
       description
         &quot;The MPLS encapsulation header information.&quot;;
       list label-operations {
         key &quot;label-oper-id&quot;;
         description
           &quot;Label operations.&quot;;
         leaf label-oper-id {
           type uint32;
           description
             &quot;An optional identifier that points
              to a label operation.&quot;;
         }
         choice label-actions {
           description
             &quot;Label action options.&quot;;
           case label-push {
             container label-push {
               description
                 &quot;Label push operation.&quot;;
               leaf label {
                 type uint32;
                 mandatory true;
                 description
                   &quot;The label to be pushed.&quot;;
               }
               leaf s-bit {
                 type boolean;
                 description
                   &quot;The s-bit (&#x27;Bottom of Stack&#x27; bit) of the label to be
                    pushed.&quot;;
               }
               leaf tc-value {
                 type uint8;
                 description
                   &quot;The traffic class value of the label to be pushed.&quot;;
               }
               leaf ttl-value {
<span class="grey"><a href="/doc/html/rfc8431">RFC 8431</a>                     RIB Data Model               September 2018</span>

                 type uint8;
                 description
                   &quot;The TTL value of the label to be pushed.&quot;;
               }
             }
           }
           case label-swap {
             container label-swap {
               description
                 &quot;Label swap operation.&quot;;
               leaf in-label {
                 type uint32;
                 mandatory true;
                 description
                   &quot;The label to be swapped.&quot;;
               }
               leaf out-label {
                 type uint32;
                 mandatory true;
                 description
                   &quot;The out MPLS label.&quot;;
               }
               leaf ttl-action {
                 type ttl-action-definition;
                 description
                   &quot;The label TTL actions:
                    - No-action
                    - Copy to inner label
                    - Decrease (the in-label)
                      by 1 and copy to the out-label&quot;;
               }
             }
           }
         }
       }
     }

     grouping tunnel-encapsulation {
       description
         &quot;Tunnel encapsulation information.&quot;;
       choice tunnel-type {
         description
           &quot;Tunnel options for nexthops.&quot;;
         case ipv4 {
           if-feature &quot;ipv4-tunnel&quot;;
           container ipv4-header {
             uses ipv4-header;
             description
<span class="grey"><a href="/doc/html/rfc8431">RFC 8431</a>                     RIB Data Model               September 2018</span>

               &quot;IPv4 header.&quot;;
           }
         }
         case ipv6 {
           if-feature &quot;ipv6-tunnel&quot;;
           container ipv6-header {
             uses ipv6-header;
             description
               &quot;IPv6 header.&quot;;
           }
         }
         case mpls {
           if-feature &quot;mpls-tunnel&quot;;
           container mpls-header {
             uses mpls-header;
             description
               &quot;MPLS header.&quot;;
           }
         }
         case gre {
           if-feature &quot;gre-tunnel&quot;;
           container gre-header {
             uses gre-header;
             description
               &quot;GRE header.&quot;;
           }
         }
         case nvgre {
           if-feature &quot;nvgre-tunnel&quot;;
           container nvgre-header {
             uses nvgre-header;
             description
               &quot;NVGRE header.&quot;;
           }
         }
         case vxlan {
           if-feature &quot;vxlan-tunnel&quot;;
           container vxlan-header {
             uses vxlan-header;
             description
               &quot;VXLAN header.&quot;;
           }
         }
       }
     }

     grouping tunnel-decapsulation {
       description
<span class="grey"><a href="/doc/html/rfc8431">RFC 8431</a>                     RIB Data Model               September 2018</span>

         &quot;Tunnel decapsulation information.&quot;;
       choice tunnel-type {
         description
           &quot;Nexthop tunnel type options.&quot;;
         case ipv4 {
           if-feature &quot;ipv4-tunnel&quot;;
           container ipv4-decapsulation {
             description
               &quot;IPv4 decapsulation.&quot;;
             leaf ipv4-decapsulation {
               type tunnel-decapsulation-action-definition;
               mandatory true;
               description
                 &quot;IPv4 decapsulation operations.&quot;;
             }
             leaf ttl-action {
               type ttl-action-definition;
               description
                 &quot;The TTL actions:
                  no-action or copy to inner header.&quot;;
             }
           }
         }
         case ipv6 {
           if-feature &quot;ipv6-tunnel&quot;;
           container ipv6-decapsulation {
             description
               &quot;IPv6 decapsulation.&quot;;
             leaf ipv6-decapsulation {
               type tunnel-decapsulation-action-definition;
               mandatory true;
               description
                 &quot;IPv6 decapsulation operations.&quot;;
             }
             leaf hop-limit-action {
               type hop-limit-action-definition;
               description
                 &quot;The hop limit actions:
                  no-action or copy to inner header.&quot;;
             }
           }
         }
         case mpls {
           if-feature &quot;mpls-tunnel&quot;;
           container label-pop {
             description
               &quot;MPLS decapsulation.&quot;;
             leaf label-pop {
<span class="grey"><a href="/doc/html/rfc8431">RFC 8431</a>                     RIB Data Model               September 2018</span>

               type mpls-label-action-definition;
               mandatory true;
               description
                 &quot;Pop a label from the label stack.&quot;;
             }
             leaf ttl-action {
               type ttl-action-definition;
               description
                 &quot;The label TTL action.&quot;;
             }
           }
         }
       }
     }

     grouping route-attributes {
       description
         &quot;Route attributes.&quot;;
       leaf route-preference {
         type uint32;
         mandatory true;
         description
           &quot;ROUTE_PREFERENCE: This is a numerical value that
            allows for comparing routes from different
            protocols.  Static configuration is also
            considered a protocol for the purpose of this
            field.  It is also known as administrative-distance.
            The lower the value, the higher the preference.&quot;;
       }
       leaf local-only {
         type boolean;
         mandatory true;
         description
           &quot;Indicate whether the attribute is local only.&quot;;
       }
       container address-family-route-attributes {
         description
           &quot;Address-family-related route attributes.&quot;;
         choice route-type {
           description
             &quot;Address-family-related route attributes. Future
              documents should specify these attributes by augmenting
              the cases in this choice.&quot;;
           case ip-route-attributes {
           }
           case mpls-route-attributes {
           }
           case ethernet-route-attributes {
<span class="grey"><a href="/doc/html/rfc8431">RFC 8431</a>                     RIB Data Model               September 2018</span>

           }
         }
       }
     }

     container routing-instance {
       description
         &quot;A routing instance, in the context of
          the RIB information model, is a collection
          of RIBs, interfaces, and routing parameters.&quot;;
       leaf name {
         type string;
         description
           &quot;The name of the routing instance.  This MUST
            be unique across all routing instances in
            a given network device.&quot;;
       }
       list interface-list {
         key &quot;name&quot;;
         description
           &quot;This represents the list of interfaces associated
            with this routing instance.  The interface list helps
            constrain the boundaries of packet forwarding.
            Packets coming on these interfaces are directly
            associated with the given routing instance.  The
            interface list contains a list of identifiers with
            each identifier uniquely identifying an interface.&quot;;
         leaf name {
           type if:interface-ref;
           description
             &quot;A reference to the name of a network-layer interface.&quot;;
         }
       }
       leaf router-id {
         type yang:dotted-quad;
         description
           &quot;Router ID: The 32-bit number in the form of a dotted quad.&quot;;
       }
       leaf lookup-limit {
         type uint8;
         description
           &quot;A limit on how many levels of a lookup can be performed.&quot;;
       }
       list rib-list {
         key &quot;name&quot;;
         description
           &quot;A list of RIBs that are associated with the routing
            instance.&quot;;
<span class="grey"><a href="/doc/html/rfc8431">RFC 8431</a>                     RIB Data Model               September 2018</span>

         leaf name {
           type string;
           mandatory true;
           description
             &quot;A reference to the name of each RIB.&quot;;
         }
         leaf address-family {
           type address-family-definition;
           mandatory true;
           description
             &quot;The address family of a RIB.&quot;;
         }
         leaf ip-rpf-check {
           type boolean;
           description
             &quot;Each RIB can be optionally associated with a
              ENABLE_IP_RPF_CHECK attribute that enables Reverse
              Path Forwarding (RPF) checks on all IP routes in that
              RIB.   An RPF check is used to
              prevent spoofing and limit malicious traffic.&quot;;
         }
         list route-list {
           key &quot;route-index&quot;;
           description
             &quot;A list of routes of a RIB.&quot;;
           uses route;
         }
         // This is a list that maintains the nexthops added to the RIB.
         uses nexthop-list;
       }
     }

     //RPC Operations

     rpc rib-add {
       description
         &quot;To add a RIB to an instance&quot;;
       input {
         leaf name {
           type string;
           mandatory true;
           description
             &quot;A reference to the name of the RIB
              that is to be added.&quot;;
         }
         leaf address-family {
           type address-family-definition;
           mandatory true;
<span class="grey"><a href="/doc/html/rfc8431">RFC 8431</a>                     RIB Data Model               September 2018</span>

           description
             &quot;The address family of the RIB.&quot;;
         }
         leaf ip-rpf-check {
           type boolean;
           description
             &quot;Each RIB can be optionally associated with an
              ENABLE_IP_RPF_CHECK attribute that enables
              RPF checks on all IP routes in that
              RIB.   An RPF check is used to
              prevent spoofing and limit malicious traffic.&quot;;
         }
       }
       output {
         leaf result {
           type boolean;
           mandatory true;
           description
             &quot;Return the result of the rib-add operation.
              true  - success;
              false - failed&quot;;
         }
         leaf reason {
           type string;
           description
             &quot;The specific reason that caused the failure.&quot;;
         }
       }
     }

     rpc rib-delete {
       description
         &quot;To delete a RIB from a routing instance.
          After deleting the RIB, all routes installed
          in the RIB will be deleted as well.&quot;;
       input {
         leaf name {
           type string;
           mandatory true;
           description
             &quot;A reference to the name of the RIB
              that is to be deleted.&quot;;
         }
       }
       output {
         leaf result {
           type boolean;
           mandatory true;
<span class="grey"><a href="/doc/html/rfc8431">RFC 8431</a>                     RIB Data Model               September 2018</span>

           description
             &quot;Return the result of the rib-delete operation.
              true  - success;
              false - failed&quot;;
         }
         leaf reason {
           type string;
           description
             &quot;The specific reason that caused failure.&quot;;
         }
       }
     }

     grouping route-operation-state {
       description
         &quot;Route operation state.&quot;;
       leaf success-count {
         type uint32;
         mandatory true;
         description
           &quot;The numbers of routes that are successfully
            added/deleted/updated.&quot;;
       }
       leaf failed-count {
         type uint32;
         mandatory true;
         description
           &quot;The numbers of the routes that fail
            to be added/deleted/updated.&quot;;
       }
       container failure-detail {
         description
           &quot;The failure detail reflects the reason why a route
            operation fails.  It is an array that includes the route
            index and error code of the failed route.&quot;;
         list failed-routes {
           key &quot;route-index&quot;;
           description
             &quot;The list of failed routes.&quot;;
           leaf route-index {
             type uint32;
             description
               &quot;The route index of the failed route.&quot;;
           }
           leaf error-code {
             type uint32;
             description
               &quot;The error code that reflects the failure reason.
<span class="grey"><a href="/doc/html/rfc8431">RFC 8431</a>                     RIB Data Model               September 2018</span>

                0 - Reserved
                1 - Trying to add a repeat route
                2 - Trying to delete or update a route that does not
                  exist
                3 - Malformed route attributes&quot;;
           }
         }
       }
     }

     rpc route-add {
       description
         &quot;To add a route or a list of routes to a RIB&quot;;
       input {
         leaf return-failure-detail {
           type boolean;
           default &quot;false&quot;;
           description
             &quot;Whether to return the failure detail.
              true  - return the failure detail
              false - do not return the failure detail
              The default is false.&quot;;
         }
         leaf rib-name {
           type string;
           mandatory true;
           description
             &quot;A reference to the name of a RIB.&quot;;
         }
         container routes {
           description
             &quot;The routes to be added to the RIB.&quot;;
           list route-list {
             key &quot;route-index&quot;;
             description
               &quot;The list of routes to be added.&quot;;
             uses route-prefix;
             container route-attributes {
               uses route-attributes;
               description
                 &quot;The route attributes.&quot;;
             }
             container route-vendor-attributes {
               if-feature &quot;route-vendor-attributes&quot;;
               uses route-vendor-attributes;
               description
                 &quot;The route vendor attributes.&quot;;
             }
<span class="grey"><a href="/doc/html/rfc8431">RFC 8431</a>                     RIB Data Model               September 2018</span>

             container nexthop {
               uses nexthop;
               description
                 &quot;The nexthop of the added route.&quot;;
             }
           }
         }
       }
       output {
         uses route-operation-state;
       }
     }

     rpc route-delete {
       description
         &quot;To delete a route or a list of routes from a RIB&quot;;
       input {
         leaf return-failure-detail {
           type boolean;
           default &quot;false&quot;;
           description
             &quot;Whether to return the failure detail.
              true  - return the failure detail
              false - do not return the failure detail
              The default is false.&quot;;
         }
         leaf rib-name {
           type string;
           mandatory true;
           description
             &quot;A reference to the name of a RIB.&quot;;
         }
         container routes {
           description
             &quot;The routes to be added to the RIB.&quot;;
           list route-list {
             key &quot;route-index&quot;;
             description
               &quot;The list of routes to be deleted.&quot;;
             uses route-prefix;
           }
         }
       }
       output {
         uses route-operation-state;
       }
     }

<span class="grey"><a href="/doc/html/rfc8431">RFC 8431</a>                     RIB Data Model               September 2018</span>

     grouping route-update-options {
       description
         &quot;Update options:
          1. update the nexthop
          2. update the route attributes
          3. update the route-vendor-attributes&quot;;
       choice update-options {
         description
           &quot;Update options:
            1. update the nexthop
            2. update the route attributes
            3. update the route-vendor-attributes&quot;;
         case update-nexthop {
           container updated-nexthop {
             uses nexthop;
             description
               &quot;The nexthop used for updating.&quot;;
           }
         }
         case update-route-attributes {
           container updated-route-attr {
             uses route-attributes;
             description
               &quot;The route attributes used for updating.&quot;;
           }
         }
         case update-route-vendor-attributes {
           container updated-route-vendor-attr {
             uses route-vendor-attributes;
             description
               &quot;The vendor route attributes used for updating.&quot;;
           }
         }
       }
     }

     rpc route-update {
       description
         &quot;To update a route or a list of routes of a RIB.
          The inputs:
            1. The match conditions, which could be:
              a. route prefix,
              b. route attributes, or
              c. nexthop.
            2. The update parameters to be used:
              a. new nexthop,
              b. new route attributes, or
              c. nexthop.
<span class="grey"><a href="/doc/html/rfc8431">RFC 8431</a>                     RIB Data Model               September 2018</span>

          Actions:
            1. update the nexthop
            2. update the route attributes
          The outputs:
            success-count - the number of routes updated
            failed-count - the number of routes fail to update
            failure-detail - the detail failure info
         &quot;;
       input {
         leaf return-failure-detail {
           type boolean;
           default &quot;false&quot;;
           description
             &quot;Whether to return the failure detail.
              true  - return the failure detail
              false - do not return the failure detail
              The default is false.&quot;;
         }
         leaf rib-name {
           type string;
           mandatory true;
           description
             &quot;A reference to the name of a RIB.&quot;;
         }
         choice match-options {
           description
             &quot;Match options.&quot;;
           case match-route-prefix {
             description
               &quot;Update the routes that match the route
                prefix(es) condition.&quot;;
             container input-routes {
               description
                 &quot;The matched routes to be updated.&quot;;
               list route-list {
                 key &quot;route-index&quot;;
                 description
                   &quot;The list of routes to be updated.&quot;;
                 uses route-prefix;
                 uses route-update-options;
               }
             }
           }
           case match-route-attributes {
             description
               &quot;Update the routes that match the
                route attributes condition.&quot;;
             container input-route-attributes {
<span class="grey"><a href="/doc/html/rfc8431">RFC 8431</a>                     RIB Data Model               September 2018</span>

               description
                 &quot;The route attributes are used for matching.&quot;;
               uses route-attributes;
             }
             container update-parameters {
               description
                 &quot;Update options:
                  1. update the nexthop
                  2. update the route attributes
                  3. update the route-vendor-attributes&quot;;
               uses route-update-options;
             }
           }
           case match-route-vendor-attributes {
             if-feature &quot;route-vendor-attributes&quot;;
             description
               &quot;Update the routes that match the
                vendor attributes condition&quot;;
             container input-route-vendor-attributes {
               description
                 &quot;The vendor route attributes are used for matching.&quot;;
               uses route-vendor-attributes;
             }
             container update-parameters-vendor {
               description
                 &quot;Update options:
                  1. update the nexthop
                  2. update the route attributes
                  3. update the route-vendor-attributes&quot;;
               uses route-update-options;
             }
           }
           case match-nexthop {
             description
               &quot;Update the routes that match the nexthop.&quot;;
             container input-nexthop {
               description
                 &quot;The nexthop used for matching.&quot;;
               uses nexthop;
             }
             container update-parameters-nexthop {
               description
                 &quot;Update options:
                  1. update the nexthop
                  2. update the route attributes
                  3. update the route-vendor-attributes&quot;;
               uses route-update-options;
             }
<span class="grey"><a href="/doc/html/rfc8431">RFC 8431</a>                     RIB Data Model               September 2018</span>

           }
         }
       }
       output {
         uses route-operation-state;
       }
     }
     rpc nh-add {
       description
         &quot;To add a nexthop to a RIB.
          Inputs parameters:
            1. rib-name
            2. nexthop
          Actions:
            Add the nexthop to the RIB
          Outputs:
            1. Operation result:
               true  - success
               false - failed
            2. nexthop identifier&quot;;
       input {
         leaf rib-name {
           type string;
           mandatory true;
           description
             &quot;A reference to the name of a RIB.&quot;;
         }
         uses nexthop;
       }
       output {
         leaf result {
           type boolean;
           mandatory true;
           description
             &quot;Return the result of the rib-add operation:
              true  - success
              false - failed&quot;;
         }
         leaf reason {
           type string;
           description
             &quot;The specific reason that caused the failure.&quot;;
         }
         leaf nexthop-id {
           type uint32;
           description
             &quot;A nexthop identifier that is allocated to the nexthop.&quot;;
         }
<span class="grey"><a href="/doc/html/rfc8431">RFC 8431</a>                     RIB Data Model               September 2018</span>

       }
     }

     rpc nh-delete {
       description
         &quot;To delete a nexthop from a RIB&quot;;
       input {
         leaf rib-name {
           type string;
           mandatory true;
           description
             &quot;A reference to the name of a RIB.&quot;;
         }
         uses nexthop;
       }
       output {
         leaf result {
           type boolean;
           mandatory true;
           description
             &quot;Return the result of the rib-add operation:
              true  - success;
              false - failed&quot;;
         }
         leaf reason {
           type string;
           description
             &quot;The specific reason that caused the failure.&quot;;
         }
       }
     }

     //Notifications

     notification nexthop-resolution-status-change {
       description
         &quot;Nexthop resolution status (resolved/unresolved)
          notification.&quot;;
       container nexthop {
         description
           &quot;The nexthop.&quot;;
         uses nexthop;
       }
       leaf nexthop-state {
         type nexthop-state-definition;
         mandatory true;
         description
           &quot;Nexthop resolution status (resolved/unresolved)
<span class="grey"><a href="/doc/html/rfc8431">RFC 8431</a>                     RIB Data Model               September 2018</span>

            notification.&quot;;
       }
     }

     notification route-change {
       description
         &quot;Route change notification.&quot;;
       leaf rib-name {
         type string;
         mandatory true;
         description
           &quot;A reference to the name of a RIB.&quot;;
       }
       leaf address-family {
         type address-family-definition;
         mandatory true;
         description
           &quot;The address family of a RIB.&quot;;
       }
       uses route-prefix;
       leaf route-installed-state {
         type route-installed-state-definition;
         mandatory true;
         description
           &quot;Indicates whether the route got installed in the FIB.&quot;;
       }
       leaf route-state {
         type route-state-definition;
         mandatory true;
         description
           &quot;Indicates whether a route is active or inactive.&quot;;
       }
       list route-change-reasons {
         key &quot;route-change-reason&quot;;
         description
           &quot;The reasons that cause the route change.  A route
            change may result from several reasons; for
            example, a nexthop becoming resolved will make a
            route A active, which is of better preference than
            a currently active route B, which results in the
            route A being installed&quot;;
         leaf route-change-reason {
           type route-change-reason-definition;
           mandatory true;
           description
             &quot;The reason that caused the route change.&quot;;
         }
       }
<span class="grey"><a href="/doc/html/rfc8431">RFC 8431</a>                     RIB Data Model               September 2018</span>

     }
   }
