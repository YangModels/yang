module ietf-inet-types {

  namespace &quot;urn:ietf:params:xml:ns:yang:ietf-inet-types&quot;;
  prefix &quot;inet&quot;;

  organization
   &quot;IETF NETMOD (NETCONF Data Modeling Language) Working Group&quot;;

  contact
   &quot;WG Web:   &lt;<a href="https://tools.ietf.org/wg/netmod/">http://tools.ietf.org/wg/netmod/</a>&gt;
    WG List:  &lt;mailto:<a href="mailto:netmod@ietf.org">netmod@ietf.org</a>&gt;

    WG Chair: David Partain
              &lt;mailto:<a href="mailto:david.partain@ericsson.com">david.partain@ericsson.com</a>&gt;

    WG Chair: David Kessens
              &lt;mailto:<a href="mailto:david.kessens@nsn.com">david.kessens@nsn.com</a>&gt;

    Editor:   Juergen Schoenwaelder
              &lt;mailto:<a href="mailto:j.schoenwaelder@jacobs-university.de">j.schoenwaelder@jacobs-university.de</a>&gt;&quot;;

  description
   &quot;This module contains a collection of generally useful derived
    YANG data types for Internet addresses and related things.

    Copyright (c) 2010 IETF Trust and the persons identified as
    authors of the code.  All rights reserved.

<span class="grey"><a href="/doc/html/rfc6021">RFC 6021</a>                       YANG-TYPES                   October 2010</span>

     Redistribution and use in source and binary forms, with or without
     modification, is permitted pursuant to, and subject to the license
     terms contained in, the Simplified BSD License set forth in <a href="#section-4">Section</a>
     <a href="#section-4">4</a>.c of the IETF Trust&#x27;s Legal Provisions Relating to IETF Documents
     (<a href="https://trustee.ietf.org/license-info">http://trustee.ietf.org/license-info</a>).

     This version of this YANG module is part of <a href="/doc/html/rfc6021">RFC 6021</a>; see
     the RFC itself for full legal notices.&quot;;

   revision 2010-09-24 {
     description
      &quot;Initial revision.&quot;;
     reference
      &quot;<a href="/doc/html/rfc6021">RFC 6021</a>: Common YANG Data Types&quot;;
   }

   /*** collection of protocol field related types ***/

   typedef ip-version {
     type enumeration {
       enum unknown {
         value &quot;0&quot;;
         description
          &quot;An unknown or unspecified version of the Internet protocol.&quot;;
       }
       enum ipv4 {
         value &quot;1&quot;;
         description
          &quot;The IPv4 protocol as defined in <a href="/doc/html/rfc791">RFC 791</a>.&quot;;
       }
       enum ipv6 {
         value &quot;2&quot;;
         description
          &quot;The IPv6 protocol as defined in <a href="/doc/html/rfc2460">RFC 2460</a>.&quot;;
       }
     }
     description
      &quot;This value represents the version of the IP protocol.

       In the value set and its semantics, this type is equivalent
       to the InetVersion textual convention of the SMIv2.&quot;;
     reference
      &quot;RFC  791: Internet Protocol
       <a href="/doc/html/rfc2460">RFC 2460</a>: Internet Protocol, Version 6 (IPv6) Specification
       <a href="/doc/html/rfc4001">RFC 4001</a>: Textual Conventions for Internet Network Addresses&quot;;
   }

   typedef dscp {
<span class="grey"><a href="/doc/html/rfc6021">RFC 6021</a>                       YANG-TYPES                   October 2010</span>

     type uint8 {
       range &quot;0..63&quot;;
     }
     description
      &quot;The dscp type represents a Differentiated Services Code-Point
       that may be used for marking packets in a traffic stream.

       In the value set and its semantics, this type is equivalent
       to the Dscp textual convention of the SMIv2.&quot;;
     reference
      &quot;<a href="/doc/html/rfc3289">RFC 3289</a>: Management Information Base for the Differentiated
                 Services Architecture
       <a href="/doc/html/rfc2474">RFC 2474</a>: Definition of the Differentiated Services Field
                 (DS Field) in the IPv4 and IPv6 Headers
       <a href="/doc/html/rfc2780">RFC 2780</a>: IANA Allocation Guidelines For Values In
                 the Internet Protocol and Related Headers&quot;;
   }

   typedef ipv6-flow-label {
     type uint32 {
       range &quot;0..1048575&quot;;
     }
     description
      &quot;The flow-label type represents flow identifier or Flow Label
       in an IPv6 packet header that may be used to discriminate
       traffic flows.

       In the value set and its semantics, this type is equivalent
       to the IPv6FlowLabel textual convention of the SMIv2.&quot;;
     reference
      &quot;<a href="/doc/html/rfc3595">RFC 3595</a>: Textual Conventions for IPv6 Flow Label
       <a href="/doc/html/rfc2460">RFC 2460</a>: Internet Protocol, Version 6 (IPv6) Specification&quot;;
   }

   typedef port-number {
     type uint16 {
       range &quot;0..65535&quot;;
     }
     description
      &quot;The port-number type represents a 16-bit port number of an
       Internet transport layer protocol such as UDP, TCP, DCCP, or
       SCTP.  Port numbers are assigned by IANA.  A current list of
       all assignments is available from &lt;<a href="https://www.iana.org/">http://www.iana.org/</a>&gt;.

       Note that the port number value zero is reserved by IANA.  In
       situations where the value zero does not make sense, it can
       be excluded by subtyping the port-number type.

<span class="grey"><a href="/doc/html/rfc6021">RFC 6021</a>                       YANG-TYPES                   October 2010</span>

       In the value set and its semantics, this type is equivalent
       to the InetPortNumber textual convention of the SMIv2.&quot;;
     reference
      &quot;RFC  768: User Datagram Protocol
       RFC  793: Transmission Control Protocol
       <a href="/doc/html/rfc4960">RFC 4960</a>: Stream Control Transmission Protocol
       <a href="/doc/html/rfc4340">RFC 4340</a>: Datagram Congestion Control Protocol (DCCP)
       <a href="/doc/html/rfc4001">RFC 4001</a>: Textual Conventions for Internet Network Addresses&quot;;
   }

   /*** collection of autonomous system related types ***/

   typedef as-number {
     type uint32;
     description
      &quot;The as-number type represents autonomous system numbers
       which identify an Autonomous System (AS).  An AS is a set
       of routers under a single technical administration, using
       an interior gateway protocol and common metrics to route
       packets within the AS, and using an exterior gateway
       protocol to route packets to other ASs&#x27;.  IANA maintains
       the AS number space and has delegated large parts to the
       regional registries.

       Autonomous system numbers were originally limited to 16
       bits.  BGP extensions have enlarged the autonomous system
       number space to 32 bits.  This type therefore uses an uint32
       base type without a range restriction in order to support
       a larger autonomous system number space.

       In the value set and its semantics, this type is equivalent
       to the InetAutonomousSystemNumber textual convention of
       the SMIv2.&quot;;
     reference
      &quot;<a href="/doc/html/rfc1930">RFC 1930</a>: Guidelines for creation, selection, and registration
                 of an Autonomous System (AS)
       <a href="/doc/html/rfc4271">RFC 4271</a>: A Border Gateway Protocol 4 (BGP-4)
       <a href="/doc/html/rfc4893">RFC 4893</a>: BGP Support for Four-octet AS Number Space
       <a href="/doc/html/rfc4001">RFC 4001</a>: Textual Conventions for Internet Network Addresses&quot;;
   }

   /*** collection of IP address and hostname related types ***/

   typedef ip-address {
     type union {
       type inet:ipv4-address;
       type inet:ipv6-address;
     }
<span class="grey"><a href="/doc/html/rfc6021">RFC 6021</a>                       YANG-TYPES                   October 2010</span>

     description
      &quot;The ip-address type represents an IP address and is IP
       version neutral.  The format of the textual representations
       implies the IP version.&quot;;
   }

   typedef ipv4-address {
     type string {
       pattern
         &#x27;(([0-9]|[1-9][0-9]|1[0-9][0-9]|2[0-4][0-9]|25[0-5])\.){3}&#x27;
       +  &#x27;([0-9]|[1-9][0-9]|1[0-9][0-9]|2[0-4][0-9]|25[0-5])&#x27;
       + &#x27;(%[\p{N}\p{L}]+)?&#x27;;
     }
     description
       &quot;The ipv4-address type represents an IPv4 address in
        dotted-quad notation.  The IPv4 address may include a zone
        index, separated by a % sign.

        The zone index is used to disambiguate identical address
        values.  For link-local addresses, the zone index will
        typically be the interface index number or the name of an
        interface.  If the zone index is not present, the default
        zone of the device will be used.

        The canonical format for the zone index is the numerical
        format&quot;;
   }

   typedef ipv6-address {
     type string {
       pattern &#x27;((:|[0-9a-fA-F]{0,4}):)([0-9a-fA-F]{0,4}:){0,5}&#x27;
             + &#x27;((([0-9a-fA-F]{0,4}:)?(:|[0-9a-fA-F]{0,4}))|&#x27;
             + &#x27;(((25[0-5]|2[0-4][0-9]|[01]?[0-9]?[0-9])\.){3}&#x27;
             + &#x27;(25[0-5]|2[0-4][0-9]|[01]?[0-9]?[0-9])))&#x27;
             + &#x27;(%[\p{N}\p{L}]+)?&#x27;;
       pattern &#x27;(([^:]+:){6}(([^:]+:[^:]+)|(.*\..*)))|&#x27;
             + &#x27;((([^:]+:)*[^:]+)?::(([^:]+:)*[^:]+)?)&#x27;
             + &#x27;(%.+)?&#x27;;
     }
     description
      &quot;The ipv6-address type represents an IPv6 address in full,
       mixed, shortened, and shortened-mixed notation.  The IPv6
       address may include a zone index, separated by a % sign.

<span class="grey"><a href="/doc/html/rfc6021">RFC 6021</a>                       YANG-TYPES                   October 2010</span>

       The zone index is used to disambiguate identical address
       values.  For link-local addresses, the zone index will
       typically be the interface index number or the name of an
       interface.  If the zone index is not present, the default
       zone of the device will be used.

       The canonical format of IPv6 addresses uses the compressed
       format described in <a href="/doc/html/rfc4291#section-2.2">RFC 4291, Section&amp;nbsp;2.2</a>, item 2 with the
       following additional rules: the :: substitution must be
       applied to the longest sequence of all-zero 16-bit chunks
       in an IPv6 address.  If there is a tie, the first sequence
       of all-zero 16-bit chunks is replaced by ::.  Single
       all-zero 16-bit chunks are not compressed.  The canonical
       format uses lowercase characters and leading zeros are
       not allowed.  The canonical format for the zone index is
       the numerical format as described in <a href="/doc/html/rfc4007#section-11.2">RFC 4007, Section&amp;nbsp;</a>
       <a href="#section-11.2">11.2</a>.&quot;;
     reference
      &quot;<a href="/doc/html/rfc4291">RFC 4291</a>: IP Version 6 Addressing Architecture
       <a href="/doc/html/rfc4007">RFC 4007</a>: IPv6 Scoped Address Architecture
       <a href="/doc/html/rfc5952">RFC 5952</a>: A Recommendation for IPv6 Address Text Representation&quot;;
   }

   typedef ip-prefix {
     type union {
       type inet:ipv4-prefix;
       type inet:ipv6-prefix;
     }
     description
      &quot;The ip-prefix type represents an IP prefix and is IP
       version neutral.  The format of the textual representations
       implies the IP version.&quot;;
   }

   typedef ipv4-prefix {
     type string {
       pattern
          &#x27;(([0-9]|[1-9][0-9]|1[0-9][0-9]|2[0-4][0-9]|25[0-5])\.){3}&#x27;
        +  &#x27;([0-9]|[1-9][0-9]|1[0-9][0-9]|2[0-4][0-9]|25[0-5])&#x27;
        + &#x27;/(([0-9])|([1-2][0-9])|(3[0-2]))&#x27;;
     }
     description
      &quot;The ipv4-prefix type represents an IPv4 address prefix.
       The prefix length is given by the number following the
       slash character and must be less than or equal to 32.

<span class="grey"><a href="/doc/html/rfc6021">RFC 6021</a>                       YANG-TYPES                   October 2010</span>

       A prefix length value of n corresponds to an IP address
       mask that has n contiguous 1-bits from the most
       significant bit (MSB) and all other bits set to 0.

       The canonical format of an IPv4 prefix has all bits of
       the IPv4 address set to zero that are not part of the
       IPv4 prefix.&quot;;
   }

   typedef ipv6-prefix {
     type string {
       pattern &#x27;((:|[0-9a-fA-F]{0,4}):)([0-9a-fA-F]{0,4}:){0,5}&#x27;
             + &#x27;((([0-9a-fA-F]{0,4}:)?(:|[0-9a-fA-F]{0,4}))|&#x27;
             + &#x27;(((25[0-5]|2[0-4][0-9]|[01]?[0-9]?[0-9])\.){3}&#x27;
             + &#x27;(25[0-5]|2[0-4][0-9]|[01]?[0-9]?[0-9])))&#x27;
             + &#x27;(/(([0-9])|([0-9]{2})|(1[0-1][0-9])|(12[0-8])))&#x27;;
       pattern &#x27;(([^:]+:){6}(([^:]+:[^:]+)|(.*\..*)))|&#x27;
             + &#x27;((([^:]+:)*[^:]+)?::(([^:]+:)*[^:]+)?)&#x27;
             + &#x27;(/.+)&#x27;;
     }
     description
      &quot;The ipv6-prefix type represents an IPv6 address prefix.
       The prefix length is given by the number following the
       slash character and must be less than or equal 128.

       A prefix length value of n corresponds to an IP address
       mask that has n contiguous 1-bits from the most
       significant bit (MSB) and all other bits set to 0.

       The IPv6 address should have all bits that do not belong
       to the prefix set to zero.

       The canonical format of an IPv6 prefix has all bits of
       the IPv6 address set to zero that are not part of the
       IPv6 prefix.  Furthermore, IPv6 address is represented
       in the compressed format described in <a href="/doc/html/rfc4291#section-2.2">RFC 4291, Section&amp;nbsp;</a>
       <a href="#section-2.2">2.2</a>, item 2 with the following additional rules: the ::
       substitution must be applied to the longest sequence of
       all-zero 16-bit chunks in an IPv6 address.  If there is
       a tie, the first sequence of all-zero 16-bit chunks is
       replaced by ::.  Single all-zero 16-bit chunks are not
       compressed.  The canonical format uses lowercase
       characters and leading zeros are not allowed.&quot;;
     reference
      &quot;<a href="/doc/html/rfc4291">RFC 4291</a>: IP Version 6 Addressing Architecture&quot;;
   }

<span class="grey"><a href="/doc/html/rfc6021">RFC 6021</a>                       YANG-TYPES                   October 2010</span>

   /*** collection of domain name and URI types ***/

   typedef domain-name {
     type string {
       pattern &#x27;((([a-zA-Z0-9_]([a-zA-Z0-9\-_]){0,61})?[a-zA-Z0-9]\.)*&#x27;
            +  &#x27;([a-zA-Z0-9_]([a-zA-Z0-9\-_]){0,61})?[a-zA-Z0-9]\.?)&#x27;
            +  &#x27;|\.&#x27;;
       length &quot;1..253&quot;;
     }
     description
      &quot;The domain-name type represents a DNS domain name.  The
       name SHOULD be fully qualified whenever possible.

       Internet domain names are only loosely specified.  <a href="/doc/html/rfc1034#section-3.5">Section</a>
       <a href="/doc/html/rfc1034#section-3.5">3.5 of RFC 1034</a> recommends a syntax (modified in <a href="/doc/html/rfc1123#section-2.1">Section</a>
       <a href="/doc/html/rfc1123#section-2.1">2.1 of RFC 1123</a>).  The pattern above is intended to allow
       for current practice in domain name use, and some possible
       future expansion.  It is designed to hold various types of
       domain names, including names used for A or AAAA records
       (host names) and other records, such as SRV records.  Note
       that Internet host names have a stricter syntax (described
       in <a href="/doc/html/rfc952">RFC 952</a>) than the DNS recommendations in RFCs 1034 and
       1123, and that systems that want to store host names in
       schema nodes using the domain-name type are recommended to
       adhere to this stricter standard to ensure interoperability.

       The encoding of DNS names in the DNS protocol is limited
       to 255 characters.  Since the encoding consists of labels
       prefixed by a length bytes and there is a trailing NULL
       byte, only 253 characters can appear in the textual dotted
       notation.

       The description clause of schema nodes using the domain-name
       type MUST describe when and how these names are resolved to
       IP addresses.  Note that the resolution of a domain-name value
       may require to query multiple DNS records (e.g., A for IPv4
       and AAAA for IPv6).  The order of the resolution process and
       which DNS record takes precedence can either be defined
       explicitely or it may depend on the configuration of the
       resolver.

       Domain-name values use the US-ASCII encoding.  Their canonical
       format uses lowercase US-ASCII characters.  Internationalized
       domain names MUST be encoded in punycode as described in <a href="/doc/html/rfc3492">RFC</a>
       <a href="/doc/html/rfc3492">3492</a>&quot;;
     reference
      &quot;RFC  952: DoD Internet Host Table Specification
       <a href="/doc/html/rfc1034">RFC 1034</a>: Domain Names - Concepts and Facilities
<span class="grey"><a href="/doc/html/rfc6021">RFC 6021</a>                       YANG-TYPES                   October 2010</span>

       <a href="/doc/html/rfc1123">RFC 1123</a>: Requirements for Internet Hosts -- Application
                 and Support
       <a href="/doc/html/rfc2782">RFC 2782</a>: A DNS RR for specifying the location of services
                 (DNS SRV)
       <a href="/doc/html/rfc3492">RFC 3492</a>: Punycode: A Bootstring encoding of Unicode for
                 Internationalized Domain Names in Applications
                 (IDNA)
       <a href="/doc/html/rfc5891">RFC 5891</a>: Internationalizing Domain Names in Applications
                 (IDNA): Protocol&quot;;
   }

   typedef host {
     type union {
       type inet:ip-address;
       type inet:domain-name;
     }
     description
      &quot;The host type represents either an IP address or a DNS
       domain name.&quot;;
   }

   typedef uri {
     type string;
     description
      &quot;The uri type represents a Uniform Resource Identifier
       (URI) as defined by STD 66.

       Objects using the uri type MUST be in US-ASCII encoding,
       and MUST be normalized as described by <a href="/doc/html/rfc3986">RFC 3986</a> Sections
       6.2.1, 6.2.2.1, and 6.2.2.2.  All unnecessary
       percent-encoding is removed, and all case-insensitive
       characters are set to lowercase except for hexadecimal
       digits, which are normalized to uppercase as described in
       <a href="#section-6.2.2.1">Section 6.2.2.1</a>.

       The purpose of this normalization is to help provide
       unique URIs.  Note that this normalization is not
       sufficient to provide uniqueness.  Two URIs that are
       textually distinct after this normalization may still be
       equivalent.

       Objects using the uri type may restrict the schemes that
       they permit.  For example, &#x27;data:&#x27; and &#x27;urn:&#x27; schemes
       might not be appropriate.

       A zero-length URI is not a valid URI.  This can be used to
       express &#x27;URI absent&#x27; where required.

<span class="grey"><a href="/doc/html/rfc6021">RFC 6021</a>                       YANG-TYPES                   October 2010</span>

       In the value set and its semantics, this type is equivalent
       to the Uri SMIv2 textual convention defined in <a href="/doc/html/rfc5017">RFC 5017</a>.&quot;;
     reference
      &quot;<a href="/doc/html/rfc3986">RFC 3986</a>: Uniform Resource Identifier (URI): Generic Syntax
       <a href="/doc/html/rfc3305">RFC 3305</a>: Report from the Joint W3C/IETF URI Planning Interest
                 Group: Uniform Resource Identifiers (URIs), URLs,
                 and Uniform Resource Names (URNs): Clarifications
                 and Recommendations
       <a href="/doc/html/rfc5017">RFC 5017</a>: MIB Textual Conventions for Uniform Resource
                 Identifiers (URIs)&quot;;
   }

 }
