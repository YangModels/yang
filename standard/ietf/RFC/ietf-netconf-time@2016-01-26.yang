module ietf-netconf-time {

   namespace &quot;urn:ietf:params:xml:ns:yang:ietf-netconf-time&quot;;

   prefix nct;
   import ietf-netconf { prefix nc; }

   import ietf-yang-types { prefix yang; }

   import ietf-netconf-monitoring { prefix ncm; }

   organization
     &quot;IETF&quot;;

   contact
     &quot;Editor: Tal Mizrahi
         &lt;<a href="mailto:dew@tx.technion.ac.il">dew@tx.technion.ac.il</a>&gt;
      Editor: Yoram Moses
         &lt;<a href="mailto:moses@ee.technion.ac.il">moses@ee.technion.ac.il</a>&gt;&quot;;

   description
     &quot;This module defines a capability-based extension to the
      Network Configuration Protocol (NETCONF) that allows
      time-triggered configuration and management operations.
      This extension allows NETCONF clients to invoke configuration
      updates according to scheduled times and allows NETCONF
      servers to attach timestamps to the data they send to NETCONF
      clients.

      Copyright (c) 2016 IETF Trust and the persons identified as
      the authors of the code.  All rights reserved.

      Redistribution and use in source and binary forms, with or
      without modification, is permitted pursuant to, and subject
      to the license terms contained in, the Simplified BSD License
      set forth in <a href="#section-4">Section 4</a>.c of the IETF Trust&#x27;s Legal Provisions
      Relating to IETF Documents
      (<a href="https://trustee.ietf.org/license-info">http://trustee.ietf.org/license-info</a>).&quot;;

   revision 2016-01-26 {
     description
       &quot;Initial version.&quot;;
<span class="grey"><a href="/doc/html/rfc7758">RFC 7758</a>               Time Capability in NETCONF          February 2016</span>

     reference
       &quot;<a href="/doc/html/rfc7758">RFC 7758</a>:
        Time Capability in NETCONF&quot;;
   }

   typedef time-interval {
     type string {
       pattern &#x27;\d{2}:\d{2}:\d{2}(\.\d+)?&#x27;;
     }
     description
       &quot;Defines a time interval, up to 24 hours.
        The format is specified as HH:mm:ss.f,
        consisting of two digits for hours,
        two digits for minutes, two digits
        for seconds, and zero or more digits
        representing second fractions.&quot;;
   }

   grouping scheduling-tolerance-parameters {
     leaf sched-max-future {
       type time-interval;
       default 00:00:15.0;
       description
         &quot;When the scheduled time is in the future, i.e., greater
          than the present time, this leaf defines the maximal
          difference between the scheduled time
          and the present time that the server is willing to
          accept.  If the difference exceeds this number, the
          server responds with an error.&quot;;
     }

     leaf sched-max-past {
       type time-interval;
       default 00:00:15.0;
       description
         &quot;When the scheduled time is in the past, i.e., less
          than the present time, this leaf defines the maximal
          difference between the present time
          and the scheduled time that the server is willing to
          accept.  If the difference exceeds this number, the
          server responds with an error.&quot;;
     }

     description
       &quot;Contains the parameters of the scheduling tolerance.&quot;;
   }
   // extending the get-config operation
   augment /nc:get-config/nc:input {
<span class="grey"><a href="/doc/html/rfc7758">RFC 7758</a>               Time Capability in NETCONF          February 2016</span>

     leaf scheduled-time {
       type yang:date-and-time;
       description
         &quot;The time at which the RPC is scheduled to be performed.&quot;;
     }

     leaf get-time {
       type empty;
       description
         &quot;Indicates that the rpc-reply should include the
          execution-time.&quot;;
     }

     description
       &quot;Adds the time element to &lt;get-config&gt;.&quot;;
   }

   augment /nc:get-config/nc:output {
     leaf execution-time {
       type yang:date-and-time;
       description
         &quot;The time at which the RPC was executed.&quot;;
     }

     description
       &quot;Adds the time element to &lt;get-config&gt;.&quot;;
   }

   augment /nc:get/nc:input {
     leaf scheduled-time {
       type yang:date-and-time;
       description
         &quot;The time at which the RPC is scheduled to be performed.&quot;;
     }

     leaf get-time {
       type empty;
       description
         &quot;Indicates that the rpc-reply should include the
          execution-time.&quot;;
     }

     description
       &quot;Adds the time element to &lt;get&gt;.&quot;;
   }

   augment /nc:get/nc:output {
     leaf execution-time {
<span class="grey"><a href="/doc/html/rfc7758">RFC 7758</a>               Time Capability in NETCONF          February 2016</span>

       type yang:date-and-time;
       description
         &quot;The time at which the RPC was executed.&quot;;
     }

     description
       &quot;Adds the time element to &lt;get&gt;.&quot;;
   }

   augment /nc:copy-config/nc:input {
     leaf scheduled-time {
       type yang:date-and-time;
       description
         &quot;The time at which the RPC is scheduled to be performed.&quot;;
     }

     leaf get-time {
       type empty;
       description
         &quot;Indicates that the rpc-reply should include the
          execution-time.&quot;;
     }

     description
       &quot;Adds the time element to &lt;copy-config&gt;.&quot;;
   }

   augment /nc:copy-config/nc:output {
     leaf execution-time {
       type yang:date-and-time;
       description
         &quot;The time at which the RPC was executed.&quot;;
     }

     description
       &quot;Adds the time element to &lt;copy-config&gt;.&quot;;
   }

   augment /nc:edit-config/nc:input {
     leaf scheduled-time {
       type yang:date-and-time;
       description
         &quot;The time at which the RPC is scheduled to be performed.&quot;;
     }

     leaf get-time {
       type empty;
       description
<span class="grey"><a href="/doc/html/rfc7758">RFC 7758</a>               Time Capability in NETCONF          February 2016</span>

         &quot;Indicates that the rpc-reply should include the
          execution-time.&quot;;
     }

     description
       &quot;Adds the time element to &lt;edit-config&gt;.&quot;;
   }

   augment /nc:edit-config/nc:output {
     leaf execution-time {
       type yang:date-and-time;
       description
         &quot;The time at which the RPC was executed.&quot;;
     }

     description
       &quot;Adds the time element to &lt;edit-config&gt;.&quot;;
   }

   augment /nc:delete-config/nc:input {
     leaf scheduled-time {
       type yang:date-and-time;
       description
         &quot;The time at which the RPC is scheduled to be performed.&quot;;
     }

     leaf get-time {
       type empty;
       description
         &quot;Indicates that the rpc-reply should include the
          execution-time.&quot;;
     }

     description
      &quot;Adds the time element to &lt;delete-config&gt;.&quot;;
   }

   augment /nc:delete-config/nc:output {
     leaf execution-time {
       type yang:date-and-time;
       description
         &quot;The time at which the RPC was executed.&quot;;
     }
     description
       &quot;Adds the time element to &lt;delete-config&gt;.&quot;;
   }

   augment /nc:lock/nc:input {
<span class="grey"><a href="/doc/html/rfc7758">RFC 7758</a>               Time Capability in NETCONF          February 2016</span>

     leaf scheduled-time {
       type yang:date-and-time;
       description
         &quot;The time at which the RPC is scheduled to be performed.&quot;;
     }

     leaf get-time {
       type empty;
       description
         &quot;Indicates that the rpc-reply should include the
          execution-time.&quot;;
     }

     description
       &quot;Adds the time element to &lt;lock&gt;.&quot;;
   }
   augment /nc:lock/nc:output {
     leaf execution-time {
       type yang:date-and-time;
       description
         &quot;The time at which the RPC was executed.&quot;;
     }

     description
       &quot;Adds the time element to &lt;lock&gt;.&quot;;
   }

   augment /nc:unlock/nc:input {
     leaf scheduled-time {
       type yang:date-and-time;
       description
         &quot;The time at which the RPC is scheduled to be performed.&quot;;
     }

     leaf get-time {
       type empty;
       description
         &quot;Indicates that the rpc-reply should include the
          execution-time.&quot;;
     }

     description
       &quot;Adds the time element to &lt;unlock&gt;.&quot;;
   }

   augment /nc:unlock/nc:output {
     leaf execution-time {
       type yang:date-and-time;
<span class="grey"><a href="/doc/html/rfc7758">RFC 7758</a>               Time Capability in NETCONF          February 2016</span>

       description
         &quot;The time at which the RPC was executed.&quot;;
     }

     description
       &quot;Adds the time element to &lt;unlock&gt;.&quot;;
   }
   augment /nc:commit/nc:input {
     leaf scheduled-time {
       type yang:date-and-time;
       description
         &quot;The time at which the RPC is scheduled to be performed.&quot;;
     }

     leaf get-time {
       type empty;
       description
         &quot;Indicates that the rpc-reply should include the
          execution-time.&quot;;
     }

     description
       &quot;Adds the time element to &lt;commit&gt;.&quot;;
   }

   augment /nc:commit/nc:output {
     leaf execution-time {
       type yang:date-and-time;
       description
         &quot;The time at which the RPC was executed.&quot;;
     }

     description
       &quot;Adds the time element to &lt;commit&gt;.&quot;;
   }

   augment /ncm:netconf-state {
     container scheduling-tolerance {
       uses scheduling-tolerance-parameters;
       description
         &quot;The scheduling tolerance when the time capability
          is enabled.&quot;;
     }
     description
       &quot;The scheduling tolerance of the server.&quot;;
   }

   rpc cancel-schedule {
<span class="grey"><a href="/doc/html/rfc7758">RFC 7758</a>               Time Capability in NETCONF          February 2016</span>

     description
       &quot;Cancels a scheduled message.&quot;;
     reference
       &quot;<a href="/doc/html/rfc7758">RFC 7758</a>:
        Time Capability in NETCONF&quot;;

     input {
       leaf cancelled-message-id {
         type string;
         description
           &quot;The ID of the message to be cancelled.&quot;;
       }
       leaf get-time {
         type empty;
         description
           &quot;Indicates that the rpc-reply should include
            the execution-time.&quot;;
       }
     }
     output {
       leaf execution-time {
         type yang:date-and-time;
         description
           &quot;The time at which the RPC was executed.&quot;;
       }
     }
   }

   notification netconf-scheduled-message {
     leaf schedule-id {
       type string;
       description
         &quot;The ID of the scheduled message.&quot;;
     }

     leaf scheduled-time {
       type yang:date-and-time;
       description
         &quot;The time at which the RPC is scheduled to be performed.&quot;;
     }
     description
       &quot;Indicates that a scheduled message was received.&quot;;
     reference
       &quot;<a href="/doc/html/rfc7758">RFC 7758</a>:
        Time Capability in NETCONF&quot;;
   }

}
