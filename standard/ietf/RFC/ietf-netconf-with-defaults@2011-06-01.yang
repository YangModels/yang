module ietf-netconf-with-defaults {

   namespace &quot;urn:ietf:params:xml:ns:yang:ietf-netconf-with-defaults&quot;;

   prefix ncwd;

   import ietf-netconf { prefix nc; }

   organization
    &quot;IETF NETCONF (Network Configuration Protocol) Working Group&quot;;

   contact
    &quot;WG Web:   &lt;<a href="https://tools.ietf.org/wg/netconf/">http://tools.ietf.org/wg/netconf/</a>&gt;

     WG List:  &lt;<a href="mailto:netconf@ietf.org">netconf@ietf.org</a>&gt;

     WG Chair: Bert Wijnen
               &lt;<a href="mailto:bertietf@bwijnen.net">bertietf@bwijnen.net</a>&gt;

     WG Chair: Mehmet Ersue
               &lt;<a href="mailto:mehmet.ersue@nsn.com">mehmet.ersue@nsn.com</a>&gt;

     Editor: Andy Bierman
             &lt;<a href="mailto:andy.bierman@brocade.com">andy.bierman@brocade.com</a>&gt;

     Editor: Balazs Lengyel
             &lt;<a href="mailto:balazs.lengyel@ericsson.com">balazs.lengyel@ericsson.com</a>&gt;&quot;;

   description
    &quot;This module defines an extension to the NETCONF protocol
     that allows the NETCONF client to control how default
     values are handled by the server in particular NETCONF
     operations.

     Copyright (c) 2011 IETF Trust and the persons identified as
     the document authors.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).

     This version of this YANG module is part of <a href="/doc/html/rfc6243">RFC 6243</a>; see
     the RFC itself for full legal notices.&quot;;
<span class="grey"><a href="/doc/html/rfc6243">RFC 6243</a>                      with-defaults                    June 2011</span>

     revision 2011-06-01 {
       description
         &quot;Initial version.&quot;;
       reference
        &quot;<a href="/doc/html/rfc6243">RFC 6243</a>: With-defaults Capability for NETCONF&quot;;
     }

     typedef with-defaults-mode {
        description
          &quot;Possible modes to report default data.&quot;;
        reference
           &quot;<a href="/doc/html/rfc6243">RFC 6243</a>; <a href="#section-3">Section 3</a>.&quot;;
        type enumeration {
           enum report-all {
               description
                 &quot;All default data is reported.&quot;;
               reference
                 &quot;<a href="/doc/html/rfc6243">RFC 6243</a>; <a href="#section-3.1">Section 3.1</a>&quot;;
           }
           enum report-all-tagged {
               description
                 &quot;All default data is reported.
                  Any nodes considered to be default data
                  will contain a &#x27;default&#x27; XML attribute,
                  set to &#x27;true&#x27; or &#x27;1&#x27;.&quot;;
               reference
                 &quot;<a href="/doc/html/rfc6243">RFC 6243</a>; <a href="#section-3.4">Section 3.4</a>&quot;;
           }
           enum trim {
               description
                 &quot;Values are not reported if they contain the default.&quot;;
               reference
                 &quot;<a href="/doc/html/rfc6243">RFC 6243</a>; <a href="#section-3.2">Section 3.2</a>&quot;;
           }
           enum explicit {
               description
                 &quot;Report values that contain the definition of
                  explicitly set data.&quot;;
               reference
                 &quot;<a href="/doc/html/rfc6243">RFC 6243</a>; <a href="#section-3.3">Section 3.3</a>&quot;;
           }
       }
     }

     grouping with-defaults-parameters {
       description
         &quot;Contains the &lt;with-defaults&gt; parameter for control
          of defaults in NETCONF retrieval operations.&quot;;
<span class="grey"><a href="/doc/html/rfc6243">RFC 6243</a>                      with-defaults                    June 2011</span>

       leaf with-defaults {
         description
           &quot;The explicit defaults processing mode requested.&quot;;
         reference
           &quot;<a href="/doc/html/rfc6243">RFC 6243</a>; <a href="#section-4.5.1">Section 4.5.1</a>&quot;;

         type with-defaults-mode;
       }
     }

     // extending the get-config operation
     augment /nc:get-config/nc:input {
         description
           &quot;Adds the &lt;with-defaults&gt; parameter to the
            input of the NETCONF &lt;get-config&gt; operation.&quot;;
         reference
           &quot;<a href="/doc/html/rfc6243">RFC 6243</a>; <a href="#section-4.5.1">Section 4.5.1</a>&quot;;

         uses with-defaults-parameters;
     }

     // extending the get operation
     augment /nc:get/nc:input {
         description
           &quot;Adds the &lt;with-defaults&gt; parameter to
            the input of the NETCONF &lt;get&gt; operation.&quot;;
         reference
           &quot;<a href="/doc/html/rfc6243">RFC 6243</a>; <a href="#section-4.5.1">Section 4.5.1</a>&quot;;

         uses with-defaults-parameters;
     }

     // extending the copy-config operation
     augment /nc:copy-config/nc:input {
         description
           &quot;Adds the &lt;with-defaults&gt; parameter to
            the input of the NETCONF &lt;copy-config&gt; operation.&quot;;
         reference
           &quot;<a href="/doc/html/rfc6243">RFC 6243</a>; <a href="#section-4.5.1">Section 4.5.1</a>&quot;;

         uses with-defaults-parameters;
     }

  }
