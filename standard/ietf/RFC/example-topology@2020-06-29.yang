module example-topology {
  yang-version 1.1;
  namespace "https://example.com/example-topology";
  prefix ex-topo;

  import ietf-network {
    prefix nw;
    reference
      "RFC 8345: A YANG Data Model for Network Topologies";
  }
  import ietf-network-topology {
    prefix nt;
    reference
      "RFC 8345: A YANG Data Model for Network Topologies";
  }
  import ietf-te-topology {
    prefix tet;
    reference
      "RFC 8795: YANG Data Model for Traffic Engineering (TE)
       Topologies";
  }

  organization
    "Example Organization";
  contact
    "Editor: Example Author";
  description
    "This module defines a topology data model for the example
     technology.";

  revision 2020-06-29 {
    description
      "Initial revision.";
    reference
      "Example reference";
  }

  /*
   * Data nodes
   */

  augment "/nw:networks/nw:network/nw:network-types/"
        + "tet:te-topology" {
    description
      "Augmentation for network types to define an example topology
       type.";
    container example-topology {
      presence "Introduces a new network type for an example
                topology";
      description
        "Its presence identifies the example topology type.";
    }
  }

  augment "/nw:networks/nw:network/tet:te" {
    when '../nw:network-types/tet:te-topology/'
       + 'ex-topo:example-topology' {
      description
        "Augmentation parameters apply only for networks with an
         example topology type.";
    }
    description
      "Augmentation for the network topology.";
    container attributes {
      description
        "Attributes for the example technology.";
      leaf attribute-1 {
        type uint8;
        description
          "Attribute 1 for the example technology.";
      }
    }
  }

  augment "/nw:networks/nw:network/nw:node/tet:te/"
        + "tet:te-node-attributes" {
    when '../../../nw:network-types/tet:te-topology/'
       + 'ex-topo:example-topology' {
      description
        "Augmentation parameters apply only for networks with an
         example topology type.";
    }
    description
      "Augmentation for node attributes.";
    container attributes {
      description
        "Attributes for the example technology.";
      leaf attribute-2 {
        type uint8;
        description
          "Attribute 2 for the example technology.";
      }
    }
  }

  augment "/nw:networks/nw:network/nw:node/tet:te/"
        + "tet:te-node-attributes/tet:connectivity-matrices" {
    when '../../../../nw:network-types/tet:te-topology/'
       + 'ex-topo:example-topology' {
      description
        "Augmentation parameters apply only for networks with an
         example topology type.";
    }
    description
      "Augmentation for node connectivity matrices.";
    container attributes {
      description
        "Attributes for the example technology.";
      leaf attribute-3 {
        type uint8;
        description
          "Attribute 3 for the example technology.";
      }
    }
  }

  augment "/nw:networks/nw:network/nw:node/tet:te/"
        + "tet:te-node-attributes/tet:connectivity-matrices/"
        + "tet:connectivity-matrix" {
    when '../../../../../nw:network-types/tet:te-topology/'
       + 'ex-topo:example-topology' {
      description
        "Augmentation parameters apply only for networks with an
         example topology type.";
    }
    description
      "Augmentation for the node connectivity matrix.";
    container attributes {
      description
        "Attributes for the example technology.";
      leaf attribute-3 {
        type uint8;
        description
          "Attribute 3 for the example technology.";
      }
    }
  }

  augment "/nw:networks/nw:network/nw:node/tet:te/"
        + "tet:tunnel-termination-point" {
    when '../../../nw:network-types/tet:te-topology/'
       + 'ex-topo:example-topology' {
      description
        "Augmentation parameters apply only for networks with an
         example topology type.";
    }
    description
      "Augmentation for a TTP.";
    container attributes {
      description
        "Attributes for the example technology.";
      leaf attribute-4 {
        type uint8;
        description
          "Attribute 4 for the example technology.";
      }
    }
  }

  augment "/nw:networks/nw:network/nw:node/nt:termination-point/"
        + "tet:te" {
    when '../../../nw:network-types/tet:te-topology/'
       + 'ex-topo:example-topology' {
      description
        "Augmentation parameters apply only for networks with an
         example topology type.";
    }
    description
      "Augmentation for an LTP.";
    container attributes {
      description
        "Attributes for the example technology.";
      leaf attribute-5 {
        type uint8;
        description
          "Attribute 5 for the example technology.";
      }
    }
  }

  augment "/nw:networks/nw:network/nt:link/tet:te/"
        + "tet:te-link-attributes" {
    when '../../../nw:network-types/tet:te-topology/'
       + 'ex-topo:example-topology' {
      description
        "Augmentation parameters apply only for networks with an
         example topology type.";
    }
    description
      "Augmentation for link attributes.";
    container attributes {
      description
        "Attributes for the example technology.";
      leaf attribute-6 {
        type uint8;
        description
          "Attribute 6 for the example technology.";
      }
    }
  }

  /*
   * Augmentations for TE bandwidth.
   */

  augment "/nw:networks/tet:te/tet:templates/"
        + "tet:link-template/tet:te-link-attributes/"
        + "tet:interface-switching-capability/tet:max-lsp-bandwidth/"
        + "tet:te-bandwidth/tet:technology" {
    case example {
      container example {
        description
          "Attributes for the example technology.";
        leaf bandwidth-1 {
          type uint32;
          description
            "Bandwidth 1 for the example technology.";
        }
      }
    }
    description
      "Augmentation for TE bandwidth.";
  }

  augment "/nw:networks/tet:te/tet:templates/"
        + "tet:link-template/tet:te-link-attributes/"
        + "tet:max-link-bandwidth/"
        + "tet:te-bandwidth/tet:technology" {
    case example {
      container example {
        description
          "Attributes for the example technology.";
        leaf bandwidth-1 {
          type uint32;
          description
            "Bandwidth 1 for the example technology.";
        }
      }
    }
    description
      "Augmentation for TE bandwidth.";
  }

  augment "/nw:networks/tet:te/tet:templates/"
        + "tet:link-template/tet:te-link-attributes/"
        + "tet:max-resv-link-bandwidth/"
        + "tet:te-bandwidth/tet:technology" {
    case example {
      container example {
        description
          "Attributes for the example technology.";
        leaf bandwidth-1 {
          type uint32;
          description
            "Bandwidth 1 for the example technology.";
        }
      }
    }
    description
      "Augmentation for TE bandwidth.";
  }

  augment "/nw:networks/tet:te/tet:templates/"
        + "tet:link-template/tet:te-link-attributes/"
        + "tet:unreserved-bandwidth/"
        + "tet:te-bandwidth/tet:technology" {
    case example {
      container example {
        description
          "Attributes for the example technology.";
        leaf bandwidth-1 {
          type uint32;
          description
            "Bandwidth 1 for the example technology.";
        }
      }
    }
    description
      "Augmentation for TE bandwidth.";
  }

  augment "/nw:networks/nw:network/nw:node/tet:te/"
        + "tet:te-node-attributes/tet:connectivity-matrices/"
        + "tet:path-constraints/tet:te-bandwidth/tet:technology" {
    when '../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nw:node/tet:te/"
        + "tet:te-node-attributes/tet:connectivity-matrices/"
        + "tet:connectivity-matrix/"
        + "tet:path-constraints/tet:te-bandwidth/tet:technology" {
    when '../../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nw:node/tet:te/"
        + "tet:information-source-entry/tet:connectivity-matrices/"
        + "tet:path-constraints/tet:te-bandwidth/tet:technology" {
    when '../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nw:node/tet:te/"
        + "tet:information-source-entry/tet:connectivity-matrices/"
        + "tet:connectivity-matrix/"
        + "tet:path-constraints/tet:te-bandwidth/tet:technology" {
    when '../../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nw:node/tet:te/"
        + "tet:tunnel-termination-point/"
        + "tet:client-layer-adaptation/tet:switching-capability/"
        + "tet:te-bandwidth/tet:technology" {
    when '../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nw:node/tet:te/"
        + "tet:tunnel-termination-point/"
        + "tet:local-link-connectivities/tet:path-constraints/"
        + "tet:te-bandwidth/tet:technology" {
    when '../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nw:node/tet:te/"
        + "tet:tunnel-termination-point/"
        + "tet:local-link-connectivities/"
        + "tet:local-link-connectivity/tet:path-constraints/"
        + "tet:te-bandwidth/tet:technology" {
    when '../../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nt:link/tet:te/"
        + "tet:te-link-attributes/"
        + "tet:interface-switching-capability/tet:max-lsp-bandwidth/"
        + "tet:te-bandwidth/tet:technology" {
    when '../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nt:link/tet:te/"
        + "tet:te-link-attributes/"
        + "tet:max-link-bandwidth/"
        + "tet:te-bandwidth/tet:technology" {
    when '../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nt:link/tet:te/"
        + "tet:te-link-attributes/"
        + "tet:max-resv-link-bandwidth/"
        + "tet:te-bandwidth/tet:technology" {
    when '../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nt:link/tet:te/"
        + "tet:information-source-entry/"
        + "tet:interface-switching-capability/tet:max-lsp-bandwidth/"
        + "tet:te-bandwidth/tet:technology" {
    when '../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nt:link/tet:te/"
        + "tet:information-source-entry/"
        + "tet:max-link-bandwidth/"
        + "tet:te-bandwidth/tet:technology" {
    when '../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nt:link/tet:te/"
        + "tet:information-source-entry/"
        + "tet:max-resv-link-bandwidth/"
        + "tet:te-bandwidth/tet:technology" {
    when '../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nt:link/tet:te/"
        + "tet:information-source-entry/"
        + "tet:unreserved-bandwidth/"
        + "tet:te-bandwidth/tet:technology" {
    when '../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  augment "/nw:networks/nw:network/nw:node/nt:termination-point/"
        + "tet:te/tet:interface-switching-capability/"
        + "tet:max-lsp-bandwidth/tet:te-bandwidth/tet:technology" {
    when '../../../../../../nw:network-types/tet:te-topology/'
       + 'ex-topo:example-topology' {
      description
        "Augmentation parameters apply only for networks with an
         example topology type.";
    }
    case example {
      container example {
        description
          "Attributes for the example technology.";
        leaf bandwidth-1 {
          type uint32;
          description
            "Bandwidth 1 for the example technology.";
        }
      }
    }
    description
      "Augmentation for TE bandwidth.";
  }

  /*
   * Augmentations for the TE label.
   */

  augment "/nw:networks/tet:te/tet:templates/"
        + "tet:link-template/tet:te-link-attributes/"
        + "tet:underlay/tet:primary-path/tet:path-element/tet:type/"
        + "tet:label/tet:label-hop/tet:te-label/tet:technology" {
    case example {
      container example {
        description
          "Attributes for the example technology.";
        leaf label-1 {
          type uint32;
          description
            "Label 1 for the example technology.";
        }
      }
    }
    description
      "Augmentation for the TE label.";
  }

  augment "/nw:networks/tet:te/tet:templates/"
        + "tet:link-template/tet:te-link-attributes/"
        + "tet:underlay/tet:backup-path/tet:path-element/tet:type/"
        + "tet:label/tet:label-hop/tet:te-label/tet:technology" {
    case example {
      container example {
        description
          "Attributes for the example technology.";
        leaf label-1 {
          type uint32;
          description
            "Label 1 for the example technology.";
        }
      }
    }
    description
      "Augmentation for the TE label.";
  }

  augment "/nw:networks/tet:te/tet:templates/"
        + "tet:link-template/tet:te-link-attributes/"
        + "tet:label-restrictions/tet:label-restriction/"
        + "tet:label-start/tet:te-label/tet:technology" {
    case example {
      container example {
        description
          "Attributes for the example technology.";
        leaf label-1 {
          type uint32;
          description
            "Label 1 for the example technology.";
        }
      }
    }
    description
      "Augmentation for the TE label.";
  }

  augment "/nw:networks/tet:te/tet:templates/"
        + "tet:link-template/tet:te-link-attributes/"
        + "tet:label-restrictions/tet:label-restriction/"
        + "tet:label-end/tet:te-label/tet:technology" {
    case example {
      container example {
        description
          "Attributes for the example technology.";
        leaf label-1 {
          type uint32;
          description
            "Label 1 for the example technology.";
        }
      }
    }
    description
      "Augmentation for the TE label.";
  }

  /* Under te-node-attributes/connectivity-matrices */

  augment "/nw:networks/nw:network/nw:node/tet:te/"
        + "tet:te-node-attributes/tet:connectivity-matrices/"
        + "tet:label-restrictions/tet:label-restriction/"
        + "tet:label-start/tet:te-label/tet:technology" {
    when '../../../../../../../../nw:network-types/tet:te-topology/'
       + 'ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:label-restrictions/tet:label-restriction/"
        + "tet:label-end/tet:te-label/tet:technology" {
    when '../../../../../../../../nw:network-types/tet:te-topology/'
       + 'ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:underlay/tet:primary-path/tet:path-element/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:underlay/tet:backup-path/tet:path-element/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:path-properties/tet:path-route-objects/"
        + "tet:path-route-object/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  /* Under te-node-attributes/.../connectivity-matrix */

  augment "/nw:networks/nw:network/nw:node/tet:te/"
        + "tet:te-node-attributes/tet:connectivity-matrices/"
        + "tet:connectivity-matrix/tet:from/tet:label-restrictions/"
        + "tet:label-restriction/tet:label-start/"
        + "tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:connectivity-matrix/tet:from/"
        + "tet:label-restrictions/tet:label-restriction/"
        + "tet:label-end/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:connectivity-matrix/tet:to/tet:label-restrictions/"
        + "tet:label-restriction/tet:label-start/"
        + "tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:connectivity-matrix/tet:to/"
        + "tet:label-restrictions/tet:label-restriction/"
        + "tet:label-end/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:connectivity-matrix/"
        + "tet:underlay/tet:primary-path/tet:path-element/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:connectivity-matrix/"
        + "tet:underlay/tet:backup-path/tet:path-element/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:te-node-attributes/tet:connectivity-matrices/"
        + "tet:connectivity-matrix/"
        + "tet:path-properties/tet:path-route-objects/"
        + "tet:path-route-object/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  /* Under information-source-entry/connectivity-matrices */

  augment "/nw:networks/nw:network/nw:node/tet:te/"
        + "tet:information-source-entry/tet:connectivity-matrices/"
        + "tet:label-restrictions/tet:label-restriction/"
        + "tet:label-start/tet:te-label/tet:technology" {
    when '../../../../../../../../nw:network-types/tet:te-topology/'
       + 'ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:label-restrictions/tet:label-restriction/"
        + "tet:label-end/tet:te-label/tet:technology" {
    when '../../../../../../../../nw:network-types/tet:te-topology/'
       + 'ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:underlay/tet:primary-path/tet:path-element/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:underlay/tet:backup-path/tet:path-element/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:path-properties/tet:path-route-objects/"
        + "tet:path-route-object/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  /* Under information-source-entry/.../connectivity-matrix */

  augment "/nw:networks/nw:network/nw:node/tet:te/"
        + "tet:information-source-entry/tet:connectivity-matrices/"
        + "tet:connectivity-matrix/tet:from/"
        + "tet:label-restrictions/tet:label-restriction/"
        + "tet:label-start/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:connectivity-matrix/tet:from/"
        + "tet:label-restrictions/tet:label-restriction/"
        + "tet:label-end/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:connectivity-matrix/tet:to/"
        + "tet:label-restrictions/tet:label-restriction/"
        + "tet:label-start/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:connectivity-matrix/tet:to/"
        + "tet:label-restrictions/tet:label-restriction/"
        + "tet:label-end/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:connectivity-matrix/"
        + "tet:underlay/tet:primary-path/tet:path-element/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:connectivity-matrix/"
        + "tet:underlay/tet:backup-path/tet:path-element/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:information-source-entry/tet:connectivity-matrices/"
        + "tet:connectivity-matrix/"
        + "tet:path-properties/tet:path-route-objects/"
        + "tet:path-route-object/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  /* Under tunnel-termination-point/local-link-connectivities */

  augment "/nw:networks/nw:network/nw:node/tet:te/"
        + "tet:tunnel-termination-point/"
        + "tet:local-link-connectivities/tet:label-restrictions/"
        + "tet:label-restriction/tet:label-start/tet:te-label/"
        + "tet:technology" {
    when '../../../../../../../../nw:network-types/tet:te-topology/'
       + 'ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:tunnel-termination-point/"
        + "tet:local-link-connectivities/tet:label-restrictions/"
        + "tet:label-restriction/tet:label-end/"
        + "tet:te-label/tet:technology" {
    when '../../../../../../../../nw:network-types/tet:te-topology/'
       + 'ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:tunnel-termination-point/"
        + "tet:local-link-connectivities/tet:underlay/"
        + "tet:primary-path/tet:path-element/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:tunnel-termination-point/"
        + "tet:local-link-connectivities/tet:underlay/"
        + "tet:backup-path/tet:path-element/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:tunnel-termination-point/"
        + "tet:local-link-connectivities/tet:path-properties/"
        + "tet:path-route-objects/tet:path-route-object/tet:type/"
        + "tet:label/tet:label-hop/tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  /* Under tunnel-termination-point/.../local-link-connectivity */

  augment "/nw:networks/nw:network/nw:node/tet:te/"
        + "tet:tunnel-termination-point/"
        + "tet:local-link-connectivities/"
        + "tet:local-link-connectivity/tet:label-restrictions/"
        + "tet:label-restriction/tet:label-start/"
        + "tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:tunnel-termination-point/"
        + "tet:local-link-connectivities/"
        + "tet:local-link-connectivity/tet:label-restrictions/"
        + "tet:label-restriction/tet:label-end/"
        + "tet:te-label/tet:technology" {
    when '../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:tunnel-termination-point/"
        + "tet:local-link-connectivities/"
        + "tet:local-link-connectivity/tet:underlay/"
        + "tet:primary-path/tet:path-element/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:tunnel-termination-point/"
        + "tet:local-link-connectivities/"
        + "tet:local-link-connectivity/tet:underlay/"
        + "tet:backup-path/tet:path-element/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nw:node/tet:te/"
        + "tet:tunnel-termination-point/"
        + "tet:local-link-connectivities/"
        + "tet:local-link-connectivity/tet:path-properties/"
        + "tet:path-route-objects/tet:path-route-object/tet:type/"
        + "tet:label/tet:label-hop/tet:te-label/tet:technology" {
    when '../../../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  /* Under te-link-attributes */

  augment "/nw:networks/nw:network/nt:link/tet:te/"
        + "tet:te-link-attributes/"
        + "tet:label-restrictions/tet:label-restriction/"
        + "tet:label-start/tet:te-label/tet:technology" {
    when '../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nt:link/tet:te/"
        + "tet:te-link-attributes/tet:label-restrictions/"
        + "tet:label-restriction/tet:label-end/"
        + "tet:te-label/tet:technology" {
    when '../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nt:link/tet:te/"
        + "tet:te-link-attributes/tet:underlay/"
        + "tet:primary-path/tet:path-element/tet:type/"
        + "tet:label/tet:label-hop/tet:te-label/tet:technology" {
    when '../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nt:link/tet:te/"
        + "tet:te-link-attributes/tet:underlay/"
        + "tet:backup-path/tet:path-element/tet:type/"
        + "tet:label/tet:label-hop/tet:te-label/tet:technology" {
    when '../../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  /* Under TE link information-source-entry */

  augment "/nw:networks/nw:network/nt:link/tet:te/"
        + "tet:information-source-entry/tet:label-restrictions/"
        + "tet:label-restriction/tet:label-start/"
        + "tet:te-label/tet:technology" {
    when '../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }

  augment "/nw:networks/nw:network/nt:link/tet:te/"
        + "tet:information-source-entry/tet:label-restrictions/"
        + "tet:label-restriction/tet:label-end/"
        + "tet:te-label/tet:technology" {
    when '../../../../../../../nw:network-types/'
       + 'tet:te-topology/ex-topo:example-topology' {
      description
        "Augmentation parameters apply only for networks with an
         example topology type.";
    }
    case example {
      container example {
        description
          "Attributes for the example technology.";
        leaf label-1 {
          type uint32;
          description
            "Label 1 for the example technology.";
        }
      }
    }
    description
      "Augmentation for the TE label.";
  }
}
