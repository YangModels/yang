module ietf-system {
  namespace &quot;urn:ietf:params:xml:ns:yang:ietf-system&quot;;
  prefix &quot;sys&quot;;

  import ietf-yang-types {
    prefix yang;
  }

  import ietf-inet-types {
    prefix inet;
  }

  import ietf-netconf-acm {
    prefix nacm;
  }

  import iana-crypt-hash {
    prefix ianach;
  }

  organization
    &quot;IETF NETMOD (NETCONF Data Modeling Language) Working Group&quot;;

<span class="grey"><a href="/doc/html/rfc7317">RFC 7317</a>                 YANG System Management              August 2014</span>

    contact
      &quot;WG Web:   &lt;<a href="https://tools.ietf.org/wg/netmod/">http://tools.ietf.org/wg/netmod/</a>&gt;
       WG List:  &lt;mailto:<a href="mailto:netmod@ietf.org">netmod@ietf.org</a>&gt;

       WG Chair: Thomas Nadeau
                 &lt;mailto:<a href="mailto:tnadeau@lucidvision.com">tnadeau@lucidvision.com</a>&gt;

       WG Chair: Juergen Schoenwaelder
                 &lt;mailto:<a href="mailto:j.schoenwaelder@jacobs-university.de">j.schoenwaelder@jacobs-university.de</a>&gt;

       Editor:   Andy Bierman
                 &lt;mailto:<a href="mailto:andy@yumaworks.com">andy@yumaworks.com</a>&gt;

       Editor:   Martin Bjorklund
                 &lt;mailto:<a href="mailto:mbj@tail-f.com">mbj@tail-f.com</a>&gt;&quot;;

    description
      &quot;This module contains a collection of YANG definitions for the
       configuration and identification of some common system
       properties within a device containing a NETCONF server.  This
       includes data node definitions for system identification,
       time-of-day management, user management, DNS resolver
       configuration, and some protocol operations for system
       management.

       Copyright (c) 2014 IETF Trust and the persons identified as
       authors of the code.  All rights reserved.

       Redistribution and use in source and binary forms, with or
       without modification, is permitted pursuant to, and subject
       to the license terms contained in, the Simplified BSD License
       set forth in <a href="#section-4">Section 4</a>.c of the IETF Trust&#x27;s Legal Provisions
       Relating to IETF Documents
       (<a href="https://trustee.ietf.org/license-info">http://trustee.ietf.org/license-info</a>).

       This version of this YANG module is part of <a href="/doc/html/rfc7317">RFC 7317</a>; see
       the RFC itself for full legal notices.&quot;;

    revision 2014-08-06 {
      description
        &quot;Initial revision.&quot;;
      reference
        &quot;<a href="/doc/html/rfc7317">RFC 7317</a>: A YANG Data Model for System Management&quot;;
    }

<span class="grey"><a href="/doc/html/rfc7317">RFC 7317</a>                 YANG System Management              August 2014</span>

   /*
    * Typedefs
    */

    typedef timezone-name {
      type string;
      description
        &quot;A time zone name as used by the Time Zone Database,
         sometimes referred to as the &#x27;Olson Database&#x27;.

         The exact set of valid values is an implementation-specific
         matter.  Client discovery of the exact set of time zone names
         for a particular server is out of scope.&quot;;
      reference
        &quot;<a href="/doc/html/rfc6557">RFC 6557</a>: Procedures for Maintaining the Time Zone Database&quot;;
     }

    /*
     * Features
     */

    feature radius {
      description
        &quot;Indicates that the device can be configured as a RADIUS
         client.&quot;;
      reference
        &quot;<a href="/doc/html/rfc2865">RFC 2865</a>: Remote Authentication Dial In User Service (RADIUS)&quot;;
    }

    feature authentication {
      description
        &quot;Indicates that the device supports configuration of
         user authentication.&quot;;
    }

    feature local-users {
      if-feature authentication;
      description
        &quot;Indicates that the device supports configuration of
         local user authentication.&quot;;
    }

<span class="grey"><a href="/doc/html/rfc7317">RFC 7317</a>                 YANG System Management              August 2014</span>

    feature radius-authentication {
      if-feature radius;
      if-feature authentication;
      description
        &quot;Indicates that the device supports configuration of user
         authentication over RADIUS.&quot;;
      reference
        &quot;<a href="/doc/html/rfc2865">RFC 2865</a>: Remote Authentication Dial In User Service (RADIUS)
         <a href="/doc/html/rfc5607">RFC 5607</a>: Remote Authentication Dial-In User Service (RADIUS)
                   Authorization for Network Access Server (NAS)
                   Management&quot;;
    }

    feature ntp {
      description
        &quot;Indicates that the device can be configured to use one or
         more NTP servers to set the system date and time.&quot;;
    }

    feature ntp-udp-port {
      if-feature ntp;
      description
        &quot;Indicates that the device supports the configuration of
         the UDP port for NTP servers.

         This is a &#x27;feature&#x27;, since many implementations do not support
         any port other than the default port.&quot;;
    }

    feature timezone-name {
      description
        &quot;Indicates that the local time zone on the device
         can be configured to use the TZ database
         to set the time zone and manage daylight saving time.&quot;;
      reference
        &quot;<a href="/doc/html/rfc6557">RFC 6557</a>: Procedures for Maintaining the Time Zone Database&quot;;
    }

    feature dns-udp-tcp-port {
      description
        &quot;Indicates that the device supports the configuration of
         the UDP and TCP port for DNS servers.

         This is a &#x27;feature&#x27;, since many implementations do not support
         any port other than the default port.&quot;;
    }

<span class="grey"><a href="/doc/html/rfc7317">RFC 7317</a>                 YANG System Management              August 2014</span>

    /*
     * Identities
     */

    identity authentication-method {
      description
        &quot;Base identity for user authentication methods.&quot;;
    }

    identity radius {
      base authentication-method;
      description
        &quot;Indicates user authentication using RADIUS.&quot;;
      reference
        &quot;<a href="/doc/html/rfc2865">RFC 2865</a>: Remote Authentication Dial In User Service (RADIUS)
         <a href="/doc/html/rfc5607">RFC 5607</a>: Remote Authentication Dial-In User Service (RADIUS)
                   Authorization for Network Access Server (NAS)
                   Management&quot;;
    }

    identity local-users {
      base authentication-method;
      description
        &quot;Indicates password-based authentication of locally
         configured users.&quot;;
    }

    identity radius-authentication-type {
      description
        &quot;Base identity for RADIUS authentication types.&quot;;
    }

    identity radius-pap {
      base radius-authentication-type;
      description
        &quot;The device requests Password Authentication Protocol (PAP)
         authentication from the RADIUS server.&quot;;
      reference
        &quot;<a href="/doc/html/rfc2865">RFC 2865</a>: Remote Authentication Dial In User Service (RADIUS)&quot;;
    }

<span class="grey"><a href="/doc/html/rfc7317">RFC 7317</a>                 YANG System Management              August 2014</span>

    identity radius-chap {
      base radius-authentication-type;
      description
        &quot;The device requests Challenge Handshake Authentication
         Protocol (CHAP) authentication from the RADIUS server.&quot;;
      reference
        &quot;<a href="/doc/html/rfc2865">RFC 2865</a>: Remote Authentication Dial In User Service (RADIUS)&quot;;
    }

    /*
     * Configuration data nodes
     */

    container system {
      description
        &quot;System group configuration.&quot;;

      leaf contact {
        type string;
        description
          &quot;The administrator contact information for the system.

           A server implementation MAY map this leaf to the sysContact
           MIB object.  Such an implementation needs to use some
           mechanism to handle the differences in size and characters
           allowed between this leaf and sysContact.  The definition of
           such a mechanism is outside the scope of this document.&quot;;
        reference
          &quot;<a href="/doc/html/rfc3418">RFC 3418</a>: Management Information Base (MIB) for the
                     Simple Network Management Protocol (SNMP)
                     SNMPv2-MIB.sysContact&quot;;
      }
      leaf hostname {
        type inet:domain-name;
       description
         &quot;The name of the host.  This name can be a single domain
          label or the fully qualified domain name of the host.&quot;;
      }
      leaf location {
        type string;
        description
          &quot;The system location.

           A server implementation MAY map this leaf to the sysLocation
           MIB object.  Such an implementation needs to use some
           mechanism to handle the differences in size and characters
           allowed between this leaf and sysLocation.  The definition
           of such a mechanism is outside the scope of this document.&quot;;
<span class="grey"><a href="/doc/html/rfc7317">RFC 7317</a>                 YANG System Management              August 2014</span>

        reference
          &quot;<a href="/doc/html/rfc3418">RFC 3418</a>: Management Information Base (MIB) for the
                     Simple Network Management Protocol (SNMP)
                     SNMPv2-MIB.sysLocation&quot;;
      }

      container clock {
        description
          &quot;Configuration of the system date and time properties.&quot;;

        choice timezone {
          description
            &quot;The system time zone information.&quot;;

          case timezone-name {
            if-feature timezone-name;
            leaf timezone-name {
              type timezone-name;
              description
                &quot;The TZ database name to use for the system, such
                 as &#x27;Europe/Stockholm&#x27;.&quot;;
            }
          }
          case timezone-utc-offset {
            leaf timezone-utc-offset {
              type int16 {
                range &quot;-1500 .. 1500&quot;;
              }
              units &quot;minutes&quot;;
              description
                &quot;The number of minutes to add to UTC time to
                 identify the time zone for this system.  For example,
                 &#x27;UTC - 8:00 hours&#x27; would be represented as &#x27;-480&#x27;.
                 Note that automatic daylight saving time adjustment
                 is not provided if this object is used.&quot;;
            }
          }
        }
      }

      container ntp {
        if-feature ntp;
        presence
          &quot;Enables the NTP client unless the &#x27;enabled&#x27; leaf
           (which defaults to &#x27;true&#x27;) is set to &#x27;false&#x27;&quot;;
        description
          &quot;Configuration of the NTP client.&quot;;

<span class="grey"><a href="/doc/html/rfc7317">RFC 7317</a>                 YANG System Management              August 2014</span>

        leaf enabled {
          type boolean;
          default true;
          description
            &quot;Indicates that the system should attempt to
             synchronize the system clock with an NTP server
             from the &#x27;ntp/server&#x27; list.&quot;;
        }
        list server {
          key name;
          description
            &quot;List of NTP servers to use for system clock
             synchronization.  If &#x27;/system/ntp/enabled&#x27;
             is &#x27;true&#x27;, then the system will attempt to
             contact and utilize the specified NTP servers.&quot;;

          leaf name {
            type string;
            description
              &quot;An arbitrary name for the NTP server.&quot;;
          }
          choice transport {
            mandatory true;
            description
              &quot;The transport-protocol-specific parameters for this
               server.&quot;;

            case udp {
              container udp {
                description
                  &quot;Contains UDP-specific configuration parameters
                   for NTP.&quot;;
                leaf address {
                  type inet:host;
                  mandatory true;
                  description
                    &quot;The address of the NTP server.&quot;;
                }
                leaf port {
                  if-feature ntp-udp-port;
                  type inet:port-number;
                  default 123;
                  description
                    &quot;The port number of the NTP server.&quot;;
                }
              }
            }
          }
<span class="grey"><a href="/doc/html/rfc7317">RFC 7317</a>                 YANG System Management              August 2014</span>

          leaf association-type {
            type enumeration {
              enum server {
                description
                  &quot;Use client association mode.  This device
                   will not provide synchronization to the
                   configured NTP server.&quot;;
              }
              enum peer {
                description
                  &quot;Use symmetric active association mode.
                   This device may provide synchronization
                   to the configured NTP server.&quot;;
              }
              enum pool {
                description
                  &quot;Use client association mode with one or
                   more of the NTP servers found by DNS
                   resolution of the domain name given by
                   the &#x27;address&#x27; leaf.  This device will not
                   provide synchronization to the servers.&quot;;
              }
            }
            default server;
            description
              &quot;The desired association type for this NTP server.&quot;;
          }
          leaf iburst {
            type boolean;
            default false;
            description
              &quot;Indicates whether this server should enable burst
               synchronization or not.&quot;;
          }
          leaf prefer {
            type boolean;
            default false;
            description
              &quot;Indicates whether this server should be preferred
               or not.&quot;;
          }
        }
      }

      container dns-resolver {
        description
          &quot;Configuration of the DNS resolver.&quot;;

<span class="grey"><a href="/doc/html/rfc7317">RFC 7317</a>                 YANG System Management              August 2014</span>

        leaf-list search {
          type inet:domain-name;
          ordered-by user;
          description
            &quot;An ordered list of domains to search when resolving
             a host name.&quot;;
        }
        list server {
          key name;
          ordered-by user;
          description
            &quot;List of the DNS servers that the resolver should query.

             When the resolver is invoked by a calling application, it
             sends the query to the first name server in this list.  If
             no response has been received within &#x27;timeout&#x27; seconds,
             the resolver continues with the next server in the list.
             If no response is received from any server, the resolver
             continues with the first server again.  When the resolver
             has traversed the list &#x27;attempts&#x27; times without receiving
             any response, it gives up and returns an error to the
             calling application.

             Implementations MAY limit the number of entries in this
             list.&quot;;

          leaf name {
            type string;
            description
              &quot;An arbitrary name for the DNS server.&quot;;
          }
          choice transport {
            mandatory true;
            description
              &quot;The transport-protocol-specific parameters for this
               server.&quot;;

            case udp-and-tcp {
              container udp-and-tcp {
                description
                  &quot;Contains UDP- and TCP-specific configuration
                   parameters for DNS.&quot;;
                reference
                  &quot;<a href="/doc/html/rfc1035">RFC 1035</a>: Domain Names - Implementation and
                             Specification
                   <a href="/doc/html/rfc5966">RFC 5966</a>: DNS Transport over TCP - Implementation
                             Requirements&quot;;

<span class="grey"><a href="/doc/html/rfc7317">RFC 7317</a>                 YANG System Management              August 2014</span>

                leaf address {
                  type inet:ip-address;
                  mandatory true;
                  description
                    &quot;The address of the DNS server.&quot;;
                }
                leaf port {
                  if-feature dns-udp-tcp-port;
                  type inet:port-number;
                  default 53;
                  description
                    &quot;The UDP and TCP port number of the DNS server.&quot;;
                }
              }
            }
          }
        }
        container options {
          description
            &quot;Resolver options.  The set of available options has been
             limited to those that are generally available across
             different resolver implementations and generally useful.&quot;;
          leaf timeout {
            type uint8 {
              range &quot;1..max&quot;;
            }
            units &quot;seconds&quot;;
            default &quot;5&quot;;
            description
              &quot;The amount of time the resolver will wait for a
               response from each remote name server before
               retrying the query via a different name server.&quot;;
          }
          leaf attempts {
            type uint8 {
              range &quot;1..max&quot;;
            }
            default &quot;2&quot;;
            description
              &quot;The number of times the resolver will send a query to
               all of its name servers before giving up and returning
               an error to the calling application.&quot;;
          }
        }
      }

<span class="grey"><a href="/doc/html/rfc7317">RFC 7317</a>                 YANG System Management              August 2014</span>

      container radius {
        if-feature radius;

        description
          &quot;Configuration of the RADIUS client.&quot;;

        list server {
          key name;
          ordered-by user;
          description
            &quot;List of RADIUS servers used by the device.

             When the RADIUS client is invoked by a calling
             application, it sends the query to the first server in
             this list.  If no response has been received within
             &#x27;timeout&#x27; seconds, the client continues with the next
             server in the list.  If no response is received from any
             server, the client continues with the first server again.
             When the client has traversed the list &#x27;attempts&#x27; times
             without receiving any response, it gives up and returns an
             error to the calling application.&quot;;

          leaf name {
            type string;
            description
              &quot;An arbitrary name for the RADIUS server.&quot;;
          }
          choice transport {
            mandatory true;
            description
              &quot;The transport-protocol-specific parameters for this
               server.&quot;;

            case udp {
              container udp {
                description
                  &quot;Contains UDP-specific configuration parameters
                   for RADIUS.&quot;;
                leaf address {
                  type inet:host;
                  mandatory true;
                  description
                    &quot;The address of the RADIUS server.&quot;;
                }

<span class="grey"><a href="/doc/html/rfc7317">RFC 7317</a>                 YANG System Management              August 2014</span>

                leaf authentication-port {
                  type inet:port-number;
                  default &quot;1812&quot;;
                  description
                    &quot;The port number of the RADIUS server.&quot;;
                }
                leaf shared-secret {
                  type string;
                  mandatory true;
                  nacm:default-deny-all;
                  description
                    &quot;The shared secret, which is known to both the
                     RADIUS client and server.&quot;;
                  reference
                    &quot;<a href="/doc/html/rfc2865">RFC 2865</a>: Remote Authentication Dial In User
                               Service (RADIUS)&quot;;
                }
              }
            }
          }
          leaf authentication-type {
            type identityref {
              base radius-authentication-type;
            }
            default radius-pap;
            description
              &quot;The authentication type requested from the RADIUS
               server.&quot;;
          }
        }
        container options {
          description
            &quot;RADIUS client options.&quot;;

          leaf timeout {
            type uint8 {
              range &quot;1..max&quot;;
            }
            units &quot;seconds&quot;;
            default &quot;5&quot;;
            description
              &quot;The number of seconds the device will wait for a
               response from each RADIUS server before trying with a
               different server.&quot;;
          }

<span class="grey"><a href="/doc/html/rfc7317">RFC 7317</a>                 YANG System Management              August 2014</span>

          leaf attempts {
            type uint8 {
              range &quot;1..max&quot;;
            }
            default &quot;2&quot;;
            description
              &quot;The number of times the device will send a query to
               all of its RADIUS servers before giving up.&quot;;
          }
        }
      }

      container authentication {
        nacm:default-deny-write;
        if-feature authentication;

         description
           &quot;The authentication configuration subtree.&quot;;

         leaf-list user-authentication-order {
           type identityref {
             base authentication-method;
           }
           must &#x27;(. != &quot;sys:radius&quot; or ../../radius/server)&#x27; {
             error-message
               &quot;When &#x27;radius&#x27; is used, a RADIUS server&quot;
             + &quot; must be configured.&quot;;
             description
               &quot;When &#x27;radius&#x27; is used as an authentication method,
                a RADIUS server must be configured.&quot;;
           }
           ordered-by user;

           description
             &quot;When the device authenticates a user with a password,
              it tries the authentication methods in this leaf-list in
              order.  If authentication with one method fails, the next
              method is used.  If no method succeeds, the user is
              denied access.

              An empty user-authentication-order leaf-list still allows
              authentication of users using mechanisms that do not
              involve a password.

              If the &#x27;radius-authentication&#x27; feature is advertised by
              the NETCONF server, the &#x27;radius&#x27; identity can be added to
              this list.

<span class="grey"><a href="/doc/html/rfc7317">RFC 7317</a>                 YANG System Management              August 2014</span>

              If the &#x27;local-users&#x27; feature is advertised by the
              NETCONF server, the &#x27;local-users&#x27; identity can be
              added to this list.&quot;;
         }

         list user {
           if-feature local-users;
           key name;
           description
             &quot;The list of local users configured on this device.&quot;;

           leaf name {
             type string;
             description
              &quot;The user name string identifying this entry.&quot;;
           }
           leaf password {
             type ianach:crypt-hash;
             description
               &quot;The password for this entry.&quot;;
           }
           list authorized-key {
             key name;
             description
               &quot;A list of public SSH keys for this user.  These keys
                are allowed for SSH authentication, as described in
                <a href="/doc/html/rfc4253">RFC 4253</a>.&quot;;
             reference
               &quot;<a href="/doc/html/rfc4253">RFC 4253</a>: The Secure Shell (SSH) Transport Layer
                          Protocol&quot;;

             leaf name {
               type string;
               description
                 &quot;An arbitrary name for the SSH key.&quot;;
             }

<span class="grey"><a href="/doc/html/rfc7317">RFC 7317</a>                 YANG System Management              August 2014</span>

             leaf algorithm {
               type string;
               mandatory true;
               description
                 &quot;The public key algorithm name for this SSH key.

                  Valid values are the values in the IANA &#x27;Secure Shell
                  (SSH) Protocol Parameters&#x27; registry, Public Key
                  Algorithm Names.&quot;;
               reference
                 &quot;IANA &#x27;Secure Shell (SSH) Protocol Parameters&#x27;
                  registry, Public Key Algorithm Names&quot;;
             }
             leaf key-data {
               type binary;
               mandatory true;
               description
                 &quot;The binary public key data for this SSH key, as
                  specified by <a href="/doc/html/rfc4253#section-6.6">RFC 4253, Section&amp;nbsp;6.6</a>, i.e.:

                    string    certificate or public key format
                              identifier
                    byte[n]   key/certificate data.&quot;;
               reference
                 &quot;<a href="/doc/html/rfc4253">RFC 4253</a>: The Secure Shell (SSH) Transport Layer
                            Protocol&quot;;
             }
           }
         }
       }
    }

    /*
     * Operational state data nodes
     */

    container system-state {
      config false;
      description
        &quot;System group operational state.&quot;;

      container platform {
        description
          &quot;Contains vendor-specific information for
           identifying the system platform and operating system.&quot;;
        reference
          &quot;IEEE Std 1003.1-2008 - sys/utsname.h&quot;;

<span class="grey"><a href="/doc/html/rfc7317">RFC 7317</a>                 YANG System Management              August 2014</span>

        leaf os-name {
          type string;
          description
            &quot;The name of the operating system in use -
             for example, &#x27;Linux&#x27;.&quot;;
          reference
            &quot;IEEE Std 1003.1-2008 - utsname.sysname&quot;;
        }
        leaf os-release {
          type string;
          description
            &quot;The current release level of the operating
             system in use.  This string MAY indicate
             the OS source code revision.&quot;;
          reference
            &quot;IEEE Std 1003.1-2008 - utsname.release&quot;;
        }
        leaf os-version {
          type string;
          description
            &quot;The current version level of the operating
             system in use.  This string MAY indicate
             the specific OS build date and target variant
             information.&quot;;
          reference
            &quot;IEEE Std 1003.1-2008 - utsname.version&quot;;
        }
        leaf machine {
          type string;
          description
            &quot;A vendor-specific identifier string representing
             the hardware in use.&quot;;
          reference
            &quot;IEEE Std 1003.1-2008 - utsname.machine&quot;;
        }
      }

      container clock {
        description
          &quot;Monitoring of the system date and time properties.&quot;;

        leaf current-datetime {
          type yang:date-and-time;
          description
            &quot;The current system date and time.&quot;;
        }

<span class="grey"><a href="/doc/html/rfc7317">RFC 7317</a>                 YANG System Management              August 2014</span>

        leaf boot-datetime {
          type yang:date-and-time;
          description
            &quot;The system date and time when the system last restarted.&quot;;
        }
      }
    }

    rpc set-current-datetime {
      nacm:default-deny-all;
      description
        &quot;Set the /system-state/clock/current-datetime leaf
         to the specified value.

         If the system is using NTP (i.e., /system/ntp/enabled
         is set to &#x27;true&#x27;), then this operation will fail with
         error-tag &#x27;operation-failed&#x27; and error-app-tag value of
         &#x27;ntp-active&#x27;.&quot;;
      input {
        leaf current-datetime {
          type yang:date-and-time;
          mandatory true;
          description
            &quot;The current system date and time.&quot;;
        }
      }
    }

    rpc system-restart {
      nacm:default-deny-all;
      description
        &quot;Request that the entire system be restarted immediately.
         A server SHOULD send an rpc reply to the client before
         restarting the system.&quot;;
    }

    rpc system-shutdown {
      nacm:default-deny-all;
      description
        &quot;Request that the entire system be shut down immediately.
         A server SHOULD send an rpc reply to the client before
         shutting down the system.&quot;;
    }

  }
