module ietf-microwave-radio-link {
  yang-version 1.1;
  namespace &quot;urn:ietf:params:xml:ns:yang:ietf-microwave-radio-link&quot;;
  prefix mrl;

<span class="grey"><a href="/doc/html/rfc8561">RFC 8561</a>          Microwave Radio Link YANG Data Model         June 2019</span>

     import ietf-yang-types {
       prefix yang;
       reference
         &quot;<a href="/doc/html/rfc6991">RFC 6991</a>&quot;;
     }
     import iana-if-type {
       prefix ianaift;
     }
     import ietf-interfaces {
       prefix if;
       reference
         &quot;<a href="/doc/html/rfc8343">RFC 8343</a>&quot;;
     }
     import ietf-interface-protection {
       prefix ifprot;
       reference
         &quot;<a href="/doc/html/rfc8561">RFC 8561</a>&quot;;
     }
     import ietf-microwave-types {
       prefix mw-types;
       reference
         &quot;<a href="/doc/html/rfc8561">RFC 8561</a>&quot;;
     }

     organization
       &quot;Internet Engineering Task Force (IETF) CCAMP WG&quot;;
     contact
       &quot;WG List: &lt;mailto:<a href="mailto:ccamp@ietf.org">ccamp@ietf.org</a>&gt;

        Editors:
         Jonas Ahlberg (<a href="mailto:jonas.ahlberg@ericsson.com">jonas.ahlberg@ericsson.com</a>)
         Min Ye (<a href="mailto:amy.yemin@huawei.com">amy.yemin@huawei.com</a>)
         Xi Li (<a href="mailto:Xi.Li@neclab.eu">Xi.Li@neclab.eu</a>)
         Daniela Spreafico (<a href="mailto:daniela.spreafico@nokia.com">daniela.spreafico@nokia.com</a>)
         Marko Vaupotic (<a href="mailto:Marko.Vaupotic@aviatnet.com">Marko.Vaupotic@aviatnet.com</a>)&quot;;
     description
       &quot;This is a module for the entities in
        a generic microwave system.

        Copyright (c) 2019 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).
<span class="grey"><a href="/doc/html/rfc8561">RFC 8561</a>          Microwave Radio Link YANG Data Model         June 2019</span>

        This version of this YANG module is part of <a href="/doc/html/rfc8561">RFC 8561</a>; see
        the RFC itself for full legal notices.&quot;;

     revision 2019-06-19 {
       description
         &quot;Initial revision.&quot;;
       reference
         &quot;<a href="/doc/html/rfc8561">RFC 8561</a>: A YANG Data Model for Microwave Radio Link&quot;;
     }

     /*
      * Features
      */

     feature xpic {
       description
         &quot;Indicates that the device supports XPIC.&quot;;
       reference
         &quot;ETSI TR 102 311&quot;;
     }

     feature mimo {
       description
         &quot;Indicates that the device supports MIMO.&quot;;
       reference
         &quot;ETSI TR 102 311&quot;;
     }

     feature tdm {
       description
         &quot;Indicates that the device supports TDM.&quot;;
     }

     /*
      * Typedefs
      */

     typedef power {
       type decimal64 {
         fraction-digits 1;
       }
       description
         &quot;Type used for the power values in the data nodes
          for configuration or status.&quot;;
     }

<span class="grey"><a href="/doc/html/rfc8561">RFC 8561</a>          Microwave Radio Link YANG Data Model         June 2019</span>

     /*
      * Radio Link Terminal (RLT)
      */

     augment &quot;/if:interfaces/if:interface&quot; {
       when &quot;derived-from-or-self(if:type,&quot;
          + &quot;&#x27;ianaift:microwaveRadioLinkTerminal&#x27;)&quot;;
       description
         &quot;Addition of data nodes for the radio link terminal to
          the standard Interface data model, for interfaces of
          the type &#x27;microwaveRadioLinkTerminal&#x27;.&quot;;
       leaf id {
         type string;
         description
           &quot;Descriptive identity of the radio link terminal used by
            far-end RLT to check that it&#x27;s connected to the correct
            near-end RLT.  Does not need to be configured if this
            check is not used.&quot;;
       }
       leaf mode {
         type identityref {
           base mw-types:rlt-mode;
         }
         mandatory true;
         description
           &quot;A description of the mode in which the radio link
            terminal is configured.  The format is X plus Y.
            X represents the number of bonded carrier terminations.
            Y represents the number of protecting carrier
            terminations.&quot;;
       }
       leaf-list carrier-terminations {
         type if:interface-ref;
         must &quot;derived-from-or-self(/if:interfaces/if:interface&quot;
            + &quot;[if:name = current()]&quot;
            + &quot;/if:type, &#x27;ianaift:microwaveCarrierTermination&#x27;)&quot; {
           description
             &quot;The type of interface must be
              &#x27;microwaveCarrierTermination&#x27;.&quot;;
         }
         min-elements 1;
         description
           &quot;A list of references to carrier terminations
            included in the radio link terminal.&quot;;
       }

<span class="grey"><a href="/doc/html/rfc8561">RFC 8561</a>          Microwave Radio Link YANG Data Model         June 2019</span>

       leaf-list rlp-groups {
         type leafref {
           path &quot;/mrl:radio-link-protection-groups/&quot;
              + &quot;mrl:protection-group/mrl:name&quot;;
         }
         description
           &quot;A list of references to the carrier termination
            groups configured for radio link protection in this
            radio link terminal.&quot;;
       }
       leaf-list xpic-pairs {
         if-feature &quot;xpic&quot;;
         type leafref {
           path &quot;/mrl:xpic-pairs/mrl:xpic-pair/mrl:name&quot;;
         }
         description
           &quot;A list of references to the XPIC pairs used in this
            radio link terminal.  One pair can be used by two
            terminals.&quot;;
         reference
           &quot;ETSI TR 102 311&quot;;
       }
       leaf-list mimo-groups {
         if-feature &quot;mimo&quot;;
         type leafref {
           path &quot;/mrl:mimo-groups/mrl:mimo-group/mrl:name&quot;;
         }
         description
           &quot;A reference to the MIMO group used in this
            radio link terminal.  One group can be used by more
            than one terminal.&quot;;
         reference
           &quot;ETSI TR 102 311&quot;;
       }
       list tdm-connections {
         if-feature &quot;tdm&quot;;
         key &quot;tdm-type&quot;;
         description
           &quot;A list stating the number of active TDM connections
            of a specified tdm-type that is configured to be
            supported by the RLT.&quot;;
         leaf tdm-type {
           type identityref {
             base mw-types:tdm-type;
           }
           description
             &quot;The type of TDM connection, which also indicates
              the supported capacity.&quot;;
<span class="grey"><a href="/doc/html/rfc8561">RFC 8561</a>          Microwave Radio Link YANG Data Model         June 2019</span>

         }
         leaf tdm-connections {
           type uint16;
           mandatory true;
           description
             &quot;Number of connections of the specified type.&quot;;
         }
       }
     }

     /*
      * Carrier Termination
      */

     augment &quot;/if:interfaces/if:interface&quot; {
       when &quot;derived-from-or-self(if:type,&quot;
          + &quot;&#x27;ianaift:microwaveCarrierTermination&#x27;)&quot;;
       description
         &quot;Addition of data nodes for carrier termination to
          the standard Interface data model, for interfaces
          of the type &#x27;microwaveCarrierTermination&#x27;.&quot;;
       leaf carrier-id {
         type string;
         default &quot;A&quot;;
         description
           &quot;ID of the carrier (e.g., A, B, C, or D).
            Used in XPIC and MIMO configurations to check that
            the carrier termination is connected to the correct
            far-end carrier termination.  Should be the same
            carrier ID on both sides of the hop.  Left as
            default value when MIMO and XPIC are not in use.&quot;;
       }
       leaf tx-enabled {
         type boolean;
         default &quot;false&quot;;
         description
           &quot;Disables (false) or enables (true) the transmitter.
            Only applicable when the interface is enabled
            (interface:enabled = true); otherwise, it&#x27;s always
            disabled.&quot;;
       }
       leaf tx-oper-status {
         type enumeration {
           enum off {
             description
               &quot;Transmitter is off.&quot;;
           }
           enum on {
<span class="grey"><a href="/doc/html/rfc8561">RFC 8561</a>          Microwave Radio Link YANG Data Model         June 2019</span>

             description
               &quot;Transmitter is on.&quot;;
           }
           enum standby {
             description
               &quot;Transmitter is in standby.&quot;;
           }
         }
         config false;
         description
           &quot;Shows the operative status of the transmitter.&quot;;
       }
       leaf tx-frequency {
         type uint32;
         units &quot;kHz&quot;;
         mandatory true;
         description
           &quot;Selected transmitter frequency.&quot;;
       }
       choice freq-or-distance {
         leaf rx-frequency {
           type uint32;
           units &quot;kHz&quot;;
           description
             &quot;Selected receiver frequency.&quot;;
         }
         leaf duplex-distance {
           type int32;
           units &quot;kHz&quot;;
           description
             &quot;Distance between transmitter and receiver frequencies.&quot;;
         }
         mandatory true;
         description
           &quot;A choice to configure rx-frequency directly or compute
            it as duplex-distance subtracted from tx-frequency.&quot;;
       }
       leaf actual-rx-frequency {
         type uint32;
         units &quot;kHz&quot;;
         config false;
         description
           &quot;Computed receiver frequency.&quot;;
       }
       leaf actual-duplex-distance {
         type uint32;
         units &quot;kHz&quot;;
         config false;
<span class="grey"><a href="/doc/html/rfc8561">RFC 8561</a>          Microwave Radio Link YANG Data Model         June 2019</span>

         description
           &quot;Computed distance between Tx and Rx frequencies.&quot;;
       }
       leaf channel-separation {
         type uint32;
         units &quot;kHz&quot;;
         mandatory true;
         description
           &quot;The amount of bandwidth allocated to a carrier.  The
            distance between adjacent channels in a radio
            frequency channels arrangement&quot;;
         reference
           &quot;ETSI EN 302 217-1&quot;;
       }
       leaf polarization {
         type enumeration {
           enum horizontal {
             description
               &quot;Horizontal polarization.&quot;;
           }
           enum vertical {
             description
               &quot;Vertical polarization.&quot;;
           }
           enum not-specified {
             description
               &quot;Polarization not specified.&quot;;
           }
         }
         default &quot;not-specified&quot;;
         description
           &quot;Polarization - a textual description for info only.&quot;;
       }
       choice power-mode {
         container rtpc {
           description
             &quot;Remote Transmit Power Control (RTPC).&quot;;
           reference
             &quot;ETSI EN 302 217-1&quot;;
           leaf maximum-nominal-power {
             type power {
               range &quot;-99..99&quot;;
             }
             units &quot;dBm&quot;;
             mandatory true;
             description
               &quot;Selected output power.&quot;;

<span class="grey"><a href="/doc/html/rfc8561">RFC 8561</a>          Microwave Radio Link YANG Data Model         June 2019</span>

             reference
               &quot;ETSI EN 302 217-1&quot;;
           }
         }
         container atpc {
           description
             &quot;Automatic Transmitter Power Control (ATPC).&quot;;
           reference
             &quot;ETSI EN 302 217-1&quot;;
           leaf maximum-nominal-power {
             type power {
               range &quot;-99..99&quot;;
             }
             units &quot;dBm&quot;;
             mandatory true;
             description
               &quot;Selected maximum output power.  Minimum output
                power is the same as the system capability,
                minimum-power.&quot;;
             reference
               &quot;ETSI EN 302 217-1&quot;;
           }
           leaf atpc-lower-threshold {
             type power {
               range &quot;-99..-20&quot;;
             }
             units &quot;dBm&quot;;
             must &#x27;current() &lt;= ../atpc-upper-threshold&#x27;;
             mandatory true;
             description
               &quot;The lower threshold for the input power at the
                far end, which is used in the ATPC mode.&quot;;
             reference
               &quot;ETSI EN 302 217-1&quot;;
           }
           leaf atpc-upper-threshold {
             type power {
               range &quot;-99..-20&quot;;
             }
             units &quot;dBm&quot;;
             mandatory true;
             description
               &quot;The upper threshold for the input power at the
                far end, which is used in the ATPC mode.&quot;;
             reference
               &quot;ETSI EN 302 217-1&quot;;
           }
         }
<span class="grey"><a href="/doc/html/rfc8561">RFC 8561</a>          Microwave Radio Link YANG Data Model         June 2019</span>

         mandatory true;
         description
           &quot;A choice of RTPC or ATPC.&quot;;
       }
       leaf actual-transmitted-level {
         type power {
           range &quot;-99..99&quot;;
         }
         units &quot;dBm&quot;;
         config false;
         description
           &quot;Actual transmitted power level (0.1 dBm resolution).&quot;;
         reference
           &quot;ETSI EN 301 129&quot;;
       }
       leaf actual-received-level {
         type power {
           range &quot;-99..-20&quot;;
         }
         units &quot;dBm&quot;;
         config false;
         description
           &quot;Actual received power level (0.1 dBm resolution).&quot;;
         reference
           &quot;ETSI EN 301 129&quot;;
       }
       choice coding-modulation-mode {
         container single {
           description
             &quot;A single modulation order only.&quot;;
           reference
             &quot;ETSI EN 302 217-1&quot;;
           leaf selected-cm {
             type identityref {
               base mw-types:coding-modulation;
             }
             mandatory true;
             description
               &quot;Selected the single coding/modulation.&quot;;
           }
         }
         container adaptive {
           description
             &quot;Adaptive coding/modulation.&quot;;
           reference
             &quot;ETSI EN 302 217-1&quot;;

<span class="grey"><a href="/doc/html/rfc8561">RFC 8561</a>          Microwave Radio Link YANG Data Model         June 2019</span>

           leaf selected-min-acm {
             type identityref {
               base mw-types:coding-modulation;
             }
             mandatory true;
             description
               &quot;Selected minimum coding/modulation.
                Adaptive coding/modulation shall not go
                below this value.&quot;;
           }
           leaf selected-max-acm {
             type identityref {
               base mw-types:coding-modulation;
             }
             mandatory true;
             description
               &quot;Selected maximum coding/modulation.
                Adaptive coding/modulation shall not go
                above this value.&quot;;
           }
         }
         mandatory true;
         description
           &quot;A selection of single or
            adaptive coding/modulation mode.&quot;;
       }
       leaf actual-tx-cm {
         type identityref {
           base mw-types:coding-modulation;
         }
         config false;
         description
           &quot;Actual coding/modulation in transmitting direction.&quot;;
       }
       leaf actual-snir {
         type decimal64 {
           fraction-digits 1;
           range &quot;0..99&quot;;
         }
         units &quot;dB&quot;;
         config false;
         description
           &quot;Actual signal to noise plus the interference ratio
            (0.1 dB resolution).&quot;;
       }
       leaf actual-xpi {
         if-feature &quot;xpic&quot;;
         type decimal64 {
<span class="grey"><a href="/doc/html/rfc8561">RFC 8561</a>          Microwave Radio Link YANG Data Model         June 2019</span>

           fraction-digits 1;
           range &quot;0..99&quot;;
         }
         units &quot;dB&quot;;
         config false;
         description
           &quot;The actual carrier to cross-polar interference.
            Only valid if XPIC is enabled (0.1 dB resolution).&quot;;
         reference
           &quot;ETSI TR 102 311&quot;;
       }
       container ct-performance-thresholds {
         description
           &quot;Specification of thresholds for when alarms should
            be sent and cleared for various performance counters.&quot;;
         leaf received-level-alarm-threshold {
           type power {
             range &quot;-99..-20&quot;;
           }
           units &quot;dBm&quot;;
           default &quot;-99&quot;;
           description
             &quot;An alarm is sent when the received power level is
              below the specified threshold.&quot;;
           reference
             &quot;ETSI EN 301 129&quot;;
         }
         leaf transmitted-level-alarm-threshold {
           type power {
             range &quot;-99..99&quot;;
           }
           units &quot;dBm&quot;;
           default &quot;-99&quot;;
           description
             &quot;An alarm is sent when the transmitted power level
              is below the specified threshold.&quot;;
           reference
             &quot;ETSI EN 301 129&quot;;
         }
         leaf ber-alarm-threshold {
           type enumeration {
             enum 1e-9 {
               description
                 &quot;Threshold at 1e-9 (10^-9).&quot;;
             }
             enum 1e-8 {
               description
                 &quot;Threshold at 1e-8 (10^-8).&quot;;
<span class="grey"><a href="/doc/html/rfc8561">RFC 8561</a>          Microwave Radio Link YANG Data Model         June 2019</span>

             }
             enum 1e-7 {
               description
                 &quot;Threshold at 1e-7 (10^-7).&quot;;
             }
             enum 1e-6 {
               description
                 &quot;Threshold at 1e-6 (10^-6).&quot;;
             }
             enum 1e-5 {
               description
                 &quot;Threshold at 1e-5 (10^-5).&quot;;
             }
             enum 1e-4 {
               description
                 &quot;Threshold at 1e-4 (10^-4).&quot;;
             }
             enum 1e-3 {
               description
                 &quot;Threshold at 1e-3 (10^-3).&quot;;
             }
             enum 1e-2 {
               description
                 &quot;Threshold at 1e-2 (10^-2).&quot;;
             }
             enum 1e-1 {
               description
                 &quot;Threshold at 1e-1 (10^-1).&quot;;
             }
           }
           default &quot;1e-6&quot;;
           description
             &quot;Specification of at which BER an alarm should
              be raised.&quot;;
           reference
             &quot;ETSI EN 302 217-1&quot;;
         }
       }
       leaf if-loop {
         type enumeration {
           enum disabled {
             description
               &quot;Disables the IF Loop.&quot;;
           }
           enum client {
             description
               &quot;Loops the signal back to the client side.&quot;;
           }
<span class="grey"><a href="/doc/html/rfc8561">RFC 8561</a>          Microwave Radio Link YANG Data Model         June 2019</span>

           enum radio {
             description
               &quot;Loops the signal back to the radio side.&quot;;
           }
         }
         default &quot;disabled&quot;;
         description
           &quot;Enable (client/radio) or disable (disabled)
            the IF Loop, which loops the signal back to
            the client side or the radio side.&quot;;
       }
       leaf rf-loop {
         type enumeration {
           enum disabled {
             description
               &quot;Disables the RF Loop.&quot;;
           }
           enum client {
             description
               &quot;Loops the signal back to the client side.&quot;;
           }
           enum radio {
             description
               &quot;Loops the signal back to the radio side.&quot;;
           }
         }
         default &quot;disabled&quot;;
         description
           &quot;Enable (client/radio) or disable (disabled)
            the RF loop, which loops the signal back to
            the client side or the radio side.&quot;;
       }
       container capabilities {
         config false;
         description
           &quot;Capabilities of the installed equipment and
            some selected configurations.&quot;;
         leaf min-tx-frequency {
           type uint32;
           units &quot;kHz&quot;;
           description
             &quot;Minimum Tx frequency possible to use.&quot;;
         }
         leaf max-tx-frequency {
           type uint32;
           units &quot;kHz&quot;;
           description
             &quot;Maximum Tx frequency possible to use.&quot;;
<span class="grey"><a href="/doc/html/rfc8561">RFC 8561</a>          Microwave Radio Link YANG Data Model         June 2019</span>

         }
         leaf min-rx-frequency {
           type uint32;
           units &quot;kHz&quot;;
           description
             &quot;Minimum Rx frequency possible to use.&quot;;
         }
         leaf max-rx-frequency {
           type uint32;
           units &quot;kHz&quot;;
           description
             &quot;Maximum Tx frequency possible to use.&quot;;
         }
         leaf minimum-power {
           type power;
           units &quot;dBm&quot;;
           description
             &quot;The minimum output power supported.&quot;;
           reference
             &quot;ETSI EN 302 217-1&quot;;
         }
         leaf maximum-available-power {
           type power;
           units &quot;dBm&quot;;
           description
             &quot;The maximum output power supported.&quot;;
           reference
             &quot;ETSI EN 302 217-1&quot;;
         }
         leaf available-min-acm {
           type identityref {
             base mw-types:coding-modulation;
           }
           description
             &quot;Minimum coding-modulation possible to use.&quot;;
         }
         leaf available-max-acm {
           type identityref {
             base mw-types:coding-modulation;
           }
           description
             &quot;Maximum coding-modulation possible to use.&quot;;
         }
       }
       container error-performance-statistics {
         config false;

<span class="grey"><a href="/doc/html/rfc8561">RFC 8561</a>          Microwave Radio Link YANG Data Model         June 2019</span>

         description
           &quot;ITU-T G.826 error performance statistics relevant for
            a microwave/millimeter wave carrier.&quot;;
         leaf bbe {
           type yang:counter32;
           units &quot;number of block errors&quot;;
           description
             &quot;Number of Background Block Errors (BBEs).  A BBE is an
              errored block not occurring as part of Severely Errored
              Seconds (SES).  Discontinuities in the value of this
              counter can occur at re-initialization of the management
              system and at other times as indicated by the value of
              &#x27;discontinuity-time&#x27; in ietf-interfaces.&quot;;
           reference
             &quot;ITU-T G.826&quot;;
         }
         leaf es {
           type yang:counter32;
           units &quot;seconds&quot;;
           description
             &quot;Number of Errored Seconds (ES).  An ES is a one-second
              period with one or more errored blocks or at least one
              defect.  Discontinuities in the value of this counter
              can occur at re-initialization of the management system
              and at other times as indicated by the value of
              &#x27;discontinuity-time&#x27; in ietf-interfaces.&quot;;
           reference
             &quot;ITU-T G.826&quot;;
         }
         leaf ses {
           type yang:counter32;
           units &quot;seconds&quot;;
           description
             &quot;Number of SES.  SES is a one-second period that contains
              equal or more than 30% errored blocks or at least
              one defect.  SES is a subset of ES.  Discontinuities in
              the value of this counter can occur at re-initialization
              of the management system and at other times as indicated
              by the value of &#x27;discontinuity-time&#x27; in ietf-interfaces.&quot;;
           reference
             &quot;ITU-T G.826&quot;;
         }
         leaf uas {
           type yang:counter32;
           units &quot;seconds&quot;;
           description
             &quot;Number of Unavailable Seconds (UAS); that is, the
              total time that the node has been unavailable.
<span class="grey"><a href="/doc/html/rfc8561">RFC 8561</a>          Microwave Radio Link YANG Data Model         June 2019</span>

              Discontinuities in the value of this counter can occur
              at re-initialization of the management system and at
              other times as indicated by the value of
              &#x27;discontinuity-time&#x27; in ietf-interfaces.&quot;;
           reference
             &quot;ITU-T G.826&quot;;
         }
       }
       container radio-performance-statistics {
         config false;
         description
           &quot;ETSI EN 301 129 radio physical interface statistics relevant
            for a carrier termination.&quot;;
         leaf min-rltm {
           type power {
             range &quot;-99..-20&quot;;
           }
           units &quot;dBm&quot;;
           description
             &quot;Minimum received power level.  Discontinuities in the
              value of this counter can occur at re-initialization
              of the management system and at other times as
              indicated by the value of &#x27;discontinuity-time&#x27; in
              ietf-interfaces.&quot;;
           reference
             &quot;ETSI EN 301 129&quot;;
         }
         leaf max-rltm {
           type power {
             range &quot;-99..-20&quot;;
           }
           units &quot;dBm&quot;;
           description
             &quot;Maximum received power level.  Discontinuities in the
              value of this counter can occur at re-initialization
              of the management system and at other times as
              indicated by the value of &#x27;discontinuity-time&#x27; in
              ietf-interfaces.&quot;;
           reference
             &quot;ETSI EN 301 129&quot;;
         }
         leaf min-tltm {
           type power {
             range &quot;-99..99&quot;;
           }
           units &quot;dBm&quot;;

<span class="grey"><a href="/doc/html/rfc8561">RFC 8561</a>          Microwave Radio Link YANG Data Model         June 2019</span>

           description
             &quot;Minimum transmitted power level.  Discontinuities
              in the value of this counter can occur at
              re-initialization of the management system and
              at other times as indicated by the value of
              &#x27;discontinuity-time&#x27; in ietf-interfaces.&quot;;
           reference
             &quot;ETSI EN 301 129&quot;;
         }
         leaf max-tltm {
           type power {
             range &quot;-99..99&quot;;
           }
           units &quot;dBm&quot;;
           description
             &quot;Maximum transmitted power level.  Discontinuities
              in the value of this counter can occur at
              re-initialization of the management system and
              at other times as indicated by the value of
              &#x27;discontinuity-time&#x27; in ietf-interfaces.&quot;;
           reference
             &quot;ETSI EN 301 129&quot;;
         }
       }
     }

     /*
      * Radio Link Protection Groups
      */

     container radio-link-protection-groups {
       description
         &quot;Configuration of radio link protected groups of
          carrier terminations in a radio link.  More than one
          protected group per radio link terminal is allowed.&quot;;
       uses ifprot:protection-groups {
         refine &quot;protection-group/members&quot; {
           must &quot;derived-from-or-self(/if:interfaces/if:interface&quot;
              + &quot;[if:name = current()]&quot;
              + &quot;/if:type, &#x27;ianaift:microwaveCarrierTermination&#x27;)&quot; {
             description
               &quot;The type of a protection member must be
                &#x27;microwaveCarrierTermination&#x27;.&quot;;
           }
         }
         refine &quot;protection-group/working-entity&quot; {
           must &quot;derived-from-or-self(/if:interfaces/if:interface&quot;
              + &quot;[if:name = current()]&quot;
<span class="grey"><a href="/doc/html/rfc8561">RFC 8561</a>          Microwave Radio Link YANG Data Model         June 2019</span>

              + &quot;/if:type, &#x27;ianaift:microwaveCarrierTermination&#x27;)&quot; {
             description
               &quot;The type of a working-entity must be
                &#x27;microwaveCarrierTermination&#x27;.&quot;;
           }
         }
       }
     }

     /*
      * XPIC &amp; MIMO groups - Configuration data nodes
      */

     container xpic-pairs {
       if-feature &quot;xpic&quot;;
       description
         &quot;Configuration of carrier termination pairs
          for operation in XPIC mode.&quot;;
       reference
         &quot;ETSI TR 102 311&quot;;
       list xpic-pair {
         key &quot;name&quot;;
         description
           &quot;List of carrier termination pairs in XPIC mode.&quot;;
         leaf name {
           type string;
           description
             &quot;Name used for identification of the XPIC pair.&quot;;
         }
         leaf enabled {
           type boolean;
           default &quot;false&quot;;
           description
             &quot;Enable(true)/disable(false) XPIC&quot;;
         }
         leaf-list members {
           type if:interface-ref;
           must &quot;derived-from-or-self(/if:interfaces/if:interface&quot;
              + &quot;[if:name = current()]&quot;
              + &quot;/if:type, &#x27;ianaift:microwaveCarrierTermination&#x27;)&quot; {
             description
               &quot;The type of a member must be
                &#x27;microwaveCarrierTermination&#x27;.&quot;;
           }
           min-elements 2;
           max-elements 2;

<span class="grey"><a href="/doc/html/rfc8561">RFC 8561</a>          Microwave Radio Link YANG Data Model         June 2019</span>

           description
             &quot;Association to XPIC pairs used in the radio link
              terminal.&quot;;
         }
       }
     }
     container mimo-groups {
       if-feature &quot;mimo&quot;;
       description
         &quot;Configuration of carrier terminations
          for operation in MIMO mode.&quot;;
       reference
         &quot;ETSI TR 102 311&quot;;
       list mimo-group {
         key &quot;name&quot;;
         description
           &quot;List of carrier terminations in MIMO mode.&quot;;
         leaf name {
           type string;
           description
             &quot;Name used for identification of the MIMO group.&quot;;
         }
         leaf enabled {
           type boolean;
           default &quot;false&quot;;
           description
             &quot;Enable(true)/disable(false) MIMO.&quot;;
         }
         leaf-list members {
           type if:interface-ref;
           must &quot;derived-from-or-self(/if:interfaces/if:interface&quot;
              + &quot;[if:name = current()]&quot;
              + &quot;/if:type, &#x27;ianaift:microwaveCarrierTermination&#x27;)&quot; {
             description
               &quot;The type of a member must be
                &#x27;microwaveCarrierTermination&#x27;.&quot;;
           }
           min-elements 2;
           description
             &quot;Association to a MIMO group if used in the radio
              link terminal.&quot;;
         }
       }
     }
   }
