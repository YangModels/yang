module ietf-nat {
 yang-version 1.1;
 namespace &quot;urn:ietf:params:xml:ns:yang:ietf-nat&quot;;
 prefix nat;

 import ietf-inet-types {
   prefix inet;
   reference
     &quot;<a href="/doc/html/rfc6991#section-4">Section&amp;nbsp;4 of RFC 6991</a>&quot;;
 }
 import ietf-yang-types {
   prefix yang;
   reference
     &quot;<a href="/doc/html/rfc6991#section-3">Section&amp;nbsp;3 of RFC 6991</a>&quot;;
 }
 import ietf-interfaces {
   prefix if;
   reference
     &quot;<a href="/doc/html/rfc8343">RFC 8343</a>: A YANG Data Model for Interface Management&quot;;
 }

 organization
   &quot;IETF OPSAWG (Operations and Management Area Working Group)&quot;;
 contact
   &quot;WG Web:   &lt;<a href="https://datatracker.ietf.org/wg/opsawg/">https://datatracker.ietf.org/wg/opsawg/</a>&gt;
    WG List:  &lt;mailto:<a href="mailto:opsawg@ietf.org">opsawg@ietf.org</a>&gt;

    Editor:  Mohamed Boucadair
             &lt;mailto:<a href="mailto:mohamed.boucadair@orange.com">mohamed.boucadair@orange.com</a>&gt;

    Author:  Senthil Sivakumar
             &lt;mailto:<a href="mailto:ssenthil@cisco.com">ssenthil@cisco.com</a>&gt;

    Author:  Christian Jacquenet
             &lt;mailto:<a href="mailto:christian.jacquenet@orange.com">christian.jacquenet@orange.com</a>&gt;

    Author:  Suresh Vinapamula
             &lt;mailto:<a href="mailto:sureshk@juniper.net">sureshk@juniper.net</a>&gt;

    Author:  Qin Wu
             &lt;mailto:<a href="mailto:bill.wu@huawei.com">bill.wu@huawei.com</a>&gt;&quot;;

 description
   &quot;This module is a YANG module for NAT implementations.
<span class="grey"><a href="/doc/html/rfc8512">RFC 8512</a>               YANG Module for NAT and NPT          January 2019</span>

     NAT44, Network Address and Protocol Translation from IPv6
     Clients to IPv4 Servers (NAT64), customer-side translator
     (CLAT), Stateless IP/ICMP Translation (SIIT), Explicit
     Address Mappings (EAM) for SIIT, IPv6 Network Prefix
     Translation (NPTv6), and Destination NAT are covered.

     Copyright (c) 2018 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
     (<a href="https://trustee.ietf.org/license-info">http://trustee.ietf.org/license-info</a>).

     This version of this YANG module is part of <a href="/doc/html/rfc8512">RFC 8512</a>; see
     the RFC itself for full legal notices.&quot;;

  revision 2019-01-10 {
    description
      &quot;Initial revision.&quot;;
    reference
      &quot;<a href="/doc/html/rfc8512">RFC 8512</a>: A YANG Module for Network Address Translation
                 (NAT) and Network Prefix Translation (NPT)&quot;;
  }

  /*
   * Definitions
   */

  typedef percent {
    type uint8 {
      range &quot;0 .. 100&quot;;
    }
    description
      &quot;Percentage&quot;;
  }

  /*
   * Features
   */

  feature basic-nat44 {
    description
      &quot;Basic NAT44 translation is limited to IP addresses alone.&quot;;
    reference
      &quot;<a href="/doc/html/rfc3022">RFC 3022</a>: Traditional IP Network Address Translator
<span class="grey"><a href="/doc/html/rfc8512">RFC 8512</a>               YANG Module for NAT and NPT          January 2019</span>

                 (Traditional NAT)&quot;;
  }

  feature napt44 {
    description
      &quot;Network Address Port Translator (NAPT): translation is
       extended to include IP addresses and transport identifiers
       (such as a TCP/UDP port or ICMP query ID).

       If the internal IP address is not sufficient to uniquely
       disambiguate NAPT44 mappings, an additional attribute is
       required.  For example, that additional attribute may
       be an IPv6 address (a.k.a., DS-Lite) or
       a Layer 2 identifier (a.k.a., Per-Interface NAT)&quot;;
    reference
      &quot;<a href="/doc/html/rfc3022">RFC 3022</a>: Traditional IP Network Address Translator
                 (Traditional NAT)&quot;;
  }

  feature dst-nat {
    description
      &quot;Destination NAT is a translation that acts on the destination
       IP address and/or destination port number.  This flavor is
       usually deployed in load balancers or at devices
       in front of public servers.&quot;;
  }

  feature nat64 {
    description
      &quot;NAT64 translation allows IPv6-only clients to contact IPv4
       servers using, e.g., UDP, TCP, or ICMP.  One or more
       public IPv4 addresses assigned to a NAT64 translator are
       shared among several IPv6-only clients.&quot;;
    reference
      &quot;<a href="/doc/html/rfc6146">RFC 6146</a>: Stateful NAT64: Network Address and Protocol
                 Translation from IPv6 Clients to IPv4 Servers&quot;;
  }

  feature siit {
    description
      &quot;The Stateless IP/ICMP Translation Algorithm (SIIT), which
       translates between IPv4 and IPv6 packet headers (including
       ICMP headers).

       In the stateless mode, an IP/ICMP translator converts IPv4
       addresses to IPv6, and vice versa, solely based on the
       configuration of the stateless IP/ICMP translator and
       information contained within the packet being translated.
<span class="grey"><a href="/doc/html/rfc8512">RFC 8512</a>               YANG Module for NAT and NPT          January 2019</span>

       The translator must support the stateless address mapping
       algorithm defined in <a href="/doc/html/rfc6052">RFC 6052</a>, which is the default behavior.&quot;;
    reference
      &quot;<a href="/doc/html/rfc7915">RFC 7915</a>: IP/ICMP Translation Algorithm&quot;;
  }

  feature clat {
    description
      &quot;CLAT is customer-side translator that algorithmically
       translates 1:1 private IPv4 addresses to global IPv6
       addresses, and vice versa.

       When a dedicated /64 prefix is not available for translation
       from DHCPv6-PD, the CLAT may perform NAT44 for all IPv4 LAN
       packets so that all the LAN-originated IPv4 packets appear
       from a single IPv4 address and are then statelessly translated
       to one interface IPv6 address that is claimed by the CLAT via
       the Neighbor Discovery Protocol (NDP) and defended with
       Duplicate Address Detection.&quot;;
    reference
      &quot;<a href="/doc/html/rfc6877">RFC 6877</a>: 464XLAT: Combination of Stateful and
                 Stateless Translation&quot;;
  }

  feature eam {
    description
      &quot;Explicit Address Mapping (EAM) is a bidirectional coupling
       between an IPv4 prefix and an IPv6 prefix.&quot;;
    reference
      &quot;<a href="/doc/html/rfc7757">RFC 7757</a>: Explicit Address Mappings for Stateless IP/ICMP
                 Translation&quot;;
  }

  feature nptv6 {
    description
      &quot;NPTv6 is a stateless transport-agnostic IPv6-to-IPv6
       prefix translation.&quot;;
    reference
      &quot;<a href="/doc/html/rfc6296">RFC 6296</a>: IPv6-to-IPv6 Network Prefix Translation&quot;;
  }

  /*
   * Identities
   */

  identity nat-type {
    description
      &quot;Base identity for nat type.&quot;;
<span class="grey"><a href="/doc/html/rfc8512">RFC 8512</a>               YANG Module for NAT and NPT          January 2019</span>

  }

  identity basic-nat44 {
    base nat:nat-type;
    description
      &quot;Identity for Basic NAT support.&quot;;
    reference
      &quot;<a href="/doc/html/rfc3022">RFC 3022</a>: Traditional IP Network Address Translator
                 (Traditional NAT)&quot;;
  }

  identity napt44 {
    base nat:nat-type;
    description
      &quot;Identity for NAPT support.&quot;;
    reference
      &quot;<a href="/doc/html/rfc3022">RFC 3022</a>: Traditional IP Network Address Translator
                 (Traditional NAT)&quot;;
  }

  identity dst-nat {
    base nat:nat-type;
    description
      &quot;Identity for Destination NAT support.&quot;;
  }

  identity nat64 {
    base nat:nat-type;
    description
      &quot;Identity for NAT64 support.&quot;;
    reference
      &quot;<a href="/doc/html/rfc6146">RFC 6146</a>: Stateful NAT64: Network Address and Protocol
                 Translation from IPv6 Clients to IPv4 Servers&quot;;
  }

  identity siit {
    base nat:nat-type;
    description
      &quot;Identity for SIIT support.&quot;;
    reference
      &quot;<a href="/doc/html/rfc7915">RFC 7915</a>: IP/ICMP Translation Algorithm&quot;;
  }

  identity clat {
    base nat:nat-type;
    description
      &quot;Identity for CLAT support.&quot;;
    reference
<span class="grey"><a href="/doc/html/rfc8512">RFC 8512</a>               YANG Module for NAT and NPT          January 2019</span>

      &quot;<a href="/doc/html/rfc6877">RFC 6877</a>: 464XLAT: Combination of Stateful and Stateless
                 Translation&quot;;
  }

  identity eam {
    base nat:nat-type;
    description
      &quot;Identity for EAM support.&quot;;
    reference
      &quot;<a href="/doc/html/rfc7757">RFC 7757</a>: Explicit Address Mappings for Stateless IP/ICMP
                 Translation&quot;;
  }

  identity nptv6 {
    base nat:nat-type;
    description
      &quot;Identity for NPTv6 support.&quot;;
    reference
      &quot;<a href="/doc/html/rfc6296">RFC 6296</a>: IPv6-to-IPv6 Network Prefix Translation&quot;;
  }

  /*
   * Grouping
   */

  grouping port-number {
    description
      &quot;An individual port number or a range of ports.
       When only start-port-number is present,
       it represents a single port number.&quot;;
    leaf start-port-number {
      type inet:port-number;
      description
        &quot;Beginning of the port range.&quot;;
      reference
        &quot;<a href="/doc/html/rfc8045#section-3.2.9">Section&amp;nbsp;3.2.9 of RFC 8045</a>&quot;;
    }
    leaf end-port-number {
      type inet:port-number;
      must &#x27;. &gt;= ../start-port-number&#x27; {
        error-message
          &quot;The end-port-number must be greater than or
           equal to start-port-number.&quot;;
      }
      description
        &quot;End of the port range.&quot;;
      reference
        &quot;<a href="/doc/html/rfc8045#section-3.2.10">Section&amp;nbsp;3.2.10 of RFC 8045</a>&quot;;
<span class="grey"><a href="/doc/html/rfc8512">RFC 8512</a>               YANG Module for NAT and NPT          January 2019</span>

    }
  }

  grouping port-set {
    description
      &quot;Indicates a set of port numbers.

       It may be a simple port range, or use the Port Set
       Identifier (PSID) algorithm to represent a range of
       transport-layer port numbers that will be used by a
       NAPT.&quot;;
    choice port-type {
      default &quot;port-range&quot;;
      description
        &quot;Port type: port-range or port-set-algo.&quot;;
      case port-range {
        uses port-number;
      }
      case port-set-algo {
        leaf psid-offset {
          type uint8 {
            range &quot;0..15&quot;;
          }
          description
            &quot;The number of offset bits (a.k.a., &#x27;a&#x27; bits).
             Specifies the numeric value for the excluded port
             range/offset bits.

             Allowed values are between 0 and 15.&quot;;
          reference
            &quot;<a href="/doc/html/rfc7597#section-5.1">Section&amp;nbsp;5.1 of RFC 7597</a>&quot;;
        }
        leaf psid-len {
          type uint8 {
            range &quot;0..15&quot;;
          }
          mandatory true;
          description
            &quot;The length of PSID, representing the sharing
             ratio for an IPv4 address.

             (also known as &#x27;k&#x27;).

             The address-sharing ratio would be 2^k.&quot;;
          reference
            &quot;<a href="/doc/html/rfc7597#section-5.1">Section&amp;nbsp;5.1 of RFC 7597</a>&quot;;
        }
        leaf psid {
<span class="grey"><a href="/doc/html/rfc8512">RFC 8512</a>               YANG Module for NAT and NPT          January 2019</span>

          type uint16;
          mandatory true;
          description
            &quot;PSID value, which identifies a set
             of ports algorithmically.&quot;;
          reference
            &quot;<a href="/doc/html/rfc7597#section-5.1">Section&amp;nbsp;5.1 of RFC 7597</a>&quot;;
        }
      }
      reference
        &quot;<a href="/doc/html/rfc7597">RFC 7597</a>: Mapping of Address and Port with
                   Encapsulation (MAP-E)&quot;;
    }
  }

  grouping mapping-entry {
    description
      &quot;NAT mapping entry.

       If an attribute is not stored in the mapping/session table,
       it means the corresponding field of a packet that
       matches this entry is not rewritten by the NAT or this
       information is not required for NAT filtering purposes.&quot;;
    leaf index {
      type uint32;
      description
        &quot;A unique identifier of a mapping entry.  This identifier
         can be automatically assigned by the NAT instance or be
         explicitly configured.&quot;;
    }
    leaf type {
      type enumeration {
        enum static {
          description
            &quot;The mapping entry is explicitly configured
             (e.g., via a command-line interface).&quot;;
        }
        enum dynamic-implicit {
          description
            &quot;This mapping is created implicitly as a side effect
             of processing a packet that requires a new mapping.&quot;;
        }
        enum dynamic-explicit {
          description
            &quot;This mapping is created as a result of an explicit
             request, e.g., a PCP message.&quot;;
        }
      }
<span class="grey"><a href="/doc/html/rfc8512">RFC 8512</a>               YANG Module for NAT and NPT          January 2019</span>

      description
        &quot;Indicates the type of a mapping entry.  For example,
         a mapping can be: static, implicit dynamic,
         or explicit dynamic.&quot;;
    }
    leaf transport-protocol {
      type uint8;
      description
        &quot;The upper-layer protocol associated with this mapping.
         Values are taken from the IANA Protocol Numbers registry:
         &lt;<a href="https://www.iana.org/assignments/protocol-numbers/">https://www.iana.org/assignments/protocol-numbers/</a>&gt;.

         For example, this field contains 6 for TCP,
         17 for UDP, 33 for DCCP, or 132 for SCTP.

         If this leaf is not instantiated, then the mapping
         applies to any protocol.&quot;;
    }
    leaf internal-src-address {
      type inet:ip-prefix;
      description
        &quot;Corresponds to the source IPv4/IPv6 address/prefix
         of the packet received on an internal interface.&quot;;
    }
    container internal-src-port {
      description
        &quot;Corresponds to the source port of the packet received
         on an internal interface.

         It is also used to indicate the internal source ICMP
         identifier.

         As a reminder, all the ICMP Query messages contain
         an &#x27;Identifier&#x27; field, which is referred to in this
         document as the &#x27;ICMP Identifier&#x27;.&quot;;
      uses port-number;
    }
    leaf external-src-address {
      type inet:ip-prefix;
      description
        &quot;Source IP address/prefix of the packet sent on an
         external interface of the NAT.&quot;;
    }
    container external-src-port {
      description
        &quot;Source port of the packet sent on an external
         interface of the NAT.

<span class="grey"><a href="/doc/html/rfc8512">RFC 8512</a>               YANG Module for NAT and NPT          January 2019</span>

         It is also used to indicate the external source ICMP
         identifier.&quot;;
      uses port-number;
    }
    leaf internal-dst-address {
      type inet:ip-prefix;
      description
        &quot;Corresponds to the destination IP address/prefix
         of the packet received on an internal interface
         of the NAT.

         For example, some NAT implementations support
         the translation of both source and destination
         addresses and port numbers, sometimes referred to
         as &#x27;Twice NAT&#x27;.&quot;;
    }
    container internal-dst-port {
      description
        &quot;Corresponds to the destination port of the
         IP packet received on the internal interface.

         It is also used to include the internal
         destination ICMP identifier.&quot;;
      uses port-number;
    }
    leaf external-dst-address {
      type inet:ip-prefix;
      description
        &quot;Corresponds to the destination IP address/prefix
         of the packet sent on an external interface
         of the NAT.&quot;;
    }
    container external-dst-port {
      description
        &quot;Corresponds to the destination port number of
         the packet sent on the external interface
         of the NAT.

         It is also used to include the external
         destination ICMP identifier.&quot;;
      uses port-number;
    }
    leaf lifetime {
      type uint32;
      units &quot;seconds&quot;;
      description
        &quot;When specified, it is used to track the connection that is
         fully formed (e.g., once the three-way handshake
<span class="grey"><a href="/doc/html/rfc8512">RFC 8512</a>               YANG Module for NAT and NPT          January 2019</span>

         TCP is completed) or the duration for maintaining
         an explicit mapping alive.  The mapping entry will be
         removed by the NAT instance once this lifetime is expired.

         When reported in a get operation, the lifetime indicates
         the remaining validity lifetime.

         Static mappings may not be associated with a
         lifetime.  If no lifetime is associated with a
         static mapping, an explicit action is required to
         remove that mapping.&quot;;
    }
  }

  /*
   * NAT Module
   */

  container nat {
    description
      &quot;NAT module&quot;;
    container instances {
      description
        &quot;NAT instances&quot;;
      list instance {
        key &quot;id&quot;;
        description
          &quot;A NAT instance.  This identifier can be automatically
           assigned or explicitly configured.&quot;;
        leaf id {
          type uint32;
          must &#x27;. &gt;= 1&#x27;;
          description
            &quot;NAT instance identifier.

             The identifier must be greater than zero.&quot;;
          reference
            &quot;<a href="/doc/html/rfc7659">RFC 7659</a>: Definitions of Managed Objects for Network
                       Address Translators (NATs)&quot;;
        }
        leaf name {
          type string;
          description
            &quot;A name associated with the NAT instance.&quot;;
          reference
            &quot;<a href="/doc/html/rfc7659">RFC 7659</a>: Definitions of Managed Objects for Network
                       Address Translators (NATs)&quot;;
        }
<span class="grey"><a href="/doc/html/rfc8512">RFC 8512</a>               YANG Module for NAT and NPT          January 2019</span>

        leaf enable {
          type boolean;
          description
            &quot;Status of the NAT instance.&quot;;
        }
        container capabilities {
          config false;
          description
            &quot;NAT capabilities.&quot;;
          leaf-list nat-flavor {
            type identityref {
              base nat-type;
            }
            description
              &quot;Supported translation type(s).&quot;;
          }
          leaf-list per-interface-binding {
            type enumeration {
              enum unsupported {
                description
                  &quot;No capability to associate a NAT binding with
                   an extra identifier.&quot;;
              }
              enum layer-2 {
                description
                  &quot;The NAT instance is able to associate a mapping with
                   a Layer 2 identifier.&quot;;
              }
              enum dslite {
                description
                  &quot;The NAT instance is able to associate a mapping with
                   an IPv6 address (a.k.a., DS-Lite).&quot;;
              }
            }
            description
              &quot;Indicates the capability of a NAT to associate a
               particular NAT session not only with the five
               tuples used for the transport connection on both
               sides of the NAT but also with the internal
               interface on which the user device is
               connected to the NAT.&quot;;
            reference
              &quot;<a href="/doc/html/rfc6619#section-4">Section&amp;nbsp;4 of RFC 6619</a>&quot;;
          }
          list transport-protocols {
            key &quot;protocol-id&quot;;
            description
              &quot;List of supported protocols.&quot;;
<span class="grey"><a href="/doc/html/rfc8512">RFC 8512</a>               YANG Module for NAT and NPT          January 2019</span>

            leaf protocol-id {
              type uint8;
              mandatory true;
              description
                &quot;The upper-layer protocol associated with a mapping.

                 Values are taken from the IANA Protocol Numbers
                 registry.

                 For example, this field contains 6 for TCP,
                 17 for UDP, 33 for DCCP, or 132 for SCTP.&quot;;
            }
            leaf protocol-name {
              type string;
              description
                &quot;The name of the upper-layer protocol associated
                 with this mapping.

                 For example, TCP, UDP, DCCP, and SCTP.&quot;;
            }
          }
          leaf restricted-port-support {
            type boolean;
            description
              &quot;Indicates source port NAT restriction support.&quot;;
            reference
              &quot;<a href="/doc/html/rfc7596">RFC 7596</a>: Lightweight 4over6: An Extension to
                         the Dual-Stack Lite Architecture&quot;;
          }
          leaf static-mapping-support {
            type boolean;
            description
              &quot;Indicates whether static mappings are supported.&quot;;
          }
          leaf port-randomization-support {
            type boolean;
            description
              &quot;Indicates whether port randomization is supported.&quot;;
            reference
              &quot;<a href="/doc/html/rfc4787#section-4.2.1">Section&amp;nbsp;4.2.1 of RFC 4787</a>&quot;;
          }
          leaf port-range-allocation-support {
            type boolean;
            description
              &quot;Indicates whether port range allocation is supported.&quot;;
            reference
              &quot;<a href="/doc/html/rfc7753#section-1.1">Section&amp;nbsp;1.1 of RFC 7753</a>&quot;;
          }
<span class="grey"><a href="/doc/html/rfc8512">RFC 8512</a>               YANG Module for NAT and NPT          January 2019</span>

          leaf port-preservation-suport {
            type boolean;
            description
              &quot;Indicates whether port preservation is supported.&quot;;
            reference
              &quot;<a href="/doc/html/rfc4787#section-4.2.1">Section&amp;nbsp;4.2.1 of RFC 4787</a>&quot;;
          }
          leaf port-parity-preservation-support {
            type boolean;
            description
              &quot;Indicates whether port parity preservation is
               supported.&quot;;
            reference
              &quot;<a href="/doc/html/rfc7857#section-8">Section&amp;nbsp;8 of RFC 7857</a>&quot;;
          }
          leaf address-roundrobin-support {
            type boolean;
            description
              &quot;Indicates whether address allocation round robin is
               supported.&quot;;
          }
          leaf paired-address-pooling-support {
            type boolean;
            description
              &quot;Indicates whether paired-address-pooling is
               supported&quot;;
            reference
              &quot;REQ-2 of <a href="/doc/html/rfc4787">RFC 4787</a>&quot;;
          }
          leaf endpoint-independent-mapping-support {
            type boolean;
            description
              &quot;Indicates whether endpoint-independent-
               mapping is supported.&quot;;
            reference
              &quot;<a href="/doc/html/rfc4787#section-4">Section&amp;nbsp;4 of RFC 4787</a>&quot;;
          }
          leaf address-dependent-mapping-support {
            type boolean;
            description
              &quot;Indicates whether address-dependent-mapping is
               supported.&quot;;
            reference
              &quot;<a href="/doc/html/rfc4787#section-4">Section&amp;nbsp;4 of RFC 4787</a>&quot;;
          }
          leaf address-and-port-dependent-mapping-support {
            type boolean;
            description
<span class="grey"><a href="/doc/html/rfc8512">RFC 8512</a>               YANG Module for NAT and NPT          January 2019</span>

              &quot;Indicates whether address-and-port-dependent-mapping is
               supported.&quot;;
            reference
              &quot;<a href="/doc/html/rfc4787#section-4">Section&amp;nbsp;4 of RFC 4787</a>&quot;;
          }
          leaf endpoint-independent-filtering-support {
            type boolean;
            description
              &quot;Indicates whether endpoint-independent-filtering is
               supported.&quot;;
            reference
              &quot;<a href="/doc/html/rfc4787#section-5">Section&amp;nbsp;5 of RFC 4787</a>&quot;;
          }
          leaf address-dependent-filtering {
            type boolean;
            description
              &quot;Indicates whether address-dependent-filtering is
               supported.&quot;;
            reference
              &quot;<a href="/doc/html/rfc4787#section-5">Section&amp;nbsp;5 of RFC 4787</a>&quot;;
          }
          leaf address-and-port-dependent-filtering {
            type boolean;
            description
              &quot;Indicates whether address-and-port-dependent is
               supported.&quot;;
            reference
              &quot;<a href="/doc/html/rfc4787#section-5">Section&amp;nbsp;5 of RFC 4787</a>&quot;;
          }
          leaf fragment-behavior {
            type enumeration {
              enum unsupported {
                description
                  &quot;No capability to translate incoming fragments.
                   All received fragments are dropped.&quot;;
              }
              enum in-order {
                description
                  &quot;The NAT instance is able to translate fragments
                   only if they are received in order.  That is, in
                   particular the header is in the first packet.
                   Fragments received out of order are dropped. &quot;;
              }
              enum out-of-order {
                description
                  &quot;The NAT instance is able to translate a fragment even
                   if it is received out of order.

<span class="grey"><a href="/doc/html/rfc8512">RFC 8512</a>               YANG Module for NAT and NPT          January 2019</span>

                   This behavior is recommended.&quot;;
                reference
                  &quot;REQ-14 of <a href="/doc/html/rfc4787">RFC 4787</a>&quot;;
              }
            }
            description
              &quot;The fragment behavior is the NAT instance&#x27;s capability to
               translate fragments received on the external interface of
               the NAT.&quot;;
          }
        }
        leaf type {
          type identityref {
            base nat-type;
          }
          description
            &quot;Specify the translation type.  Particularly useful when
             multiple translation flavors are supported.

             If one type is supported by a NAT, this parameter is by
             default set to that type.&quot;;
        }
        leaf per-interface-binding {
          type enumeration {
            enum disabled {
              description
                &quot;Disable the capability to associate an extra identifier
                 with NAT mappings.&quot;;
            }
            enum layer-2 {
              description
                &quot;The NAT instance is able to associate a mapping with
                 a Layer 2 identifier.&quot;;
            }
            enum dslite {
              description
                &quot;The NAT instance is able to associate a mapping with
                 an IPv6 address (a.k.a., DS-Lite).&quot;;
            }
          }
          description
            &quot;A NAT that associates a particular NAT session not
             only with the five tuples used for the transport
             connection on both sides of the NAT but also with
             the internal interface on which the user device is
             connected to the NAT.

             If supported, this mode of operation should be
<span class="grey"><a href="/doc/html/rfc8512">RFC 8512</a>               YANG Module for NAT and NPT          January 2019</span>

             configurable, and it should be disabled by default in
             general-purpose NAT devices.
             If one single per-interface binding behavior is
             supported by a NAT, this parameter is by default set to
             that behavior.&quot;;
          reference
            &quot;<a href="/doc/html/rfc6619#section-4">Section&amp;nbsp;4 of RFC 6619</a>&quot;;
        }
        list nat-pass-through {
          if-feature &quot;basic-nat44 or napt44 or dst-nat&quot;;
          key &quot;id&quot;;
          description
            &quot;IP prefix NAT pass-through.&quot;;
          leaf id {
            type uint32;
            description
              &quot;An identifier of the IP prefix pass-through.&quot;;
          }
          leaf prefix {
            type inet:ip-prefix;
            mandatory true;
            description
              &quot;The IP addresses that match should not be translated.

               It must be possible to administratively turn
               off translation for specific destination addresses
               and/or ports.&quot;;
            reference
              &quot;REQ-6 of <a href="/doc/html/rfc6888">RFC 6888</a>&quot;;
          }
          leaf port {
            type inet:port-number;
            description
              &quot;It must be possible to administratively turn off
               translation for specific destination addresses
               and/or ports.

               If no prefix is defined, the NAT pass-through bound
               to a given port applies for any destination address.&quot;;
            reference
              &quot;REQ-6 of <a href="/doc/html/rfc6888">RFC 6888</a>&quot;;
          }
        }
        list policy {
          key &quot;id&quot;;
          description
            &quot;NAT parameters for a given instance&quot;;
          leaf id {
<span class="grey"><a href="/doc/html/rfc8512">RFC 8512</a>               YANG Module for NAT and NPT          January 2019</span>

            type uint32;
            description
              &quot;An identifier of the NAT policy.  It must be unique
               within the NAT instance.&quot;;
          }
          container clat-parameters {
            if-feature &quot;clat&quot;;
            description
              &quot;CLAT parameters.&quot;;
            list clat-ipv6-prefixes {
              key &quot;ipv6-prefix&quot;;
              description
                &quot;464XLAT double-translation treatment is stateless
                 when a dedicated /64 is available for translation
                 on the CLAT.  Otherwise, the CLAT will have both
                 stateful and stateless translation since it requires
                 NAT44 from the LAN to a single IPv4 address and then
                 stateless translation to a single IPv6 address.&quot;;
              reference
                &quot;<a href="/doc/html/rfc6877">RFC 6877</a>: 464XLAT: Combination of Stateful and
                           Stateless Translation&quot;;
              leaf ipv6-prefix {
                type inet:ipv6-prefix;
                description
                  &quot;An IPv6 prefix used for CLAT.&quot;;
              }
            }
            list ipv4-prefixes {
              key &quot;ipv4-prefix&quot;;
              description
                &quot;Pool of IPv4 addresses used for CLAT.
                 192.0.0.0/29 is the IPv4 service continuity prefix.&quot;;
              reference
                &quot;<a href="/doc/html/rfc7335">RFC 7335</a>: IPv4 Service Continuity Prefix&quot;;
              leaf ipv4-prefix {
                type inet:ipv4-prefix;
                description
                  &quot;464XLAT double-translation treatment is
                   stateless when a dedicated /64 is available
                   for translation on the CLAT.  Otherwise, the
                   CLAT will have both stateful and stateless
                   translation since it requires NAT44 from the
                   LAN to a single IPv4 address and then stateless
                   translation to a single IPv6 address.
                   The CLAT performs NAT44 for all IPv4 LAN
                   packets so that all the LAN-originated IPv4
                   packets appear from a single IPv4 address
                   and are then statelessly translated to one
<span class="grey"><a href="/doc/html/rfc8512">RFC 8512</a>               YANG Module for NAT and NPT          January 2019</span>

                   interface IPv6 address that is claimed by
                   the CLAT.

                   An IPv4 address from this pool is also
                   provided to an application that makes
                   use of literals.&quot;;
                reference
                  &quot;<a href="/doc/html/rfc6877">RFC 6877</a>: 464XLAT: Combination of Stateful and
                             Stateless Translation&quot;;
              }
            }
          }
          list nptv6-prefixes {
            if-feature &quot;nptv6&quot;;
            key &quot;internal-ipv6-prefix&quot;;
            description
              &quot;Provides one or a list of (internal IPv6 prefix,
               external IPv6 prefix) required for NPTv6.

               In its simplest form, NPTv6 interconnects two
               network links: one is an &#x27;internal&#x27; network
               link attached to a leaf network within a single
               administrative domain, and the other is an
               &#x27;external&#x27; network with connectivity to the
               global Internet.&quot;;
            reference
              &quot;<a href="/doc/html/rfc6296">RFC 6296</a>: IPv6-to-IPv6 Network Prefix Translation&quot;;
            leaf internal-ipv6-prefix {
              type inet:ipv6-prefix;
              mandatory true;
              description
                &quot;An IPv6 prefix used by an internal interface of
                 NPTv6.&quot;;
              reference
                &quot;<a href="/doc/html/rfc6296">RFC 6296</a>: IPv6-to-IPv6 Network Prefix Translation&quot;;
            }
            leaf external-ipv6-prefix {
              type inet:ipv6-prefix;
              mandatory true;
              description
                &quot;An IPv6 prefix used by the external interface of
                 NPTv6.&quot;;
              reference
                &quot;<a href="/doc/html/rfc6296">RFC 6296</a>: IPv6-to-IPv6 Network Prefix Translation&quot;;
            }
          }
          list eam {
            if-feature &quot;eam&quot;;
<span class="grey"><a href="/doc/html/rfc8512">RFC 8512</a>               YANG Module for NAT and NPT          January 2019</span>

            key &quot;ipv4-prefix&quot;;
            description
              &quot;The Explicit Address Mapping Table is a conceptual
               table in which each row represents an EAM.

               Each EAM describes a mapping between IPv4 and IPv6
               prefixes/addresses.&quot;;
            reference
              &quot;<a href="/doc/html/rfc7757#section-3.1">Section&amp;nbsp;3.1 of RFC 7757</a>&quot;;
            leaf ipv4-prefix {
              type inet:ipv4-prefix;
              mandatory true;
              description
                &quot;The IPv4 prefix of an EAM.&quot;;
              reference
                &quot;<a href="/doc/html/rfc7757#section-3.2">Section&amp;nbsp;3.2 of RFC 7757</a>&quot;;
            }
            leaf ipv6-prefix {
              type inet:ipv6-prefix;
              mandatory true;
              description
                &quot;The IPv6 prefix of an EAM.&quot;;
              reference
                &quot;<a href="/doc/html/rfc7757#section-3.2">Section&amp;nbsp;3.2 of RFC 7757</a>&quot;;
            }
          }
          list nat64-prefixes {
            if-feature &quot;siit or nat64 or clat&quot;;
            key &quot;nat64-prefix&quot;;
            description
              &quot;Provides one or a list of NAT64 prefixes
               with or without a list of destination IPv4 prefixes.
               It allows mapping IPv4 address ranges to IPv6 prefixes.
               For example:
               192.0.2.0/24 is mapped to 2001:db8:122:300::/56.
               198.51.100.0/24 is mapped to 2001:db8:122::/48.&quot;;
            reference
              &quot;<a href="/doc/html/rfc7050#section-5.1">Section&amp;nbsp;5.1 of RFC 7050</a>&quot;;
            leaf nat64-prefix {
              type inet:ipv6-prefix;
              mandatory true;
              description
                &quot;A NAT64 prefix.  Can be a Network-Specific Prefix (NSP)
                 or a Well-Known Prefix (WKP).

                 Organizations deploying stateless IPv4/IPv6 translation
                 should assign an NSP to their IPv4/IPv6 translation
                 service.
<span class="grey"><a href="/doc/html/rfc8512">RFC 8512</a>               YANG Module for NAT and NPT          January 2019</span>

                 For stateless NAT64, IPv4-translatable IPv6 addresses
                 must use the selected NSP.

                 Both IPv4-translatable IPv6 addresses and
                 IPv4-converted IPv6 addresses should use
                 the same prefix.&quot;;
              reference
                &quot;Sections <a href="#section-3.3">3.3</a> and <a href="#section-3.4">3.4</a> of <a href="/doc/html/rfc6052">RFC 6052</a>&quot;;
            }
            list destination-ipv4-prefix {
              key &quot;ipv4-prefix&quot;;
              description
                &quot;An IPv4 prefix/address.&quot;;
              leaf ipv4-prefix {
                type inet:ipv4-prefix;
                description
                  &quot;An IPv4 address/prefix.&quot;;
              }
            }
            leaf stateless-enable {
              type boolean;
              default &quot;false&quot;;
              description
                &quot;Enable explicitly stateless NAT64.&quot;;
            }
          }
          list external-ip-address-pool {
            if-feature &quot;basic-nat44 or napt44 or nat64&quot;;
            key &quot;pool-id&quot;;
            description
              &quot;Pool of external IP addresses used to service internal
               hosts.

               A pool is a set of IP prefixes.&quot;;
            leaf pool-id {
              type uint32;
              must &#x27;. &gt;= 1&#x27;;
              description
                &quot;An identifier that uniquely identifies the address pool
                 within a NAT instance.

                 The identifier must be greater than zero.&quot;;
              reference
                &quot;<a href="/doc/html/rfc7659">RFC 7659</a>: Definitions of Managed Objects for
                           Network Address Translators (NATs)&quot;;
            }
            leaf external-ip-pool {
              type inet:ipv4-prefix;
<span class="grey"><a href="/doc/html/rfc8512">RFC 8512</a>               YANG Module for NAT and NPT          January 2019</span>

              mandatory true;
              description
                &quot;An IPv4 prefix used for NAT purposes.&quot;;
            }
          }
          container port-set-restrict {
            if-feature &quot;napt44 or nat64&quot;;
            description
              &quot;Configures contiguous and non-contiguous port ranges.

               The port set is used to restrict the external source
               port numbers used by the translator.&quot;;
            uses port-set;
          }
          leaf dst-nat-enable {
            if-feature &quot;basic-nat44 or napt44&quot;;
            type boolean;
            default &quot;false&quot;;
            description
              &quot;Enable/disable Destination NAT.

               A NAT44 may be configured to enable Destination
               NAT, too.&quot;;
          }
          list dst-ip-address-pool {
            if-feature &quot;dst-nat&quot;;
            key &quot;pool-id&quot;;
            description
              &quot;Pool of IP addresses used for Destination NAT.&quot;;
            leaf pool-id {
              type uint32;
              description
                &quot;An identifier of the address pool.&quot;;
            }
            leaf dst-in-ip-pool {
              type inet:ip-prefix;
              description
                &quot;Is used to identify an internal destination
                 IP prefix/address to be translated.&quot;;
            }
            leaf dst-out-ip-pool {
              type inet:ip-prefix;
              mandatory true;
              description
                &quot;IP address/prefix used for Destination NAT.&quot;;
            }
          }
          list transport-protocols {
<span class="grey"><a href="/doc/html/rfc8512">RFC 8512</a>               YANG Module for NAT and NPT          January 2019</span>

            if-feature &quot;napt44 or nat64 or dst-nat&quot;;
            key &quot;protocol-id&quot;;
            description
              &quot;Configure the transport protocols to be handled by
               the translator.

               TCP and UDP are supported by default.&quot;;
            leaf protocol-id {
              type uint8;
              mandatory true;
              description
                &quot;The upper-layer protocol associated with this
                 mapping.

                 Values are taken from the IANA Protocol Numbers
                 registry.

                 For example, this field contains 6 for TCP,
                 17 for UDP, 33 for DCCP, or 132 for SCTP.&quot;;
            }
            leaf protocol-name {
              type string;
              description
                &quot;The name of the upper-layer protocol associated
                 with this mapping.

                 For example, TCP, UDP, DCCP, and SCTP.&quot;;
            }
          }
          leaf subscriber-mask-v6 {
            type uint8 {
              range &quot;0 .. 128&quot;;
            }
            description
              &quot;The subscriber mask is an integer that indicates
               the length of significant bits to be applied on
               the source IPv6 address (internal side) to
               unambiguously identify a user device (e.g., CPE).

               Subscriber mask is a system-wide configuration
               parameter that is used to enforce generic
               per-subscriber policies (e.g., port-quota).

               The enforcement of these generic policies does not
               require the configuration of every subscriber&#x27;s
               prefix.

               Example: suppose the 2001:db8:100:100::/56 prefix
<span class="grey"><a href="/doc/html/rfc8512">RFC 8512</a>               YANG Module for NAT and NPT          January 2019</span>

               is assigned to a NAT64-serviced CPE.  Suppose also
               that 2001:db8:100:100::1 is the IPv6 address used
               by the client that resides in that CPE.  When the
               NAT64 receives a packet from this client,
               it applies the subscriber-mask-v6 (e.g., 56) on
               the source IPv6 address to compute the associated
               prefix for this client (2001:db8:100:100::/56).
               Then, the NAT64 enforces policies based on that
               prefix (2001:db8:100:100::/56), not on the exact
               source IPv6 address.&quot;;
          }
          list subscriber-match {
            if-feature &quot;basic-nat44 or napt44 or dst-nat&quot;;
            key &quot;match-id&quot;;
            description
              &quot;IP prefix match.
               A subscriber is identified by a subnet.&quot;;
            leaf match-id {
              type uint32;
              description
                &quot;An identifier of the subscriber match.&quot;;
            }
            leaf subnet {
              type inet:ip-prefix;
              mandatory true;
              description
                &quot;The IP address subnets that match
                 should be translated.  For example, all addresses
                 that belong to the 192.0.2.0/24 prefix must
                 be processed by the NAT.&quot;;
            }
          }
          leaf address-allocation-type {
            type enumeration {
              enum arbitrary {
                if-feature &quot;basic-nat44 or napt44 or nat64&quot;;
                description
                  &quot;Arbitrary pooling behavior means that the NAT
                   instance may create the new port mapping using any
                   address in the pool that has a free port for the
                   protocol concerned.&quot;;
              }
              enum roundrobin {
                if-feature &quot;basic-nat44 or napt44 or nat64&quot;;
                description
                  &quot;Round-robin allocation.&quot;;
              }
              enum paired {
<span class="grey"><a href="/doc/html/rfc8512">RFC 8512</a>               YANG Module for NAT and NPT          January 2019</span>

                if-feature &quot;napt44 or nat64&quot;;
                description
                  &quot;Paired address pooling informs the NAT
                   that all the flows from an internal IP
                   address must be assigned the same external
                   address.  This is the recommended behavior
                   for NAPT/NAT64.&quot;;
                reference
                  &quot;<a href="/doc/html/rfc4787">RFC 4787</a>: Network Address Translation (NAT)
                             Behavioral Requirements for Unicast UDP&quot;;
              }
            }
            description
              &quot;Specifies how external IP addresses are allocated.&quot;;
          }
          leaf port-allocation-type {
            if-feature &quot;napt44 or nat64&quot;;
            type enumeration {
              enum random {
                description
                  &quot;Port randomization is enabled.  A NAT port allocation
                   scheme should make it hard for attackers to guess
                   port numbers&quot;;
                reference
                  &quot;REQ-15 of <a href="/doc/html/rfc6888">RFC 6888</a>&quot;;
              }
              enum port-preservation {
                description
                  &quot;Indicates whether the NAT should preserve the
                   internal port number.&quot;;
              }
              enum port-parity-preservation {
                description
                  &quot;Indicates whether the NAT should preserve the port
                   parity of the internal port number.&quot;;
              }
              enum port-range-allocation {
                description
                  &quot;Indicates whether the NAT assigns a range of ports
                   for an internal host.  This scheme allows the
                   minimizing of the log volume.&quot;;
                reference
                  &quot;REQ-14 of <a href="/doc/html/rfc6888">RFC 6888</a>&quot;;
              }
            }
            description
              &quot;Indicates the type of port allocation.&quot;;
          }
<span class="grey"><a href="/doc/html/rfc8512">RFC 8512</a>               YANG Module for NAT and NPT          January 2019</span>

          leaf mapping-type {
            if-feature &quot;napt44 or nat64&quot;;
            type enumeration {
              enum eim {
                description
                  &quot;endpoint-independent-mapping.&quot;;
                reference
                  &quot;<a href="/doc/html/rfc4787#section-4">Section&amp;nbsp;4 of RFC 4787</a>&quot;;
              }
              enum adm {
                description
                  &quot;address-dependent-mapping.&quot;;
                reference
                  &quot;<a href="/doc/html/rfc4787#section-4">Section&amp;nbsp;4 of RFC 4787</a>&quot;;
              }
              enum edm {
                description
                  &quot;address-and-port-dependent-mapping.&quot;;
                reference
                  &quot;<a href="/doc/html/rfc4787#section-4">Section&amp;nbsp;4 of RFC 4787</a>&quot;;
              }
            }
            description
              &quot;Indicates the type of NAT mapping.&quot;;
          }
          leaf filtering-type {
            if-feature &quot;napt44 or nat64&quot;;
            type enumeration {
              enum eif {
                description
                  &quot;endpoint-independent-filtering.&quot;;
                reference
                  &quot;<a href="/doc/html/rfc4787#section-5">Section&amp;nbsp;5 of RFC 4787</a>&quot;;
              }
              enum adf {
                description
                  &quot;address-dependent-filtering.&quot;;
                reference
                  &quot;<a href="/doc/html/rfc4787#section-5">Section&amp;nbsp;5 of RFC 4787</a>&quot;;
              }
              enum edf {
                description
                  &quot;address-and-port-dependent-filtering&quot;;
                reference
                  &quot;<a href="/doc/html/rfc4787#section-5">Section&amp;nbsp;5 of RFC 4787</a>&quot;;
              }
            }
            description
<span class="grey"><a href="/doc/html/rfc8512">RFC 8512</a>               YANG Module for NAT and NPT          January 2019</span>

              &quot;Indicates the type of NAT filtering.&quot;;
          }
          leaf fragment-behavior {
            if-feature &quot;napt44 or nat64&quot;;
            type enumeration {
              enum drop-all {
                description
                  &quot;All received fragments are dropped.&quot;;
              }
              enum in-order {
                description
                  &quot;Translate fragments only if they are received
                   in order.&quot;;
              }
              enum out-of-order {
                description
                  &quot;Translate a fragment even if it is received out
                   of order.

                   This behavior is recommended.&quot;;
                reference
                  &quot;REQ-14 of <a href="/doc/html/rfc4787">RFC 4787</a>&quot;;
              }
            }
            description
              &quot;The fragment behavior instructs the NAT about the
               behavior to follow to translate fragments received
               on the external interface of the NAT.&quot;;
          }
          list port-quota {
            if-feature &quot;napt44 or nat64&quot;;
            key &quot;quota-type&quot;;
            description
              &quot;Configures a port quota to be assigned per subscriber.
               It corresponds to the maximum number of ports to be
               used by a subscriber.&quot;;
            leaf port-limit {
              type uint16;
              description
                &quot;Configures a port quota to be assigned per subscriber.
                 It corresponds to the maximum number of ports to be
                 used by a subscriber.&quot;;
              reference
                &quot;REQ-4 of <a href="/doc/html/rfc6888">RFC 6888</a>&quot;;
            }
            leaf quota-type {
              type uint8;
              description
<span class="grey"><a href="/doc/html/rfc8512">RFC 8512</a>               YANG Module for NAT and NPT          January 2019</span>

                &quot;Indicates whether the port quota applies to
                 all protocols (0) or to a specific protocol.&quot;;
            }
          }
          container port-set {
            when &quot;../port-allocation-type = &#x27;port-range-allocation&#x27;&quot;;
            if-feature &quot;napt44 or nat64&quot;;
            description
              &quot;Manages port-set assignments.&quot;;
            leaf port-set-size {
              type uint16;
              mandatory true;
              description
                &quot;Indicates the size of assigned port sets.&quot;;
            }
            leaf port-set-timeout {
              type uint32;
              units &quot;seconds&quot;;
              description
                &quot;inactivity timeout for port sets.&quot;;
            }
          }
          container timers {
            if-feature &quot;napt44 or nat64&quot;;
            description
              &quot;Configure values of various timeouts.&quot;;
            leaf udp-timeout {
              type uint32;
              units &quot;seconds&quot;;
              default &quot;300&quot;;
              description
                &quot;UDP inactivity timeout.  That is the time a mapping
                 will stay active without packets traversing the NAT.&quot;;
              reference
                &quot;<a href="/doc/html/rfc4787">RFC 4787</a>: Network Address Translation (NAT)
                           Behavioral Requirements for Unicast UDP&quot;;
            }
            leaf tcp-idle-timeout {
              type uint32;
              units &quot;seconds&quot;;
              default &quot;7440&quot;;
              description
                &quot;TCP idle timeout should be 2 hours and 4 minutes.&quot;;
              reference
                &quot;<a href="/doc/html/rfc5382">RFC 5382</a>: NAT Behavioral Requirements for TCP&quot;;
            }
            leaf tcp-trans-open-timeout {
              type uint32;
<span class="grey"><a href="/doc/html/rfc8512">RFC 8512</a>               YANG Module for NAT and NPT          January 2019</span>

              units &quot;seconds&quot;;
              default &quot;240&quot;;
              description
                &quot;The value of the transitory open connection
                 idle-timeout.

                 A NAT should provide different configurable
                 parameters for configuring the open and
                 closing idle timeouts.

                 To accommodate deployments that consider
                 a partially open timeout of 4 minutes as being
                 excessive from a security standpoint, a NAT may
                 allow the configured timeout to be less than
                 4 minutes.

                 However, a minimum default transitory connection
                 idle-timeout of 4 minutes is recommended.&quot;;
              reference
                &quot;<a href="/doc/html/rfc7857#section-2.1">Section&amp;nbsp;2.1 of RFC 7857</a>&quot;;
            }
            leaf tcp-trans-close-timeout {
              type uint32;
              units &quot;seconds&quot;;
              default &quot;240&quot;;
              description
                &quot;The value of the transitory close connection
                 idle-timeout.

                 A NAT should provide different configurable
                 parameters for configuring the open and
                 closing idle timeouts.&quot;;
              reference
                &quot;<a href="/doc/html/rfc7857#section-2.1">Section&amp;nbsp;2.1 of RFC 7857</a>&quot;;
            }
            leaf tcp-in-syn-timeout {
              type uint32;
              units &quot;seconds&quot;;
              default &quot;6&quot;;
              description
                &quot;A NAT must not respond to an unsolicited
                 inbound SYN packet for at least 6 seconds
                 after the packet is received.  If during
                 this interval the NAT receives and translates
                 an outbound SYN for the connection the NAT
                 must silently drop the original unsolicited
                 inbound SYN packet.&quot;;
              reference
<span class="grey"><a href="/doc/html/rfc8512">RFC 8512</a>               YANG Module for NAT and NPT          January 2019</span>

                &quot;<a href="/doc/html/rfc5382">RFC 5382</a> NAT Behavioral Requirements for TCP&quot;;
            }
            leaf fragment-min-timeout {
              when &quot;../../fragment-behavior=&#x27;out-of-order&#x27;&quot;;
              type uint32;
              units &quot;seconds&quot;;
              default &quot;2&quot;;
              description
                &quot;As long as the NAT has available resources,
                 the NAT allows the fragments to arrive
                 over the fragment-min-timeout interval.
                 The default value is inspired from <a href="/doc/html/rfc6146">RFC 6146</a>.&quot;;
            }
            leaf icmp-timeout {
              type uint32;
              units &quot;seconds&quot;;
              default &quot;60&quot;;
              description
                &quot;An ICMP Query session timer must not expire
                 in less than 60 seconds.  It is recommended
                 that the ICMP Query session timer be made
                 configurable&quot;;
              reference
                &quot;<a href="/doc/html/rfc5508">RFC 5508</a>: NAT Behavioral Requirements for ICMP&quot;;
            }
            list per-port-timeout {
              key &quot;port-number&quot;;
              description
                &quot;Some NATs are configurable with short timeouts
                 for some ports, e.g., as 10 seconds on
                 port 53 (DNS) and 123 (NTP), and longer timeouts
                 on other ports.&quot;;
              leaf port-number {
                type inet:port-number;
                description
                  &quot;A port number.&quot;;
              }
              leaf protocol {
                type uint8;
                description
                  &quot;The upper-layer protocol associated with this port.

                   Values are taken from the IANA Protocol Numbers
                   registry.

                   If no protocol is indicated, it means &#x27;any
                   protocol&#x27;.&quot;;
              }
<span class="grey"><a href="/doc/html/rfc8512">RFC 8512</a>               YANG Module for NAT and NPT          January 2019</span>

              leaf timeout {
                type uint32;
                units &quot;seconds&quot;;
                mandatory true;
                description
                  &quot;Timeout for this port number&quot;;
              }
            }
            leaf hold-down-timeout {
              type uint32;
              units &quot;seconds&quot;;
              default &quot;120&quot;;
              description
                &quot;Hold-down timer.

                 Ports in the hold-down pool are not reassigned until
                 hold-down-timeout expires.

                 The length of time and the maximum number of ports in
                 this state must be configurable by the administrator.

                 This is necessary in order to prevent collisions
                 between old and new mappings and sessions.  It ensures
                 that all established sessions are broken instead of
                 redirected to a different peer.&quot;;
              reference
                &quot;REQ-8 of <a href="/doc/html/rfc6888">RFC 6888</a>&quot;;
            }
            leaf hold-down-max {
              type uint32;
              description
                &quot;Maximum ports in the hold-down port pool.&quot;;
              reference
                &quot;REQ-8 of <a href="/doc/html/rfc6888">RFC 6888</a>&quot;;
            }
          }
          leaf fragments-limit {
            when &quot;../fragment-behavior=&#x27;out-of-order&#x27;&quot;;
            type uint32;
            description
              &quot;Limits the number of out-of-order fragments that can
               be handled.&quot;;
            reference
              &quot;<a href="/doc/html/rfc4787#section-11">Section&amp;nbsp;11 of RFC 4787</a>&quot;;
          }
          list algs {
            key &quot;name&quot;;
            description
<span class="grey"><a href="/doc/html/rfc8512">RFC 8512</a>               YANG Module for NAT and NPT          January 2019</span>

              &quot;Features related to the Application Layer
               Gateway (ALG).&quot;;
            leaf name {
              type string;
              description
                &quot;The name of the ALG.&quot;;
            }
            leaf transport-protocol {
              type uint32;
              description
                &quot;The transport protocol used by the ALG
                 (e.g., TCP and UDP).&quot;;
            }
            container dst-transport-port {
              uses port-number;
              description
                &quot;The destination port number(s) used by the ALG.
                 For example,
                   - 21 for the FTP ALG
                   - 53 for the DNS ALG.&quot;;
            }
            container src-transport-port {
              uses port-number;
              description
                &quot;The source port number(s) used by the ALG.&quot;;
            }
            leaf status {
              type boolean;
              description
                &quot;Enable/disable the ALG.&quot;;
            }
          }
          leaf all-algs-enable {
            type boolean;
            description
              &quot;Disable/enable all ALGs.

               When specified, this parameter overrides the one
               that may be indicated, eventually, by the &#x27;status&#x27;
               of an individual ALG.&quot;;
          }
          container notify-pool-usage {
            if-feature &quot;basic-nat44 or napt44 or nat64&quot;;
            description
              &quot;Notification of pool usage when certain criteria
               are met.&quot;;
            leaf pool-id {
              type uint32;
<span class="grey"><a href="/doc/html/rfc8512">RFC 8512</a>               YANG Module for NAT and NPT          January 2019</span>

              description
                &quot;Pool-ID for which the notification criteria
                 is defined&quot;;
            }
            leaf low-threshold {
              type percent;
              description
                &quot;Notification must be generated when the defined low
                 threshold is reached.

                 For example, if a notification is required when the
                 pool utilization reaches below 10%, this
                 configuration parameter must be set to 10.

                 0% indicates that low-threshold notification is
                 disabled.&quot;;
            }
            leaf high-threshold {
              type percent;
              must &#x27;. &gt;= ../low-threshold&#x27; {
                error-message
                  &quot;The high threshold must be greater than or equal
                   to the low threshold.&quot;;
              }
              description
                &quot;Notification must be generated when the defined high
                 threshold is reached.

                 For example, if a notification is required when the
                 pool utilization reaches 90%, this configuration
                 parameter must be set to 90.

                 Setting the same value as low-threshold is equivalent
                 to disabling high-threshold notification.&quot;;
            }
            leaf notify-interval {
              type uint32 {
                range &quot;1 .. 3600&quot;;
              }
              units &quot;seconds&quot;;
              default &quot;20&quot;;
              description
                &quot;Minimum number of seconds between successive
                 notifications for this pool.&quot;;
              reference
                &quot;<a href="/doc/html/rfc7659">RFC 7659</a>: Definitions of Managed Objects for
                           Network Address Translators (NATs)&quot;;
            }
<span class="grey"><a href="/doc/html/rfc8512">RFC 8512</a>               YANG Module for NAT and NPT          January 2019</span>

          }
          container external-realm {
            description
              &quot;Identifies the external realm of the NAT instance.&quot;;
            choice realm-type {
              description
                &quot;Can be an interface, VRF instance, etc.&quot;;
              case interface {
                description
                  &quot;External interface.&quot;;
                leaf external-interface {
                  type if:interface-ref;
                  description
                    &quot;Name of the external interface.&quot;;
                }
              }
            }
          }
        }
        container mapping-limits {
          if-feature &quot;napt44 or nat64&quot;;
          description
            &quot;Information about the configuration parameters that
             limits the mappings based upon various criteria.&quot;;
          leaf limit-subscribers {
            type uint32;
            description
              &quot;Maximum number of subscribers that can be serviced
               by a NAT instance.

               A subscriber is identified by a given prefix.&quot;;
            reference
              &quot;<a href="/doc/html/rfc7659">RFC 7659</a>: Definitions of Managed Objects for
                         Network Address Translators (NATs)&quot;;
          }
          leaf limit-address-mappings {
            type uint32;
            description
              &quot;Maximum number of address mappings that can be
               handled by a NAT instance.

               When this limit is reached, packets that would
               normally trigger translation will be dropped.&quot;;
            reference
              &quot;<a href="/doc/html/rfc7659">RFC 7659</a>: Definitions of Managed Objects for
                         Network Address Translators (NATs)&quot;;
          }
          leaf limit-port-mappings {
<span class="grey"><a href="/doc/html/rfc8512">RFC 8512</a>               YANG Module for NAT and NPT          January 2019</span>

            type uint32;
            description
              &quot;Maximum number of port mappings that can be handled
               by a NAT instance.

               When this limit is reached, packets that would
               normally trigger translation will be dropped.&quot;;
            reference
              &quot;<a href="/doc/html/rfc7659">RFC 7659</a>: Definitions of Managed Objects for
                         Network Address Translators (NATs)&quot;;
          }
          list limit-per-protocol {
            if-feature &quot;napt44 or nat64 or dst-nat&quot;;
            key &quot;protocol-id&quot;;
            description
              &quot;Configure limits per transport protocol&quot;;
            leaf protocol-id {
              type uint8;
              mandatory true;
              description
                &quot;The upper-layer protocol.

                 Values are taken from the IANA Protocol Numbers
                 registry.

                 For example, this field contains 6 for TCP,
                 17 for UDP, 33 for DCCP, or 132 for SCTP.&quot;;
            }
            leaf limit {
              type uint32;
              description
                &quot;Maximum number of protocol-specific NAT mappings
                 per instance.&quot;;
            }
          }
        }
        container connection-limits {
          if-feature &quot;basic-nat44 or napt44 or nat64&quot;;
          description
            &quot;Information about the configuration parameters that
             rate-limit the translation based upon various criteria.&quot;;
          leaf limit-per-subscriber {
            type uint32;
            units &quot;bits/second&quot;;
            description
              &quot;Rate-limit the number of new mappings and sessions
               per subscriber.&quot;;
          }
<span class="grey"><a href="/doc/html/rfc8512">RFC 8512</a>               YANG Module for NAT and NPT          January 2019</span>

          leaf limit-per-instance {
            type uint32;
            units &quot;bits/second&quot;;
            description
              &quot;Rate-limit the number of new mappings and sessions
               per instance.&quot;;
          }
          list limit-per-protocol {
            if-feature &quot;napt44 or nat64&quot;;
            key &quot;protocol-id&quot;;
            description
              &quot;Configure limits per transport protocol&quot;;
            leaf protocol-id {
              type uint8;
              mandatory true;
              description
                &quot;The upper-layer protocol.

                 Values are taken from the IANA Protocol Numbers
                 registry.

                 For example, this field contains 6 for TCP,
                 17 for UDP, 33 for DCCP, or 132 for SCTP.&quot;;
            }
            leaf limit {
              type uint32;
              description
                &quot;Limit the number of protocol-specific mappings
                 and sessions per instance.&quot;;
            }
          }
        }
        container notification-limits {
          description
            &quot;Sets notification limits.&quot;;
          leaf notify-interval {
            if-feature &quot;basic-nat44 or napt44 or nat64&quot;;
            type uint32 {
              range &quot;1 .. 3600&quot;;
            }
            units &quot;seconds&quot;;
            default &quot;10&quot;;
            description
              &quot;Minimum number of seconds between successive
               notifications for this NAT instance.&quot;;
            reference
              &quot;<a href="/doc/html/rfc7659">RFC 7659</a>: Definitions of Managed Objects for
                         Network Address Translators (NATs)&quot;;
<span class="grey"><a href="/doc/html/rfc8512">RFC 8512</a>               YANG Module for NAT and NPT          January 2019</span>

          }
          leaf notify-addresses-usage {
            if-feature &quot;basic-nat44 or napt44 or nat64&quot;;
            type percent;
            description
              &quot;Notification of address mappings usage over
               the whole NAT instance.

               Notification must be generated when the defined
               threshold is reached.

               For example, if a notification is required when
               the address mappings utilization reaches 90%,
               this configuration parameter must be set
               to 90.&quot;;
          }
          leaf notify-ports-usage {
            if-feature &quot;napt44 or nat64&quot;;
            type percent;
            description
              &quot;Notification of port mappings usage over the
               whole NAT instance.

               Notification must be generated when the defined
               threshold is reached.

               For example, if a notification is required when
               the port mappings utilization reaches 90%, this
               configuration parameter must be set to 90.&quot;;
          }
          leaf notify-subscribers-limit {
            if-feature &quot;basic-nat44 or napt44 or nat64&quot;;
            type uint32;
            description
              &quot;Notification of active subscribers per NAT
               instance.

               Notification must be generated when the defined
               threshold is reached.&quot;;
          }
        }
        container mapping-table {
          if-feature &quot;basic-nat44 or napt44 or nat64 &quot;
                   + &quot;or clat or dst-nat&quot;;
          description
            &quot;NAT mapping table.  Applicable for functions that maintain
             static and/or dynamic mappings, such as NAT44, Destination
             NAT, NAT64, or CLAT.&quot;;
<span class="grey"><a href="/doc/html/rfc8512">RFC 8512</a>               YANG Module for NAT and NPT          January 2019</span>

          list mapping-entry {
            key &quot;index&quot;;
            description
              &quot;NAT mapping entry.&quot;;
            uses mapping-entry;
          }
        }
        container statistics {
          config false;
          description
            &quot;Statistics related to the NAT instance.&quot;;
          leaf discontinuity-time {
            type yang:date-and-time;
            mandatory true;
            description
              &quot;The time on the most recent occasion at which the NAT
               instance suffered a discontinuity.  This must be
               initialized when the NAT instance is configured
               or rebooted.&quot;;
          }
          container traffic-statistics {
            description
              &quot;Generic traffic statistics.&quot;;
            leaf sent-packets {
              type yang:zero-based-counter64;
              description
                &quot;Number of packets sent.&quot;;
            }
            leaf sent-bytes {
              type yang:zero-based-counter64;
              units &quot;bytes&quot;;
              description
                &quot;Counter for sent traffic in bytes.&quot;;
            }
            leaf rcvd-packets {
              type yang:zero-based-counter64;
              description
                &quot;Number of received packets.&quot;;
            }
            leaf rcvd-bytes {
              type yang:zero-based-counter64;
              units &quot;bytes&quot;;
              description
                &quot;Counter for received traffic in bytes.&quot;;
            }
            leaf dropped-packets {
              type yang:zero-based-counter64;
              description
<span class="grey"><a href="/doc/html/rfc8512">RFC 8512</a>               YANG Module for NAT and NPT          January 2019</span>

                &quot;Number of dropped packets.&quot;;
            }
            leaf dropped-bytes {
              type yang:zero-based-counter64;
              units &quot;bytes&quot;;
              description
                &quot;Counter for dropped traffic in bytes.&quot;;
            }
            leaf dropped-fragments {
              if-feature &quot;napt44 or nat64&quot;;
              type yang:zero-based-counter64;
              description
                &quot;Number of dropped fragments on the external realm.&quot;;
            }
            leaf dropped-address-limit-packets {
              if-feature &quot;basic-nat44 or napt44 or nat64&quot;;
              type yang:zero-based-counter64;
              description
                &quot;Number of dropped packets because an address limit
                  is reached.&quot;;
            }
            leaf dropped-address-limit-bytes {
              if-feature &quot;basic-nat44 or napt44 or nat64&quot;;
              type yang:zero-based-counter64;
              units &quot;bytes&quot;;
              description
                &quot;Counter of dropped packets because an address limit
                  is reached, in bytes.&quot;;
            }
            leaf dropped-address-packets {
              if-feature &quot;basic-nat44 or napt44 or nat64&quot;;
              type yang:zero-based-counter64;
              description
                &quot;Number of dropped packets because no address is
                 available for allocation.&quot;;
            }
            leaf dropped-address-bytes {
              if-feature &quot;basic-nat44 or napt44 or nat64&quot;;
              type yang:zero-based-counter64;
              units &quot;bytes&quot;;
              description
                &quot;Counter of dropped packets because no address is
                 available for allocation, in bytes.&quot;;
            }
            leaf dropped-port-limit-packets {
              if-feature &quot;napt44 or nat64&quot;;
              type yang:zero-based-counter64;
              description
<span class="grey"><a href="/doc/html/rfc8512">RFC 8512</a>               YANG Module for NAT and NPT          January 2019</span>

                &quot;Number of dropped packets because a port limit
                 is reached.&quot;;
            }
            leaf dropped-port-limit-bytes {
              if-feature &quot;napt44 or nat64&quot;;
              type yang:zero-based-counter64;
              units &quot;bytes&quot;;
              description
                &quot;Counter of dropped packets because a port limit
                 is reached, in bytes.&quot;;
            }
            leaf dropped-port-packets {
              if-feature &quot;napt44 or nat64&quot;;
              type yang:zero-based-counter64;
              description
                &quot;Number of dropped packets because no port is
                 available for allocation.&quot;;
            }
            leaf dropped-port-bytes {
              if-feature &quot;napt44 or nat64&quot;;
              type yang:zero-based-counter64;
              units &quot;bytes&quot;;
              description
                &quot;Counter of dropped packets because no port is
                 available for allocation, in bytes.&quot;;
            }
            leaf dropped-subscriber-limit-packets {
              if-feature &quot;basic-nat44 or napt44 or nat64&quot;;
              type yang:zero-based-counter64;
              description
                &quot;Number of dropped packets because the subscriber
                 limit per instance is reached.&quot;;
            }
            leaf dropped-subscriber-limit-bytes {
              if-feature &quot;basic-nat44 or napt44 or nat64&quot;;
              type yang:zero-based-counter64;
              units &quot;bytes&quot;;
              description
                &quot;Counter of dropped packets because the subscriber
                  limit per instance is reached, in bytes.&quot;;
            }
          }
          container mappings-statistics {
            description
              &quot;Mappings statistics.&quot;;
            leaf total-active-subscribers {
              if-feature &quot;basic-nat44 or napt44 or nat64&quot;;
              type yang:gauge32;
<span class="grey"><a href="/doc/html/rfc8512">RFC 8512</a>               YANG Module for NAT and NPT          January 2019</span>

              description
                &quot;Total number of active subscribers (that is,
                 subscribers for which the NAT maintains active
                 mappings).

                 A subscriber is identified by a subnet,
                 subscriber-mask, etc.&quot;;
            }
            leaf total-address-mappings {
              if-feature &quot;basic-nat44 or napt44 or nat64 &quot;
                       + &quot;or clat or dst-nat&quot;;
              type yang:gauge32;
              description
                &quot;Total number of address mappings present at a given
                 time.  It includes both static and dynamic mappings.&quot;;
              reference
                &quot;<a href="/doc/html/rfc7659#section-3.3.8">Section&amp;nbsp;3.3.8 of RFC 7659</a>&quot;;
            }
            leaf total-port-mappings {
              if-feature &quot;napt44 or nat64&quot;;
              type yang:gauge32;
              description
                &quot;Total number of NAT port mappings present at
                 a given time.  It includes both static and dynamic
                 mappings.&quot;;
              reference
                &quot;<a href="/doc/html/rfc7659#section-3.3.9">Section&amp;nbsp;3.3.9 of RFC 7659</a>&quot;;
            }
            list total-per-protocol {
              if-feature &quot;napt44 or nat64&quot;;
              key &quot;protocol-id&quot;;
              description
                &quot;Total mappings for each enabled/supported protocol.&quot;;
              leaf protocol-id {
                type uint8;
                mandatory true;
                description
                  &quot;The upper-layer protocol.
                   For example, this field contains 6 for TCP,
                   17 for UDP, 33 for DCCP, or 132 for SCTP.&quot;;
              }
              leaf total {
                type yang:gauge32;
                description
                  &quot;Total number of a protocol-specific mappings present
                   at a given time.  The protocol is identified by
                   protocol-id.&quot;;
              }
<span class="grey"><a href="/doc/html/rfc8512">RFC 8512</a>               YANG Module for NAT and NPT          January 2019</span>

            }
          }
          container pools-stats {
            if-feature &quot;basic-nat44 or napt44 or nat64&quot;;
            description
              &quot;Statistics related to address/prefix pools
               usage&quot;;
            leaf addresses-allocated {
              type yang:gauge32;
              description
                &quot;Number of all allocated addresses.&quot;;
            }
            leaf addresses-free {
              type yang:gauge32;
              description
                &quot;Number of unallocated addresses of all pools at
                 a given time.  The sum of unallocated and allocated
                 addresses is the total number of addresses of
                 the pools.&quot;;
            }
            container ports-stats {
              if-feature &quot;napt44 or nat64&quot;;
              description
                &quot;Statistics related to port numbers usage.&quot;;
              leaf ports-allocated {
                type yang:gauge32;
                description
                  &quot;Number of allocated ports from all pools.&quot;;
              }
              leaf ports-free {
                type yang:gauge32;
                description
                  &quot;Number of unallocated addresses from all pools.&quot;;
              }
            }
            list per-pool-stats {
              if-feature &quot;basic-nat44 or napt44 or nat64&quot;;
              key &quot;pool-id&quot;;
              description
                &quot;Statistics related to address/prefix pool usage&quot;;
              leaf pool-id {
                type uint32;
                description
                  &quot;Unique identifier that represents a pool of
                   addresses/prefixes.&quot;;
              }
              leaf discontinuity-time {
                type yang:date-and-time;
<span class="grey"><a href="/doc/html/rfc8512">RFC 8512</a>               YANG Module for NAT and NPT          January 2019</span>

                mandatory true;
                description
                  &quot;The time on the most recent occasion at which this
                   pool counter suffered a discontinuity.  This must
                   be initialized when the address pool is
                   configured.&quot;;
              }
              container pool-stats {
                description
                  &quot;Statistics related to address/prefix pool usage&quot;;
                leaf addresses-allocated {
                  type yang:gauge32;
                  description
                    &quot;Number of allocated addresses from this pool.&quot;;
                }
                leaf addresses-free {
                  type yang:gauge32;
                  description
                    &quot;Number of unallocated addresses in this pool.&quot;;
                }
              }
              container port-stats {
                if-feature &quot;napt44 or nat64&quot;;
                description
                  &quot;Statistics related to port numbers usage.&quot;;
                leaf ports-allocated {
                  type yang:gauge32;
                  description
                    &quot;Number of allocated ports from this pool.&quot;;
                }
                leaf ports-free {
                  type yang:gauge32;
                  description
                    &quot;Number of unallocated addresses from this pool.&quot;;
                }
              }
            }
          }
        }
      }
    }
  }

  /*
   * Notifications
   */

  notification nat-pool-event {
<span class="grey"><a href="/doc/html/rfc8512">RFC 8512</a>               YANG Module for NAT and NPT          January 2019</span>

    if-feature &quot;basic-nat44 or napt44 or nat64&quot;;
    description
      &quot;Notifications must be generated when the defined high/low
       threshold is reached.  Related configuration parameters
       must be provided to trigger the notifications.&quot;;
    leaf id {
      type leafref {
        path &quot;/nat/instances/instance/id&quot;;
      }
      mandatory true;
      description
        &quot;NAT instance identifier.&quot;;
    }
    leaf policy-id {
      type leafref {
        path &quot;/nat/instances/instance/policy/id&quot;;
      }
      description
        &quot;Policy identifier.&quot;;
    }
    leaf pool-id {
      type leafref {
        path &quot;/nat/instances/instance/policy&quot;
           + &quot;/external-ip-address-pool/pool-id&quot;;
      }
      mandatory true;
      description
        &quot;Pool Identifier.&quot;;
    }
    leaf notify-pool-threshold {
      type percent;
      mandatory true;
      description
        &quot;A threshold (high threshold or low threshold) has
         been fired.&quot;;
    }
  }

  notification nat-instance-event {
    if-feature &quot;basic-nat44 or napt44 or nat64&quot;;
    description
      &quot;Notifications must be generated when notify-addresses-usage
       and/or notify-ports-usage thresholds are reached.&quot;;
    leaf id {
      type leafref {
        path &quot;/nat/instances/instance/id&quot;;
      }
      mandatory true;
<span class="grey"><a href="/doc/html/rfc8512">RFC 8512</a>               YANG Module for NAT and NPT          January 2019</span>

      description
        &quot;NAT instance identifier.&quot;;
    }
    leaf notify-subscribers-threshold {
      type uint32;
      description
        &quot;The notify-subscribers-limit threshold has been fired.&quot;;
    }
    leaf notify-addresses-threshold {
      type percent;
      description
        &quot;The notify-addresses-usage threshold has been fired.&quot;;
    }
    leaf notify-ports-threshold {
      type percent;
      description
        &quot;The notify-ports-usage threshold has been fired.&quot;;
    }
  }
 }
