module ietf-packet-fields {
  yang-version 1.1;
  namespace &quot;urn:ietf:params:xml:ns:yang:ietf-packet-fields&quot;;
  prefix packet-fields;

  import ietf-inet-types {
    prefix inet;
    reference
      &quot;<a href="/doc/html/rfc6991">RFC 6991</a> - Common YANG Data Types.&quot;;
  }

  import ietf-yang-types {
    prefix yang;
    reference
      &quot;<a href="/doc/html/rfc6991">RFC 6991</a> - Common YANG Data Types.&quot;;
  }

  import ietf-ethertypes {
    prefix eth;
    reference
      &quot;<a href="/doc/html/rfc8519">RFC 8519</a> - YANG Data Model for Network Access Control
                  Lists (ACLs).&quot;;
  }

  organization
    &quot;IETF NETMOD (Network Modeling) Working Group.&quot;;

  contact
    &quot;WG Web:  &lt;<a href="https://datatracker.ietf.org/wg/netmod/">https://datatracker.ietf.org/wg/netmod/</a>&gt;
     WG List: <a href="mailto:netmod@ietf.org">netmod@ietf.org</a>

     Editor: Mahesh Jethanandani
             <a href="mailto:mjethanandani@gmail.com">mjethanandani@gmail.com</a>
     Editor: Lisa Huang
             <a href="mailto:huangyi_99@yahoo.com">huangyi_99@yahoo.com</a>
     Editor: Sonal Agarwal
             <a href="mailto:sagarwal12@gmail.com">sagarwal12@gmail.com</a>
     Editor: Dana Blair
             <a href="mailto:dana@blairhome.com">dana@blairhome.com</a>&quot;;

<span class="grey"><a href="/doc/html/rfc8519">RFC 8519</a>                YANG Data Model for ACLs              March 2019</span>

  description
    &quot;This YANG module defines groupings that are used by
     the ietf-access-control-list YANG module.  Their usage
     is not limited to ietf-access-control-list and can be
     used anywhere as applicable.

     Copyright (c) 2019 IETF Trust and the persons identified as
     the document authors.  All rights reserved.

     Redistribution and use in source and binary forms, with or
     without modification, is permitted pursuant to, and subject
     to the license terms contained in, the Simplified BSD
     License set forth in <a href="#section-4">Section 4</a>.c of the IETF Trust&#x27;s Legal
     Provisions Relating to IETF Documents
     (<a href="https://trustee.ietf.org/license-info">http://trustee.ietf.org/license-info</a>).

     This version of this YANG module is part of <a href="/doc/html/rfc8519">RFC 8519</a>; see
     the RFC itself for full legal notices.&quot;;

  revision 2019-03-04 {
    description
      &quot;Initial version.&quot;;
    reference
      &quot;<a href="/doc/html/rfc8519">RFC 8519</a>: YANG Data Model for Network Access Control
                 Lists (ACLs).&quot;;
  }

  /*
   * Typedefs
   */
  typedef operator {
    type enumeration {
      enum lte {
        description
          &quot;Less than or equal to.&quot;;
      }
      enum gte {
        description
          &quot;Greater than or equal to.&quot;;
      }
      enum eq {
        description
          &quot;Equal to.&quot;;
      }
      enum neq {
        description
          &quot;Not equal to.&quot;;
      }
<span class="grey"><a href="/doc/html/rfc8519">RFC 8519</a>                YANG Data Model for ACLs              March 2019</span>

    }
    description
      &quot;The source and destination port range definitions
       can be further qualified using an operator.  An
       operator is needed only if the lower-port is specified
       and the upper-port is not specified.  The operator
       therefore further qualifies the lower-port only.&quot;;
  }

  /*
   * Groupings
   */
  grouping port-range-or-operator {
    choice port-range-or-operator {
      case range {
        leaf lower-port {
          type inet:port-number;
          must &#x27;. &lt;= ../upper-port&#x27; {
            error-message
              &quot;The lower-port must be less than or equal to
               the upper-port.&quot;;
          }
          mandatory true;
          description
            &quot;Lower boundary for a port.&quot;;
        }
        leaf upper-port {
          type inet:port-number;
          mandatory true;
          description
            &quot;Upper boundary for a port.&quot;;
        }
      }
      case operator {
        leaf operator {
          type operator;
          default &quot;eq&quot;;
          description
            &quot;Operator to be applied on the port below.&quot;;
        }
        leaf port {
          type inet:port-number;
          mandatory true;
          description
            &quot;Port number along with the operator on which to
             match.&quot;;
        }
      }
<span class="grey"><a href="/doc/html/rfc8519">RFC 8519</a>                YANG Data Model for ACLs              March 2019</span>

      description
        &quot;Choice of specifying a port range or a single
         port along with an operator.&quot;;
    }
    description
      &quot;Grouping for port definitions in the form of a
       choice statement.&quot;;
  }

  grouping acl-ip-header-fields {
    description
      &quot;IP header fields common to IPv4 and IPv6&quot;;
    reference
      &quot;<a href="/doc/html/rfc791">RFC 791</a>: Internet Protocol.&quot;;

    leaf dscp {
      type inet:dscp;
      description
        &quot;Differentiated Services Code Point.&quot;;
      reference
        &quot;<a href="/doc/html/rfc2474">RFC 2474</a>: Definition of the Differentiated Services
                   Field (DS Field) in the IPv4 and IPv6
                   Headers.&quot;;
    }

    leaf ecn {
      type uint8 {
        range &quot;0..3&quot;;
      }
      description
        &quot;Explicit Congestion Notification.&quot;;
      reference
        &quot;<a href="/doc/html/rfc3168">RFC 3168</a>: The Addition of Explicit Congestion
                   Notification (ECN) to IP.&quot;;
    }

    leaf length {
      type uint16;
      description
        &quot;In the IPv4 header field, this field is known as the Total
         Length.  Total Length is the length of the datagram, measured
         in octets, including internet header and data.

         In the IPv6 header field, this field is known as the Payload
         Length, which is the length of the IPv6 payload, i.e., the rest
         of the packet following the IPv6 header, in octets.&quot;;
      reference
        &quot;<a href="/doc/html/rfc791">RFC 791</a>: Internet Protocol
<span class="grey"><a href="/doc/html/rfc8519">RFC 8519</a>                YANG Data Model for ACLs              March 2019</span>

         <a href="/doc/html/rfc8200">RFC 8200</a>: Internet Protocol, Version 6 (IPv6) Specification.&quot;;
    }
    leaf ttl {
      type uint8;
      description
        &quot;This field indicates the maximum time the datagram is allowed
         to remain in the internet system.  If this field contains the
         value zero, then the datagram must be dropped.

         In IPv6, this field is known as the Hop Limit.&quot;;
      reference
        &quot;<a href="/doc/html/rfc791">RFC 791</a>: Internet Protocol
         <a href="/doc/html/rfc8200">RFC 8200</a>: Internet Protocol, Version 6 (IPv6) Specification.&quot;;
    }
    leaf protocol {
      type uint8;
      description
        &quot;Internet Protocol number.  Refers to the protocol of the
         payload.  In IPv6, this field is known as &#x27;next-header&#x27;,
         and if extension headers are present, the protocol is
         present in the &#x27;upper-layer&#x27; header.&quot;;
      reference
        &quot;<a href="/doc/html/rfc791">RFC 791</a>: Internet Protocol
         <a href="/doc/html/rfc8200">RFC 8200</a>: Internet Protocol, Version 6 (IPv6) Specification.&quot;;
    }
  }

  grouping acl-ipv4-header-fields {
    description
      &quot;Fields in the IPv4 header.&quot;;
    leaf ihl {
      type uint8 {
        range &quot;5..60&quot;;
      }
      description
        &quot;In an IPv4 header field, the Internet Header Length (IHL) is
         the length of the internet header in 32-bit words and
         thus points to the beginning of the data.  Note that the
         minimum value for a correct header is 5.&quot;;
    }
    leaf flags {
      type bits {
        bit reserved {
          position 0;
          description
            &quot;Reserved.  Must be zero.&quot;;
        }
        bit fragment {
<span class="grey"><a href="/doc/html/rfc8519">RFC 8519</a>                YANG Data Model for ACLs              March 2019</span>

          position 1;
          description
            &quot;Setting the value to 0 indicates may fragment, while
             setting the value to 1 indicates do not fragment.&quot;;
        }
        bit more {
          position 2;
          description
            &quot;Setting the value to 0 indicates this is the last fragment,
             and setting the value to 1 indicates more fragments are
             coming.&quot;;
        }
      }
      description
        &quot;Bit definitions for the Flags field in the IPv4 header.&quot;;
    }
    leaf offset {
      type uint16 {
        range &quot;20..65535&quot;;
      }
      description
        &quot;The fragment offset is measured in units of 8 octets (64 bits).
         The first fragment has offset zero.  The length is 13 bits&quot;;
    }
    leaf identification {
      type uint16;
      description
        &quot;An identifying value assigned by the sender to aid in
         assembling the fragments of a datagram.&quot;;
    }

    choice destination-network {
      case destination-ipv4-network {
        leaf destination-ipv4-network {
          type inet:ipv4-prefix;
          description
            &quot;Destination IPv4 address prefix.&quot;;
        }
      }
      description
        &quot;Choice of specifying a destination IPv4 address or
         referring to a group of IPv4 destination addresses.&quot;;
    }

    choice source-network {
      case source-ipv4-network {
        leaf source-ipv4-network {
          type inet:ipv4-prefix;
<span class="grey"><a href="/doc/html/rfc8519">RFC 8519</a>                YANG Data Model for ACLs              March 2019</span>

          description
            &quot;Source IPv4 address prefix.&quot;;
        }
      }
      description
        &quot;Choice of specifying a source IPv4 address or
         referring to a group of IPv4 source addresses.&quot;;
    }
  }

  grouping acl-ipv6-header-fields {
    description
      &quot;Fields in the IPv6 header.&quot;;

    choice destination-network {
      case destination-ipv6-network {
        leaf destination-ipv6-network {
          type inet:ipv6-prefix;
          description
            &quot;Destination IPv6 address prefix.&quot;;
        }
      }
      description
        &quot;Choice of specifying a destination IPv6 address
         or referring to a group of IPv6 destination
         addresses.&quot;;
    }

    choice source-network {
      case source-ipv6-network {
        leaf source-ipv6-network {
          type inet:ipv6-prefix;
          description
            &quot;Source IPv6 address prefix.&quot;;
        }
      }
      description
        &quot;Choice of specifying a source IPv6 address or
         referring to a group of IPv6 source addresses.&quot;;
    }

    leaf flow-label {
      type inet:ipv6-flow-label;
      description
        &quot;IPv6 Flow label.&quot;;
    }
    reference
      &quot;<a href="/doc/html/rfc4291">RFC 4291</a>: IP Version 6 Addressing Architecture
<span class="grey"><a href="/doc/html/rfc8519">RFC 8519</a>                YANG Data Model for ACLs              March 2019</span>

       <a href="/doc/html/rfc4007">RFC 4007</a>: IPv6 Scoped Address Architecture
       <a href="/doc/html/rfc5952">RFC 5952</a>: A Recommendation for IPv6 Address Text
                 Representation.&quot;;
  }

  grouping acl-eth-header-fields {
    description
      &quot;Fields in the Ethernet header.&quot;;
    leaf destination-mac-address {
      type yang:mac-address;
      description
        &quot;Destination IEEE 802 Media Access Control (MAC)
         address.&quot;;
    }
    leaf destination-mac-address-mask {
      type yang:mac-address;
      description
        &quot;Destination IEEE 802 MAC address mask.&quot;;
    }
    leaf source-mac-address {
      type yang:mac-address;
      description
        &quot;Source IEEE 802 MAC address.&quot;;
    }
    leaf source-mac-address-mask {
      type yang:mac-address;
      description
        &quot;Source IEEE 802 MAC address mask.&quot;;
    }
    leaf ethertype {
      type eth:ethertype;
      description
        &quot;The Ethernet Type (or Length) value represented
         in the canonical order defined by IEEE 802.
         The canonical representation uses lowercase
         characters.&quot;;
      reference
        &quot;IEEE 802-2014, Clause 9.2.&quot;;
    }
    reference
      &quot;IEEE 802: IEEE Standard for Local and Metropolitan
       Area Networks: Overview and Architecture.&quot;;
  }

  grouping acl-tcp-header-fields {
    description
      &quot;Collection of TCP header fields that can be used to
       set up a match filter.&quot;;
<span class="grey"><a href="/doc/html/rfc8519">RFC 8519</a>                YANG Data Model for ACLs              March 2019</span>

    leaf sequence-number {
      type uint32;
      description
        &quot;Sequence number that appears in the packet.&quot;;
    }
    leaf acknowledgement-number {
      type uint32;
      description
        &quot;The acknowledgement number that appears in the
         packet.&quot;;
    }
    leaf data-offset {
      type uint8 {
        range &quot;5..15&quot;;
      }
      description
        &quot;Specifies the size of the TCP header in 32-bit
         words.  The minimum size header is 5 words and
         the maximum is 15 words; thus, this gives a
         minimum size of 20 bytes and a maximum of 60
         bytes, allowing for up to 40 bytes of options
         in the header.&quot;;
    }
    leaf reserved {
      type uint8;
      description
        &quot;Reserved for future use.&quot;;
    }
    leaf flags {
      type bits {
        bit cwr {
          position 1;
          description
            &quot;The Congestion Window Reduced (CWR) flag is set
             by the sending host to indicate that it received
             a TCP segment with the ECN-Echo (ECE) flag set
             and had responded in the congestion control
             mechanism.&quot;;
          reference
            &quot;<a href="/doc/html/rfc3168">RFC 3168</a>: The Addition of Explicit Congestion
                       Notification (ECN) to IP.&quot;;
        }
        bit ece {
          position 2;
          description
            &quot;ECN-Echo has a dual role, depending on the value
             of the SYN flag.  It indicates the following: if
             the SYN flag is set (1), the TCP peer is ECN
<span class="grey"><a href="/doc/html/rfc8519">RFC 8519</a>                YANG Data Model for ACLs              March 2019</span>

             capable, and if the SYN flag is clear (0), a packet
             with the Congestion Experienced flag set (ECN=11)
             in the IP header was received during normal
             transmission (added to the header by <a href="/doc/html/rfc3168">RFC 3168</a>).
             This serves as an indication of network congestion
             (or impending congestion) to the TCP sender.&quot;;
          reference
            &quot;<a href="/doc/html/rfc3168">RFC 3168</a>: The Addition of Explicit Congestion
                       Notification (ECN) to IP.&quot;;
        }
        bit urg {
          position 3;
          description
            &quot;Indicates that the Urgent Pointer field is significant.&quot;;
        }
        bit ack {
          position 4;
          description
            &quot;Indicates that the Acknowledgement field is significant.
             All packets after the initial SYN packet sent by the
             client should have this flag set.&quot;;
        }
        bit psh {
          position 5;
          description
            &quot;Push function.  Asks to push the buffered data to the
             receiving application.&quot;;
        }
        bit rst {
          position 6;
          description
            &quot;Reset the connection.&quot;;
        }
        bit syn {
          position 7;
          description
            &quot;Synchronize sequence numbers.  Only the first packet
             sent from each end should have this flag set.  Some
             other flags and fields change meaning based on this
             flag, and some are only valid for when it is set,
             and others when it is clear.&quot;;
        }
        bit fin {
          position 8;
          description
            &quot;Last package from the sender.&quot;;
        }
      }
<span class="grey"><a href="/doc/html/rfc8519">RFC 8519</a>                YANG Data Model for ACLs              March 2019</span>

      description
        &quot;Also known as Control Bits.  Contains nine 1-bit flags.&quot;;
      reference
        &quot;<a href="/doc/html/rfc793">RFC 793</a>: Transmission Control Protocol.&quot;;
    }
    leaf window-size {
      type uint16;
      units &quot;bytes&quot;;
      description
        &quot;The size of the receive window, which specifies
         the number of window size units beyond the segment
         identified by the sequence number in the Acknowledgement
         field that the sender of this segment is currently
         willing to receive.&quot;;
    }
    leaf urgent-pointer {
      type uint16;
      description
        &quot;This field is an offset from the sequence number
         indicating the last urgent data byte.&quot;;
    }
    leaf options {
      type binary {
        length &quot;1..40&quot;;
      }
      description
        &quot;The length of this field is determined by the
         Data Offset field.  Options have up to three
         fields: Option-Kind (1 byte), Option-Length
         (1 byte), and Option-Data (variable).  The Option-Kind
         field indicates the type of option and is the
         only field that is not optional.  Depending on
         what kind of option we are dealing with,
         the next two fields may be set: the Option-Length
         field indicates the total length of the option,
         and the Option-Data field contains the value of
         the option, if applicable.&quot;;
    }
  }

  grouping acl-udp-header-fields {
    description
      &quot;Collection of UDP header fields that can be used
       to set up a match filter.&quot;;
    leaf length {
      type uint16;
      description
        &quot;A field that specifies the length in bytes of
<span class="grey"><a href="/doc/html/rfc8519">RFC 8519</a>                YANG Data Model for ACLs              March 2019</span>

         the UDP header and UDP data.  The minimum
         length is 8 bytes because that is the length of
         the header.  The field size sets a theoretical
         limit of 65,535 bytes (8-byte header plus 65,527
         bytes of data) for a UDP datagram.  However, the
         actual limit for the data length, which is
         imposed by the underlying IPv4 protocol, is
         65,507 bytes (65,535 minus 8-byte UDP header
         minus 20-byte IP header).

         In IPv6 jumbograms, it is possible to have
         UDP packets of a size greater than 65,535 bytes.
         <a href="/doc/html/rfc2675">RFC 2675</a> specifies that the Length field is set
         to zero if the length of the UDP header plus
         UDP data is greater than 65,535.&quot;;
    }
  }

  grouping acl-icmp-header-fields {
    description
      &quot;Collection of ICMP header fields that can be
       used to set up a match filter.&quot;;
    leaf type {
      type uint8;
      description
        &quot;Also known as control messages.&quot;;
      reference
        &quot;<a href="/doc/html/rfc792">RFC 792</a>: Internet Control Message Protocol
         <a href="/doc/html/rfc4443">RFC 4443</a>: Internet Control Message Protocol (ICMPv6)
                   for Internet Protocol Version 6 (IPv6)
                   Specification.&quot;;
    }
    leaf code {
      type uint8;
      description
        &quot;ICMP subtype.  Also known as control messages.&quot;;
      reference
        &quot;<a href="/doc/html/rfc792">RFC 792</a>: Internet Control Message Protocol
         <a href="/doc/html/rfc4443">RFC 4443</a>: Internet Control Message Protocol (ICMPv6)
                   for Internet Protocol Version 6 (IPv6)
                   Specification.&quot;;
    }
    leaf rest-of-header {
      type binary;
      description
        &quot;Unbounded in length, the contents vary based on the
         ICMP type and code.  Also referred to as &#x27;Message Body&#x27;
         in ICMPv6.&quot;;
<span class="grey"><a href="/doc/html/rfc8519">RFC 8519</a>                YANG Data Model for ACLs              March 2019</span>

      reference
        &quot;<a href="/doc/html/rfc792">RFC 792</a>: Internet Control Message Protocol
         <a href="/doc/html/rfc4443">RFC 4443</a>: Internet Control Message Protocol (ICMPv6)
                   for Internet Protocol Version 6 (IPv6)
                   Specification.&quot;;
    }
  }
}
