module ietf-network {
  yang-version 1.1;
  namespace &quot;urn:ietf:params:xml:ns:yang:ietf-network&quot;;
  prefix nw;

  import ietf-inet-types {
    prefix inet;
    reference
      &quot;<a href="/doc/html/rfc6991">RFC 6991</a>: Common YANG Data Types&quot;;
  }

  organization
    &quot;IETF I2RS (Interface to the Routing System) Working Group&quot;;

  contact
    &quot;WG Web:    &lt;<a href="https://datatracker.ietf.org/wg/i2rs/">https://datatracker.ietf.org/wg/i2rs/</a>&gt;
     WG List:   &lt;mailto:<a href="mailto:i2rs@ietf.org">i2rs@ietf.org</a>&gt;

     Editor:    Alexander Clemm
                &lt;mailto:<a href="mailto:ludwig@clemm.org">ludwig@clemm.org</a>&gt;

     Editor:    Jan Medved
                &lt;mailto:<a href="mailto:jmedved@cisco.com">jmedved@cisco.com</a>&gt;

     Editor:    Robert Varga
                &lt;mailto:<a href="mailto:robert.varga@pantheon.tech">robert.varga@pantheon.tech</a>&gt;

     Editor:    Nitin Bahadur
                &lt;mailto:<a href="mailto:nitin_bahadur@yahoo.com">nitin_bahadur@yahoo.com</a>&gt;

     Editor:    Hariharan Ananthakrishnan
                &lt;mailto:<a href="mailto:hari@packetdesign.com">hari@packetdesign.com</a>&gt;

     Editor:    Xufeng Liu
                &lt;mailto:<a href="mailto:xufeng.liu.ietf@gmail.com">xufeng.liu.ietf@gmail.com</a>&gt;&quot;;
<span class="grey"><a href="/doc/html/rfc8345">RFC 8345</a>         YANG Data Model for Network Topologies       March 2018</span>

     description
       &quot;This module defines a common base data model for a collection
        of nodes in a network.  Node definitions are further used
        in network topologies and inventories.

        Copyright (c) 2018 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">https://trustee.ietf.org/license-info</a>).

        This version of this YANG module is part of <a href="/doc/html/rfc8345">RFC 8345</a>;
        see the RFC itself for full legal notices.&quot;;

     revision 2018-02-26 {
       description
         &quot;Initial revision.&quot;;
       reference
         &quot;<a href="/doc/html/rfc8345">RFC 8345</a>: A YANG Data Model for Network Topologies&quot;;
     }

     typedef node-id {
       type inet:uri;
       description
         &quot;Identifier for a node.  The precise structure of the node-id
          will be up to the implementation.  For example, some
          implementations MAY pick a URI that includes the network-id
          as part of the path.  The identifier SHOULD be chosen
          such that the same node in a real network topology will
          always be identified through the same identifier, even if
          the data model is instantiated in separate datastores.  An
          implementation MAY choose to capture semantics in the
          identifier -- for example, to indicate the type of node.&quot;;
     }

<span class="grey"><a href="/doc/html/rfc8345">RFC 8345</a>         YANG Data Model for Network Topologies       March 2018</span>

     typedef network-id {
       type inet:uri;
       description
         &quot;Identifier for a network.  The precise structure of the
          network-id will be up to the implementation.  The identifier
          SHOULD be chosen such that the same network will always be
          identified through the same identifier, even if the data model
          is instantiated in separate datastores.  An implementation MAY
          choose to capture semantics in the identifier -- for example,
          to indicate the type of network.&quot;;
     }

     grouping network-ref {
       description
         &quot;Contains the information necessary to reference a network --
          for example, an underlay network.&quot;;
       leaf network-ref {
         type leafref {
           path &quot;/nw:networks/nw:network/nw:network-id&quot;;
         require-instance false;
         }
         description
           &quot;Used to reference a network -- for example, an underlay
            network.&quot;;
       }
     }

     grouping node-ref {
       description
         &quot;Contains the information necessary to reference a node.&quot;;
       leaf node-ref {
         type leafref {
           path &quot;/nw:networks/nw:network[nw:network-id=current()/../&quot;+
             &quot;network-ref]/nw:node/nw:node-id&quot;;
           require-instance false;
         }
         description
           &quot;Used to reference a node.
            Nodes are identified relative to the network that
            contains them.&quot;;
       }
       uses network-ref;
     }

<span class="grey"><a href="/doc/html/rfc8345">RFC 8345</a>         YANG Data Model for Network Topologies       March 2018</span>

     container networks {
       description
         &quot;Serves as a top-level container for a list of networks.&quot;;
       list network {
         key &quot;network-id&quot;;
         description
           &quot;Describes a network.
            A network typically contains an inventory of nodes,
            topological information (augmented through the
            network-topology data model), and layering information.&quot;;
         leaf network-id {
           type network-id;
           description
             &quot;Identifies a network.&quot;;
         }
         container network-types {
           description
             &quot;Serves as an augmentation target.
              The network type is indicated through corresponding
              presence containers augmented into this container.&quot;;
         }
         list supporting-network {
           key &quot;network-ref&quot;;
           description
             &quot;An underlay network, used to represent layered network
              topologies.&quot;;
           leaf network-ref {
             type leafref {
               path &quot;/nw:networks/nw:network/nw:network-id&quot;;
             require-instance false;
             }
             description
               &quot;References the underlay network.&quot;;
           }
         }

<span class="grey"><a href="/doc/html/rfc8345">RFC 8345</a>         YANG Data Model for Network Topologies       March 2018</span>

         list node {
           key &quot;node-id&quot;;
           description
             &quot;The inventory of nodes of this network.&quot;;
           leaf node-id {
             type node-id;
             description
               &quot;Uniquely identifies a node within the containing
                network.&quot;;
           }
           list supporting-node {
             key &quot;network-ref node-ref&quot;;
             description
               &quot;Represents another node that is in an underlay network
                and that supports this node.  Used to represent layering
                structure.&quot;;
             leaf network-ref {
               type leafref {
                 path &quot;../../../nw:supporting-network/nw:network-ref&quot;;
               require-instance false;
               }
               description
                 &quot;References the underlay network of which the
                  underlay node is a part.&quot;;
             }
             leaf node-ref {
               type leafref {
                 path &quot;/nw:networks/nw:network/nw:node/nw:node-id&quot;;
               require-instance false;
               }
               description
                 &quot;References the underlay node itself.&quot;;
             }
           }
         }
       }
     }
   }
