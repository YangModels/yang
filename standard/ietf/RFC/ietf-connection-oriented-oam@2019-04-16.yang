module ietf-connection-oriented-oam {
  yang-version 1.1;
  namespace &quot;urn:ietf:params:xml:ns:yang:ietf-connection-oriented-oam&quot;;
  prefix co-oam;

  import ietf-yang-types {
    prefix yang;
  }
  import ietf-inet-types {
    prefix inet;
  }
  import ietf-interfaces {
    prefix if;
  }

  organization
    &quot;IETF LIME Working Group&quot;;
  contact
    &quot;WG Web:    <a href="https://datatracker.ietf.org/wg/lime">http://datatracker.ietf.org/wg/lime</a>
     WG List:   &lt;mailto:<a href="mailto:lime@ietf.org">lime@ietf.org</a>&gt;
     Editor:    Deepak Kumar &lt;<a href="mailto:dekumar@cisco.com">dekumar@cisco.com</a>&gt;
     Editor:    Qin Wu &lt;<a href="mailto:bill.wu@huawei.com">bill.wu@huawei.com</a>&gt;
     Editor:    Michael Wang &lt;<a href="mailto:wangzitao@huawei.com">wangzitao@huawei.com</a>&gt;&quot;;
  description
    &quot;This YANG module defines the generic configuration,
     statistics and RPC for connection-oriented OAM
     to be used within IETF in a protocol-independent manner.
     Functional-level abstraction is independent
     with YANG modeling. It is assumed that each protocol
     maps corresponding abstracts to its native format.
     Each protocol may extend the YANG data model defined
     here to include protocol-specific extensions

     Copyright (c) 2019 IETF Trust and the persons identified as
     authors of the code.  All rights reserved.

     Redistribution and use in source and binary forms, with or
     without modification, is permitted pursuant to, and subject
     to the license terms contained in, the Simplified BSD License
     set forth in <a href="#section-4">Section 4</a>.c of the IETF Trust&#x27;s Legal Provisions
     Relating to IETF Documents
<span class="grey"><a href="/doc/html/rfc8531">RFC 8531</a>         Connection-Oriented OAM YANG Data Model      April 2019</span>

     (<a href="https://trustee.ietf.org/license-info">http://trustee.ietf.org/license-info</a>).

     This version of this YANG module is part of <a href="/doc/html/rfc8531">RFC 8531</a>; see
     the RFC itself for full legal notices.&quot;;

  revision 2019-04-16 {
    description
      &quot;Initial revision.&quot;;
    reference
      &quot;<a href="/doc/html/rfc8531">RFC 8531</a>: Generic YANG Data Model for Connection-
       Oriented Operations, Administration, and Maintenance (OAM)
       Protocols&quot;;
  }

  feature connectivity-verification {
    description
      &quot;This feature indicates that the server supports
       executing a connectivity verification OAM command and
       returning a response.  Servers that do not advertise
       this feature will not support executing a
       connectivity verification command or RPC model for a
       connectivity verification command.&quot;;
  }

  feature continuity-check {
    description
      &quot;This feature indicates that the server supports
       executing a Continuity Check OAM command and
       returning a response.  Servers that do not advertise
       this feature will not support executing a
       Continuity Check command or RPC model for a
       Continuity Check command.&quot;;
  }

  feature traceroute {
    description
      &quot;This feature indicates that the server supports
       executing a traceroute OAM command and
       returning a response.  Servers that do not advertise
       this feature will not support executing a
       traceroute command or RPC model for a
       traceroute command.&quot;;
  }

  feature mip {
    description
      &quot;This feature indicates that the Maintenance
       Intermediate Point (MIP) needs to be explicitly configured&quot;;
<span class="grey"><a href="/doc/html/rfc8531">RFC 8531</a>         Connection-Oriented OAM YANG Data Model      April 2019</span>

  }

  identity technology-types {
    description
      &quot;This is the base identity of technology types that are
       TRILL, MPLS-TP, etc.&quot;;
  }

  identity command-sub-type {
    description
      &quot;Defines different RPC command subtypes,
       e.g., TRILL OAM as specified in <a href="/doc/html/rfc6905">RFC 6905</a>; this is
       optional for most cases.&quot;;
    reference
      &quot;<a href="/doc/html/rfc6905">RFC 6905</a>: Requirements for OAM in Transparent
       Interconnection of Lots of Links (TRILL)&quot;;
  }

  identity on-demand {
    base command-sub-type;
    description
      &quot;On-demand activation indicates that the tool is activated
       manually to detect a specific anomaly.
       An on-demand OAM method requires only transient configuration.&quot;;
    reference
      &quot;<a href="/doc/html/rfc7276">RFC 7276</a>: An Overview of Operations, Administration, and
       Maintenance (OAM) Tools&quot;;
  }

  identity proactive {
    base command-sub-type;
    description
      &quot;Proactive activation indicates that the tool is activated on a
       continual basis, where messages are sent periodically, and errors
       are detected when a certain number of expected messages are not
       received.  A proactive OAM method requires persistent
       configuration.&quot;;
    reference
      &quot;<a href="/doc/html/rfc7276">RFC 7276</a>: An Overview of Operations, Administration, and
       Maintenance (OAM) Tools&quot;;
  }

  identity name-format {
    description
      &quot;This defines the name format, CFM (IEEE 802.1Q) defines varying
       styles of names.  It is expected that name format is an identity
       reference to be extended with new types.&quot;;
  }
<span class="grey"><a href="/doc/html/rfc8531">RFC 8531</a>         Connection-Oriented OAM YANG Data Model      April 2019</span>

  identity name-format-null {
    base name-format;
    description
      &quot;Defines name format as null.&quot;;
  }

  identity identifier-format {
    description
      &quot;Identifier-format identity can be augmented to define other
       format identifiers used in MEP-ID, etc.&quot;;
  }

  identity identifier-format-integer {
    base identifier-format;
    description
      &quot;Defines identifier-format to be integer.&quot;;
  }

  identity defect-types {
    description
      &quot;Defines different defect types, e.g.,
       Remote Defect Indication (RDI), loss of continuity.&quot;;
  }

  identity rdi {
    base defect-types;
    description
      &quot;The RDI indicates the
       aggregate health of the remote Maintenance End Points (MEPs).&quot;;
  }

  identity remote-mep-defect {
    base defect-types;
    description
      &quot;Indicates that one or more of the remote MEPs are
       reporting a failure.&quot;;
  }

  identity loss-of-continuity {
    base defect-types;
    description
      &quot;Indicates that there are no proactive Continuity Check (CC)
       OAM packets from the source MEP (and in the case of
       Connectivity Verification, this includes the requirement to have
       the expected unique, technology-dependent source MEP identifier)
       received within the interval.&quot;;
    reference
      &quot;<a href="/doc/html/rfc6371">RFC 6371</a>: Operations, Administration, and Maintenance
<span class="grey"><a href="/doc/html/rfc8531">RFC 8531</a>         Connection-Oriented OAM YANG Data Model      April 2019</span>

       Framework for MPLS-Based Transport Networks&quot;;
  }

  identity cv-defect {
    base defect-types;
    description
      &quot;This function should support monitoring between the MEPs
       and, in addition, between a MEP and MIP.  When performing
       Connectivity Verification, the Continuity Check and
       Connectivity Verification (CC-V) messages need to include
       unique identification of the MEG that is being monitored and
       the MEP that originated the message.&quot;;
    reference
      &quot;<a href="/doc/html/rfc6371">RFC 6371</a>: Operations, Administration, and Maintenance
       Framework for MPLS-Based Transport Networks&quot;;
  }

  identity invalid-oam-defect {
    base defect-types;
    description
      &quot;Indicates that one or more invalid OAM messages have been
       received and that 3.5 times that OAM message transmission
       interval has not yet expired.&quot;;
  }

  identity cross-connect-defect {
    base defect-types;
    description
      &quot;Indicates that one or more cross-connect defect
       (for example, a service ID does not match the VLAN)
       messages have been received and that 3.5 times that OAM message
       transmission interval has not yet expired.&quot;;
  }

  typedef mep-name {
    type string;
    description
      &quot;Generic administrative name for a MEP.&quot;;
  }

  typedef time-interval {
    type decimal64 {
      fraction-digits 2;
    }
    units &quot;milliseconds&quot;;
    description
      &quot;Time interval between packets in milliseconds.
       Time interval should not be less than 0.
<span class="grey"><a href="/doc/html/rfc8531">RFC 8531</a>         Connection-Oriented OAM YANG Data Model      April 2019</span>

       0 means no packets are sent.&quot;;
  }

  typedef md-name-string {
    type string;
    description
      &quot;Generic administrative name for Maintenance Domain (MD).&quot;;
  }

  typedef ma-name-string {
    type string;
    description
      &quot;Generic administrative name for a
       Maintenance Association (MA).&quot;;
  }

  typedef oam-counter32 {
    type yang:zero-based-counter32;
    description
      &quot;Define 32-bit counter for OAM.&quot;;
  }

  typedef md-level {
    type uint32 {
      range &quot;0..255&quot;;
    }
    description
      &quot;Maintenance Domain Level.  The level may be restricted in
       certain protocols (e.g., protocol in layer 0 to layer 7).&quot;;
  }

  grouping maintenance-domain-reference {
    description
      &quot;This grouping uniquely identifies a Maintenance Domain.&quot;;
    leaf maintenance-domain {
      type leafref {
        path &quot;/co-oam:domains/co-oam:domain/co-oam:md-name-string&quot;;
      }
      description
        &quot;A reference to a specific Maintenance Domain.&quot;;
    }
  }

  grouping maintenance-association-reference {
    description
      &quot;This grouping uniquely identifies a
       Maintenance Association.  It consists
       of a maintenance-domain-reference and
<span class="grey"><a href="/doc/html/rfc8531">RFC 8531</a>         Connection-Oriented OAM YANG Data Model      April 2019</span>

       a maintenance-association leafref.&quot;;
    uses maintenance-domain-reference;
    leaf maintenance-association {
      type leafref {
        path &quot;/co-oam:domains/co-oam:domain[co-oam:md-name-string &quot;
           + &quot;= current()/../maintenance-domain]/co-oam:mas&quot;
           + &quot;/co-oam:ma/co-oam:ma-name-string&quot;;
      }
      description
        &quot;A reference to a specific Maintenance Association.&quot;;
    }
  }

  grouping maintenance-association-end-point-reference {
    description
      &quot;This grouping uniquely identifies
       a Maintenance Association.  It consists
       of a maintenance-association-reference and
       a maintenance-association-end-point leafref.&quot;;
    uses maintenance-association-reference;
    leaf maintenance-association-end-point {
      type leafref {
        path &quot;/co-oam:domains/co-oam:domain[co-oam:md-name-string &quot;
           + &quot;= current()/../maintenance-domain]/co-oam:mas&quot;
           + &quot;/co-oam:ma[co-oam:ma-name-string = &quot;
           + &quot;current()/../maintenance-association]&quot;
           + &quot;/co-oam:mep/co-oam:mep-name&quot;;
      }
      description
        &quot;A reference to a specific Maintenance
         association End Point.&quot;;
    }
  }

  grouping time-to-live {
    leaf ttl {
      type uint8;
      description
        &quot;Time to Live.&quot;;
    }
    description
      &quot;Time to Live grouping.&quot;;
  }

  grouping defect-message {
    choice defect {
      case defect-null {
        description
<span class="grey"><a href="/doc/html/rfc8531">RFC 8531</a>         Connection-Oriented OAM YANG Data Model      April 2019</span>

          &quot;This is a placeholder when no defect status is needed.&quot;;
        leaf defect-null {
          type empty;
          description
            &quot;There is no defect to be defined; it will be defined in
             a technology-specific model.&quot;;
        }
      }
      case defect-code {
        description
          &quot;This is a placeholder to display defect code.&quot;;
        leaf defect-code {
          type int32;
          description
            &quot;Defect code is integer value specific to a technology.&quot;;
        }
      }
      description
        &quot;Defect Message choices.&quot;;
    }
    description
      &quot;Defect Message.&quot;;
  }

  grouping mep-address {
    choice mep-address {
      default &quot;ip-address&quot;;
      case mac-address {
        leaf mac-address {
          type yang:mac-address;
          description
            &quot;MAC Address.&quot;;
        }
        description
          &quot;MAC Address based MEP Addressing.&quot;;
      }
      case ip-address {
        leaf ip-address {
          type inet:ip-address;
          description
            &quot;IP Address.&quot;;
        }
        description
          &quot;IP Address based MEP Addressing.&quot;;
      }
      description
        &quot;MEP Addressing.&quot;;
    }
<span class="grey"><a href="/doc/html/rfc8531">RFC 8531</a>         Connection-Oriented OAM YANG Data Model      April 2019</span>

    description
      &quot;Grouping for MEP Address&quot;;
  }

  grouping mip-address {
    choice mip-address {
      default &quot;ip-address&quot;;
      case mac-address {
        leaf mac-address {
          type yang:mac-address;
          description
            &quot;MAC Address of Maintenance Intermediate Point&quot;;
        }
        description
          &quot;MAC Address based MIP Addressing.&quot;;
      }
      case ip-address {
        leaf ip-address {
          type inet:ip-address;
          description
            &quot;IP Address.&quot;;
        }
        description
          &quot;IP Address based MIP Addressing.&quot;;
      }
      description
        &quot;MIP Addressing.&quot;;
    }
    description
      &quot;MIP Address.&quot;;
  }

  grouping maintenance-domain-id {
    description
      &quot;Grouping containing leaves sufficient to identify
       a Maintenance Domain.&quot;;
    leaf technology {
      type identityref {
        base technology-types;
      }
      mandatory true;
      description
        &quot;Defines the technology.&quot;;
    }
    leaf md-name-string {
      type md-name-string;
      mandatory true;
      description
<span class="grey"><a href="/doc/html/rfc8531">RFC 8531</a>         Connection-Oriented OAM YANG Data Model      April 2019</span>

        &quot;Defines the generic administrative Maintenance Domain name.&quot;;
    }
  }

  grouping md-name {
    leaf md-name-format {
      type identityref {
        base name-format;
      }
      description
        &quot;Maintenance Domain Name format.&quot;;
    }
    choice md-name {
      case md-name-null {
        leaf md-name-null {
          when &quot;derived-from-or-self(../md-name-format,&quot;
             + &quot;&#x27;name-format-null&#x27;)&quot; {
            description
              &quot;MD name format is equal to null format.&quot;;
          }
          type empty;
          description
            &quot;MD name null.&quot;;
        }
      }
      description
        &quot;MD name.&quot;;
    }
    description
      &quot;MD name.&quot;;
  }

  grouping ma-identifier {
    description
      &quot;Grouping containing leaves sufficient to identify an MA.&quot;;
    leaf ma-name-string {
      type ma-name-string;
      description
        &quot;MA name string.&quot;;
    }
  }

  grouping ma-name {
    description
      &quot;MA name.&quot;;
    leaf ma-name-format {
      type identityref {
        base name-format;
<span class="grey"><a href="/doc/html/rfc8531">RFC 8531</a>         Connection-Oriented OAM YANG Data Model      April 2019</span>

      }
      description
        &quot;MA name format.&quot;;
    }
    choice ma-name {
      case ma-name-null {
        leaf ma-name-null {
          when &quot;derived-from-or-self(../ma-name-format,&quot;
             + &quot;&#x27;name-format-null&#x27;)&quot; {
            description
              &quot;MA.&quot;;
          }
          type empty;
          description
            &quot;Empty&quot;;
        }
      }
      description
        &quot;MA name.&quot;;
    }
  }

  grouping mep-id {
    choice mep-id {
      default &quot;mep-id-int&quot;;
      case mep-id-int {
        leaf mep-id-int {
          type int32;
          description
            &quot;MEP ID
             in integer format.&quot;;
        }
      }
      description
        &quot;MEP ID.&quot;;
    }
    leaf mep-id-format {
      type identityref {
        base identifier-format;
      }
      description
        &quot;MEP ID format.&quot;;
    }
    description
      &quot;MEP ID.&quot;;
  }

  grouping mep {
<span class="grey"><a href="/doc/html/rfc8531">RFC 8531</a>         Connection-Oriented OAM YANG Data Model      April 2019</span>

    description
      &quot;Defines elements within the MEP.&quot;;
    leaf mep-name {
      type mep-name;
      mandatory true;
      description
        &quot;Generic administrative name of the
         MEP.&quot;;
    }
    uses mep-id;
    uses mep-address;
  }

  grouping monitor-stats {
    description
      &quot;Grouping for monitoring statistics; this will be augmented
       by others who use this component.&quot;;
    choice monitor-stats {
      default &quot;monitor-null&quot;;
      case monitor-null {
        description
          &quot;This is a placeholder when
           no monitoring statistics are needed.&quot;;
        leaf monitor-null {
          type empty;
          description
            &quot;There are no monitoring statistics to be defined.&quot;;
        }
      }
      description
        &quot;Define the monitor stats.&quot;;
    }
  }

  grouping connectivity-context {
    description
      &quot;Grouping defining the connectivity context for an MA,
       for example, an LSP for MPLS-TP.  This will be
       augmented by each protocol that uses this component.&quot;;
    choice connectivity-context {
      default &quot;context-null&quot;;
      case context-null {
        description
          &quot;This is a placeholder when no context is needed.&quot;;
        leaf context-null {
          type empty;
          description
            &quot;There is no context to be defined.&quot;;
<span class="grey"><a href="/doc/html/rfc8531">RFC 8531</a>         Connection-Oriented OAM YANG Data Model      April 2019</span>

        }
      }
      description
        &quot;Connectivity context.&quot;;
    }
  }

  grouping cos {
    description
      &quot;Grouping for Priority used in transmitted packets,
       for example, in the CoS field in MPLS-TP.&quot;;
    leaf cos-id {
      type uint8;
      description
        &quot;Class of Service (CoS) ID; this value is used to indicate
         Class of Service information .&quot;;
    }
  }

  grouping mip-grouping {
    uses mip-address;
    description
      &quot;Grouping for MIP
       configuration.&quot;;
  }

  container domains {
    description
      &quot;Contains configuration related data.  Within the
       container, there is a list of fault domains.  Each
       domain has a list of MAs.&quot;;
    list domain {
      key &quot;technology md-name-string&quot;;
      description
        &quot;Define a list of Domains within the
         ietf-connection-oriented-oam module.&quot;;
      uses maintenance-domain-id;
      uses md-name;
      leaf md-level {
        type md-level;
        description
          &quot;Define the MD level.&quot;;
      }
      container mas {
        description
          &quot;Contains configuration-related data.  Within the
           container, there is a list of MAs.  Each MA has a
           list of MEPs.&quot;;
<span class="grey"><a href="/doc/html/rfc8531">RFC 8531</a>         Connection-Oriented OAM YANG Data Model      April 2019</span>

        list ma {
          key &quot;ma-name-string&quot;;
          uses ma-identifier;
          uses ma-name;
          uses connectivity-context;
          uses cos {
            description
              &quot;Default class of service for this MA;
               it may be overridden for particular MEPs,
               sessions, or operations.&quot;;
          }
          leaf cc-enable {
            type boolean;
            description
              &quot;Indicate whether the CC is enabled.&quot;;
          }
          list mep {
            key &quot;mep-name&quot;;
            description
              &quot;Contain a list of MEPs.&quot;;
            uses mep;
            uses cos;
            leaf cc-enable {
              type boolean;
              description
                &quot;Indicate whether the CC is enabled.&quot;;
            }
            list session {
              key &quot;session-cookie&quot;;
              description
                &quot;Monitoring session to/from a particular remote MEP.
                 Depending on the protocol, this could represent
                 CC messages received from a single remote MEP (if the
                 protocol uses multicast CCs) or a target to which
                 unicast echo request CCs are sent and from which
                 responses are received (if the protocol uses a
                 unicast request/response mechanism).&quot;;
              leaf session-cookie {
                type uint32;
                description
                  &quot;Cookie to identify different sessions, when there
                   are multiple remote MEPs or multiple sessions to
                   the same remote MEP.&quot;;
              }
              container destination-mep {
                uses mep-id;
                description
                  &quot;Destination MEP.&quot;;
<span class="grey"><a href="/doc/html/rfc8531">RFC 8531</a>         Connection-Oriented OAM YANG Data Model      April 2019</span>

              }
              container destination-mep-address {
                uses mep-address;
                description
                  &quot;Destination MEP Address.&quot;;
              }
              uses cos;
            }
          }
          list mip {
            if-feature &quot;mip&quot;;
            key &quot;name&quot;;
            leaf name {
              type string;
              description
                &quot;Identifier of Maintenance Intermediate Point&quot;;
            }
            leaf interface {
              type if:interface-ref;
              description
                &quot;Interface.&quot;;
            }
            uses mip-grouping;
            description
              &quot;List for MIP.&quot;;
          }
          description
            &quot;Maintenance Association list.&quot;;
        }
      }
    }
  }

  notification defect-condition-notification {
    description
      &quot;When the defect condition is met, this notification is sent.&quot;;
    leaf technology {
      type identityref {
        base technology-types;
      }
      description
        &quot;The technology.&quot;;
    }
    leaf md-name-string {
      type leafref {
        path &quot;/domains/domain/md-name-string&quot;;
      }
      mandatory true;
<span class="grey"><a href="/doc/html/rfc8531">RFC 8531</a>         Connection-Oriented OAM YANG Data Model      April 2019</span>

      description
        &quot;Indicate which MD the defect belongs to.&quot;;
    }
    leaf ma-name-string {
      type leafref {
        path &quot;/domains/domain/mas/ma/ma-name-string&quot;;
      }
      mandatory true;
      description
        &quot;Indicate which MA the defect is associated with.&quot;;
    }
    leaf mep-name {
      type leafref {
        path &quot;/domains/domain/mas/ma/mep/mep-name&quot;;
      }
      description
        &quot;Indicate which MEP is seeing the defect.&quot;;
    }
    leaf defect-type {
      type identityref {
        base defect-types;
      }
      description
        &quot;The currently active defects on the specific MEP.&quot;;
    }
    container generating-mepid {
      uses mep-id;
      description
        &quot;Indicate who is generating the defect (if known). If
         unknown, set it to 0.&quot;;
    }
    uses defect-message {
      description
        &quot;Defect message to provide more details.&quot;;
    }
  }

  notification defect-cleared-notification {
    description
      &quot;When the defect is cleared, this notification is sent.&quot;;
    leaf technology {
      type identityref {
        base technology-types;
      }
      description
        &quot;The technology.&quot;;
    }
    leaf md-name-string {
<span class="grey"><a href="/doc/html/rfc8531">RFC 8531</a>         Connection-Oriented OAM YANG Data Model      April 2019</span>

      type leafref {
        path &quot;/domains/domain/md-name-string&quot;;
      }
      mandatory true;
      description
        &quot;Indicate which MD the defect belongs to&quot;;
    }
    leaf ma-name-string {
      type leafref {
        path &quot;/domains/domain/mas/ma/ma-name-string&quot;;
      }
      mandatory true;
      description
        &quot;Indicate which MA the defect is associated with.&quot;;
    }
    leaf mep-name {
      type leafref {
        path &quot;/domains/domain/mas/ma/mep/mep-name&quot;;
      }
      description
        &quot;Indicate which MEP is seeing the defect.&quot;;
    }
    leaf defect-type {
      type identityref {
        base defect-types;
      }
      description
        &quot;The currently active defects on the specific MEP.&quot;;
    }
    container generating-mepid {
      uses mep-id;
      description
        &quot;Indicate who is generating the defect (if known). If
         unknown, set it to 0.&quot;;
    }
    uses defect-message {
      description
        &quot;Defect message to provide more details.&quot;;
    }
  }

  rpc continuity-check {
    if-feature &quot;continuity-check&quot;;
    description
      &quot;Generates Continuity Check as per Table 4 of <a href="/doc/html/rfc7276">RFC 7276</a>.&quot;;
    input {
      leaf technology {
        type identityref {
<span class="grey"><a href="/doc/html/rfc8531">RFC 8531</a>         Connection-Oriented OAM YANG Data Model      April 2019</span>

          base technology-types;
        }
        description
          &quot;The technology.&quot;;
      }
      leaf md-name-string {
        type leafref {
          path &quot;/domains/domain/md-name-string&quot;;
        }
        mandatory true;
        description
          &quot;Indicate which MD the defect belongs to.&quot;;
      }
      leaf md-level {
        type leafref {
          path &quot;/domains/domain/md-level&quot;;
        }
        description
          &quot;The Maintenance Domain Level.&quot;;
      }
      leaf ma-name-string {
        type leafref {
          path &quot;/domains/domain/mas/ma/ma-name-string&quot;;
        }
        mandatory true;
        description
          &quot;Indicate which MA the defect is associated with.&quot;;
      }
      uses cos;
      uses time-to-live;
      leaf sub-type {
        type identityref {
          base command-sub-type;
        }
        description
          &quot;Defines different command types.&quot;;
      }
      leaf source-mep {
        type leafref {
          path &quot;/domains/domain/mas/ma/mep/mep-name&quot;;
        }
        description
          &quot;Source MEP.&quot;;
      }
      container destination-mep {
        uses mep-address;
        uses mep-id {
          description
<span class="grey"><a href="/doc/html/rfc8531">RFC 8531</a>         Connection-Oriented OAM YANG Data Model      April 2019</span>

            &quot;Only applicable if the destination is a MEP.&quot;;
        }
        description
          &quot;Destination MEP.&quot;;
      }
      leaf count {
        type uint32;
        default &quot;3&quot;;
        description
          &quot;Number of continuity-check messages to be sent.&quot;;
      }
      leaf cc-transmit-interval {
        type time-interval;
        description
          &quot;Time interval between echo requests.&quot;;
      }
      leaf packet-size {
        type uint32 {
          range &quot;64..10000&quot;;
        }
        description
          &quot;Size of continuity-check packets, in octets.&quot;;
      }
    }
    output {
      uses monitor-stats {
        description
          &quot;Stats of Continuity Check.&quot;;
      }
    }
  }

  rpc continuity-verification {
    if-feature &quot;connectivity-verification&quot;;
    description
      &quot;Generates Connectivity Verification as per Table 4 in <a href="/doc/html/rfc7276">RFC 7276</a>.&quot;;
    input {
      leaf md-name-string {
        type leafref {
          path &quot;/domains/domain/md-name-string&quot;;
        }
        mandatory true;
        description
          &quot;Indicate which MD the defect belongs to.&quot;;
      }
      leaf md-level {
        type leafref {
          path &quot;/domains/domain/md-level&quot;;
<span class="grey"><a href="/doc/html/rfc8531">RFC 8531</a>         Connection-Oriented OAM YANG Data Model      April 2019</span>

        }
        description
          &quot;The Maintenance Domain Level.&quot;;
      }
      leaf ma-name-string {
        type leafref {
          path &quot;/domains/domain/mas/ma/ma-name-string&quot;;
        }
        mandatory true;
        description
          &quot;Indicate which MA the defect is associated with.&quot;;
      }
      uses cos;
      uses time-to-live;
      leaf sub-type {
        type identityref {
          base command-sub-type;
        }
        description
          &quot;Defines different command types.&quot;;
      }
      leaf source-mep {
        type leafref {
          path &quot;/domains/domain/mas/ma/mep/mep-name&quot;;
        }
        description
          &quot;Source MEP.&quot;;
      }
      container destination-mep {
        uses mep-address;
        uses mep-id {
          description
            &quot;Only applicable if the destination is a MEP.&quot;;
        }
        description
          &quot;Destination MEP.&quot;;
      }
      leaf count {
        type uint32;
        default &quot;3&quot;;
        description
          &quot;Number of continuity-verification messages to be sent.&quot;;
      }
      leaf interval {
        type time-interval;
        description
          &quot;Time interval between echo requests.&quot;;
      }
<span class="grey"><a href="/doc/html/rfc8531">RFC 8531</a>         Connection-Oriented OAM YANG Data Model      April 2019</span>

      leaf packet-size {
        type uint32 {
          range &quot;64..10000&quot;;
        }
        description
          &quot;Size of continuity-verification packets, in octets.&quot;;
      }
    }
    output {
      uses monitor-stats {
        description
          &quot;Stats of Continuity Check.&quot;;
      }
    }
  }

  rpc traceroute {
    if-feature &quot;traceroute&quot;;
    description
      &quot;Generates Traceroute or Path Trace and returns response.
       References <a href="/doc/html/rfc7276">RFC 7276</a> for common Toolset name -- for
       MPLS-TP OAM, it&#x27;s Route Tracing, and for TRILL OAM, it&#x27;s
       Path Tracing tool.  Starts with TTL of one and increments
       by one at each hop until the destination is reached or TTL
       reaches max value.&quot;;
    input {
      leaf md-name-string {
        type leafref {
          path &quot;/domains/domain/md-name-string&quot;;
        }
        mandatory true;
        description
          &quot;Indicate which MD the defect belongs to.&quot;;
      }
      leaf md-level {
        type leafref {
          path &quot;/domains/domain/md-level&quot;;
        }
        description
          &quot;The Maintenance Domain Level.&quot;;
      }
      leaf ma-name-string {
        type leafref {
          path &quot;/domains/domain/mas/ma/ma-name-string&quot;;
        }
        mandatory true;
        description
          &quot;Indicate which MA the defect is associated with.&quot;;
<span class="grey"><a href="/doc/html/rfc8531">RFC 8531</a>         Connection-Oriented OAM YANG Data Model      April 2019</span>

      }
      uses cos;
      uses time-to-live;
      leaf command-sub-type {
        type identityref {
          base command-sub-type;
        }
        description
          &quot;Defines different command types.&quot;;
      }
      leaf source-mep {
        type leafref {
          path &quot;/domains/domain/mas/ma/mep/mep-name&quot;;
        }
        description
          &quot;Source MEP.&quot;;
      }
      container destination-mep {
        uses mep-address;
        uses mep-id {
          description
            &quot;Only applicable if the destination is a MEP.&quot;;
        }
        description
          &quot;Destination MEP.&quot;;
      }
      leaf count {
        type uint32;
        default &quot;1&quot;;
        description
          &quot;Number of traceroute probes to send.  In protocols where a
           separate message is sent at each TTL, this is the number
           of packets to be sent at each TTL.&quot;;
      }
      leaf interval {
        type time-interval;
        description
          &quot;Time interval between echo requests.&quot;;
      }
    }
    output {
      list response {
        key &quot;response-index&quot;;
        leaf response-index {
          type uint8;
          description
            &quot;Arbitrary index for the response.  In protocols that
             guarantee there is only a single response at each TTL,
<span class="grey"><a href="/doc/html/rfc8531">RFC 8531</a>         Connection-Oriented OAM YANG Data Model      April 2019</span>

             the TTL can be used as the response index.&quot;;
        }
        uses time-to-live;
        container destination-mep {
          description
            &quot;MEP from which the response has been received&quot;;
          uses mep-address;
          uses mep-id {
            description
              &quot;Only applicable if the destination is a MEP.&quot;;
          }
        }
        container mip {
          if-feature &quot;mip&quot;;
          leaf interface {
            type if:interface-ref;
            description
              &quot;MIP interface.&quot;;
          }
          uses mip-address;
          description
            &quot;MIP responding with traceroute&quot;;
        }
        uses monitor-stats {
          description
            &quot;Stats of traceroute.&quot;;
        }
        description
          &quot;List of responses.&quot;;
      }
    }
  }
}
