module iana-msd-types {
  yang-version 1.1;
  namespace "urn:ietf:params:xml:ns:yang:iana-msd-types";
  prefix iana-msd-types;

  organization
    "Internet Assigned Numbers Authority (IANA)";

  contact
    "Internet Assigned Numbers Authority

     ICANN
     12025 Waterfront Drive, Suite 300
     Los Angeles, CA 90094-2536
     United States of America

     Tel:    +1 310 301 5800
     <mailto:iana@iana.org>";

  description
    "The YANG module defines the identities for Maximum Segment
     Identifier (SID) Depth (MSD) Types.

     This YANG module is maintained by IANA and reflects the 'IGP
     MSD-Types' registry.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This initial version of this YANG module is part of RFC 9702
     (https://www.rfc-editor.org/info/rfc9702); see the RFC itself
     for full legal notices.

     The latest version of this YANG module is available at
     https://www.iana.org/assignments/yang-parameters.";

  revision 2025-01-10 {
    description
      "Initial Version";
    reference
      "RFC 9702: YANG Data Model for Maximum Segment Identifier (SID)
                 Depth Types and MPLS Maximum SID Depth";
  }

  identity msd-base {
    description
      "Base identity for Maximum SID Depth (MSD) Type. The MSD type
       definition is defined in the IANA 'IGP MSD-Types' registry.";
  }

  identity msd-base-mpls {
    base msd-base;
    description
      "Base identity of MSD types for the MPLS data plane.";
  }

  identity base-mpls-imposition-msd {
    base msd-base-mpls;
    description
      "Base MPLS Imposition MSD.";
    reference
      "RFC 8491: Signaling Maximum SID Depth (MSD) Using IS-IS
       RFC 8476: Signaling Maximum SID Depth (MSD) Using OSPF
       RFC 8664: Path Computation Element Communication Protocol
                 (PCEP) Extensions for Segment Routing
       RFC 8814: Signaling Maximum SID Depth (MSD) Using the Border
                 Gateway Protocol - Link State";
  }

  identity erld-msd {
    base msd-base-mpls;
    description
      "msd-erld is defined to advertise the Entropy Readable
       Label Depth (ERLD).";
    reference
      "RFC 8662: Entropy Label for Source Packet Routing in
                 Networking (SPRING) Tunnels
       RFC 9088: Signaling Entropy Label Capability and Entropy
                 Readable Label Depth Using IS-IS";
  }

  identity msd-base-srh {
    base msd-base;
    description
      "Base identity of MSD types for Segment Routing Header (SRH).";
  }

  identity srh-max-sl {
    base msd-base-srh;
    description
      "The Maximum Segments Left MSD type.";
    reference
      "RFC 9352: IS-IS Extensions to Support Segment Routing
                 over the IPv6 Data Plane";
  }

  identity srh-max-end-pop {
    base msd-base-srh;
    description
      "The Maximum End Pop MSD Type.";
    reference
      "RFC 9352: IS-IS Extensions to Support Segment Routing
                 over the IPv6 Data Plane";
  }

  identity srh-max-h-encaps {
    base msd-base-srh;
    description
      "The Maximum H.Encaps MSD Type.";
    reference
      "RFC 9352: IS-IS Extensions to Support Segment Routing
                 over the IPv6 Data Plane";
  }

  identity srh-max-end-d {
    base msd-base-srh;
    description
      "The Maximum End D MSD Type.";
    reference
      "RFC 9352: IS-IS Extensions to Support Segment Routing
                 over the IPv6 Data Plane";
  }
}
