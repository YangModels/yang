module ietf-key-chain {
  yang-version 1.1;
  namespace &quot;urn:ietf:params:xml:ns:yang:ietf-key-chain&quot;;
  prefix key-chain;

  import ietf-yang-types {
    prefix yang;
  }
  import ietf-netconf-acm {
    prefix nacm;
  }

  organization
    &quot;IETF RTGWG - Routing Area Working Group&quot;;
  contact
    &quot;WG Web:   &lt;<a href="https://datatracker.ietf.org/group/rtgwg">https://datatracker.ietf.org/group/rtgwg</a>&gt;
     WG List:  &lt;mailto:<a href="mailto:rtgwg@ietf.org">rtgwg@ietf.org</a>&gt;

     Editor: Acee Lindem
             &lt;mailto:<a href="mailto:acee@cisco.com">acee@cisco.com</a>&gt;
<span class="grey"><a href="/doc/html/rfc8177">RFC 8177</a>                     YANG Key Chain                    June 2017</span>

                Yingzhen Qu
                &lt;mailto:<a href="mailto:yingzhen.qu@huawei.com">yingzhen.qu@huawei.com</a>&gt;
                Derek Yeung
                &lt;mailto:<a href="mailto:derek@arrcus.com">derek@arrcus.com</a>&gt;
                Ing-Wher Chen
                &lt;mailto:<a href="mailto:Ing-Wher_Chen@jabail.com">Ing-Wher_Chen@jabail.com</a>&gt;
                Jeffrey Zhang
                &lt;mailto:<a href="mailto:zzhang@juniper.net">zzhang@juniper.net</a>&gt;&quot;;

     description
       &quot;This YANG module defines the generic configuration
        data for key chains.  It is intended that the module
        will be extended by vendors to define vendor-specific
        key chain configuration parameters.

        Copyright (c) 2017 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc8177">RFC 8177</a>;
        see the RFC itself for full legal notices.&quot;;

     reference &quot;<a href="/doc/html/rfc8177">RFC 8177</a>&quot;;

     revision 2017-06-15 {
       description
         &quot;Initial RFC Revision&quot;;
       reference &quot;<a href="/doc/html/rfc8177">RFC 8177</a>: YANG Data Model for Key Chains&quot;;
     }

     feature hex-key-string {
       description
         &quot;Support hexadecimal key string.&quot;;
     }

     feature accept-tolerance {
       description
         &quot;Support the tolerance or acceptance limit.&quot;;
     }

     feature independent-send-accept-lifetime {
       description
<span class="grey"><a href="/doc/html/rfc8177">RFC 8177</a>                     YANG Key Chain                    June 2017</span>

         &quot;Support for independent send and accept key lifetimes.&quot;;
     }

     feature crypto-hmac-sha-1-12 {
       description
         &quot;Support for TCP HMAC-SHA-1 12-byte digest hack.&quot;;
     }

     feature cleartext {
       description
         &quot;Support for cleartext algorithm.  Usage is
          NOT RECOMMENDED.&quot;;
     }

     feature aes-cmac-prf-128 {
       description
         &quot;Support for AES Cipher-based Message Authentication
          Code Pseudorandom Function.&quot;;
     }

     feature aes-key-wrap {
       description
         &quot;Support for Advanced Encryption Standard (AES) Key Wrap.&quot;;
     }

     feature replay-protection-only {
       description
         &quot;Provide replay protection without any authentication
          as required by protocols such as Bidirectional
          Forwarding Detection (BFD).&quot;;
     }
     identity crypto-algorithm {
       description
         &quot;Base identity of cryptographic algorithm options.&quot;;
     }

     identity hmac-sha-1-12 {
       base crypto-algorithm;
       if-feature &quot;crypto-hmac-sha-1-12&quot;;
       description
         &quot;The HMAC-SHA1-12 algorithm.&quot;;
     }

     identity aes-cmac-prf-128 {
       base crypto-algorithm;
       if-feature &quot;aes-cmac-prf-128&quot;;
       description
         &quot;The AES-CMAC-PRF-128 algorithm - required by
<span class="grey"><a href="/doc/html/rfc8177">RFC 8177</a>                     YANG Key Chain                    June 2017</span>

          <a href="/doc/html/rfc5926">RFC 5926</a> for TCP-AO key derivation functions.&quot;;
     }

     identity md5 {
       base crypto-algorithm;
       description
         &quot;The MD5 algorithm.&quot;;
     }

     identity sha-1 {
       base crypto-algorithm;
       description
         &quot;The SHA-1 algorithm.&quot;;
     }

     identity hmac-sha-1 {
       base crypto-algorithm;
       description
         &quot;HMAC-SHA-1 authentication algorithm.&quot;;
     }

     identity hmac-sha-256 {
       base crypto-algorithm;
       description
         &quot;HMAC-SHA-256 authentication algorithm.&quot;;
     }

     identity hmac-sha-384 {
       base crypto-algorithm;
       description
         &quot;HMAC-SHA-384 authentication algorithm.&quot;;
     }

     identity hmac-sha-512 {
       base crypto-algorithm;
       description
         &quot;HMAC-SHA-512 authentication algorithm.&quot;;
     }

     identity cleartext {
       base crypto-algorithm;
       if-feature &quot;cleartext&quot;;
       description
         &quot;cleartext.&quot;;
     }

     identity replay-protection-only {
       base crypto-algorithm;
<span class="grey"><a href="/doc/html/rfc8177">RFC 8177</a>                     YANG Key Chain                    June 2017</span>

       if-feature &quot;replay-protection-only&quot;;
       description
         &quot;Provide replay protection without any authentication as
          required by protocols such as Bidirectional Forwarding
          Detection (BFD).&quot;;
     }

     typedef key-chain-ref {
       type leafref {
         path
         &quot;/key-chain:key-chains/key-chain:key-chain/key-chain:name&quot;;
       }
       description
         &quot;This type is used by data models that need to reference
          configured key chains.&quot;;
     }

     grouping lifetime {
       description
         &quot;Key lifetime specification.&quot;;
       choice lifetime {
         default &quot;always&quot;;
         description
           &quot;Options for specifying key accept or send lifetimes&quot;;
         case always {
           leaf always {
             type empty;
             description
               &quot;Indicates key lifetime is always valid.&quot;;
           }
         }
         case start-end-time {
           leaf start-date-time {
             type yang:date-and-time;
             description
               &quot;Start time.&quot;;
           }
           choice end-time {
             default &quot;infinite&quot;;
             description
               &quot;End-time setting.&quot;;
             case infinite {
               leaf no-end-time {
                 type empty;
                 description
                   &quot;Indicates key lifetime end-time is infinite.&quot;;
               }
             }
<span class="grey"><a href="/doc/html/rfc8177">RFC 8177</a>                     YANG Key Chain                    June 2017</span>

             case duration {
               leaf duration {
                 type uint32 {
                   range &quot;1..2147483646&quot;;
                 }
                 units &quot;seconds&quot;;
                 description
                   &quot;Key lifetime duration, in seconds&quot;;
               }
             }
             case end-date-time {
               leaf end-date-time {
                 type yang:date-and-time;
                 description
                   &quot;End time.&quot;;
               }
             }
           }
         }
       }
     }

     container key-chains {
       description
         &quot;All configured key-chains on the device.&quot;;
       list key-chain {
         key &quot;name&quot;;
         description
           &quot;List of key-chains.&quot;;
         leaf name {
           type string;
           description
             &quot;Name of the key-chain.&quot;;
         }
         leaf description {
           type string;
           description
             &quot;A description of the key-chain&quot;;
         }
         container accept-tolerance {
           if-feature &quot;accept-tolerance&quot;;
           description
             &quot;Tolerance for key lifetime acceptance (seconds).&quot;;
           leaf duration {
             type uint32;
             units &quot;seconds&quot;;
             default &quot;0&quot;;
             description
<span class="grey"><a href="/doc/html/rfc8177">RFC 8177</a>                     YANG Key Chain                    June 2017</span>

               &quot;Tolerance range, in seconds.&quot;;
           }
         }
         leaf last-modified-timestamp {
           type yang:date-and-time;
           config false;
           description
             &quot;Timestamp of the most recent update to the key-chain&quot;;
         }
         list key {
           key &quot;key-id&quot;;
           description
             &quot;Single key in key chain.&quot;;
           leaf key-id {
             type uint64;
             description
               &quot;Numeric value uniquely identifying the key&quot;;
           }
           container lifetime {
             description
               &quot;Specify a key&#x27;s lifetime.&quot;;
             choice lifetime {
               description
                 &quot;Options for specification of send and accept
                  lifetimes.&quot;;
               case send-and-accept-lifetime {
                 description
                   &quot;Send and accept key have the same lifetime.&quot;;
                 container send-accept-lifetime {
                   description
                     &quot;Single lifetime specification for both
                      send and accept lifetimes.&quot;;
                   uses lifetime;
                 }
               }
               case independent-send-accept-lifetime {
                 if-feature &quot;independent-send-accept-lifetime&quot;;
                 description
                   &quot;Independent send and accept key lifetimes.&quot;;
                 container send-lifetime {
                   description
                     &quot;Separate lifetime specification for send
                      lifetime.&quot;;
                   uses lifetime;
                 }
                 container accept-lifetime {
                   description
                     &quot;Separate lifetime specification for accept
<span class="grey"><a href="/doc/html/rfc8177">RFC 8177</a>                     YANG Key Chain                    June 2017</span>

                      lifetime.&quot;;
                   uses lifetime;
                 }
               }
             }
           }
           leaf crypto-algorithm {
             type identityref {
               base crypto-algorithm;
             }
             mandatory true;
             description
               &quot;Cryptographic algorithm associated with key.&quot;;
           }
           container key-string {
             description
               &quot;The key string.&quot;;
             nacm:default-deny-all;
             choice key-string-style {
               description
                 &quot;Key string styles&quot;;
                case keystring {
                  leaf keystring {
                   type string;
                   description
                     &quot;Key string in ASCII format.&quot;;
                 }
               }
               case hexadecimal {
                 if-feature &quot;hex-key-string&quot;;
                 leaf hexadecimal-string {
                   type yang:hex-string;
                   description
                     &quot;Key in hexadecimal string format.  When compared
                      to ASCII, specification in hexadecimal affords
                      greater key entropy with the same number of
                      internal key-string octets.  Additionally, it
                      discourages usage of well-known words or
                      numbers.&quot;;
                 }
               }
             }
           }
           leaf send-lifetime-active {
             type boolean;
             config false;
             description
               &quot;Indicates if the send lifetime of the
<span class="grey"><a href="/doc/html/rfc8177">RFC 8177</a>                     YANG Key Chain                    June 2017</span>

                key-chain key is currently active.&quot;;
              }
           leaf accept-lifetime-active {
             type boolean;
             config false;
             description
               &quot;Indicates if the accept lifetime of the
                key-chain key is currently active.&quot;;
           }
         }
       }
       container aes-key-wrap {
         if-feature &quot;aes-key-wrap&quot;;
         description
           &quot;AES Key Wrap encryption for key-chain key-strings.  The
            encrypted key-strings are encoded as hexadecimal key
            strings using the hex-key-string leaf.&quot;;
         leaf enable {
           type boolean;
           default &quot;false&quot;;
           description
             &quot;Enable AES Key Wrap encryption.&quot;;
         }
       }
     }
   }
