module ietf-lmap-control {

  yang-version 1.1;
  namespace &quot;urn:ietf:params:xml:ns:yang:ietf-lmap-control&quot;;
  prefix &quot;lmapc&quot;;

  import ietf-yang-types {
    prefix yang;
  }
  import ietf-netconf-acm {
<span class="grey"><a href="/doc/html/rfc8194">RFC 8194</a>                YANG Data Model for LMAP             August 2017</span>

       prefix nacm;
     }
     import ietf-lmap-common {
       prefix lmap;
     }

     organization
       &quot;IETF Large-Scale Measurement of Broadband Performance
        Working Group&quot;;

     contact
       &quot;WG Web:   &lt;<a href="https://datatracker.ietf.org/wg/lmap">https://datatracker.ietf.org/wg/lmap</a>&gt;
        WG List:  &lt;mailto:<a href="mailto:lmap@ietf.org">lmap@ietf.org</a>&gt;

        Editor:   Juergen Schoenwaelder
                  &lt;<a href="mailto:j.schoenwaelder@jacobs-university.de">j.schoenwaelder@jacobs-university.de</a>&gt;

        Editor:   Vaibhav Bajpai
                  &lt;<a href="mailto:bajpaiv@in.tum.de">bajpaiv@in.tum.de</a>&gt;&quot;;

     description
       &quot;This module defines a data model for controlling Measurement
        Agents that are part of a Large-Scale Measurement Platform
        (LMAP).  This data model is expected to be implemented by
        Measurement Agents.&quot;;

     revision &quot;2017-08-08&quot; {
       description
         &quot;Initial version&quot;;
       reference
         &quot;<a href="/doc/html/rfc8194">RFC 8194</a>: A YANG Data Model for LMAP Measurement Agents&quot;;
     }

     /*
      * Typedefs
      */

     typedef event-ref {
       type leafref {
         path &quot;/lmap/events/event/name&quot;;
       }
       description
         &quot;This type is used by data models that need to reference
          a configured event source.&quot;;
     }

     typedef task-ref {
       type leafref {
<span class="grey"><a href="/doc/html/rfc8194">RFC 8194</a>                YANG Data Model for LMAP             August 2017</span>

         path &quot;/lmap/tasks/task/name&quot;;
       }
       description
         &quot;This type is used by data models that need to reference
          a configured Task.&quot;;
     }

     typedef schedule-ref {
       type leafref {
         path &quot;/lmap/schedules/schedule/name&quot;;
       }
       description
         &quot;This type is used by data models that need to reference
          a configured Schedule.&quot;;
     }

     /*
      * Groupings
      */

     grouping start-end-grouping {
       description
         &quot;A grouping that provides start and end times for
          Event objects.&quot;;
       leaf start {
         type yang:date-and-time;
         description
           &quot;The date and time when the Event object
            starts to create triggers.&quot;;
       }
       leaf end {
         type yang:date-and-time;
         description
           &quot;The date and time when the Event object
            stops to create triggers.

            It is generally a good idea to always configure
            an end time and to refresh the end time as needed
            to ensure that agents that lose connectivity to
            their Controller do not continue executing Schedules
            forever.&quot;;
       }
     }

     /*
      * Capability, configuration, and state data nodes
      */

<span class="grey"><a href="/doc/html/rfc8194">RFC 8194</a>                YANG Data Model for LMAP             August 2017</span>

     container lmap {
       description
         &quot;Configuration and control of a Measurement Agent.&quot;;

       container capabilities {
         config false;
         description
           &quot;Agent capabilities including a list of supported Tasks.&quot;;

         leaf version {
           type string;
           config false;
           mandatory true;
           description
             &quot;A short description of the software implementing the
              Measurement Agent.  This should include the version
              number of the Measurement Agent software.&quot;;
         }

         leaf-list tag {
           type lmap:tag;
           config false;
           description
             &quot;An optional unordered set of tags that provide
              additional information about the capabilities of
              the Measurement Agent.&quot;;
         }

         container tasks {
           description
             &quot;A list of Tasks that the Measurement Agent supports.&quot;;

           list task {
             key name;
             description
               &quot;The list of Tasks supported by the Measurement Agent.&quot;;

             leaf name {
               type lmap:identifier;
               description
                 &quot;The unique name of a Task capability.&quot;;
             }

             uses lmap:registry-grouping;

             leaf version {
               type string;

<span class="grey"><a href="/doc/html/rfc8194">RFC 8194</a>                YANG Data Model for LMAP             August 2017</span>

               description
                 &quot;A short description of the software implementing
                  the Task.  This should include the version
                  number of the Measurement Task software.&quot;;
             }

             leaf program {
               type string;
               description
                 &quot;The (local) program to invoke in order to execute
                  the Task.&quot;;
             }
           }
         }
       }

       /*
        * Agent Configuration
        */

       container agent {
         description
           &quot;Configuration of parameters affecting the whole
            Measurement Agent.&quot;;

         leaf agent-id {
           type yang:uuid;
           description
             &quot;The agent-id identifies a Measurement Agent with
              a very low probability of collision.  In certain
              deployments, the agent-id may be considered
              sensitive, and hence this object is optional.&quot;;
         }

         leaf group-id {
           type string;
           description
             &quot;The group-id identifies a group of Measurement
              Agents.  In certain deployments, the group-id
              may be considered less sensitive than the
              agent-id.&quot;;
         }

         leaf measurement-point {
           type string;
           description
             &quot;The measurement point indicating where the
               Measurement Agent is located on a path.&quot;;
<span class="grey"><a href="/doc/html/rfc8194">RFC 8194</a>                YANG Data Model for LMAP             August 2017</span>

           reference
             &quot;<a href="/doc/html/rfc7398">RFC 7398</a>: A Reference Path and Measurement Points
                        for Large-Scale Measurement of Broadband
                        Performance&quot;;
         }

         leaf report-agent-id {
           type boolean;
           must &#x27;. != &quot;true&quot; or ../agent-id&#x27; {
             description
               &quot;An agent-id must exist for this to be set
                to true.&quot;;
           }
           default false;
           description
             &quot;The &#x27;report-agent-id&#x27; controls whether the
              &#x27;agent-id&#x27; is reported to Collectors.&quot;;
         }

         leaf report-group-id {
           type boolean;
           must &#x27;. != &quot;true&quot; or ../group-id&#x27; {
             description
               &quot;A group-id must exist for this to be set
                to true.&quot;;
           }
           default false;
           description
             &quot;The &#x27;report-group-id&#x27; controls whether the
              &#x27;group-id&#x27; is reported to Collectors.&quot;;
         }

         leaf report-measurement-point {
           type boolean;
           must &#x27;. != &quot;true&quot; or ../measurement-point&#x27; {
             description
               &quot;A measurement-point must exist for this to be
                set to true.&quot;;
           }
           default false;
           description
             &quot;The &#x27;report-measurement-point&#x27; controls whether
              the &#x27;measurement-point&#x27; is reported to Collectors.&quot;;
         }

         leaf controller-timeout {
           type uint32;
           units &quot;seconds&quot;;
<span class="grey"><a href="/doc/html/rfc8194">RFC 8194</a>                YANG Data Model for LMAP             August 2017</span>

           description
             &quot;A timer is started after each successful contact
              with a Controller.  When the timer reaches the
              controller-timeout, an event (controller-lost) is
              raised indicating that connectivity to the Controller
              has been lost.&quot;;
         }

         leaf last-started {
           type yang:date-and-time;
           config false;
           mandatory true;
           description
             &quot;The date and time the Measurement Agent last started.&quot;;
         }
       }

       /*
        * Task Configuration
        */

       container tasks {
         description
           &quot;Configuration of LMAP Tasks.&quot;;

         list task {
           key name;
           description
             &quot;The list of Tasks configured on the Measurement
              Agent.  Note that a configured Task MUST resolve to a
              Task listed in the capabilities.  Attempts to execute
              a configured Task that is not listed in the capabilities
              result in a runtime execution error.&quot;;

           leaf name {
             type lmap:identifier;
             description
               &quot;The unique name of a Task.&quot;;
           }

           uses lmap:registry-grouping;

           leaf program {
             type string;
             nacm:default-deny-write;

<span class="grey"><a href="/doc/html/rfc8194">RFC 8194</a>                YANG Data Model for LMAP             August 2017</span>

             description
               &quot;The (local) program to invoke in order to execute
                the Task.  If this leaf is not set, then the system
                will try to identify a suitable program based on
                the registry information present.&quot;;
           }

           uses lmap:options-grouping {
             description
               &quot;The list of Task-specific options.&quot;;
           }

           leaf-list tag {
             type lmap:identifier;
             description
               &quot;A set of Task-specific tags that are reported
                together with the measurement results to a Collector.
                A tag can be used, for example, to carry the
                Measurement Cycle ID.&quot;;
           }
         }
       }

       /*
        * Schedule Instructions
        */

       container schedules {
         description
           &quot;Configuration of LMAP Schedules.  Schedules control
            which Tasks are executed by the LMAP implementation.&quot;;

         list schedule {
           key name;
           description
             &quot;Configuration of a particular Schedule.&quot;;

           leaf name {
             type lmap:identifier;
             description
               &quot;The locally unique, administratively assigned name
                for this Schedule.&quot;;
           }

           leaf start {
             type event-ref;
             mandatory true;

<span class="grey"><a href="/doc/html/rfc8194">RFC 8194</a>                YANG Data Model for LMAP             August 2017</span>

             description
               &quot;The event source controlling the start of the
                scheduled Actions.&quot;;
           }

           choice stop {
             description
               &quot;This choice contains optional leafs that control the
                graceful forced termination of scheduled Actions.
                When the end has been reached, the scheduled Actions
                should be forced to terminate the measurements.
                This may involve being active some additional time in
                order to properly finish the Action&#x27;s activity (e.g.,
                waiting for any messages that are still outstanding).&quot;;

             leaf end {
               type event-ref;
               description
                 &quot;The event source controlling the graceful
                  forced termination of the scheduled Actions.&quot;;
             }

             leaf duration {
               type uint32;
               units &quot;seconds&quot;;
               description
                 &quot;The duration controlling the graceful forced
                  termination of the scheduled Actions.&quot;;
             }
           }

           leaf execution-mode {
             type enumeration {
               enum sequential {
                 value 1;
                 description
                   &quot;The Actions of the Schedule are executed
                    sequentially.&quot;;
               }
               enum parallel {
                 value 2;
                 description
                   &quot;The Actions of the Schedule are executed
                    concurrently.&quot;;
               }
               enum pipelined {
                 value 3;

<span class="grey"><a href="/doc/html/rfc8194">RFC 8194</a>                YANG Data Model for LMAP             August 2017</span>

                 description
                   &quot;The Actions of the Schedule are executed in a
                    pipelined mode.  Output created by an Action is
                    passed as input to the subsequent Action.&quot;;
               }
             }
             default pipelined;
             description
               &quot;The execution mode of this Schedule determines in
                which order the Actions of the Schedule are executed.&quot;;
           }

           leaf-list tag {
             type lmap:tag;
             description
               &quot;A set of Schedule-specific tags that are reported
                together with the measurement results to a Collector.&quot;;
           }

           leaf-list suppression-tag {
             type lmap:tag;
             description
               &quot;A set of Suppression tags that are used to select
                Schedules to be suppressed.&quot;;
           }

           leaf state {
             type enumeration {
               enum enabled {
                 value 1;
                 description
                   &quot;The value &#x27;enabled&#x27; indicates that the
                    Schedule is currently enabled.&quot;;
               }
               enum disabled {
                 value 2;
                 description
                   &quot;The value &#x27;disabled&#x27; indicates that the
                    Schedule is currently disabled.&quot;;
               }
               enum running {
                 value 3;
                 description
                   &quot;The value &#x27;running&#x27; indicates that the
                    Schedule is currently running.&quot;;
               }
               enum suppressed {
                 value 4;
<span class="grey"><a href="/doc/html/rfc8194">RFC 8194</a>                YANG Data Model for LMAP             August 2017</span>

                 description
                   &quot;The value &#x27;suppressed&#x27; indicates that the
                    Schedule is currently suppressed.&quot;;
               }
             }
             config false;
             mandatory true;
             description
               &quot;The current state of the Schedule.&quot;;
           }

           leaf storage {
             type yang:gauge64;
             units &quot;bytes&quot;;
             config false;
             mandatory true;
             description
               &quot;The amount of secondary storage (e.g., allocated in a
                file system) holding temporary data allocated to the
                Schedule in bytes.  This object reports the amount of
                allocated physical storage and not the storage used
                by logical data records.&quot;;
           }

           leaf invocations {
             type yang:counter32;
             config false;
             mandatory true;
             description
               &quot;Number of invocations of this Schedule.  This counter
                does not include suppressed invocations or invocations
                that were prevented due to an overlap with a previous
                invocation of this Schedule.&quot;;
           }

           leaf suppressions {
             type yang:counter32;
             config false;
             mandatory true;
             description
               &quot;Number of suppressed executions of this Schedule.&quot;;
           }

           leaf overlaps {
             type yang:counter32;
             config false;
             mandatory true;

<span class="grey"><a href="/doc/html/rfc8194">RFC 8194</a>                YANG Data Model for LMAP             August 2017</span>

             description
               &quot;Number of executions prevented due to overlaps with
                a previous invocation of this Schedule.&quot;;
           }

           leaf failures {
             type yang:counter32;
             config false;
             mandatory true;
             description
               &quot;Number of failed executions of this Schedule.  A
                failed execution is an execution where at least
                one Action failed.&quot;;
           }

           leaf last-invocation {
             type yang:date-and-time;
             config false;
             description
               &quot;The date and time of the last invocation of
                this Schedule.&quot;;
           }

           list action {
             key name;
             description
               &quot;An Action describes a Task that is invoked by the
                Schedule.  Multiple Actions are invoked according to
                the execution-mode of the Schedule.&quot;;

             leaf name {
               type lmap:identifier;
               description
                 &quot;The unique identifier for this Action.&quot;;
             }

             leaf task {
               type task-ref;
               mandatory true;
               description
                 &quot;The Task invoked by this Action.&quot;;
             }

             container parameters {
               description
                 &quot;This container is a placeholder for runtime
                  parameters defined in Task-specific data models
                  augmenting the base LMAP control data model.&quot;;
<span class="grey"><a href="/doc/html/rfc8194">RFC 8194</a>                YANG Data Model for LMAP             August 2017</span>

               choice extension {
                 description
                   &quot;This choice is provided to augment in different
                    sets of parameters.&quot;;
               }
             }

             uses lmap:options-grouping {
               description
                 &quot;The list of Action-specific options that are
                  appended to the list of Task-specific options.&quot;;
             }

             leaf-list destination {
               type schedule-ref;
               description
                 &quot;A set of Schedules receiving the output produced
                  by this Action.  The output is stored temporarily
                  since the Destination Schedules will in general
                  not be running when output is passed to them.  The
                  behavior of an Action passing data to its own
                  Schedule is implementation specific.

                  Data passed to a sequential or pipelined Schedule
                  is received by the Schedule&#x27;s first Action.  Data
                  passed to a parallel Schedule is received by all
                  Actions of the Schedule.&quot;;
             }

             leaf-list tag {
               type lmap:tag;
               description
                 &quot;A set of Action-specific tags that are reported
                  together with the measurement results to a
                  Collector.&quot;;
             }

             leaf-list suppression-tag {
               type lmap:tag;
               description
                 &quot;A set of Suppression tags that are used to select
                  Actions to be suppressed.&quot;;
             }

             leaf state {
               type enumeration {
                 enum enabled {
                   value 1;
<span class="grey"><a href="/doc/html/rfc8194">RFC 8194</a>                YANG Data Model for LMAP             August 2017</span>

                   description
                     &quot;The value &#x27;enabled&#x27; indicates that the
                      Action is currently enabled.&quot;;
                 }
                 enum disabled {
                   value 2;
                   description
                     &quot;The value &#x27;disabled&#x27; indicates that the
                      Action is currently disabled.&quot;;
                 }
                 enum running {
                   value 3;
                   description
                     &quot;The value &#x27;running&#x27; indicates that the
                      Action is currently running.&quot;;
                 }
                 enum suppressed {
                   value 4;
                   description
                     &quot;The value &#x27;suppressed&#x27; indicates that the
                      Action is currently suppressed.&quot;;
                 }
               }
               config false;
               mandatory true;
               description
                 &quot;The current state of the Action.&quot;;
             }

             leaf storage {
               type yang:gauge64;
               units &quot;bytes&quot;;
               config false;
               mandatory true;
               description
                 &quot;The amount of secondary storage (e.g., allocated in a
                  file system) holding temporary data allocated to the
                  Schedule in bytes.  This object reports the amount of
                  allocated physical storage and not the storage used
                  by logical data records.&quot;;
             }

             leaf invocations {
               type yang:counter32;
               config false;
               mandatory true;

<span class="grey"><a href="/doc/html/rfc8194">RFC 8194</a>                YANG Data Model for LMAP             August 2017</span>

               description
                 &quot;Number of invocations of this Action.  This counter
                  does not include suppressed invocations or invocations
                  that were prevented due to an overlap with a previous
                  invocation of this Action.&quot;;
             }

             leaf suppressions {
               type yang:counter32;
               config false;
               mandatory true;
               description
                 &quot;Number of suppressed executions of this Action.&quot;;
             }

             leaf overlaps {
               type yang:counter32;
               config false;
               mandatory true;
               description
                 &quot;Number of executions prevented due to overlaps with
                  a previous invocation of this Action.&quot;;
             }

             leaf failures {
               type yang:counter32;
               config false;
               mandatory true;
               description
                 &quot;Number of failed executions of this Action.&quot;;
             }

             leaf last-invocation {
               type yang:date-and-time;
               config false;
               mandatory true;
               description
                 &quot;The date and time of the last invocation of
                  this Action.&quot;;
             }

             leaf last-completion {
               type yang:date-and-time;
               config false;
               mandatory true;
               description
                 &quot;The date and time of the last completion of
                  this Action.&quot;;
<span class="grey"><a href="/doc/html/rfc8194">RFC 8194</a>                YANG Data Model for LMAP             August 2017</span>

             }

             leaf last-status {
               type lmap:status-code;
               config false;
               mandatory true;
               description
                 &quot;The status code returned by the last execution of
                  this Action.&quot;;
             }

             leaf last-message {
               type string;
               config false;
               mandatory true;
               description
                 &quot;The status message produced by the last execution
                  of this Action.&quot;;
             }

             leaf last-failed-completion {
               type yang:date-and-time;
               config false;
               mandatory true;
               description
                 &quot;The date and time of the last failed completion
                  of this Action.&quot;;
             }

             leaf last-failed-status {
               type lmap:status-code;
               config false;
               mandatory true;
               description
                 &quot;The status code returned by the last failed
                  execution of this Action.&quot;;
             }

             leaf last-failed-message {
               type string;
               config false;
               mandatory true;
               description
                 &quot;The status message produced by the last failed
                  execution of this Action.&quot;;
             }
           }
         }
<span class="grey"><a href="/doc/html/rfc8194">RFC 8194</a>                YANG Data Model for LMAP             August 2017</span>

       }

       /*
        * Suppression Instructions
        */

       container suppressions {
         description
           &quot;Suppression information to prevent Schedules or
            certain Actions from starting.&quot;;

         list suppression {
           key name;
           description
             &quot;Configuration of a particular Suppression.&quot;;

           leaf name {
             type lmap:identifier;
             description
               &quot;The locally unique, administratively assigned name
                for this Suppression.&quot;;
           }

           leaf start {
             type event-ref;
             description
               &quot;The event source controlling the start of the
                Suppression period.&quot;;
           }

           leaf end {
             type event-ref;
             description
               &quot;The event source controlling the end of the
                Suppression period.  If not present, Suppression
                continues indefinitely.&quot;;
           }

           leaf-list match {
             type lmap:glob-pattern;
             description
               &quot;A set of Suppression match patterns.  The Suppression
                will apply to all Schedules (and their Actions) that
                have a matching value in their suppression-tags
                and to all Actions that have a matching value in
                their suppression-tags.&quot;;
           }

<span class="grey"><a href="/doc/html/rfc8194">RFC 8194</a>                YANG Data Model for LMAP             August 2017</span>

           leaf stop-running {
             type boolean;
             default false;
             description
               &quot;If &#x27;stop-running&#x27; is true, running Schedules and
                Actions matching the Suppression will be terminated
                when Suppression is activated.  If &#x27;stop-running&#x27; is
                false, running Schedules and Actions will not be
                affected if Suppression is activated.&quot;;
           }

           leaf state {
             type enumeration {
               enum enabled {
                 value 1;
                 description
                   &quot;The value &#x27;enabled&#x27; indicates that the
                    Suppression is currently enabled.&quot;;
               }
               enum disabled {
                 value 2;
                 description
                   &quot;The value &#x27;disabled&#x27; indicates that the
                    Suppression is currently disabled.&quot;;
               }
               enum active {
                 value 3;
                 description
                   &quot;The value &#x27;active&#x27; indicates that the
                    Suppression is currently active.&quot;;
               }
             }
             config false;
             mandatory true;
             description
               &quot;The current state of the Suppression.&quot;;
           }
         }
       }

       /*
        * Event Instructions
        */

       container events {
         description
           &quot;Configuration of LMAP events.

<span class="grey"><a href="/doc/html/rfc8194">RFC 8194</a>                YANG Data Model for LMAP             August 2017</span>

            Implementations may be forced to delay acting
            upon the occurrence of events in the face of local
            constraints.  An Action triggered by an event
            therefore should not rely on the accuracy
            provided by the scheduler implementation.&quot;;

         list event {
           key name;
           description
             &quot;The list of event sources configured on the
              Measurement Agent.&quot;;

           leaf name {
             type lmap:identifier;
             description
               &quot;The unique name of an event source.&quot;;
           }

           leaf random-spread {
             type uint32;
             units seconds;
             description
               &quot;This optional leaf adds a random spread to the
                computation of the event&#x27;s trigger time.  The
                random spread is a uniformly distributed random
                number taken from the interval [0:random-spread].&quot;;
           }

           leaf cycle-interval {
             type uint32;
             units seconds;
             description
               &quot;The optional cycle-interval defines the duration
                of the time interval in seconds that is used to
                calculate cycle numbers.  No cycle number is
                calculated if the optional cycle-interval does
                not exist.&quot;;
           }

           choice event-type {
             description
               &quot;Different types of events are handled by
                different branches of this choice.  Note that
                this choice can be extended via augmentations.&quot;;

             case periodic {
               container periodic {

<span class="grey"><a href="/doc/html/rfc8194">RFC 8194</a>                YANG Data Model for LMAP             August 2017</span>

                 description
                   &quot;A periodic timing object triggers periodically
                    according to a regular interval.&quot;;

                 leaf interval {
                   type uint32 {
                     range &quot;1..max&quot;;
                   }
                   units &quot;seconds&quot;;
                   mandatory true;
                   description
                     &quot;The number of seconds between two triggers
                      generated by this periodic timing object.&quot;;
                 }
                 uses start-end-grouping;
               }
             }

             case calendar {
               container calendar {
                 description
                   &quot;A calendar timing object triggers based on the
                    current calendar date and time.&quot;;

                 leaf-list month {
                   type lmap:month-or-all;
                   min-elements 1;
                   description
                     &quot;A set of months at which this calendar timing
                      will trigger.  The wildcard means all months.&quot;;
                 }

                 leaf-list day-of-month {
                   type lmap:day-of-months-or-all;
                   min-elements 1;
                   description
                     &quot;A set of days of the month at which this
                      calendar timing will trigger.  The wildcard means
                      all days of a month.&quot;;
                 }

                 leaf-list day-of-week {
                   type lmap:weekday-or-all;
                   min-elements 1;
                   description
                     &quot;A set of weekdays at which this calendar timing
                      will trigger.  The wildcard means all weekdays.&quot;;
                 }
<span class="grey"><a href="/doc/html/rfc8194">RFC 8194</a>                YANG Data Model for LMAP             August 2017</span>

                 leaf-list hour {
                   type lmap:hour-or-all;
                   min-elements 1;
                   description
                     &quot;A set of hours at which this calendar timing will
                      trigger.  The wildcard means all hours of a day.&quot;;
                 }

                 leaf-list minute {
                   type lmap:minute-or-all;
                   min-elements 1;
                   description
                     &quot;A set of minutes at which this calendar timing
                      will trigger.  The wildcard means all minutes of
                      an hour.&quot;;
                 }

                 leaf-list second {
                   type lmap:second-or-all;
                   min-elements 1;
                   description
                     &quot;A set of seconds at which this calendar timing
                      will trigger.  The wildcard means all seconds of
                      a minute.&quot;;
                 }

                 leaf timezone-offset {
                   type lmap:timezone-offset;
                   description
                     &quot;The time zone in which this calendar timing
                      object will be evaluated.  If not present,
                      the system&#x27;s local time zone will be used.&quot;;
                 }
                 uses start-end-grouping;
               }
             }

             case one-off {
               container one-off {
                 description
                   &quot;A one-off timing object triggers exactly once.&quot;;

                 leaf time {
                   type yang:date-and-time;
                   mandatory true;
                   description
                     &quot;This one-off timing object triggers once at
                      the configured date and time.&quot;;
<span class="grey"><a href="/doc/html/rfc8194">RFC 8194</a>                YANG Data Model for LMAP             August 2017</span>

                 }
               }
             }

             case immediate {
               leaf immediate {
                 type empty;
                 mandatory true;
                 description
                   &quot;This immediate Event object triggers immediately
                    when it is configured.&quot;;
               }
             }

             case startup {
               leaf startup {
                 type empty;
                 mandatory true;
                 description
                   &quot;This startup Event object triggers whenever the
                    Measurement Agent (re)starts.&quot;;
               }
             }

             case controller-lost {
               leaf controller-lost {
                 type empty;
                 mandatory true;
                 description
                   &quot;The controller-lost Event object triggers when
                    the connectivity to the Controller has been lost
                    for at least &#x27;controller-timeout&#x27; seconds.&quot;;
               }
             }

             case controller-connected {
               leaf controller-connected {
                 type empty;
                 mandatory true;
                 description
                   &quot;The controller-connected Event object triggers
                    when the connectivity to the Controller has been
                    restored after it was lost for at least
                    &#x27;controller-timeout&#x27; seconds.&quot;;
               }
             }
           }

<span class="grey"><a href="/doc/html/rfc8194">RFC 8194</a>                YANG Data Model for LMAP             August 2017</span>

         }
       }
     }
   }
