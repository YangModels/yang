module example-iftunnel-extension {
  yang-version 1.1;

  namespace "urn:ietf:params:xml:ns:yang:example-iftunnel-extension";
  prefix example;

  import ietf-inet-types {
    prefix inet;
    reference
      "RFC 6991: Common YANG Data Types, Section 4";
  }

  import ietf-interfaces {
    prefix if;
    reference
      "RFC 8343: A YANG Data Model for Interface Management";
  }

  import iana-tunnel-type  {
    prefix iana-tunnel-type;
    reference
      "RFC 8675:  A Tunnel Extension to the Interface Management
                  YANG Module";
  }

  organization "IETF Softwire Working Group";

  contact

    "WG Web:   <https://datatracker.ietf.org/wg/softwire/>
     WG List:  <mailto:softwire@ietf.org>

     Author:  Mohamed Boucadair 
              <mailto:mohamed.boucadair@orange.com>";

   description
      "This is an example YANG module to extend the Interface YANG 
       module with tunnel-specific parameters.

      Copyright (c) 2019 IETF Trust and the persons identified as
      authors of the code.  All rights reserved.

      Redistribution and use in source and binary forms, with or
      without modification, is permitted pursuant to, and subject
      to the license terms contained in, the Simplified BSD License
      set forth in Section 4.c of the IETF Trust's Legal Provisions
      Relating to IETF Documents
      (http://trustee.ietf.org/license-info).

      This version of this YANG module is part of RFC 8675; see
      the RFC itself for full legal notices.";

  revision 2019-10-21 {
    description
      "Initial revision.";
    reference
      "RFC 8675:  Tunnel Interface Types YANG Module";
  }

  augment "/if:interfaces/if:interface" {
    when "derived-from(if:type, 'iana-tunnel-type:gre')";
    description 
      "Augments Interface module with specific tunnel parameters."; 

    leaf remote-endpoint {
      type inet:ipv6-address;
      description 
        "IPv6 address of the remote GRE endpoint.";
    }   
  }
}
