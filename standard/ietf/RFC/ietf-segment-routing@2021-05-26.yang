module ietf-segment-routing {
  yang-version 1.1;
  namespace "urn:ietf:params:xml:ns:yang:ietf-segment-routing";
  prefix sr;

  import ietf-routing {
    prefix rt;
    reference "RFC 8349: A YANG Data Model for Routing
                         Management (NMDA Version)";
  }

  organization
    "IETF SPRING - SPRING Working Group";
  contact
    "WG Web:   &lt;https://datatracker.ietf.org/wg/spring/&gt;
     WG List:  &lt;mailto:spring@ietf.org&gt;

     Author:    Stephane Litkowski
               &lt;mailto:slitkows.ietf@gmail.com&gt;
     Author:    Yingzhen Qu
               &lt;mailto:yingzhen.qu@futurewei.com&gt;
     Author:    Acee Lindem
               &lt;mailto:acee@cisco.com&gt;
     Author:    Pushpasis Sarkar
               &lt;mailto:pushpasis.ietf@gmail.com&gt;
     Author:    Jeff Tantsura
               &lt;jefftant.ietf@gmail.com&gt;

    ";
  description
    "This YANG module defines a generic framework for Segment
     Routing (SR).  It is to be augmented by models for different
     SR data planes.

     This YANG module conforms to the Network Management
     Datastore Architecture (NMDA), as described in RFC 8242.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).

     This version of this YANG module is part of RFC 9020;
     see the RFC itself for full legal notices.";

  reference
    "RFC 9020: YANG Data Model for Segment Routing.";

  revision 2021-05-26 {
    description
      "Initial version";
    reference
      "RFC 9020: YANG Data Model for Segment Routing.";
  }

  augment "/rt:routing" {
    description
      "This module augments the routing data model (RFC 8349)
       with Segment Routing (SR).";
    container segment-routing {
      description
        "Segment Routing configuration.  This container
         is to be augmented by models for different SR
         data planes.";
      reference
        "RFC 8402: Segment Routing Architecture.";
    }
  }
}
