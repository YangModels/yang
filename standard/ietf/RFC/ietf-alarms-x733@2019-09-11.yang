module ietf-alarms-x733 {
  yang-version 1.1;
  namespace &quot;urn:ietf:params:xml:ns:yang:ietf-alarms-x733&quot;;
  prefix x733;

  import ietf-alarms {
    prefix al;
  }
  import ietf-yang-types {
    prefix yang;
    reference
      &quot;<a href="/doc/html/rfc6991">RFC 6991</a>: Common YANG Data Types&quot;;
  }

  organization
    &quot;IETF CCAMP Working Group&quot;;
<span class="grey"><a href="/doc/html/rfc8632">RFC 8632</a>         A YANG Data Model for Alarm Management   September 2019</span>

     contact
       &quot;WG Web:   &lt;<a href="https://trac.ietf.org/trac/ccamp">https://trac.ietf.org/trac/ccamp</a>&gt;
        WG List:  &lt;mailto:<a href="mailto:ccamp@ietf.org">ccamp@ietf.org</a>&gt;

        Editor:   Stefan Vallin
                  &lt;mailto:<a href="mailto:stefan@wallan.se">stefan@wallan.se</a>&gt;

        Editor:   Martin Bjorklund
                  &lt;mailto:<a href="mailto:mbj@tail-f.com">mbj@tail-f.com</a>&gt;&quot;;
     description
       &quot;This module augments the ietf-alarms module with X.733 alarm
        parameters.

        The following structures are augmented with the X.733 event type
        and probable cause:

         1) alarms/alarm-inventory: all possible alarm types
         2) alarms/alarm-list: every alarm in the system
         3) alarm-notification: notifications indicating alarm-state
            changes
         4) alarms/shelved-alarms

        The module also optionally allows the alarm-management system
        to configure the mapping from the ietf-alarms&#x27; alarm keys
        to the ITU tuple (event-type, probable-cause).

        The mapping does not include a corresponding problem value
        specific to X.733.  The recommendation is to use the
        &#x27;alarm-type-qualifier&#x27; leaf, which serves the same purpose.

        The module uses an integer and a corresponding string for
        probable cause instead of a globally defined enumeration, in
        order to be able to manage conflicting enumeration definitions.
        A single globally defined enumeration is challenging to
        maintain.

        The key words &#x27;MUST&#x27;, &#x27;MUST NOT&#x27;, &#x27;REQUIRED&#x27;, &#x27;SHALL&#x27;, &#x27;SHALL
        NOT&#x27;, &#x27;SHOULD&#x27;, &#x27;SHOULD NOT&#x27;, &#x27;RECOMMENDED&#x27;, &#x27;NOT RECOMMENDED&#x27;,
        &#x27;MAY&#x27;, and &#x27;OPTIONAL&#x27; in this document are to be interpreted as
        described in <a href="/doc/html/bcp14">BCP 14</a> (<a href="/doc/html/rfc2119">RFC 2119</a>) (<a href="/doc/html/rfc8174">RFC 8174</a>) when, and only when,
        they appear in all capitals, as shown here.

        Copyright (c) 2019 IETF Trust and the persons identified as
        authors of the code.  All rights reserved.

        Redistribution and use in source and binary forms, with or
        without modification, is permitted pursuant to, and subject to
        the license terms contained in, the Simplified BSD License set
<span class="grey"><a href="/doc/html/rfc8632">RFC 8632</a>         A YANG Data Model for Alarm Management   September 2019</span>

        forth in <a href="#section-4">Section 4</a>.c of the IETF Trust&#x27;s Legal Provisions
        Relating to IETF Documents
        (<a href="https://trustee.ietf.org/license-info">https://trustee.ietf.org/license-info</a>).

        This version of this YANG module is part of <a href="/doc/html/rfc8632">RFC 8632</a>; see
        the RFC itself for full legal notices.&quot;;
     reference
       &quot;ITU-T Recommendation X.733: Information Technology
          - Open Systems Interconnection
          - System Management: Alarm Reporting Function&quot;;

     revision 2019-09-11 {
       description
         &quot;Initial revision.&quot;;
       reference
         &quot;<a href="/doc/html/rfc8632">RFC 8632</a>: A YANG Data Model for Alarm Management&quot;;
     }

     /*
      * Features
      */

     feature configure-x733-mapping {
       description
         &quot;The system supports configurable X733 mapping from
          the ietf-alarms&#x27; alarm-type to X733 event-type
          and probable-cause.&quot;;
     }

     /*
      * Typedefs
      */

     typedef event-type {
       type enumeration {
         enum other {
           value 1;
           description
             &quot;None of the below.&quot;;
         }
         enum communications-alarm {
           value 2;
           description
             &quot;An alarm of this type is principally associated with the
              procedures and/or processes required to convey
              information from one point to another.&quot;;
         }
         enum quality-of-service-alarm {
<span class="grey"><a href="/doc/html/rfc8632">RFC 8632</a>         A YANG Data Model for Alarm Management   September 2019</span>

           value 3;
           description
             &quot;An alarm of this type is principally associated with a
              degradation in the quality of a service.&quot;;
         }
         enum processing-error-alarm {
           value 4;
           description
             &quot;An alarm of this type is principally associated with a
              software or processing fault.&quot;;
         }
         enum equipment-alarm {
           value 5;
           description
             &quot;An alarm of this type is principally associated with an
              equipment fault.&quot;;
         }
         enum environmental-alarm {
           value 6;
           description
             &quot;An alarm of this type is principally associated with a
              condition relating to an enclosure in which the equipment
              resides.&quot;;
         }
         enum integrity-violation {
           value 7;
           description
             &quot;An indication that information may have been illegally
              modified, inserted, or deleted.&quot;;
         }
         enum operational-violation {
           value 8;
           description
             &quot;An indication that the provision of the requested service
              was not possible due to the unavailability, malfunction,
              or incorrect invocation of the service.&quot;;
         }
         enum physical-violation {
           value 9;
           description
             &quot;An indication that a physical resource has been violated
              in a way that suggests a security attack.&quot;;
         }
         enum security-service-or-mechanism-violation {
           value 10;
           description
             &quot;An indication that a security attack has been detected by
              a security service or mechanism.&quot;;
<span class="grey"><a href="/doc/html/rfc8632">RFC 8632</a>         A YANG Data Model for Alarm Management   September 2019</span>

         }
         enum time-domain-violation {
           value 11;
           description
             &quot;An indication that an event has occurred at an unexpected
              or prohibited time.&quot;;
         }
       }
       description
         &quot;The event types as defined by X.733 and X.736.&quot;;
       reference
         &quot;ITU-T Recommendation X.733: Information Technology
            - Open Systems Interconnection
            - System Management: Alarm Reporting Function
          ITU-T Recommendation X.736: Information Technology
            - Open Systems Interconnection
            - System Management: Security Alarm Reporting Function&quot;;
     }

     typedef trend {
       type enumeration {
         enum less-severe {
           description
             &quot;There is at least one outstanding alarm of a
              severity higher (more severe) than that in the
              current alarm.&quot;;
         }
         enum no-change {
           description
             &quot;The Perceived severity reported in the current
              alarm is the same as the highest (most severe)
              of any of the outstanding alarms&quot;;
         }
         enum more-severe {
           description
             &quot;The Perceived severity in the current alarm is
              higher (more severe) than that reported in any
              of the outstanding alarms.&quot;;
         }
       }
       description
         &quot;This type is used to describe the
          severity trend of the alarming resource.&quot;;
       reference
         &quot;ITU-T Recommendation X.721: Information Technology
             - Open Systems Interconnection
             - Structure of management information:
               Definition of management information
<span class="grey"><a href="/doc/html/rfc8632">RFC 8632</a>         A YANG Data Model for Alarm Management   September 2019</span>

               Module Attribute-ASN1Module&quot;;
     }

     typedef value-type {
       type union {
         type int64;
         type uint64;
         type decimal64 {
           fraction-digits 2;
         }
       }
       description
         &quot;A generic union type to match the ITU choice of
          integer and real.&quot;;
     }

     /*
      * Groupings
      */

     grouping x733-alarm-parameters {
       description
         &quot;Common X.733 parameters for alarms.&quot;;
       leaf event-type {
         type event-type;
         description
           &quot;The X.733/X.736 event type for this alarm.&quot;;
       }
       leaf probable-cause {
         type uint32;
         description
           &quot;The X.733 probable cause for this alarm.&quot;;
       }
       leaf probable-cause-string {
         type string;
         description
           &quot;The user-friendly string matching
            the probable cause integer value.  The string
            SHOULD match the X.733 enumeration.  For example,
            value 27 is &#x27;localNodeTransmissionError&#x27;.&quot;;
       }
       container threshold-information {
         description
           &quot;This parameter shall be present when the alarm
            is a result of crossing a threshold. &quot;;
         leaf triggered-threshold {
           type string;
           description
<span class="grey"><a href="/doc/html/rfc8632">RFC 8632</a>         A YANG Data Model for Alarm Management   September 2019</span>

             &quot;The identifier of the threshold attribute that
              caused the notification.&quot;;
         }
         leaf observed-value {
           type value-type;
           description
             &quot;The value of the gauge or counter that crossed
              the threshold.  This may be different from the
              threshold value if, for example, the gauge may
              only take on discrete values.&quot;;
         }
         choice threshold-level {
           description
             &quot;In the case of a gauge, the threshold level specifies
              a pair of threshold values: the first is the value
              of the crossed threshold, and the second is its
              corresponding hysteresis; in the case of a counter,
              the threshold level specifies only the threshold
              value.&quot;;
           case up {
             leaf up-high {
               type value-type;
               description
                 &quot;The going-up threshold for raising the alarm.&quot;;
             }
             leaf up-low {
               type value-type;
               description
                 &quot;The going-down threshold for clearing the alarm.
                  This is used for hysteresis functions for gauges.&quot;;
             }
           }
           case down {
             leaf down-low {
               type value-type;
               description
                 &quot;The going-down threshold for raising the alarm.&quot;;
             }
             leaf down-high {
               type value-type;
               description
                 &quot;The going-up threshold for clearing the alarm.
                  This is used for hysteresis functions for gauges.&quot;;
             }
           }
         }
         leaf arm-time {
           type yang:date-and-time;
<span class="grey"><a href="/doc/html/rfc8632">RFC 8632</a>         A YANG Data Model for Alarm Management   September 2019</span>

           description
             &quot;For a gauge threshold, it&#x27;s the time at which the
              threshold was last re-armed; namely, it&#x27;s the time after
              the previous threshold crossing at which the hysteresis
              value of the threshold was exceeded, thus again permitting
              the generation of notifications when the threshold is
              crossed.  For a counter threshold, it&#x27;s the later of the
              time at which the threshold offset was last applied or the
              counter was last initialized (for resettable counters).&quot;;
         }
       }
       list monitored-attributes {
         uses attribute;
         key &quot;id&quot;;
         description
           &quot;The Monitored attributes parameter, when present, defines
            one or more attributes of the resource and their
            corresponding values at the time of the alarm.&quot;;
       }
       leaf-list proposed-repair-actions {
         type string;
         description
           &quot;This parameter, when present, is used if the cause is
            known and the system being managed can suggest one or
            more solutions (such as switch in standby equipment,
            retry, and replace media).&quot;;
       }
       leaf trend-indication {
         type trend;
         description
           &quot;This parameter specifies the current severity
            trend of the resource.  If present, it indicates
            that there are one or more alarms (&#x27;outstanding
            alarms&#x27;) that have not been cleared and that
            pertain to the same resource as this alarm
            (&#x27;current alarm&#x27;) does.  The possible values are:

              more-severe: The Perceived severity in the current
                alarm is higher (more severe) than that reported in
                any of the outstanding alarms.

              no-change: The Perceived severity reported in the
                current alarm is the same as the highest (most severe)
                of any of the outstanding alarms.

              less-severe: There is at least one outstanding alarm
                of a severity higher (more severe) than that in the
                current alarm.&quot;;
<span class="grey"><a href="/doc/html/rfc8632">RFC 8632</a>         A YANG Data Model for Alarm Management   September 2019</span>

       }
       leaf backedup-status {
         type boolean;
         description
           &quot;This parameter, when present, specifies whether or not the
            object emitting the alarm has been backed up; therefore, it
            is possible to know whether or not services provided to the
            user have been disrupted when this parameter is included.
            The use of this field in conjunction with the
            &#x27;perceived-severity&#x27; field provides information in an
            independent form to qualify the seriousness of the alarm and
            the ability of the system as a whole to continue to provide
            services.  If the value of this parameter is true, it
            indicates that the object emitting the alarm has been backed
            up; if false, the object has not been backed up.&quot;;
       }
       leaf backup-object {
         type al:resource;
         description
           &quot;This parameter SHALL be present when the &#x27;backedup-status&#x27;
            parameter is present and has the value &#x27;true&#x27;.  This
            parameter specifies the managed object instance that is
            providing back-up services for the managed object to which
            the notification pertains.  This parameter is useful, for
            example, when the back-up object is from a pool of objects,
            any of which may be dynamically allocated to replace a
            faulty object.&quot;;
       }
       list additional-information {
         key &quot;identifier&quot;;
         description
           &quot;This parameter allows the inclusion of an additional
            information set in the alarm.  It is a series of data
            structures, each of which contains three items of
            information: an identifier, a significance indicator,
            and the problem information.&quot;;
         leaf identifier {
           type string;
           description
             &quot;Identifies the data type of the information parameter.&quot;;
         }
         leaf significant {
           type boolean;
           description
             &quot;Set to &#x27;true&#x27; if the receiving system must be able to
              parse the contents of the information subparameter
              for the event report to be fully understood.&quot;;
         }
<span class="grey"><a href="/doc/html/rfc8632">RFC 8632</a>         A YANG Data Model for Alarm Management   September 2019</span>

         leaf information {
           type string;
           description
             &quot;Additional information about the alarm.&quot;;
         }
       }
       leaf security-alarm-detector {
         type al:resource;
         description
           &quot;This parameter identifies the detector of the security
            alarm.&quot;;
       }
       leaf service-user {
         type al:resource;
         description
           &quot;This parameter identifies the service-user whose request
            for service led to the generation of the security alarm.&quot;;
       }
       leaf service-provider {
         type al:resource;
         description
           &quot;This parameter identifies the intended service-provider
            of the service that led to the generation of the security
            alarm.&quot;;
       }
       reference
         &quot;ITU-T Recommendation X.733: Information Technology
            - Open Systems Interconnection
            - System Management: Alarm Reporting Function
          ITU-T Recommendation X.736: Information Technology
            - Open Systems Interconnection
            - System Management: Security Alarm Reporting Function&quot;;
     }

     grouping x733-alarm-definition-parameters {
       description
         &quot;Common X.733 parameters for alarm definitions.
          This grouping is used to define those alarm
          attributes that can be mapped from the alarm-type
          mechanism in the ietf-alarms module.&quot;;
       leaf event-type {
         type event-type;
         description
           &quot;The alarm type has this X.733/X.736 event type.&quot;;
       }
       leaf probable-cause {
         type uint32;
         description
<span class="grey"><a href="/doc/html/rfc8632">RFC 8632</a>         A YANG Data Model for Alarm Management   September 2019</span>

           &quot;The alarm type has this X.733 probable cause value.
            This module defines probable cause as an integer
            and not as an enumeration.  The reason being that the
            primary use of probable cause is in the management
            application if it is based on the X.733 standard.
            However, most management applications have their own
            defined enum definitions and merging enums from
            different systems might create conflicts.  By using
            a configurable uint32, the system can be configured
            to match the enum values in the management application.&quot;;
       }
       leaf probable-cause-string {
         type string;
         description
           &quot;This string can be used to give a user-friendly string
            to the probable cause value.&quot;;
       }
     }

     grouping attribute {
       description
         &quot;A grouping to match the ITU generic reference to
          an attribute.&quot;;
       leaf id {
         type al:resource;
         description
           &quot;The resource representing the attribute.&quot;;
       }
       leaf value {
         type string;
         description
           &quot;The value represented as a string since it could
            be of any type.&quot;;
       }
       reference
         &quot;ITU-T Recommendation X.721: Information Technology
             - Open Systems Interconnection
             - Structure of management information:
               Definition of management information
          Module Attribute-ASN1Module&quot;;
     }

     /*
      * Add X.733 parameters to the alarm definitions, alarms,
      * and notification.
      */

     augment &quot;/al:alarms/al:alarm-inventory/al:alarm-type&quot; {
<span class="grey"><a href="/doc/html/rfc8632">RFC 8632</a>         A YANG Data Model for Alarm Management   September 2019</span>

       description
         &quot;Augment X.733 mapping information to the alarm inventory.&quot;;
       uses x733-alarm-definition-parameters;
     }

     /*
      * Add X.733 configurable mapping.
      */

     augment &quot;/al:alarms/al:control&quot; {
       description
         &quot;Add X.733 mapping capabilities. &quot;;
       list x733-mapping {
         if-feature &quot;configure-x733-mapping&quot;;
         key &quot;alarm-type-id alarm-type-qualifier-match&quot;;
         description
           &quot;This list allows a management application to control the
            X.733 mapping for all alarm types in the system.  Any entry
            in this list will allow the alarm manager to override the
            default X.733 mapping in the system, and the final mapping
            will be shown in the alarm inventory.&quot;;
         leaf alarm-type-id {
           type al:alarm-type-id;
           description
             &quot;Map the alarm type with this alarm type identifier.&quot;;
         }
         leaf alarm-type-qualifier-match {
           type string;
           description
             &quot;A W3C regular expression that is used when mapping an
              alarm type and alarm-type-qualifier to X.733 parameters.&quot;;
         }
         uses x733-alarm-definition-parameters;
       }
     }

     augment &quot;/al:alarms/al:alarm-list/al:alarm&quot; {
       description
         &quot;Augment X.733 information to the alarm.&quot;;
       uses x733-alarm-parameters;
     }

     augment &quot;/al:alarms/al:shelved-alarms/al:shelved-alarm&quot; {
       description
         &quot;Augment X.733 information to the alarm.&quot;;
       uses x733-alarm-parameters;
     }

<span class="grey"><a href="/doc/html/rfc8632">RFC 8632</a>         A YANG Data Model for Alarm Management   September 2019</span>

     augment &quot;/al:alarm-notification&quot; {
       description
         &quot;Augment X.733 information to the alarm notification.&quot;;
       uses x733-alarm-parameters;
     }
   }
