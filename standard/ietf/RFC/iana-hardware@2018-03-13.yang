module iana-hardware {
  yang-version 1.1;
  namespace &quot;urn:ietf:params:xml:ns:yang:iana-hardware&quot;;
  prefix ianahw;

  organization &quot;IANA&quot;;
  contact
    &quot;        Internet Assigned Numbers Authority

     Postal: ICANN
             12025 Waterfront Drive, Suite 300
             Los Angeles, CA  90094-2536
             United States of America

     Tel:    +1 310 301 5800
     E-Mail: <a href="mailto:iana@iana.org">iana@iana.org</a>&gt;&quot;;

  description
    &quot;IANA-defined identities for hardware class.

     The latest revision of this YANG module can be obtained from
     the IANA website.

     Requests for new values should be made to IANA via
     email (<a href="mailto:iana@iana.org">iana@iana.org</a>).

     Copyright (c) 2018 IETF Trust and the persons identified as
     authors of the code.  All rights reserved.

     Redistribution and use in source and binary forms, with or
     without modification, is permitted pursuant to, and subject
     to the license terms contained in, the Simplified BSD License

<span class="grey"><a href="/doc/html/rfc8348">RFC 8348</a>                YANG Hardware Management              March 2018</span>

        set forth in <a href="#section-4">Section 4</a>.c of the IETF Trust&#x27;s Legal Provisions
        Relating to IETF Documents
        (<a href="https://trustee.ietf.org/license-info">https://trustee.ietf.org/license-info</a>).

        The initial version of this YANG module is part of <a href="/doc/html/rfc8348">RFC 8348</a>;
        see the RFC itself for full legal notices.&quot;;
     reference
       &quot;<a href="https://www.iana.org/assignments/yang-parameters&quot;;">https://www.iana.org/assignments/yang-parameters&quot;;</a>

     revision 2018-03-13 {
       description
         &quot;Initial revision.&quot;;
       reference
         &quot;<a href="/doc/html/rfc8348">RFC 8348</a>: A YANG Data Model for Hardware Management&quot;;
     }

     /*
      * Identities
      */

     identity hardware-class {
       description
         &quot;This identity is the base for all hardware class
          identifiers.&quot;;
     }

     identity unknown {
       base ianahw:hardware-class;
       description
         &quot;This identity is applicable if the hardware class is unknown
          to the server.&quot;;
     }

     identity chassis {
       base ianahw:hardware-class;
       description
         &quot;This identity is applicable if the hardware class is an
          overall container for networking equipment.  Any class of
          physical component, except a stack, may be contained within a
          chassis; a chassis may only be contained within a stack.&quot;;
     }

     identity backplane {
       base ianahw:hardware-class;
       description
         &quot;This identity is applicable if the hardware class is some sort
          of device for aggregating and forwarding networking traffic,
          such as a shared backplane in a modular ethernet switch.  Note
<span class="grey"><a href="/doc/html/rfc8348">RFC 8348</a>                YANG Hardware Management              March 2018</span>

          that an implementation may model a backplane as a single
          physical component, which is actually implemented as multiple
          discrete physical components (within a chassis or stack).&quot;;
     }

     identity container {
       base ianahw:hardware-class;
       description
         &quot;This identity is applicable if the hardware class is capable
          of containing one or more removable physical entities,
          possibly of different types.  For example, each (empty or
          full) slot in a chassis will be modeled as a container.  Note
          that all removable physical components should be modeled
          within a container component, such as field-replaceable
          modules, fans, or power supplies.  Note that all known
          containers should be modeled by the agent, including empty
          containers.&quot;;
     }

     identity power-supply {
       base ianahw:hardware-class;
       description
         &quot;This identity is applicable if the hardware class is a
          power-supplying component.&quot;;
     }

     identity fan {
       base ianahw:hardware-class;
       description
         &quot;This identity is applicable if the hardware class is a fan or
          other heat-reduction component.&quot;;
     }

     identity sensor {
       base ianahw:hardware-class;
       description
         &quot;This identity is applicable if the hardware class is some sort
          of sensor, such as a temperature sensor within a router
          chassis.&quot;;
     }

     identity module {
       base ianahw:hardware-class;
       description
         &quot;This identity is applicable if the hardware class is some sort
          of self-contained sub-system.  If a module component is
          removable, then it should be modeled within a container

<span class="grey"><a href="/doc/html/rfc8348">RFC 8348</a>                YANG Hardware Management              March 2018</span>

          component; otherwise, it should be modeled directly within
          another physical component (e.g., a chassis or another
          module).&quot;;
     }

     identity port {
       base ianahw:hardware-class;
       description
         &quot;This identity is applicable if the hardware class is some sort
          of networking port capable of receiving and/or transmitting
          networking traffic.&quot;;
     }

     identity stack {
       base ianahw:hardware-class;
       description
         &quot;This identity is applicable if the hardware class is some sort
          of super-container (possibly virtual) intended to group
          together multiple chassis entities.  A stack may be realized
          by a virtual cable, a real interconnect cable attached to
          multiple chassis, or multiple interconnect cables.  A stack
          should not be modeled within any other physical components,
          but a stack may be contained within another stack.  Only
          chassis components should be contained within a stack.&quot;;
     }

     identity cpu {
       base ianahw:hardware-class;
       description
         &quot;This identity is applicable if the hardware class is some sort
          of central processing unit.&quot;;
     }

     identity energy-object {
       base ianahw:hardware-class;
       description
         &quot;This identity is applicable if the hardware class is some sort
          of energy object, i.e., it is a piece of equipment that is
          part of or attached to a communications network that is
          monitored, it is controlled, or it aids in the management of
          another device for Energy Management.&quot;;
     }

     identity battery {
       base ianahw:hardware-class;
       description
         &quot;This identity is applicable if the hardware class is some sort
          of battery.&quot;;
<span class="grey"><a href="/doc/html/rfc8348">RFC 8348</a>                YANG Hardware Management              March 2018</span>

     }

     identity storage-drive {
       base ianahw:hardware-class;
       description
         &quot;This identity is applicable if the hardware class is some sort
          of component with data storage capability as its main
          functionality, e.g., hard disk drive (HDD), solid-state device
          (SSD), solid-state hybrid drive (SSHD), object storage device
          (OSD), or other.&quot;;
     }
   }
