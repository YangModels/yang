submodule ietf-snmp-community {

  belongs-to ietf-snmp {
    prefix snmp;
  }

  import ietf-netconf-acm {
    prefix nacm;
  }

  include ietf-snmp-common;
  include ietf-snmp-target;
  include ietf-snmp-proxy;

  organization
    &quot;IETF NETMOD (NETCONF Data Modeling Language) Working Group&quot;;

  contact
    &quot;WG Web:   &lt;<a href="https://tools.ietf.org/wg/netmod/">http://tools.ietf.org/wg/netmod/</a>&gt;
     WG List:  &lt;mailto:<a href="mailto:netmod@ietf.org">netmod@ietf.org</a>&gt;

     WG Chair: Thomas Nadeau
               &lt;mailto:<a href="mailto:tnadeau@lucidvision.com">tnadeau@lucidvision.com</a>&gt;

     WG Chair: Juergen Schoenwaelder
               &lt;mailto:<a href="mailto:j.schoenwaelder@jacobs-university.de">j.schoenwaelder@jacobs-university.de</a>&gt;
<span class="grey"><a href="/doc/html/rfc7407">RFC 7407</a>         YANG Data Model for SNMP Configuration    December 2014</span>

        Editor:   Martin Bjorklund
                  &lt;mailto:<a href="mailto:mbj@tail-f.com">mbj@tail-f.com</a>&gt;

        Editor:   Juergen Schoenwaelder
                  &lt;mailto:<a href="mailto:j.schoenwaelder@jacobs-university.de">j.schoenwaelder@jacobs-university.de</a>&gt;&quot;;

     description
       &quot;This submodule contains a collection of YANG definitions
        for configuring community-based SNMP.

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc7407">RFC 7407</a>; see
        the RFC itself for full legal notices.&quot;;

     reference
       &quot;<a href="/doc/html/rfc3584">RFC 3584</a>: Coexistence between Version 1, Version 2, and
          Version 3 of the Internet-standard Network
          Management Framework&quot;;

     revision 2014-12-10 {
       description
         &quot;Initial revision.&quot;;
       reference
         &quot;<a href="/doc/html/rfc7407">RFC 7407</a>: A YANG Data Model for SNMP Configuration&quot;;
     }

     augment /snmp:snmp {

       list community {
         key index;

         description
           &quot;List of communities.&quot;;
         reference
           &quot;<a href="/doc/html/rfc3584">RFC 3584</a>: Coexistence between Version 1, Version 2,
              and Version 3 of the Internet-standard
              Network Management Framework.
              SNMP-COMMUNITY-MIB.snmpCommunityTable&quot;;

<span class="grey"><a href="/doc/html/rfc7407">RFC 7407</a>         YANG Data Model for SNMP Configuration    December 2014</span>

         leaf index {
           type snmp:identifier;
           description
             &quot;Index into the community list.&quot;;
           reference
             &quot;<a href="/doc/html/rfc3584">RFC 3584</a>: Coexistence between Version 1, Version 2,
                and Version 3 of the Internet-standard
                Network Management Framework.
                SNMP-COMMUNITY-MIB.snmpCommunityIndex&quot;;
         }
         choice name {
           nacm:default-deny-all;
           description
             &quot;The community name, specified as either a string or
              a binary value.  The binary name is used when the
              community name contains characters that are not legal
              in a string.

              If not set, the value of &#x27;security-name&#x27; is operationally
              used as the snmpCommunityName.&quot;;
           reference
             &quot;<a href="/doc/html/rfc3584">RFC 3584</a>: Coexistence between Version 1, Version 2,
                and Version 3 of the Internet-standard
                Network Management Framework.
                SNMP-COMMUNITY-MIB.snmpCommunityName&quot;;
           leaf text-name {
             type string;
             description
               &quot;A community name that can be represented as a
                YANG string.&quot;;
           }
           leaf binary-name {
             type binary;
             description
               &quot;A community name represented as a binary value.&quot;;
           }
         }
         leaf security-name {
           type snmp:security-name;
           mandatory true;
           nacm:default-deny-all;
           description
             &quot;The snmpCommunitySecurityName of this entry.&quot;;
           reference
             &quot;<a href="/doc/html/rfc3584">RFC 3584</a>: Coexistence between Version 1, Version 2,
                and Version 3 of the Internet-standard
                Network Management Framework.
                SNMP-COMMUNITY-MIB.snmpCommunitySecurityName&quot;;
<span class="grey"><a href="/doc/html/rfc7407">RFC 7407</a>         YANG Data Model for SNMP Configuration    December 2014</span>

         }
         leaf engine-id {
           if-feature snmp:proxy;
           type snmp:engine-id;
           description
             &quot;If not set, the value of the local SNMP engine is
              operationally used by the device.&quot;;
           reference
             &quot;<a href="/doc/html/rfc3584">RFC 3584</a>: Coexistence between Version 1, Version 2,
                and Version 3 of the Internet-standard
                Network Management Framework.
                SNMP-COMMUNITY-MIB.snmpCommunityContextEngineID&quot;;
         }
         leaf context {
           type snmp:context-name;
           default &quot;&quot;;
           description
             &quot;The context in which management information is accessed
              when using the community string specified by this entry.&quot;;
           reference
             &quot;<a href="/doc/html/rfc3584">RFC 3584</a>: Coexistence between Version 1, Version 2,
                and Version 3 of the Internet-standard
                Network Management Framework.
                SNMP-COMMUNITY-MIB.snmpCommunityContextName&quot;;
         }
         leaf target-tag {
           type snmp:tag-value;
           description
             &quot;Used to limit access for this community to the specified
              targets.

              Implementations MAY restrict the values of this leaf
              to be one of the available values of /snmp/target/tag in
              a valid configuration.&quot;;
           reference
             &quot;<a href="/doc/html/rfc3584">RFC 3584</a>: Coexistence between Version 1, Version 2,
                and Version 3 of the Internet-standard
                Network Management Framework.
                SNMP-COMMUNITY-MIB.snmpCommunityTransportTag&quot;;
         }
       }
     }

     grouping v1-target-params {
       container v1 {
         description
           &quot;SNMPv1 parameters type.
            Represents snmpTargetParamsMPModel &#x27;0&#x27;,
<span class="grey"><a href="/doc/html/rfc7407">RFC 7407</a>         YANG Data Model for SNMP Configuration    December 2014</span>

            snmpTargetParamsSecurityModel &#x27;1&#x27;, and
            snmpTargetParamsSecurityLevel &#x27;noAuthNoPriv&#x27;.&quot;;
         leaf security-name {
           type snmp:security-name;
           mandatory true;
           description
             &quot;Implementations MAY restrict the values of this leaf
              to be one of the available values of
              /snmp/community/security-name in a valid configuration.&quot;;
           reference
             &quot;<a href="/doc/html/rfc3413">RFC 3413</a>: Simple Network Management Protocol (SNMP).
                Applications.
                SNMP-TARGET-MIB.snmpTargetParamsSecurityName&quot;;
         }
       }
     }

     grouping v2c-target-params {
       container v2c {
         description
           &quot;SNMPv2 community parameters type.
            Represents snmpTargetParamsMPModel &#x27;1&#x27;,
            snmpTargetParamsSecurityModel &#x27;2&#x27;, and
            snmpTargetParamsSecurityLevel &#x27;noAuthNoPriv&#x27;.&quot;;
         leaf security-name {
           type snmp:security-name;
           mandatory true;
           description
             &quot;Implementations MAY restrict the values of this leaf
              to be one of the available values of
              /snmp/community/security-name in a valid configuration.&quot;;
           reference
             &quot;<a href="/doc/html/rfc3413">RFC 3413</a>: Simple Network Management Protocol (SNMP).
                Applications.
                SNMP-TARGET-MIB.snmpTargetParamsSecurityName&quot;;
         }
       }
     }

     augment /snmp:snmp/snmp:target-params/snmp:params {
       case v1 {
         uses v1-target-params;
       }
       case v2c {
         uses v2c-target-params;
       }
     }

<span class="grey"><a href="/doc/html/rfc7407">RFC 7407</a>         YANG Data Model for SNMP Configuration    December 2014</span>

     augment /snmp:snmp/snmp:target {
       when &quot;snmp:v1 or snmp:v2c&quot;;
       leaf mms {
         type union {
           type enumeration {
             enum &quot;unknown&quot; { value 0; }
           }
           type int32 {
             range &quot;484..max&quot;;
           }
         }
         default &quot;484&quot;;
         description
           &quot;The maximum message size.&quot;;
         reference
           &quot;<a href="/doc/html/rfc3584">RFC 3584</a>: Coexistence between Version 1, Version 2,
              and Version 3 of the Internet-standard
              Network Management Framework.
              SNMP-COMMUNITY-MIB.snmpTargetAddrMMS&quot;;
       }
     }

   }
