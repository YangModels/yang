module ietf-routing {

  yang-version &quot;1.1&quot;;

  namespace &quot;urn:ietf:params:xml:ns:yang:ietf-routing&quot;;

  prefix &quot;rt&quot;;

  import ietf-yang-types {
    prefix &quot;yang&quot;;
  }

  import ietf-interfaces {
    prefix &quot;if&quot;;
  }

  organization
    &quot;IETF NETMOD (NETCONF Data Modeling Language) Working Group&quot;;

  contact
    &quot;WG Web:   &lt;<a href="https://datatracker.ietf.org/wg/netmod/">https://datatracker.ietf.org/wg/netmod/</a>&gt;
     WG List:  &lt;mailto:<a href="mailto:netmod@ietf.org">netmod@ietf.org</a>&gt;

<span class="grey"><a href="/doc/html/rfc8022">RFC 8022</a>                 YANG Routing Management           November 2016</span>

        WG Chair: Lou Berger
                  &lt;mailto:<a href="mailto:lberger@labn.net">lberger@labn.net</a>&gt;

        WG Chair: Kent Watsen
                  &lt;mailto:<a href="mailto:kwatsen@juniper.net">kwatsen@juniper.net</a>&gt;

        Editor:   Ladislav Lhotka
                  &lt;mailto:<a href="mailto:lhotka@nic.cz">lhotka@nic.cz</a>&gt;

        Editor:   Acee Lindem
                  &lt;mailto:<a href="mailto:acee@cisco.com">acee@cisco.com</a>&gt;&quot;;

     description
       &quot;This YANG module defines essential components for the management
        of a routing subsystem.

        Copyright (c) 2016 IETF Trust and the persons identified as
        authors of the code.  All rights reserved.

        Redistribution and use in source and binary forms, with or
        without modification, is permitted pursuant to, and subject to
        the license terms contained in, the Simplified BSD License set
        forth in <a href="#section-4">Section 4</a>.c of the IETF Trust&#x27;s Legal Provisions
        Relating to IETF Documents
        (<a href="https://trustee.ietf.org/license-info">http://trustee.ietf.org/license-info</a>).

        The key words &#x27;MUST&#x27;, &#x27;MUST NOT&#x27;, &#x27;REQUIRED&#x27;, &#x27;SHALL&#x27;, &#x27;SHALL
        NOT&#x27;, &#x27;SHOULD&#x27;, &#x27;SHOULD NOT&#x27;, &#x27;RECOMMENDED&#x27;, &#x27;MAY&#x27;, and
        &#x27;OPTIONAL&#x27; in the module text are to be interpreted as described
        in <a href="/doc/html/rfc2119">RFC 2119</a>.

        This version of this YANG module is part of <a href="/doc/html/rfc8022">RFC 8022</a>;
        see the RFC itself for full legal notices.&quot;;

     revision 2016-11-04 {
       description
         &quot;Initial revision.&quot;;
       reference
         &quot;<a href="/doc/html/rfc8022">RFC 8022</a>: A YANG Data Model for Routing Management&quot;;
     }

     /* Features */

     feature multiple-ribs {
       description
         &quot;This feature indicates that the server supports user-defined
          RIBs.

<span class="grey"><a href="/doc/html/rfc8022">RFC 8022</a>                 YANG Routing Management           November 2016</span>

          Servers that do not advertise this feature SHOULD provide
          exactly one system-controlled RIB per supported address family
          and make it also the default RIB.  This RIB then appears as an
          entry of the list /routing-state/ribs/rib.&quot;;
     }

     feature router-id {
       description
         &quot;This feature indicates that the server supports configuration
          of an explicit 32-bit router ID that is used by some routing
          protocols.

          Servers that do not advertise this feature set a router ID
          algorithmically, usually to one of the configured IPv4
          addresses.  However, this algorithm is implementation
          specific.&quot;;
     }

     /* Identities */

     identity address-family {
       description
         &quot;Base identity from which identities describing address
          families are derived.&quot;;
     }

     identity ipv4 {
       base address-family;
       description
         &quot;This identity represents IPv4 address family.&quot;;
     }

     identity ipv6 {
       base address-family;
       description
         &quot;This identity represents IPv6 address family.&quot;;
     }

     identity control-plane-protocol {
       description
         &quot;Base identity from which control-plane protocol identities are
          derived.&quot;;
     }

     identity routing-protocol {
       base control-plane-protocol;
       description
         &quot;Identity from which Layer 3 routing protocol identities are
<span class="grey"><a href="/doc/html/rfc8022">RFC 8022</a>                 YANG Routing Management           November 2016</span>

          derived.&quot;;
     }

     identity direct {
       base routing-protocol;
       description
         &quot;Routing pseudo-protocol that provides routes to directly
          connected networks.&quot;;
     }

     identity static {
       base routing-protocol;
       description
         &quot;Static routing pseudo-protocol.&quot;;
     }

     /* Type Definitions */

     typedef route-preference {
       type uint32;
       description
         &quot;This type is used for route preferences.&quot;;
     }

     /* Groupings */

     grouping address-family {
       description
         &quot;This grouping provides a leaf identifying an address
          family.&quot;;
       leaf address-family {
         type identityref {
           base address-family;
         }
         mandatory &quot;true&quot;;
         description
           &quot;Address family.&quot;;
       }
     }

     grouping router-id {
       description
         &quot;This grouping provides router ID.&quot;;
       leaf router-id {
         type yang:dotted-quad;
         description
           &quot;A 32-bit number in the form of a dotted quad that is used by
            some routing protocols identifying a router.&quot;;
<span class="grey"><a href="/doc/html/rfc8022">RFC 8022</a>                 YANG Routing Management           November 2016</span>

         reference
           &quot;<a href="/doc/html/rfc2328">RFC 2328</a>: OSPF Version 2.&quot;;
       }
     }

     grouping special-next-hop {
       description
         &quot;This grouping provides a leaf with an enumeration of special
          next hops.&quot;;
       leaf special-next-hop {
         type enumeration {
           enum blackhole {
             description
               &quot;Silently discard the packet.&quot;;
           }
           enum unreachable {
             description
               &quot;Discard the packet and notify the sender with an error
                message indicating that the destination host is
                unreachable.&quot;;
           }
           enum prohibit {
             description
               &quot;Discard the packet and notify the sender with an error
                message indicating that the communication is
                administratively prohibited.&quot;;
           }
           enum receive {
             description
               &quot;The packet will be received by the local system.&quot;;
           }
         }
         description
           &quot;Options for special next hops.&quot;;
       }
     }

     grouping next-hop-content {
       description
         &quot;Generic parameters of next hops in static routes.&quot;;
       choice next-hop-options {
         mandatory &quot;true&quot;;
         description
           &quot;Options for next hops in static routes.

            It is expected that further cases will be added through
            augments from other modules.&quot;;
         case simple-next-hop {
<span class="grey"><a href="/doc/html/rfc8022">RFC 8022</a>                 YANG Routing Management           November 2016</span>

           description
             &quot;This case represents a simple next hop consisting of the
              next-hop address and/or outgoing interface.

              Modules for address families MUST augment this case with a
              leaf containing a next-hop address of that address
              family.&quot;;
           leaf outgoing-interface {
             type if:interface-ref;
             description
               &quot;Name of the outgoing interface.&quot;;
           }
         }
         case special-next-hop {
           uses special-next-hop;
         }
         case next-hop-list {
           container next-hop-list {
             description
               &quot;Container for multiple next-hops.&quot;;
             list next-hop {
               key &quot;index&quot;;
               description
                 &quot;An entry of a next-hop list.

                  Modules for address families MUST augment this list
                  with a leaf containing a next-hop address of that
                  address family.&quot;;
               leaf index {
                 type string;
                 description
                   &quot;A user-specified identifier utilized to uniquely
                    reference the next-hop entry in the next-hop list.
                    The value of this index has no semantic meaning
                    other than for referencing the entry.&quot;;
               }
               leaf outgoing-interface {
                 type if:interface-ref;
                 description
                   &quot;Name of the outgoing interface.&quot;;
               }
             }
           }
         }
       }
     }

<span class="grey"><a href="/doc/html/rfc8022">RFC 8022</a>                 YANG Routing Management           November 2016</span>

     grouping next-hop-state-content {
       description
         &quot;Generic parameters of next hops in state data.&quot;;
       choice next-hop-options {
         mandatory &quot;true&quot;;
         description
           &quot;Options for next hops in state data.

            It is expected that further cases will be added through
            augments from other modules, e.g., for recursive
            next hops.&quot;;
         case simple-next-hop {
           description
             &quot;This case represents a simple next hop consisting of the
              next-hop address and/or outgoing interface.

              Modules for address families MUST augment this case with a
              leaf containing a next-hop address of that address
              family.&quot;;
           leaf outgoing-interface {
             type if:interface-state-ref;
             description
               &quot;Name of the outgoing interface.&quot;;
           }
         }
         case special-next-hop {
           uses special-next-hop;
         }
         case next-hop-list {
           container next-hop-list {
             description
               &quot;Container for multiple next hops.&quot;;
             list next-hop {
               description
                 &quot;An entry of a next-hop list.

                  Modules for address families MUST augment this list
                  with a leaf containing a next-hop address of that
                  address family.&quot;;
               leaf outgoing-interface {
                 type if:interface-state-ref;
                 description
                   &quot;Name of the outgoing interface.&quot;;
               }
             }
           }
         }
       }
<span class="grey"><a href="/doc/html/rfc8022">RFC 8022</a>                 YANG Routing Management           November 2016</span>

     }

     grouping route-metadata {
       description
         &quot;Common route metadata.&quot;;
       leaf source-protocol {
         type identityref {
           base routing-protocol;
         }
         mandatory &quot;true&quot;;
         description
           &quot;Type of the routing protocol from which the route
            originated.&quot;;
       }
       leaf active {
         type empty;
         description
           &quot;Presence of this leaf indicates that the route is preferred
            among all routes in the same RIB that have the same
            destination prefix.&quot;;
       }
       leaf last-updated {
         type yang:date-and-time;
         description
           &quot;Time stamp of the last modification of the route.  If the
            route was never modified, it is the time when the route was
            inserted into the RIB.&quot;;
       }
     }

     /* State data */

     container routing-state {
       config &quot;false&quot;;
       description
         &quot;State data of the routing subsystem.&quot;;
       uses router-id {
         description
           &quot;Global router ID.

            It may be either configured or assigned algorithmically by
            the implementation.&quot;;
       }
       container interfaces {
         description
           &quot;Network-layer interfaces used for routing.&quot;;
         leaf-list interface {
           type if:interface-state-ref;
<span class="grey"><a href="/doc/html/rfc8022">RFC 8022</a>                 YANG Routing Management           November 2016</span>

           description
             &quot;Each entry is a reference to the name of a configured
              network-layer interface.&quot;;
         }
       }
       container control-plane-protocols {
         description
           &quot;Container for the list of routing protocol instances.&quot;;
         list control-plane-protocol {
           key &quot;type name&quot;;
           description
             &quot;State data of a control-plane protocol instance.

              An implementation MUST provide exactly one
              system-controlled instance of the &#x27;direct&#x27;
              pseudo-protocol.  Instances of other control-plane
              protocols MAY be created by configuration.&quot;;
           leaf type {
             type identityref {
               base control-plane-protocol;
             }
             description
               &quot;Type of the control-plane protocol.&quot;;
           }
           leaf name {
             type string;
             description
               &quot;The name of the control-plane protocol instance.

                For system-controlled instances this name is persistent,
                i.e., it SHOULD NOT change across reboots.&quot;;
           }
         }
       }
       container ribs {
         description
           &quot;Container for RIBs.&quot;;
         list rib {
           key &quot;name&quot;;
           min-elements &quot;1&quot;;
           description
             &quot;Each entry represents a RIB identified by the &#x27;name&#x27; key.
              All routes in a RIB MUST belong to the same address
              family.

              An implementation SHOULD provide one system-controlled
              default RIB for each supported address family.&quot;;
           leaf name {
<span class="grey"><a href="/doc/html/rfc8022">RFC 8022</a>                 YANG Routing Management           November 2016</span>

             type string;
             description
               &quot;The name of the RIB.&quot;;
           }
           uses address-family;
           leaf default-rib {
             if-feature &quot;multiple-ribs&quot;;
             type boolean;
             default &quot;true&quot;;
             description
               &quot;This flag has the value of &#x27;true&#x27; if and only if the RIB
                is the default RIB for the given address family.

                By default, control-plane protocols place their routes
                in the default RIBs.&quot;;
           }
           container routes {
             description
               &quot;Current content of the RIB.&quot;;
             list route {
               description
                 &quot;A RIB route entry.  This data node MUST be augmented
                  with information specific for routes of each address
                  family.&quot;;
               leaf route-preference {
                 type route-preference;
                 description
                   &quot;This route attribute, also known as administrative
                    distance, allows for selecting the preferred route
                    among routes with the same destination prefix.  A
                    smaller value means a more preferred route.&quot;;
               }
               container next-hop {
                 description
                   &quot;Route&#x27;s next-hop attribute.&quot;;
                 uses next-hop-state-content;
               }
               uses route-metadata;
             }
           }
           action active-route {
             description
               &quot;Return the active RIB route that is used for the
                destination address.

                Address-family-specific modules MUST augment input
                parameters with a leaf named &#x27;destination-address&#x27;.&quot;;
             output {
<span class="grey"><a href="/doc/html/rfc8022">RFC 8022</a>                 YANG Routing Management           November 2016</span>

               container route {
                 description
                   &quot;The active RIB route for the specified destination.

                    If no route exists in the RIB for the destination
                    address, no output is returned.

                    Address-family-specific modules MUST augment this
                    container with appropriate route contents.&quot;;
                 container next-hop {
                   description
                     &quot;Route&#x27;s next-hop attribute.&quot;;
                   uses next-hop-state-content;
                 }
                 uses route-metadata;
               }
             }
           }
         }
       }
     }

     /* Configuration Data */

     container routing {
       description
         &quot;Configuration parameters for the routing subsystem.&quot;;
       uses router-id {
         if-feature &quot;router-id&quot;;
         description
           &quot;Configuration of the global router ID.  Routing protocols
            that use router ID can use this parameter or override it
            with another value.&quot;;
       }
       container control-plane-protocols {
         description
           &quot;Configuration of control-plane protocol instances.&quot;;
         list control-plane-protocol {
           key &quot;type name&quot;;
           description
             &quot;Each entry contains configuration of a control-plane
              protocol instance.&quot;;
           leaf type {
             type identityref {
               base control-plane-protocol;
             }
             description
               &quot;Type of the control-plane protocol - an identity derived
<span class="grey"><a href="/doc/html/rfc8022">RFC 8022</a>                 YANG Routing Management           November 2016</span>

                from the &#x27;control-plane-protocol&#x27; base identity.&quot;;
           }
           leaf name {
             type string;
             description
               &quot;An arbitrary name of the control-plane protocol
                instance.&quot;;
           }
           leaf description {
             type string;
             description
               &quot;Textual description of the control-plane protocol
                instance.&quot;;
           }
           container static-routes {
             when &quot;derived-from-or-self(../type, &#x27;rt:static&#x27;)&quot; {
               description
                 &quot;This container is only valid for the &#x27;static&#x27; routing
                  protocol.&quot;;
             }
             description
               &quot;Configuration of the &#x27;static&#x27; pseudo-protocol.

                Address-family-specific modules augment this node with
                their lists of routes.&quot;;
           }
         }
       }
       container ribs {
         description
           &quot;Configuration of RIBs.&quot;;
         list rib {
           key &quot;name&quot;;
           description
             &quot;Each entry contains configuration for a RIB identified by
              the &#x27;name&#x27; key.

              Entries having the same key as a system-controlled entry
              of the list /routing-state/ribs/rib are used for
              configuring parameters of that entry.  Other entries
              define additional user-controlled RIBs.&quot;;
           leaf name {
             type string;
             description
               &quot;The name of the RIB.

                For system-controlled entries, the value of this leaf
                must be the same as the name of the corresponding entry
<span class="grey"><a href="/doc/html/rfc8022">RFC 8022</a>                 YANG Routing Management           November 2016</span>

                in state data.

                For user-controlled entries, an arbitrary name can be
                used.&quot;;
           }
           uses address-family {
             description
               &quot;Address family of the RIB.

                It is mandatory for user-controlled RIBs.  For
                system-controlled RIBs it can be omitted; otherwise, it
                must match the address family of the corresponding state
                entry.&quot;;
             refine &quot;address-family&quot; {
               mandatory &quot;false&quot;;
             }
           }
           leaf description {
             type string;
             description
               &quot;Textual description of the RIB.&quot;;
           }
         }
       }
     }
   }
