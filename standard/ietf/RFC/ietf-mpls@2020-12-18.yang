module ietf-mpls {
  yang-version 1.1;
  namespace "urn:ietf:params:xml:ns:yang:ietf-mpls";

  prefix mpls;

  import ietf-routing {
    prefix rt;
    reference
      "RFC 8349: A YANG Data Model for Routing Management
       (NMDA Version)";
  }
  import ietf-routing-types {
    prefix rt-types;
    reference
      "RFC 8294: Common YANG Data Types for the Routing Area";
  }
  import ietf-yang-types {
    prefix yang;
    reference
      "RFC 6991: Common YANG Data Types";
  }
  import ietf-interfaces {
    prefix if;
    reference
      "RFC 8343: A YANG Data Model for Interface Management";
  }

  organization
    "IETF MPLS Working Group";
  contact
    "WG Web:   <https://datatracker.ietf.org/wg/mpls/>
     WG List:  <mailto:mpls@ietf.org>

     Editor:   Tarek Saad
               <mailto:tsaad@juniper.net>

     Editor:   Kamran Raza
               <mailto:skraza@cisco.com>

     Editor:   Rakesh Gandhi
               <mailto:rgandhi@cisco.com>

     Editor:   Xufeng Liu
               <mailto:xufeng.liu.ietf@gmail.com>

     Editor:   Vishnu Pavan Beeram
               <mailto:vbeeram@juniper.net>";
  description
    "This YANG module defines the essential components for the
     management of the MPLS subsystem.  The model fully conforms
     to the Network Management Datastore Architecture (NMDA).

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC 8960; see the
     RFC itself for full legal notices.";

  revision 2020-12-18 {
    description
      "Initial revision.";
    reference
      "RFC 8960: A YANG Data Model for MPLS Base";
  }

  /* Identities */

  identity mpls {
    base rt:address-family;
    description
      "This identity represents the MPLS address family.";
  }

  identity mpls-unicast {
    base mpls:mpls;
    description
      "This identity represents the MPLS unicast address family.";
  }

  identity label-block-alloc-mode {
    description
      "Base identity for label-block allocation mode.";
  }

  identity label-block-alloc-mode-manager {
    base label-block-alloc-mode;
    description
      "Label-block allocation on the reserved block
       is managed by the label manager.";
  }

  identity label-block-alloc-mode-application {
    base label-block-alloc-mode;
    description
      "Label-block allocation on the reserved block
       is managed by the application.";
  }

  /**
   * Typedefs
   */

  typedef mpls-operations-type {
    type enumeration {
      enum impose-and-forward {
        description
          "Operation to impose one or more outgoing labels and
           forward to the next hop.";
      }
      enum pop-and-forward {
        description
          "Operation to pop the incoming label and forward to the
           next hop.";
      }
      enum pop-impose-and-forward {
        description
          "Operation to pop the incoming label, impose one or more
           outgoing labels, and forward to the next hop.";
      }
      enum swap-and-forward {
        description
          "Operation to swap the incoming label with the outgoing
           label and forward to the next hop.";
      }
      enum pop-and-lookup {
        description
          "Operation to pop the incoming label and perform
           a lookup.";
      }
    }
    description
      "Types of MPLS operations.";
  }

  typedef nhlfe-role {
    type enumeration {
      enum primary {
        description
          "The next hop acts as the primary for carrying traffic.";
      }
      enum backup {
        description
          "The next hop acts as the backup.";
      }
      enum primary-and-backup {
        description
          "The next hop simultaneously acts as both the primary and
           the backup for carrying traffic.";
      }
    }
    description
      "Role of the next hop.";
  }

  grouping nhlfe-single-contents {
    description
      "A grouping that describes a single Next Hop Label Forwarding
       Entry (NHLFE) and its associated parameters as described in
       the MPLS architecture.  This grouping is specific to the case
       when a single next hop is associated with the route.";
    uses rt-types:mpls-label-stack;
  }

  grouping nhlfe-multiple-contents {
    description
      "A grouping that describes a set of NHLFEs and their
       associated parameters as described in the MPLS
       architecture.  This grouping is used when multiple next hops
       are associated with the route.";
    leaf index {
      type string;
      description
        "A user-specified identifier utilized to uniquely
         reference the next-hop entry in the next-hop list.
         The value of this index has no semantic meaning
         other than for referencing the entry.";
    }
    leaf backup-index {
      type string;
      description
        "A user-specified identifier utilized to uniquely
         reference the backup next-hop entry in the NHLFE list.
         The value of this index has no semantic meaning
         other than for referencing the entry.";
      reference
        "RFC 4090: Fast Reroute Extensions to RSVP-TE for LSP Tunnels
         RFC 5714: IP Fast Reroute Framework";
    }
    leaf loadshare {
      type uint16;
      default "1";
      description
        "This value is used to compute a load share to perform
         unequal load balancing when multiple outgoing next hops are
         specified.  A share is computed as a ratio of this number to
         the total under all next hops.";
      reference
        "RFC 3031: Multiprotocol Label Switching Architecture,
         Sections 3.11 and 3.12
         RFC 7424: Mechanisms for Optimizing Link Aggregation Group
         (LAG) and Equal-Cost Multipath (ECMP) Component Link
         Utilization in Networks, Section 5.4";
    }
    leaf role {
      type nhlfe-role;
      description
        "Role of the NHLFE.";
    }
    uses nhlfe-single-contents;
  }

  grouping interfaces-mpls {
    description
      "List of MPLS interfaces.";
    container interfaces {
      description
        "List of MPLS-enabled interfaces.";
      list interface {
        key "name";
        description
          "MPLS-enabled interface entry.";
        leaf name {
          type if:interface-ref;
          description
            "A reference to the name of an interface in the system
             that is to be enabled for MPLS.";
        }
        leaf mpls-enabled {
          type boolean;
          default "false";
          description
            "'true' if MPLS encapsulation is enabled on the
             interface.
             'false' if MPLS encapsulation is disabled on the
             interface.";
        }
        leaf maximum-labeled-packet {
          type uint32;
          units "octets";
          description
            "Maximum labeled packet size.";
          reference
            "RFC 3032: MPLS Label Stack Encoding, Section 3.2";
        }
      }
    }
  }

  grouping globals {
    description
      "MPLS global configuration grouping.";
    leaf ttl-propagate {
      type boolean;
      default "true";
      description
        "Propagate TTL between IP and MPLS.";
    }
  }

  grouping label-blocks {
    description
      "Label-block allocation grouping.";
    container mpls-label-blocks {
      description
        "Label-block allocation container.";
      list mpls-label-block {
        key "index";
        description
          "List of MPLS label blocks.";
        leaf index {
          type string;
          description
            "A user-specified identifier utilized to uniquely
             reference an MPLS label block.";
        }
        leaf start-label {
          type rt-types:mpls-label;
          must '. <= ../end-label' {
            error-message "'start-label' must be less than or equal "
                        + "to 'end-label'";
          }
          description
            "Label-block start.";
        }
        leaf end-label {
          type rt-types:mpls-label;
          must '. >= ../start-label' {
            error-message "'end-label' must be greater than or "
                        + "equal to 'start-label'";
          }
          description
            "Label-block end.";
        }
        leaf block-allocation-mode {
          type identityref {
            base label-block-alloc-mode;
          }
          description
            "Label-block allocation mode.";
        }
        leaf inuse-labels-count {
          when "derived-from-or-self(../block-allocation-mode, "
             + "'mpls:label-block-alloc-mode-manager')";
          type yang:gauge32;
          config false;
          description
            "Number of labels in use in the label block.";
        }
      }
    }
  }

  grouping rib-mpls-properties {
    description
      "A grouping of native MPLS RIB properties.";
    leaf destination-prefix {
      type leafref {
        path "../mpls-local-label";
      }
      description
        "MPLS destination prefix.";
    }
    leaf route-context {
      type string;
      description
        "A context associated with the native MPLS route.";
    }
  }

  grouping rib-active-route-mpls-input {
    description
      "A grouping applicable to native MPLS RIB 'active-route'
       RPC input augmentation.";
    leaf destination-address {
      type leafref {
        path "../mpls-local-label";
      }
      description
        "MPLS native 'active-route' destination.";
    }
    leaf mpls-local-label {
      type rt-types:mpls-label;
      description
        "MPLS local label.";
    }
  }

  augment "/rt:routing" {
    description
      "MPLS augmentation.";
    container mpls {
      description
        "MPLS container to be used as an augmentation target node
         for the configuration of other MPLS sub-features, e.g.,
         MPLS static Label Switched Paths (LSPs), MPLS LDP LSPs,
         and Traffic Engineering MPLS LSP Tunnels.";
      uses globals;
      uses label-blocks;
      uses interfaces-mpls;
    }
  }

  /* Augmentation of MPLS routes */

  augment "/rt:routing/rt:ribs/rt:rib/rt:routes/rt:route" {
    description
      "This augmentation is applicable to all MPLS routes.";
    leaf mpls-enabled {
      type boolean;
      default "false";
      description
        "Indicates whether MPLS is enabled for this route.";
    }
    leaf mpls-local-label {
      when "../mpls-enabled = 'true'";
      type rt-types:mpls-label;
      description
        "MPLS local label associated with the route.";
    }
    uses rib-mpls-properties {
      /* MPLS Address Family (AF) augmentation to the
         native MPLS RIB */
      when "derived-from-or-self(../../rt:address-family, "
         + "'mpls:mpls')" {
        description
          "This augment is valid only for routes of the native MPLS
           RIB.";
      }
    }
  }

  /* MPLS simple-next-hop augmentation */

  augment "/rt:routing/rt:ribs/rt:rib/rt:routes/rt:route/"
        + "rt:next-hop/rt:next-hop-options/rt:simple-next-hop" {
    description
      "Augments the 'simple-next-hop' case in IP unicast routes.";
    uses nhlfe-single-contents {
      when "/rt:routing/rt:ribs/rt:rib/rt:routes/rt:route"
         + "/mpls:mpls-enabled = 'true'";
    }
  }

  /* MPLS next-hop-list augmentation */

  augment "/rt:routing/rt:ribs/rt:rib/rt:routes/rt:route/"
        + "rt:next-hop/rt:next-hop-options/rt:next-hop-list/"
        + "rt:next-hop-list/rt:next-hop" {
    description
      "This leaf augments the 'next-hop-list' case of IP unicast
       routes.";
    uses nhlfe-multiple-contents {
      when "/rt:routing/rt:ribs/rt:rib/rt:routes/rt:route"
         + "/mpls:mpls-enabled = 'true'";
    }
  }

  /* MPLS RPC input augmentation */

  augment "/rt:routing/rt:ribs/rt:rib/rt:active-route/rt:input" {
    description
      "Input MPLS augmentation for the 'active-route' action
       statement.";
    uses rib-active-route-mpls-input {
      /* MPLS AF augmentation to the native MPLS RIB */
      when "derived-from-or-self(../rt:address-family, "
         + "'mpls:mpls')" {
        description
          "This augment is valid only for routes of the native MPLS
           RIB.";
      }
    }
  }

  /* MPLS RPC output augmentation */

  augment "/rt:routing/rt:ribs/rt:rib/rt:active-route/"
        + "rt:output/rt:route/"
        + "rt:next-hop/rt:next-hop-options/rt:simple-next-hop" {
    description
      "Output MPLS augmentation for the 'active-route' action
       statement.";
    uses nhlfe-single-contents;
  }

  augment "/rt:routing/rt:ribs/rt:rib/rt:active-route/"
        + "rt:output/rt:route/"
        + "rt:next-hop/rt:next-hop-options/rt:next-hop-list/"
        + "rt:next-hop-list/rt:next-hop" {
    description
      "Output MPLS augmentation for the 'active-route' action
       statement.";
    uses nhlfe-multiple-contents;
  }
}
