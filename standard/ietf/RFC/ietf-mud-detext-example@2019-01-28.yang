module ietf-mud-detext-example {
  yang-version 1.1;
  namespace &quot;urn:ietf:params:xml:ns:yang:ietf-mud-detext-example&quot;;
  prefix ietf-mud-detext-example;

  import ietf-mud {
    prefix ietf-mud;
  }

  organization
    &quot;IETF OPSAWG (Operations and Management Area Working Group)&quot;;
  contact
    &quot;WG Web: &lt;<a href="https://datatracker.ietf.org/wg/opsawg/">https://datatracker.ietf.org/wg/opsawg/</a>&gt;
     WG List: <a href="mailto:opsawg@ietf.org">opsawg@ietf.org</a>

     Author: Eliot Lear
             <a href="mailto:lear@cisco.com">lear@cisco.com</a>

     Author: Ralph Droms
             <a href="mailto:rdroms@gmail.com">rdroms@gmail.com</a>

     Author: Dan Romascanu
             <a href="mailto:dromasca@gmail.com">dromasca@gmail.com</a>
    &quot;;
  description
    &quot;Sample extension to a MUD module to indicate a need
     for DETNET support.&quot;;

  revision 2019-01-28 {
    description
      &quot;Initial revision.&quot;;
    reference
      &quot;<a href="/doc/html/rfc8520">RFC 8520</a>: Manufacturer Usage Description
       Specification&quot;;
  }

  augment &quot;/ietf-mud:mud&quot; {
    description
      &quot;This adds a simple extension for a manufacturer
        to indicate whether DETNET is required by a
       device.&quot;;
    leaf is-detnet-required {
      type boolean;
      description
        &quot;This value will equal &#x27;true&#x27; if a device requires
<span class="grey"><a href="/doc/html/rfc8520">RFC 8520</a>             Manufacturer Usage Descriptions          March 2019</span>

            DETNET to properly function.&quot;;
       }
     }
   }
