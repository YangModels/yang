module ietf-datastores {
  yang-version 1.1;
  namespace &quot;urn:ietf:params:xml:ns:yang:ietf-datastores&quot;;
  prefix ds;

  organization
    &quot;IETF Network Modeling (NETMOD) Working Group&quot;;

  contact
    &quot;WG Web:   &lt;<a href="https://datatracker.ietf.org/wg/netmod/">https://datatracker.ietf.org/wg/netmod/</a>&gt;

     WG List:  &lt;mailto:<a href="mailto:netmod@ietf.org">netmod@ietf.org</a>&gt;

     Author:   Martin Bjorklund
               &lt;mailto:<a href="mailto:mbj@tail-f.com">mbj@tail-f.com</a>&gt;

     Author:   Juergen Schoenwaelder
               &lt;mailto:<a href="mailto:j.schoenwaelder@jacobs-university.de">j.schoenwaelder@jacobs-university.de</a>&gt;

     Author:   Phil Shafer
               &lt;mailto:<a href="mailto:phil@juniper.net">phil@juniper.net</a>&gt;

     Author:   Kent Watsen
               &lt;mailto:<a href="mailto:kwatsen@juniper.net">kwatsen@juniper.net</a>&gt;

     Author:   Rob Wilton
               &lt;<a href="mailto:rwilton@cisco.com">rwilton@cisco.com</a>&gt;&quot;;

  description
    &quot;This YANG module defines a set of identities for identifying
     datastores.

     Copyright (c) 2018 IETF Trust and the persons identified as
     authors of the code.  All rights reserved.

     Redistribution and use in source and binary forms, with or
     without modification, is permitted pursuant to, and subject to
     the license terms contained in, the Simplified BSD License set
     forth in <a href="#section-4">Section 4</a>.c of the IETF Trust&#x27;s Legal Provisions
     Relating to IETF Documents
     (<a href="https://trustee.ietf.org/license-info">https://trustee.ietf.org/license-info</a>).

<span class="grey"><a href="/doc/html/rfc8342">RFC 8342</a>                          NMDA                        March 2018</span>

        This version of this YANG module is part of <a href="/doc/html/rfc8342">RFC 8342</a>
        (<a href="https://www.rfc-editor.org/info/rfc8342">https://www.rfc-editor.org/info/rfc8342</a>); see the RFC itself
        for full legal notices.&quot;;

     revision 2018-02-14 {
       description
         &quot;Initial revision.&quot;;
       reference
         &quot;<a href="/doc/html/rfc8342">RFC 8342</a>: Network Management Datastore Architecture (NMDA)&quot;;
     }

     /*
      * Identities
      */

     identity datastore {
       description
         &quot;Abstract base identity for datastore identities.&quot;;
     }

     identity conventional {
       base datastore;
       description
         &quot;Abstract base identity for conventional configuration
          datastores.&quot;;
     }

     identity running {
       base conventional;
       description
         &quot;The running configuration datastore.&quot;;
     }

     identity candidate {
       base conventional;
       description
         &quot;The candidate configuration datastore.&quot;;
     }

     identity startup {
       base conventional;
       description
         &quot;The startup configuration datastore.&quot;;
     }

<span class="grey"><a href="/doc/html/rfc8342">RFC 8342</a>                          NMDA                        March 2018</span>

     identity intended {
       base conventional;
       description
         &quot;The intended configuration datastore.&quot;;
     }

     identity dynamic {
       base datastore;
       description
         &quot;Abstract base identity for dynamic configuration datastores.&quot;;
     }

     identity operational {
       base datastore;
       description
         &quot;The operational state datastore.&quot;;
     }

     /*
      * Type definitions
      */

     typedef datastore-ref {
       type identityref {
         base datastore;
       }
       description
         &quot;A datastore identity reference.&quot;;
     }
   }
