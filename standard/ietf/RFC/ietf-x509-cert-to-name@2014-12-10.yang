module ietf-x509-cert-to-name {

  namespace &quot;urn:ietf:params:xml:ns:yang:ietf-x509-cert-to-name&quot;;
  prefix x509c2n;

  import ietf-yang-types {
    prefix yang;
  }

  organization
    &quot;IETF NETMOD (NETCONF Data Modeling Language) Working Group&quot;;

  contact
    &quot;WG Web:   &lt;<a href="https://tools.ietf.org/wg/netmod/">http://tools.ietf.org/wg/netmod/</a>&gt;
     WG List:  &lt;mailto:<a href="mailto:netmod@ietf.org">netmod@ietf.org</a>&gt;

     WG Chair: Thomas Nadeau
               &lt;mailto:<a href="mailto:tnadeau@lucidvision.com">tnadeau@lucidvision.com</a>&gt;

     WG Chair: Juergen Schoenwaelder
               &lt;mailto:<a href="mailto:j.schoenwaelder@jacobs-university.de">j.schoenwaelder@jacobs-university.de</a>&gt;

     Editor:   Martin Bjorklund
               &lt;mailto:<a href="mailto:mbj@tail-f.com">mbj@tail-f.com</a>&gt;

     Editor:   Juergen Schoenwaelder
               &lt;mailto:<a href="mailto:j.schoenwaelder@jacobs-university.de">j.schoenwaelder@jacobs-university.de</a>&gt;&quot;;

  description
    &quot;This module contains a collection of YANG definitions for
     extracting a name from an X.509 certificate.
<span class="grey"><a href="/doc/html/rfc7407">RFC 7407</a>         YANG Data Model for SNMP Configuration    December 2014</span>

        The algorithm used to extract a name from an X.509 certificate
        was first defined in <a href="/doc/html/rfc6353">RFC 6353</a>.

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc7407">RFC 7407</a>; see
        the RFC itself for full legal notices.&quot;;

     reference
       &quot;<a href="/doc/html/rfc6353">RFC 6353</a>: Transport Layer Security (TLS) Transport Model for
          the Simple Network Management Protocol (SNMP)&quot;;

     revision 2014-12-10 {
       description
         &quot;Initial revision.&quot;;
       reference
         &quot;<a href="/doc/html/rfc7407">RFC 7407</a>: A YANG Data Model for SNMP Configuration&quot;;

     }

     typedef tls-fingerprint {
       type yang:hex-string {
         pattern &#x27;([0-9a-fA-F]){2}(:([0-9a-fA-F]){2}){0,254}&#x27;;
       }
       description
        &quot;A fingerprint value that can be used to uniquely reference
         other data of potentially arbitrary length.

         A tls-fingerprint value is composed of a 1-octet hashing
         algorithm identifier followed by the fingerprint value.  The
         first octet value identifying the hashing algorithm is taken
         from the IANA &#x27;TLS HashAlgorithm Registry&#x27; (<a href="/doc/html/rfc5246">RFC 5246</a>).  The
         remaining octets are filled using the results of the hashing
         algorithm.&quot;;
       reference
        &quot;<a href="/doc/html/rfc6353">RFC 6353</a>: Transport Layer Security (TLS) Transport Model
           for the Simple Network Management Protocol (SNMP).
           SNMP-TLS-TM-MIB.SnmpTLSFingerprint&quot;;
     }

<span class="grey"><a href="/doc/html/rfc7407">RFC 7407</a>         YANG Data Model for SNMP Configuration    December 2014</span>

     /* Identities */

     identity cert-to-name {
       description
         &quot;Base identity for algorithms to derive a name from a
          certificate.&quot;;
     }

     identity specified {
       base cert-to-name;
       description
         &quot;Directly specifies the name to be used for the certificate.
          The value of the leaf &#x27;name&#x27; in the cert-to-name list is
          used.&quot;;
       reference
         &quot;<a href="/doc/html/rfc6353">RFC 6353</a>: Transport Layer Security (TLS) Transport Model
            for the Simple Network Management Protocol (SNMP).
            SNMP-TLS-TM-MIB.snmpTlstmCertSpecified&quot;;
     }

     identity san-rfc822-name {
       base cert-to-name;
       description
         &quot;Maps a subjectAltName&#x27;s rfc822Name to a name.  The local part
          of the rfc822Name is passed unaltered, but the host-part of
          the name must be passed in lowercase.  For example, the
          rfc822Name field <a href="mailto:FooBar@Example.COM">FooBar@Example.COM</a> is mapped to name
          <a href="mailto:FooBar@example.com">FooBar@example.com</a>.&quot;;
       reference
         &quot;<a href="/doc/html/rfc6353">RFC 6353</a>: Transport Layer Security (TLS) Transport Model
            for the Simple Network Management Protocol (SNMP).
            SNMP-TLS-TM-MIB.snmpTlstmCertSANRFC822Name&quot;;
     }

     identity san-dns-name {
       base cert-to-name;
       description
         &quot;Maps a subjectAltName&#x27;s dNSName to a name after first
          converting it to all lowercase (<a href="/doc/html/rfc5280">RFC 5280</a> does not specify
          converting to lowercase, so this involves an extra step).
          This mapping results in a 1:1 correspondence between
          subjectAltName dNSName values and the name values.&quot;;
       reference
         &quot;<a href="/doc/html/rfc6353">RFC 6353</a>: Transport Layer Security (TLS) Transport Model
            for the Simple Network Management Protocol (SNMP).
            SNMP-TLS-TM-MIB.snmpTlstmCertSANDNSName&quot;;
     }

<span class="grey"><a href="/doc/html/rfc7407">RFC 7407</a>         YANG Data Model for SNMP Configuration    December 2014</span>

     identity san-ip-address {
       base cert-to-name;
       description
         &quot;Maps a subjectAltName&#x27;s iPAddress to a name by
          transforming the binary-encoded address as follows:

            1) for IPv4, the value is converted into a
               decimal-dotted quad address (e.g., &#x27;192.0.2.1&#x27;).

            2) for IPv6 addresses, the value is converted into a
               32-character, all-lowercase hexadecimal string
               without any colon separators.

          This mapping results in a 1:1 correspondence between
          subjectAltName iPAddress values and the name values.&quot;;
       reference
         &quot;<a href="/doc/html/rfc6353">RFC 6353</a>: Transport Layer Security (TLS) Transport Model
            for the Simple Network Management Protocol (SNMP).
            SNMP-TLS-TM-MIB.snmpTlstmCertSANIpAddress&quot;;
     }

     identity san-any {
       base cert-to-name;
       description
         &quot;Maps any of the following fields using the corresponding
          mapping algorithms:

            +------------+-----------------+
            | Type       | Algorithm       |
            |------------+-----------------|
            | rfc822Name | san-rfc822-name |
            | dNSName    | san-dns-name    |
            | iPAddress  | san-ip-address  |
            +------------+-----------------+

          The first matching subjectAltName value found in the
          certificate of the above types MUST be used when deriving
          the name.  The mapping algorithm specified in the
          &#x27;Algorithm&#x27; column MUST be used to derive the name.

          This mapping results in a 1:1 correspondence between
          subjectAltName values and name values.  The three sub-mapping
          algorithms produced by this combined algorithm cannot produce
          conflicting results between themselves.&quot;;
       reference
         &quot;<a href="/doc/html/rfc6353">RFC 6353</a>: Transport Layer Security (TLS) Transport Model
            for the Simple Network Management Protocol (SNMP).
            SNMP-TLS-TM-MIB.snmpTlstmCertSANAny&quot;;
<span class="grey"><a href="/doc/html/rfc7407">RFC 7407</a>         YANG Data Model for SNMP Configuration    December 2014</span>

     }

     identity common-name {
       base cert-to-name;
       description
         &quot;Maps a certificate&#x27;s CommonName to a name after converting
          it to a UTF-8 encoding.  The usage of CommonNames is
          deprecated, and users are encouraged to use subjectAltName
          mapping methods instead.  This mapping results in a 1:1
          correspondence between certificate CommonName values and name
          values.&quot;;
       reference
         &quot;<a href="/doc/html/rfc6353">RFC 6353</a>: Transport Layer Security (TLS) Transport Model
            for the Simple Network Management Protocol (SNMP).
            SNMP-TLS-TM-MIB.snmpTlstmCertCommonName&quot;;
     }

     /*
      * Groupings
      */

     grouping cert-to-name {
       description
         &quot;Defines nodes for mapping certificates to names.  Modules
          that use this grouping should describe how the resulting
          name is used.&quot;;

       list cert-to-name {
         key id;
         description
           &quot;This list defines how certificates are mapped to names.
            The name is derived by considering each cert-to-name
            list entry in order.  The cert-to-name entry&#x27;s fingerprint
            determines whether the list entry is a match:

            1) If the cert-to-name list entry&#x27;s fingerprint value
               matches that of the presented certificate, then consider
               the list entry a successful match.

            2) If the cert-to-name list entry&#x27;s fingerprint value
               matches that of a locally held copy of a trusted CA
               certificate, and that CA certificate was part of the CA
               certificate chain to the presented certificate, then
               consider the list entry a successful match.

           Once a matching cert-to-name list entry has been found, the
           map-type is used to determine how the name associated with
           the certificate should be determined.  See the map-type
<span class="grey"><a href="/doc/html/rfc7407">RFC 7407</a>         YANG Data Model for SNMP Configuration    December 2014</span>

           leaf&#x27;s description for details on determining the name value.
           If it is impossible to determine a name from the cert-to-name
           list entry&#x27;s data combined with the data presented in the
           certificate, then additional cert-to-name list entries MUST
           be searched to look for another potential match.

           Security administrators are encouraged to make use of
           certificates with subjectAltName fields that can be mapped to
           names so that a single root CA certificate can allow all
           child certificates&#x27; subjectAltName fields to map directly to
           a name via a 1:1 transformation.&quot;;
         reference
          &quot;<a href="/doc/html/rfc6353">RFC 6353</a>: Transport Layer Security (TLS) Transport Model
             for the Simple Network Management Protocol (SNMP).
             SNMP-TLS-TM-MIB.snmpTlstmCertToTSNEntry&quot;;

         leaf id {
           type uint32;
           description
             &quot;The id specifies the order in which the entries in the
              cert-to-name list are searched.  Entries with lower
              numbers are searched first.&quot;;
           reference
             &quot;<a href="/doc/html/rfc6353">RFC 6353</a>: Transport Layer Security (TLS) Transport Model
                for the Simple Network Management Protocol
                (SNMP).
                SNMP-TLS-TM-MIB.snmpTlstmCertToTSNID&quot;;
         }

         leaf fingerprint {
           type x509c2n:tls-fingerprint;
           mandatory true;
           description
             &quot;Specifies a value with which the fingerprint of the
              full certificate presented by the peer is compared.  If
              the fingerprint of the full certificate presented by the
              peer does not match the fingerprint configured, then the
              entry is skipped, and the search for a match continues.&quot;;
           reference
             &quot;<a href="/doc/html/rfc6353">RFC 6353</a>: Transport Layer Security (TLS) Transport Model
                for the Simple Network Management Protocol
                (SNMP).
                SNMP-TLS-TM-MIB.snmpTlstmCertToTSNFingerprint&quot;;
         }

         leaf map-type {
           type identityref {
             base cert-to-name;
<span class="grey"><a href="/doc/html/rfc7407">RFC 7407</a>         YANG Data Model for SNMP Configuration    December 2014</span>

           }
           mandatory true;
           description
             &quot;Specifies the algorithm used to map the certificate
              presented by the peer to a name.

              Mappings that need additional configuration objects should
              use the &#x27;when&#x27; statement to make them conditional based on
              the map-type.&quot;;
           reference
             &quot;<a href="/doc/html/rfc6353">RFC 6353</a>: Transport Layer Security (TLS) Transport Model
                for the Simple Network Management Protocol
                (SNMP).
                SNMP-TLS-TM-MIB.snmpTlstmCertToTSNMapType&quot;;
         }

         leaf name {
           when &quot;../map-type = &#x27;x509c2n:specified&#x27;&quot;;
           type string;
           mandatory true;
           description
             &quot;Directly specifies the NETCONF username when the
              map-type is &#x27;specified&#x27;.&quot;;
           reference
             &quot;<a href="/doc/html/rfc6353">RFC 6353</a>: Transport Layer Security (TLS) Transport Model
                for the Simple Network Management Protocol
                (SNMP).
                SNMP-TLS-TM-MIB.snmpTlstmCertToTSNData&quot;;
         }
       }
     }
   }
