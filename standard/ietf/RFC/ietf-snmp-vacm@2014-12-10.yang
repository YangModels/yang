submodule ietf-snmp-vacm {

  belongs-to ietf-snmp {
    prefix snmp;
  }

  include ietf-snmp-common;

  organization
    &quot;IETF NETMOD (NETCONF Data Modeling Language) Working Group&quot;;

  contact
    &quot;WG Web:   &lt;<a href="https://tools.ietf.org/wg/netmod/">http://tools.ietf.org/wg/netmod/</a>&gt;
     WG List:  &lt;mailto:<a href="mailto:netmod@ietf.org">netmod@ietf.org</a>&gt;

     WG Chair: Thomas Nadeau
               &lt;mailto:<a href="mailto:tnadeau@lucidvision.com">tnadeau@lucidvision.com</a>&gt;

<span class="grey"><a href="/doc/html/rfc7407">RFC 7407</a>         YANG Data Model for SNMP Configuration    December 2014</span>

        WG Chair: Juergen Schoenwaelder
                  &lt;mailto:<a href="mailto:j.schoenwaelder@jacobs-university.de">j.schoenwaelder@jacobs-university.de</a>&gt;

        Editor:   Martin Bjorklund
                  &lt;mailto:<a href="mailto:mbj@tail-f.com">mbj@tail-f.com</a>&gt;

        Editor:   Juergen Schoenwaelder
                  &lt;mailto:<a href="mailto:j.schoenwaelder@jacobs-university.de">j.schoenwaelder@jacobs-university.de</a>&gt;&quot;;

     description
       &quot;This submodule contains a collection of YANG definitions
        for configuring the View-based Access Control Model (VACM)
        of SNMP.

        Copyright (c) 2014 IETF Trust and the persons identified as
        authors of the code.  All rights reserved.

        Redistribution and use in source and binary forms, with or
        without modification, is permitted pursuant to, and subject
        to the license terms contained in, the Simplified BSD License
        set forth in <a href="#section-4">Section 4</a>.c of the IETF Trust&#x27;s Legal Provisions
        Relating to IETF Documents
        (<a href="https://trustee.ietf.org/license-info">http://trustee.ietf.org/license-info</a>).

        This version of this YANG module is part of <a href="/doc/html/rfc7407">RFC 7407</a>; see
        the RFC itself for full legal notices.&quot;;

     reference
       &quot;<a href="/doc/html/rfc3415">RFC 3415</a>: View-based Access Control Model (VACM) for the
          Simple Network Management Protocol (SNMP)&quot;;

     revision 2014-12-10 {
       description
         &quot;Initial revision.&quot;;
       reference
         &quot;<a href="/doc/html/rfc7407">RFC 7407</a>: A YANG Data Model for SNMP Configuration&quot;;
     }

     typedef view-name {
       type snmp:identifier;
       description
         &quot;The view-name type represents an SNMP VACM view name.&quot;;
     }

     typedef group-name {
       type snmp:identifier;
       description
         &quot;The group-name type represents an SNMP VACM group name.&quot;;
<span class="grey"><a href="/doc/html/rfc7407">RFC 7407</a>         YANG Data Model for SNMP Configuration    December 2014</span>

     }

     augment /snmp:snmp {

       container vacm {
         description
           &quot;Configuration of the View-based Access Control Model.&quot;;

         list group {
           key name;
           description
             &quot;VACM groups.

              This data model has a different structure than the MIB.
              Groups are explicitly defined in this list, and group
              members are defined in the &#x27;member&#x27; list (mapped to
              vacmSecurityToGroupTable), and access for the group is
              defined in the &#x27;access&#x27; list (mapped to
              vacmAccessTable).&quot;;
           reference
             &quot;<a href="/doc/html/rfc3415">RFC 3415</a>: View-based Access Control Model (VACM) for the
                Simple Network Management Protocol (SNMP).
                SNMP-VIEW-BASED-ACM-MIB.vacmSecurityToGroupTable
                SNMP-VIEW-BASED-ACM-MIB.vacmAccessTable&quot;;

           leaf name {
             type group-name;
             description
               &quot;The name of this VACM group.&quot;;
             reference
               &quot;<a href="/doc/html/rfc3415">RFC 3415</a>: View-based Access Control Model (VACM) for the
                  Simple Network Management Protocol (SNMP).
                  SNMP-VIEW-BASED-ACM-MIB.vacmGroupName&quot;;
           }

           list member {
             key &quot;security-name&quot;;
             description
               &quot;A member of this VACM group.

                A specific combination of security-name and
                security-model MUST NOT be present in more than
                one group.&quot;;
             reference
               &quot;<a href="/doc/html/rfc3415">RFC 3415</a>: View-based Access Control Model (VACM) for the
                  Simple Network Management Protocol (SNMP).
                  SNMP-VIEW-BASED-ACM-MIB.vacmSecurityToGroupTable&quot;;

<span class="grey"><a href="/doc/html/rfc7407">RFC 7407</a>         YANG Data Model for SNMP Configuration    December 2014</span>

             leaf security-name {
               type snmp:security-name;
               description
                 &quot;The securityName of a group member.&quot;;
               reference
                 &quot;<a href="/doc/html/rfc3415">RFC 3415</a>: View-based Access Control Model (VACM) for
                    the Simple Network Management Protocol (SNMP).
                    SNMP-VIEW-BASED-ACM-MIB.vacmSecurityName&quot;;
             }

             leaf-list security-model {
               type snmp:security-model;
               min-elements 1;
               description
                 &quot;The security models under which this security-name
                  is a member of this group.&quot;;
               reference
                 &quot;<a href="/doc/html/rfc3415">RFC 3415</a>: View-based Access Control Model (VACM) for
                    the Simple Network Management Protocol (SNMP).
                    SNMP-VIEW-BASED-ACM-MIB.vacmSecurityModel&quot;;
             }
           }

           list access {
             key &quot;context security-model security-level&quot;;
             description
               &quot;Definition of access right for groups.&quot;;
             reference
               &quot;<a href="/doc/html/rfc3415">RFC 3415</a>: View-based Access Control Model (VACM) for
                  the Simple Network Management Protocol (SNMP).
                  SNMP-VIEW-BASED-ACM-MIB.vacmAccessTable&quot;;

             leaf context {
               type snmp:context-name;
               description
                 &quot;The context (prefix) under which the access rights
                  apply.&quot;;
               reference
                 &quot;<a href="/doc/html/rfc3415">RFC 3415</a>: View-based Access Control Model (VACM) for
                    the Simple Network Management Protocol (SNMP).
                    SNMP-VIEW-BASED-ACM-MIB.vacmAccessContextPrefix&quot;;
             }

             leaf context-match {
               type enumeration {
                 enum exact { value 1; }
                 enum prefix { value 2; }
               }
<span class="grey"><a href="/doc/html/rfc7407">RFC 7407</a>         YANG Data Model for SNMP Configuration    December 2014</span>

               default exact;
               reference
                 &quot;<a href="/doc/html/rfc3415">RFC 3415</a>: View-based Access Control Model (VACM) for
                    the Simple Network Management Protocol (SNMP).
                    SNMP-VIEW-BASED-ACM-MIB.vacmAccessContextMatch&quot;;
             }

             leaf security-model {
               type snmp:security-model-or-any;
               description
                 &quot;The security model under which the access rights
                 apply.&quot;;
               reference
                 &quot;<a href="/doc/html/rfc3415">RFC 3415</a>: View-based Access Control Model (VACM) for
                    the Simple Network Management Protocol (SNMP).
                    SNMP-VIEW-BASED-ACM-MIB.vacmAccessSecurityModel&quot;;
             }

             leaf security-level {
               type snmp:security-level;
               description
                 &quot;The minimum security level under which the access
                  rights apply.&quot;;
               reference
                 &quot;<a href="/doc/html/rfc3415">RFC 3415</a>: View-based Access Control Model (VACM) for
                    the Simple Network Management Protocol (SNMP).
                    SNMP-VIEW-BASED-ACM-MIB.vacmAccessSecurityLevel&quot;;
             }

             leaf read-view {
               type view-name;
               description
                 &quot;The name of the MIB view of the SNMP context
                  authorizing read access.  If this leaf does not
                  exist in a configuration, it maps to a zero-length
                  vacmAccessReadViewName.

                  Implementations MAY restrict the values of this
                  leaf to be one of the available values of
                  /snmp/vacm/view/name in a valid configuration.&quot;;
               reference
                 &quot;<a href="/doc/html/rfc3415">RFC 3415</a>: View-based Access Control Model (VACM) for
                    the Simple Network Management Protocol (SNMP).
                    SNMP-VIEW-BASED-ACM-MIB.vacmAccessReadViewName&quot;;
             }

             leaf write-view {
               type view-name;
<span class="grey"><a href="/doc/html/rfc7407">RFC 7407</a>         YANG Data Model for SNMP Configuration    December 2014</span>

               description
                 &quot;The name of the MIB view of the SNMP context
                  authorizing write access.  If this leaf does not
                  exist in a configuration, it maps to a zero-length
                  vacmAccessWriteViewName.

                  Implementations MAY restrict the values of this
                  leaf to be one of the available values of
                  /snmp/vacm/view/name in a valid configuration.&quot;;
               reference
                 &quot;<a href="/doc/html/rfc3415">RFC 3415</a>: View-based Access Control Model (VACM) for
                    the Simple Network Management Protocol (SNMP).
                    SNMP-VIEW-BASED-ACM-MIB.vacmAccessWriteViewName&quot;;
             }

             leaf notify-view {
               type view-name;
               description
                 &quot;The name of the MIB view of the SNMP context
                  authorizing notify access.  If this leaf does not
                  exist in a configuration, it maps to a zero-length
                  vacmAccessNotifyViewName.

                  Implementations MAY restrict the values of this
                  leaf to be one of the available values of
                  /snmp/vacm/view/name in a valid configuration.&quot;;
               reference
                 &quot;<a href="/doc/html/rfc3415">RFC 3415</a>: View-based Access Control Model (VACM) for
                      the Simple Network Management Protocol (SNMP).
                      SNMP-VIEW-BASED-ACM-MIB.vacmAccessNotifyViewName&quot;;
             }
           }
         }

         list view {
           key name;
           description
             &quot;Definition of MIB views.&quot;;
           reference
             &quot;<a href="/doc/html/rfc3415">RFC 3415</a>: View-based Access Control Model (VACM) for
                the Simple Network Management Protocol (SNMP).
                SNMP-VIEW-BASED-ACM-MIB.vacmViewTreeFamilyTable&quot;;

           leaf name {
             type view-name;
             description
               &quot;The name of this VACM MIB view.&quot;;

<span class="grey"><a href="/doc/html/rfc7407">RFC 7407</a>         YANG Data Model for SNMP Configuration    December 2014</span>

             reference
               &quot;<a href="/doc/html/rfc3415">RFC 3415</a>: View-based Access Control Model (VACM) for
                  the Simple Network Management Protocol (SNMP).
                  SNMP-VIEW-BASED-ACM-MIB.vacmViewTreeFamilyName&quot;;
           }

           leaf-list include {
             type snmp:wildcard-object-identifier;
             description
               &quot;A family of subtrees included in this MIB view.&quot;;
             reference
                 &quot;<a href="/doc/html/rfc3415">RFC 3415</a>: View-based Access Control Model (VACM) for
                    the Simple Network Management Protocol (SNMP).
                    SNMP-VIEW-BASED-ACM-MIB.vacmViewTreeFamilySubtree
                    SNMP-VIEW-BASED-ACM-MIB.vacmViewTreeFamilyMask
                    SNMP-VIEW-BASED-ACM-MIB.vacmViewTreeFamilyType&quot;;
           }

           leaf-list exclude {
             type snmp:wildcard-object-identifier;
             description
               &quot;A family of subtrees excluded from this MIB view.&quot;;
             reference
               &quot;<a href="/doc/html/rfc3415">RFC 3415</a>: View-based Access Control Model (VACM) for
                  the Simple Network Management Protocol (SNMP).
                  SNMP-VIEW-BASED-ACM-MIB.vacmViewTreeFamilySubtree
                  SNMP-VIEW-BASED-ACM-MIB.vacmViewTreeFamilyMask
                  SNMP-VIEW-BASED-ACM-MIB.vacmViewTreeFamilyType&quot;;
           }
         }
       }
     }
   }
