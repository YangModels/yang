module ietf-bfd {
  namespace "urn:ietf:params:xml:ns:yang:ietf-bfd";
  // replace with IANA namespace when assigned
  prefix "bfd";
  import ietf-interfaces {
    prefix "if";
  }
  import ietf-inet-types {
    prefix "inet";
  }
  import ietf-yang-types {
    prefix "yang";
  }
  import ietf-routing {
    prefix "rt";
  }
  organization "IETF BFD Working Group";
  contact
    "WG Web:   <http://tools.ietf.org/wg/bfd>
     WG List:  <rtg-bfd@ietf.org>
     WG Chair: Jeff Haas
     WG Chair: Nobo Akiya
     Editor:   Lianshu Zheng and Reshad Rahman";
  description
    "This module contains the YANG definition for BFD parameters as
     per RFC5880, RFC5881 and RFC5883";
  revision 2015-07-01 {
    description "Initial revision.";
    reference "RFC XXXX: A YANG data model for BFD";
  }
  identity bfd {
    base "rt:routing-protocol";
    description "BFD protocol";
  }
  typedef discriminator {
    type uint32 {
      range 1..4294967295;
    }
    description "BFD discriminator";
  }
  typedef diagnostic {
    type enumeration {
      enum none {
        value 0;
        description "None";
      }
      enum controlExpiry {
        value 1;
        description "Control timer expiry";
      }
      enum echoFailed {
        value 2;
        description "Echo failure";
      }
      enum nborDown {
        value 3;
        description "Neighbor down";
      }
      enum fwdingReset {
        value 4;
        description "Forwarding reset";
      }
      enum pathDown {
        value 5;
        description "Path down";
      }
      enum concPathDown {
        value 6;
        description "Concatenated path down";
      }
      enum adminDown {
        value 7;
        description "Admin down";
      }
      enum reverseConcPathDown {
        value 8;
        description "Reverse concatenated path down";
      }
    }
    description "BFD diagnostic";
  }
  typedef state {
    type enumeration {
      enum adminDown {
        value 0;
        description "admindown";
      }
      enum down {
        value 1;
        description "down";
      }
      enum init {
        value 2;
        description "init";
      }
      enum up {
        value 3;
        description "up";
      }
    }
    description "BFD state";
  }
  typedef multiplier {
    type uint8 {
      range 1..255;
    }
    description "Multiplier";
  }
  typedef ttl {
    type uint8 {
      range 1..255;
    }
    description "Time To Live";
  }
  typedef bfd-session-type {
    type enumeration {
      enum ip-single-hop {
        description "IP single hop";
      }
      enum ip-multi-hop {
        description "IP multi hop";
      }
      enum te-tunnel {
        description "Traffic Engineering tunnes";
      }
      enum ldp-lsp {
        description "LDP Label Switched Path";
      }
      enum lag {
        description "Micro-BFD on LAG member links";
      }
    }
    description
      "BFD session type, this indicates the path type that BFD is
       running on";
  }
  typedef bfd-auth-algorithm {
    type enumeration {
      enum simple-password {
        description
          "Simple password";
      }
      enum keyed-md5 {
        description
          "Keyed message Digest 5";
      }
      enum meticulous-keyed-md5 {
        description
          "Meticulous keyed message Digest 5";
      }
      enum keyed-sha-1 {
        description
          "Keyed secure hash algorithm (SHA1) ";
      }
      enum meticulous-keyed-sha-1 {
        description
          "Meticulous keyed secure hash algorithm (SHA1) ";
      }
    }
    description "Authentication algorithm";
  }
  feature bfd-interface-config {
    description "BFD per-interface config supported";
  }
  feature bfd-authentication {
    description "BFD authentication supported";
  }
  grouping bfd-grouping-base-cfg-parms {
    description "BFD grouping for base config parameters";
    leaf local-multiplier {
      type multiplier;
      default 3;
      description "Multiplier transmitted by local system";
    }
    choice interval-config-type {
      description
        "Two interval values or 1 value used for both tx and rx";
      case tx-rx-intervals {
        leaf desired-min-tx-interval {
          type uint32;
          units microseconds;
          mandatory true;
          description
            "Desired minimum transmit interval of control packets";
        }
        leaf required-min-rx-interval {
          type uint32;
          units microseconds;
          mandatory true;
          description
            "Required minimum receive interval of control packets";
        }
      }
      case single-interval {
        leaf min-interval {
          type uint32;
          units microseconds;
          mandatory true;
          description
            "Desired minimum transmit interval and required " +
            "minimum receive interval of control packets";
        }
      }
    }
  }
  grouping bfd-grouping-common-cfg-parms {
    description "BFD grouping for common config parameters";
    uses bfd-grouping-base-cfg-parms;
    leaf demand-enabled {
      type boolean;
      default false;
      description "To enbale demand mode";
    }
    leaf enable-authentication {
      type boolean;
      default false;
      description
        "If set, the Authentication Section is present and the
         session is to be authenticated (see RFC5880 section 6.7
         for details).";
    }
    container authentication-parms {
      if-feature bfd-authentication;
      description "Parameters for authentication";
      leaf key-chain-name {
        type string;
        must "../algorithm" {
          error-message
            "May not be configured without algorithm";
          description "Requires algorithm";
        }
        description
          "Key chain name";
      }
      leaf algorithm {
        type bfd-auth-algorithm;
        must "../key-chain" {
          error-message
            "May not be configured without key-chain";
          description "Requires key-chain";
        }
        description "Authentication algorithm to be used";
      }
    }
  }
  grouping bfd-grouping-echo-cfg-parms {
    description "BFD grouping for echo config parameters";
    leaf desired-min-echo-tx-interval {
      type uint32;
      units microseconds;
      default 0;
      description "Desired minumum transmit interval for echo";
    }
    leaf required-min-echo-rx-interval {
      type uint32;
      units microseconds;
      default 0;
      description "Required minimum receive interval for echo";
    }
  }
  grouping bfd-client-base-cfg-parms {
    description
      "BFD grouping for base config parameters which could be used
       by a protocol which is a client of BFD";
    container bfd-cfg {
      description "BFD configuration";
      leaf enabled {
        type boolean;
        default false;
        description "True if BFD is enabled";
      }
      uses bfd-grouping-base-cfg-parms;
    }
  }
  grouping bfd-all-session {
    description "BFD session operational information";
    leaf session-type {
      type bfd-session-type;
      description
        "BFD session type, this indicates the path type that BFD is
        running on";
    }
    leaf local-discriminator {
      type discriminator;
      description "Local discriminator";
    }
    leaf remote-discriminator {
      type discriminator;
      description "Remote discriminator";
    }
    leaf remote-multiplier {
      type multiplier;
      description "Remote multiplier";
    }
    leaf out-interface {
      type if:interface-ref;
      description "Outgoing physical interface name";
    }
    leaf demand-capability {
      type boolean;
      description "Local demand mode capability";
    }
    leaf source-port {
      type inet:port-number;
      description "Source UDP port";
    }
    leaf dest-port {
      type inet:port-number;
      description "Destination UDP port";
    }
    list session-running {
      description "BFD session running information";
      leaf session-index {
        type uint32;
        description
          "An index used to uniquely identify BFD sessions";
      }
      leaf local-state {
        type state;
        description "Local state";
      }
      leaf remote-state {
        type state;
        description "Remote state";
      }
      leaf local-diagnostic {
        type diagnostic;
        description "Local diagnostic";
      }
      leaf remote-diagnostic {
        type diagnostic;
        description "Remote diagnostic";
      }
      leaf detection-mode {
        type enumeration {
          enum async-with-echo {
            value "1";
            description "Async with echo";
          }
          enum async-without-echo {
            value "2";
            description "Async without echo";
          }
          enum demand-with-echo {
            value "3";
            description "Demand with echo";
          }
          enum demand-without-echo {
            value "4";
            description "Demand without echo";
          }
        }
        description "Detection mode";
      }
      leaf negotiated-tx-interval {
        type uint32;
        units microseconds;
        description "Negotiated transmit interval";
      }
      leaf negotiated-rx-interval {
        type uint32;
        units microseconds;
        description "Negotiated receive interval";
      }
      leaf negotiated-echo-tx-interval {
        type uint32;
        units microseconds;
        description "Negotiated echo transmit interval";
      }
      leaf detection-time {
        type uint32;
        units microseconds;
        description "Detection time";
      }
    }
    list sesssion-statistics {
      description "BFD session statistics";
      leaf create-time {
        type yang:date-and-time;
        description
          "Time and date when session was created";
      }
      leaf last-down-time {
        type yang:date-and-time;
        description
          "Time and date of last time the session went down";
      }
      leaf last-up-time {
        type yang:date-and-time;
        description
          "Time and date of last time the session went up";
      }
      leaf down-count {
        type uint32;
        description "Session Down Count";
      }
      leaf admin-down-count {
        type uint32;
        description "Session Admin-Down Count";
      }
      leaf receive-packet-count {
        type uint64;
        description "Received Packet Count";
      }
      leaf send-packet-count {
        type uint64;
        description "Sent Packet Count";
      }
      leaf receive-bad-packet {
        type uint64;
        description "Received bad packet count";
      }
      leaf send-failed-packet {
        type uint64;
        description "Packet Failed to Send Count";
      }
    }
  }
  augment "/rt:routing/rt:routing-instance/rt:routing-protocols/"
    + "rt:routing-protocol" {
    when "rt:type = 'bfd:bfd'" {
      description
        "This augment is only valid for a protocol instance
        of BFD.";
    }
    description "BFD augmentation.";
    container bfd {
      description "BFD top-level container";
      container bfd-cfg {
        description "BFD configuration";
        container bfd-session-cfg {
          description "BFD session configuration";
          list session-ip-mh {
            key "source-addr dest-addr";
            description "List of IP multi-hop sessions";
            leaf source-addr {
              type inet:ip-address;
              description
                "Local IP address";
            }
            leaf dest-addr {
              type inet:ip-address;
              description
                "IP address of the peer";
            }
            leaf admin-down {
              type boolean;
              default false;
              description
                "Is the BFD session administratively down";
            }
            uses bfd-grouping-common-cfg-parms;
            leaf tx-ttl {
              type ttl;
              default 255;
              description "TTL of outgoing BFD control packets";
            }
            leaf rx-ttl {
              type ttl;
              mandatory true;
              description
                "Minimum allowed TTL value for incoming BFD control
                 packets";
            }
          }
        }
        list bfd-interface-cfg {
          if-feature bfd-interface-config;
          key interface;
          description "Per-interface BFD configuration";
          leaf interface {
            type if:interface-ref;
            description "Interface";
          }
          uses bfd-grouping-common-cfg-parms;
          uses bfd-grouping-echo-cfg-parms;
        }
      }
      container bfd-oper {
        config "false";
        description "BFD operational container";
        container bfd-session-statistics {
          description "BFD session counters";
          leaf ip-sh-session-num {
            type uint32;
            description "IP single hop session number";
          }
          leaf ip-mh-session-num {
            type uint32;
            description "IP multi hop session Number";
          }
          leaf total-session-num {
            type uint32;
            description "Total session number";
          }
          leaf session-up-num {
            type uint32;
            description "Session up number";
          }
          leaf sess-down-num {
            type uint32;
            description "Session down number";
          }
          leaf sess-admin-down-num {
            type uint32;
            description "Session admin-down number";
          }
        }
        container bfd-session-lists {
          description
            "Contains multiple session lists, one per type";
          list session-ip-sh {
            key "interface dest-addr";
            description "BFD IP single-hop sessions";
            leaf interface {
              type if:interface-ref;
              description
                "Interface on which the BFD session is running.";
            }
            leaf dest-addr {
              type inet:ip-address;
              description "BFD peer address";
            }
            leaf source-addr {
              type inet:ip-address;
              description "BFD source address";
            }
            uses bfd-all-session;
          }
          list session-ip-mh-group {
            key "source-addr dest-addr";
            description
              "BFD IP multi-hop group of sessions. A group of " +
              "sessions is between 1 source and 1 destination, " +
              "each session uses a different source UDP port for " +
              "ECMP.";
            leaf source-addr {
              type inet:ip-address;
              description "BFD source address";
            }
            leaf dest-addr {
              type inet:ip-address;
              description "BFD peer address";
            }
            list session-ip-mh {
              key "source-port";
              description
                "The BFD sessions between a source and a. " +
                "destination. Source UDP port is unique for " +
                "each session in the group.";
              leaf ttl {
                type ttl;
                description "TTL of outgoing packets";
              }
              uses bfd-all-session;
            }
          }
          list session-te-tunnel {
            key "tunnel-name";
            description "BFD over TE tunnel";
            leaf tunnel-name {
              type string;
              description "Name of TE tunnel";
            }
            uses bfd-all-session;
          }
          list session-ldp-lsp-group {
            key "ldp-fec";
            description
              "BFD over LDP LSP group of sessions. A group of " +
              "sessions is to one LDP FEC, each session uses a " +
              "different source UDP port for ECMP.";
            leaf ldp-fec {
              type inet:ip-prefix;
              description "LDP FEC";
            }
            list session-ldp-lsp {
              key "source-port";
              description
                "The BFD sessions on an LDP FEC. Source UDP " +
                "port is unique for each session in the group.";
              leaf ttl {
                type ttl;
                description "TTL of outgoing packets";
              }
              uses bfd-all-session;
            }
          }
          list session-lag {
            key "lag-name";
            description "A LAG interface on which BFD is running";
            leaf lag-name {
              type if:interface-ref ;
              description "Name of the LAG";
            }
            list session-lag-micro {
            key "member-link";
              description
                "Micro-BFD over LAG. This represents BFD " +
                "over one member link";
              leaf member-link {
                type if:interface-ref;
                description
                  "Member link on which micro-BFD is running";
              }
              uses bfd-all-session;
            }
          }
        }
      }
    }
  }
  grouping bfd-notification-parms {
    description
      "This group describes common parameters that will be sent " +
      "as part of BFD notification";
    leaf local-discr {
      type discriminator;
      description "BFD local discriminator";
    }
    leaf remote-discr {
      type discriminator;
      description "BFD remote discriminator";
    }
    leaf new-state {
      type state;
      description "Current BFD state";
    }
    leaf state-change-reason {
      type string;
      description "BFD state change reason";
    }
    leaf time-in-previous-state {
      type string;
      description
        "How long the BFD session was in the previous state";
    }
    leaf dest-addr {
      type inet:ip-address;
      description "BFD peer address";
    }
    leaf source-addr {
      type inet:ip-address;
      description "BFD local address";
    }
    leaf session-index {
      type uint32;
      description "An index used to uniquely identify BFD sessions";
    }
    leaf session-type {
      type bfd-session-type;
      description "BFD session type";
    }
  }
  notification bfd-singlehop-notification {
    description
      "Notification for BFD single-hop session state change. An " +
      "implementation may rate-limit notifications, e.g. when a" +
      "session is continuously changing state.";
    uses bfd-notification-parms;
    leaf interface {
      type if:interface-ref;
      description "Interface to which this BFD session belongs to";
    }
    leaf echo-enabled {
      type boolean;
      description "Was echo enabled for BFD";
    }
  }
  notification bfd-multihop-notification {
    description
      "Notification for BFD multi-hop session state change. An " +
      "implementation may rate-limit notifications, e.g. when a" +
      "session is continuously changing state.";
    uses bfd-notification-parms;
  }
  notification bfd-te-tunnel-notification {
    description
      "Notification for BFD over TE tunnel session state change. " +
      "An implementation may rate-limit notifications, e.g. " +
      "when a session is continuously changing state.";
    uses bfd-notification-parms;
    leaf tunnel-name {
      type string;
      description "TE tunnel to which this BFD session belongs to";
    }
  }
  notification bfd-ldp-lsp-notification {
    description
      "Notification for BFD over LDP LSP session state change. " +
      "An implementation may rate-limit notifications, e.g. " +
      "when a session is continuously changing state.";
    uses bfd-notification-parms;
    leaf ldp-fec {
      type inet:ip-prefix;
      description "LDP FEC";
    }
    leaf source-port {
      type inet:port-number;
      description "Source UDP port";
    }
  }
  notification bfd-lag-notification {
    description
      "Notification for BFD over LAG session state change. " +
      "An implementation may rate-limit notifications, e.g. " +
      "when a session is continuously changing state.";
    uses bfd-notification-parms;
    leaf lag-name {
      type if:interface-ref;
      description "LAG interface name";
    }
    leaf member-link {
      type if:interface-ref;
      description "Member link on which BFD is running";
    }
  }
}
