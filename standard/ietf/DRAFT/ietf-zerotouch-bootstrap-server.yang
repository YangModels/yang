module ietf-zerotouch-bootstrap-server {

  namespace
    "urn:ietf:params:xml:ns:yang:ietf-zerotouch-bootstrap-server";
  prefix "ztbs";

  import ietf-inet-types {           // RFC 6991
    prefix inet;
  }

  organization
   "IETF NETCONF (Network Configuration) Working Group";
  contact
   "WG Web:   <http://tools.ietf.org/wg/netconf/>
    WG List:  <mailto:netconf@ietf.org>
    WG Chair: Mehmet Ersue
              <mailto:mehmet.ersue@nsn.com>
    WG Chair: Mahesh Jethanandani
              <mailto:mjethanandani@gmail.com>
    Editor:   Kent Watsen
              <mailto:kwatsen@juniper.net>";


  description
   "This module defines the southbound interface for Zero Touch
    bootstrap servers.

    Copyright (c) 2014 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";

  revision "2015-10-19" {
    description
     "Initial version";
    reference
     "RFC XXXX: Zero Touch Provisioning for NETCONF Call Home";
  }


  grouping redirect-information-grouping {
    description
      "This container contains information the device may use
       to redirect it to another bootstrap server.";

    leaf address {
      type inet:host;
      mandatory true;
      description
       "The IP address or hostname of the bootstrap server
        the device should redirect to.";
    }
    leaf trust-anchor {
      type binary;
      mandatory true;
      description
        "A certificate that a device can use as a trust anchor to
         authenticate the bootstrap server it is being redirected
         to.  The binary certificate structure as specified by RFC
         5246, Section 7.4.6, i.e.,: opaque ASN.1Cert<1..2^24>;
        ";
      reference
        "RFC 5246: The Transport Layer Security (TLS)
                   Protocol Version 1.2";
    }

    leaf signature {
      type string;
      must "../../ownership-voucher";
      description
        "The signature over the concatenation of the previous leafs
         using the organization's private key.  Specifically,
         sign(name+md5+sha1+path), where simple string concatenation
         to join values is used, resulting in a single null-terminated
         string.";
      }


  }


  grouping bootstrap-information-grouping {

    container boot-image {
      description
        "It is intended that the device will fetch this container
         as a whole, as it contains values that need to be
         processed together.";
      leaf name {
        type string;
        mandatory true;
        description
          "The name of the image of software the device is expected
           to be running.";
      }
      leaf md5 {
        type string;
        mandatory true;
        description
          "The output of the MD5 hash algorithm over the image file.";
      }
      leaf sha1 {
        type string;
        mandatory true;
        description
          "The output of the SHA-1 hash algorithm over the image file.";
      }
      leaf path {
        type string;
        mandatory true;
        description
          "An absolute path to the boot-image file hosted on this
           Bootstrap server.";
      }
      leaf signature {
        type string;
        must "../../../ownership-voucher";
        description
          "The signature over the concatenation of the previous leafs
           using the organization's private key.  Specifically,
           sign(name+md5+sha1+path), where simple string concatenation
           to join values is used, resulting in a single null-terminated
           string.";
      }
    }

    container configuration {
      description
        "It is intended that the device will fetch this container
         as a whole, as its contents need to be processed together.";
      anyxml config {
        mandatory true;
        description
          "Any configuration data model known to the device.  It may
           contain Vendor-specific and/or standards-based data models.
           An example configuration using a couple IETF-defined data
           models is presented the Appendix of RFC XXXX.";
      }
      leaf signature {
        type string;
        must "../../../ownership-voucher";
        description
          "The signature over the concatenation of the previous leaf
           using the organization's private key.  Specifically,
           sign(config), where 'config' is treated as a single null-
           terminated string.";
      }
    }
  }


  grouping owner-certificate-grouping {

    leaf certificate {
      type string;
      mandatory true;
      description
        "This is an X.509 certificate, signed by a Vendor, for
         a business organization.  This certificate must encode a
         Vendor-assigned value identifying the organization. This
         identifier must match the owner identifier encoded in
         the Ownership Voucher.";
    }
    leaf issuer-crl {
      type string;
      description
        "An optional CRL for the issuer used by the
         Vendor to sign Owner Certificates.  The CRL should be
         as up to date as possible.  This leaf is optional as
         it is primarily to support deployments where the device
         is unable to download the CRL from the CRL distribution
         point URLs listed in the Vendor's trust anchor
         certificate.";
    }
  }

  grouping ownership-voucher-grouping {
    leaf voucher {
      type binary;
      mandatory true;
      description
        "A Vendor-specific encoding binding unique device
         identifiers to an owner identifier value matching the
         value encoded in the owner-certificate below.  An
         example format for a voucher is presented in the
         Appendix of RFC XXXX.";
    }
    leaf issuer-crl {
      type string;
      description
        "An optional CRL for the issuer used by the
         Vendor to sign Ownership Vouchers.  The CRL should be
         as up to date as possible.  This leaf is optional as
         it is primarily to support deployments where the device
         is unable to download the CRL from the CRL distribution
         point URLs listed in the Vendor's trust anchor
         certificate.";
    }
  }

  container devices {
    config false;
    description
      "A read-only list of device entries";
    list device {

      key unique-id;
      leaf unique-id {
        type string;
        description
          "A unique identifier for the device (e.g., serial number).
           Each device accesses its bootstrapping record by its unique
           identifier.";
      }

      choice type {

        container redirect-information {
          uses redirect-information-grouping;
        }

        container bootstrap-information {
          uses bootstrap-information-grouping;
        }

      }

      container ownership-voucher {
        description
          "This container contains the Ownership Voucher that the
           device uses to ascertain the identity of its rightful
           owner, as certified by its Vendor.";

        when "../redirect-information/signature or ../bootstrap-information/*/signature";
        //must "../owner-certificate and ../redirect-information/signature or ../bootstrap-information/*/signature";
        must "../owner-certificate";

        uses ownership-voucher-grouping;
      }

      container owner-certificate {
        description
          "It is intended that the device will fetch this container
           as a whole, as it contains values that need to be
           processed together.";

        when "../ownership-voucher";
        //must "../ownership-voucher and ../redirect-information/signature or ../bootstrap-information/*/signature";

        uses owner-certificate-grouping;
      }


      action notification {
        input {
          leaf type {
            type enumeration {
              enum bootstrap-complete {
                description
                  "Indicates that the device successfully processed the
                   bootstrap data, that is currently running the specified
                   boot image and has committed the configuration.  At
                   this point, the device is ready to be managed by an
                   external NMS system.  The device is never expected
                   access the bootstrap server again, unless reset to
                   its factory default again.";
              }
            }
            mandatory true;
          }
          leaf message {
            type string;
            description
              "A human-readable value.";
          }
          container ssh-host-keys {
            list ssh-host-key {
              when "../type = bootstrap-complete";
              leaf format {
                type enumeration {
                  enum ssh-dss;
                  enum ssh-rsa;
                }
                mandatory true;
              }
              leaf key-data {
                type string;
                mandatory true;
              }
            }
          }
        }
      } // end action
    }
  }

}
