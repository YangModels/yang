/*
 * Copyright (c) 2018 Juniper Networks, Inc.
 * All rights reserved.
 */
 module junos-nfx-conf-isdn {
   namespace "http://yang.juniper.net/junos-nfx/conf/isdn";

   prefix jc-isdn;

   import junos-common-ddl-extensions {
     prefix junos;
   }

   import junos-common-types {
     prefix jt;
   }

   import junos-nfx-conf-root {
     prefix jc;
   }

   organization "Juniper Networks, Inc.";

   contact "yang-support@juniper.net";

   description "Junos isdn configuration module";

   revision 2018-01-01 {
     description "Junos: 18.2R1.9";
   }

   augment /jc:configuration {
     uses isdn-group;
   }
   augment /jc:configuration/jc:groups {
     uses isdn-group;
   }
   grouping isdn-group {
   }
 }
