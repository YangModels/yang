/*
 * Copyright (c) 2018 Juniper Networks, Inc.
 * All rights reserved.
 */
 module junos-nfx-conf-jsrc-partition {
   namespace "http://yang.juniper.net/junos-nfx/conf/jsrc-partition";

   prefix jc-jsrc-partition;

   import junos-common-types {
     prefix jt;
   }

   import junos-nfx-conf-root {
     prefix jc;
   }

   organization "Juniper Networks, Inc.";

   contact "yang-support@juniper.net";

   description "Junos jsrc-partition configuration module";

   revision 2018-01-01 {
     description "Junos: 18.2R1.9";
   }

   augment /jc:configuration {
     uses jsrc-partition-group;
   }
   augment /jc:configuration/jc:groups {
     uses jsrc-partition-group;
   }
   grouping jsrc-partition-group {
   }
 }
