/*
 * Copyright (c) 2018 Juniper Networks, Inc.
 * All rights reserved.
 */
 module junos-nfx-rpc-security {
   namespace "http://yang.juniper.net/junos-nfx/rpc/security";

   prefix security;

   import junos-common-types {
     prefix jt;
   }

   organization "Juniper Networks, Inc.";

   contact "yang-support@juniper.net";

   description "Junos RPC YANG module for security command(s)";

   revision 2018-01-01 {
     description "Junos: 18.2R1.9";
   }

   rpc get-security-alarm-information {
     description "Show active security alarm information";
     input {
       leaf alarm-id {
         description "Alarm ID filter";
         type union {
           type uint32;
           type string {
             pattern "<.*>|$.*";
           }
         }
       }
       leaf-list alarm-type {
         ordered-by user;
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type jt:time;
       }
       leaf older-than {
         description "Alarms older than filter (YYYY-MM-DD.HH:MM:SS)";
         type jt:time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf style {
         type enumeration {
           enum "detail" {
             description "Show detail alarm information";
           }
         }
       }
     }
     output {
       choice output_c {
         case output-tag {
           leaf output {
             type string;
           }
         }
         case actual-tag {
           anyxml security-alarm-information;
         }
         case multichassis-tag {
           anyxml multi-routing-engine-results;
         }
       }
     }
   }
   rpc get-security-log-information {
     description "Show auditable security log information";
     input {
       leaf destination-address {
         description "Destination address and optional prefix length";
         type jt:ipprefix-optional;
       }
       leaf destination-port {
         description "Destination port";
         type union {
           type uint32;
           type string {
             pattern "<.*>|$.*";
           }
         }
       }
       leaf event-id {
         description "Event ID filter";
         type string;
       }
       leaf interface-name {
         description "Name of interface";
         type string;
       }
       leaf older-than {
         description "Events older than filter (YYYY-MM-DD.HH:MM:SS)";
         type jt:time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type jt:time;
       }
       leaf result {
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type jt:ipprefix-optional;
       }
       leaf source-port {
         description "Source port";
         type union {
           type uint32;
           type string {
             pattern "<.*>|$.*";
           }
         }
       }
       leaf username {
         description "Username filter";
         type string;
       }
       leaf sort-by {
         description "Sort by selected field";
         default "time";
         type enumeration {
           enum "destination-address" {
             description "Sort by destination address";
           }
           enum "destination-port" {
             description "Sort by destination port";
           }
           enum "interface-name" {
             description "Sort by interface name";
           }
           enum "policy-name" {
             description "Sort by policy name";
           }
           enum "protocol" {
             description "Sort by protocol";
           }
           enum "source-address" {
             description "Sort by source address";
           }
           enum "source-port" {
             description "Sort by source port";
           }
           enum "time" {
             description "Sort by time of event arrival";
           }
           enum "username" {
             description "Sort by event user name ";
           }
         }
       }
       leaf direction {
         default "ascending";
         type enumeration {
           enum "ascending" {
             description "Sort in ascending order";
           }
           enum "descending" {
             description "Sort in descending order";
           }
         }
       }
       leaf style {
         type enumeration {
           enum "detail" {
             description "Show detail alarm information";
           }
         }
       }
     }
     output {
       choice output_c {
         case output-tag {
           leaf output {
             type string;
           }
         }
         case actual-tag {
           anyxml security-log-information;
         }
         case multichassis-tag {
           anyxml multi-routing-engine-results;
         }
       }
     }
   }
   rpc show-security-hpl-infile {
     description "Show security logs in binary format";
     input {
       leaf file_name {
         description "Name of the binary log file to be displayed ";
         type string {
           length "1 .. 256";
         }
       }
     }
     output {
       choice output_c {
         case output-tag {
           leaf output {
             type string;
           }
         }
         case actual-tag {
           anyxml show-hpl-infile;
         }
         case multichassis-tag {
           anyxml multi-routing-engine-results;
         }
       }
     }
   }
   rpc show-security-hpl-infile-last {
     description "Show recent security logs in binary format";
     input {
       leaf seconds {
         description "Number of seconds of binary logs to display";
         type union {
           type uint32;
           type string {
             pattern "<.*>|$.*";
           }
         }
       }
     }
     output {
       choice output_c {
         case output-tag {
           leaf output {
             type string;
           }
         }
         case actual-tag {
           anyxml show-hpl-infile;
         }
         case multichassis-tag {
           anyxml multi-routing-engine-results;
         }
       }
     }
   }
   rpc get-hakr-keychain-information {
     description "Show all protocols keychain";
     input {
       leaf verbosity {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml hakr-keychain-information;
         }
         case multichassis-tag {
           anyxml multi-routing-engine-results;
         }
       }
     }
   }
   rpc get-pki-certificate-request {
     description "Show PKCS-10 certificate request information";
     input {
       uses command-forwarding;
       leaf certificate-id {
         description "Certificate identifier";
         type string {
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-ca-certificate {
     description "Show certificate-authority certificate information";
     input {
       uses command-forwarding;
       choice ca-cert-choice {
         case ca-profile {
           leaf ca-profile {
             description "Certificate authority profile";
             type string {
             }
           }
         }
         case ca-profile-group {
           leaf ca-profile-group {
             description "Show CA profile group";
             type string {
             }
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-local-certificate {
     description "Show router certificate information";
     input {
       uses command-forwarding;
       choice certificate-choice {
         case certificate-id {
           leaf certificate-id {
             description "Certificate identifier";
             type string {
             }
           }
         }
         case system-generated {
           leaf system-generated {
             description "Autogenerated self-signed certificate";
             type empty;
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-crl {
     description "Show certificate revocation list information";
     input {
       uses command-forwarding;
       leaf ca-profile {
         description "Certificate authority profile";
         type string {
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pkid-crl-information-list;
         }
         case multichassis-tag {
           anyxml multi-routing-engine-results;
         }
       }
     }
   }
   rpc get-security-associations-information {
     description "Show IPSec security association information";
     input {
       uses command-forwarding;
       leaf level {
         default "brief";
         type enumeration {
           enum "brief" {
             description "Display brief output";
           }
           enum "detail" {
             description "Display detailed output";
           }
         }
       }
       leaf family {
         description "Show IPSec security association information by family";
         default "inet";
         type enumeration {
           enum "inet" {
             description "Show IPv4";
           }
           enum "inet6" {
             description "Show IPv6";
           }
         }
       }
       leaf sa-type {
         description "Show IPSec security association by type";
         type enumeration {
           enum "shortcut" {
             description "Show Shortcut SAs";
           }
         }
       }
       leaf show-index-ipsec-security-association {
         description "Index of security association";
         type union {
           type string {
             pattern "<.*>|$.*";
           }
           type uint32 {
             range "1 .. 4294967295";
           }
         }
       }
       leaf show-vpnname-ipsec-security-association {
         description "VPN name";
         default "all";
         type string;
       }
       leaf show-trafficselectorname-ipsec-security-association {
         description "Traffic-selector name";
         default "all";
         type string;
       }
       leaf show-fcnamename-ipsec-security-association {
         description "COS Forward Class name";
         type string;
       }
     }
     output {
       choice output_c {
         case output-tag {
           leaf output {
             type string;
           }
         }
         case actual-tag {
           anyxml security-associations-information;
         }
         case multichassis-tag {
           anyxml multi-routing-engine-results;
         }
       }
     }
   }
   rpc get-control-plane-security-associations-information {
     description "Show IPSec control plane security association information";
     input {
       uses command-forwarding;
       leaf level {
         default "brief";
         type enumeration {
           enum "brief" {
             description "Display brief output";
           }
           enum "detail" {
             description "Display detailed output";
           }
         }
       }
       leaf show-saname-ipsec-control-plane-security-association {
         description "SA name";
         default "all";
         type string;
       }
     }
     output {
       choice output_c {
         case output-tag {
           leaf output {
             type string;
           }
         }
         case actual-tag {
           anyxml control-plane-security-associations-information;
         }
         case multichassis-tag {
           anyxml multi-routing-engine-results;
         }
       }
     }
   }
   rpc get-ipsec-statistics-information {
     description "Show IPSec statistics";
     input {
       uses command-forwarding;
       leaf show-index-ipsec-statistics {
         description "Index of Security Association";
         default "0";
         type union {
           type uint32;
           type string {
             pattern "<.*>|$.*";
           }
         }
       }
     }
     output {
       choice output_c {
         case output-tag {
           leaf output {
             type string;
           }
         }
         case actual-tag {
           anyxml usp-ipsec-total-statistics-information;
         }
         case multichassis-tag {
           anyxml multi-routing-engine-results;
         }
       }
     }
   }
   rpc get-inactive-tunnels {
     description "Inactive-tunnels";
     input {
       uses command-forwarding;
       leaf level {
         default "brief";
         type enumeration {
           enum "brief" {
             description "Display brief output";
           }
           enum "detail" {
             description "Display detailed output";
           }
         }
       }
       leaf family {
         description "Show IPSec security association information by family";
         default "inet";
         type enumeration {
           enum "inet" {
             description "Show IPv4";
           }
           enum "inet6" {
             description "Show IPv6";
           }
         }
       }
       leaf show-index-ipsec-security-association {
         description "Index of security association";
         default "0";
         type union {
           type uint32;
           type string {
             pattern "<.*>|$.*";
           }
         }
       }
       leaf show-vpnname-ipsec-security-association {
         description "VPN name";
         default "all";
         type string;
       }
       leaf sa-type {
         description "Show inactive IPSec SAs by type";
         type enumeration {
           enum "shortcut" {
             description "Show Shortcut SAs";
           }
         }
       }
     }
     output {
       choice output_c {
         case output-tag {
           leaf output {
             type string;
           }
         }
         case actual-tag {
           anyxml ipsec-unestablished-tunnel-information;
         }
         case multichassis-tag {
           anyxml multi-routing-engine-results;
         }
       }
     }
   }
   rpc get-ipsec-next-hop-tunnel-information {
     description "Show manual and auto next-hop-tunnel entries";
     input {
       uses command-forwarding;
       leaf interface-name {
         description "Name of secure tunnel logical interface";
         default "all";
         type string;
       }
       leaf family {
         description "Show IPSec next-hop-tunnel entries by family";
         default "inet";
         type enumeration {
           enum "inet" {
             description "Show IPv4";
           }
           enum "inet6" {
             description "Show IPv6";
           }
         }
       }
       leaf show-index-ipsec-security-association {
         description "Index of security association";
         type union {
           type string {
             pattern "<.*>|$.*";
           }
           type uint32 {
             range "1 .. 4294967295";
           }
         }
       }
     }
     output {
       choice output_c {
         case output-tag {
           leaf output {
             type string;
           }
         }
         case actual-tag {
           anyxml usp-ipsec-next-hop-tunnel-information;
         }
         case multichassis-tag {
           anyxml multi-routing-engine-results;
         }
       }
     }
   }
   rpc get-ipsec-traffic-selector-information {
     description "Show traffic-selector information for a st0 interface";
     input {
       uses command-forwarding;
       leaf interface-name {
         description "Name of secure tunnel logical interface";
         type string;
         mandatory true;
       }
       leaf source-address {
         description "Source IP address";
         type jt:ipprefix-mandatory;
       }
       leaf destination-address {
         description "Destination IP address";
         type jt:ipprefix-mandatory;
       }
     }
     output {
       choice output_c {
         case output-tag {
           leaf output {
             type string;
           }
         }
         case actual-tag {
           anyxml usp-ipsec-traffic-selector-information;
         }
         case multichassis-tag {
           anyxml multi-routing-engine-results;
         }
       }
     }
   }
   rpc get-ipsec-tunnel-event-statistics {
     description "Show tunnel event statstics";
     output {
       choice output_c {
         case output-tag {
           leaf output {
             type string;
           }
         }
         case actual-tag {
           anyxml ipsec-tunnel-event-statistics;
         }
         case multichassis-tag {
           anyxml multi-routing-engine-results;
         }
       }
     }
   }
   rpc get-ipsec-tunnel-distribution {
     description "Show tunnel distribution";
     input {
       uses command-forwarding;
       leaf level {
         default "brief";
         type enumeration {
           enum "brief" {
             description "Display brief IPsec tunnel-distribution (default)";
           }
           enum "summary" {
             description "Display IPsec tunnel-distribution summary info";
           }
         }
       }
     }
     output {
       choice output_c {
         case output-tag {
           leaf output {
             type string;
           }
         }
         case actual-tag {
           anyxml ipsec-tunnel-distribution-information;
         }
         case multichassis-tag {
           anyxml multi-routing-engine-results;
         }
       }
     }
   }
   rpc get-pre-shared-key {
     description "Show IKE pre-shared key information for a particular group-ike-id user";
     input {
       uses command-forwarding;
       leaf user-id {
         description "IKE user-id value";
         type string;
       }
       leaf master-key {
         description "Master pre-shared key";
         type string;
         mandatory true;
       }
     }
     output {
       choice output_c {
         case output-tag {
           leaf output {
             type string;
           }
         }
         case actual-tag {
           anyxml ike-show-pre-shared-key-information;
         }
         case multichassis-tag {
           anyxml multi-routing-engine-results;
         }
       }
     }
   }
   rpc get-ike-security-associations-information {
     description "Show IKE security association information";
     input {
       uses command-forwarding;
       leaf peer-address {
         description "IP address of the peer";
         type jt:ipaddr;
       }
       leaf level {
         default "brief";
         type enumeration {
           enum "brief" {
             description "Show brief output (default)";
           }
           enum "detail" {
             description "Show detailed output";
           }
         }
       }
       leaf family {
         description "Show IKE security association by family";
         default "inet";
         type enumeration {
           enum "inet" {
             description "Show IPv4";
           }
           enum "inet6" {
             description "Show IPv6";
           }
         }
       }
       leaf show-index-ike-security-association {
         description "Index of security association";
         type union {
           type string {
             pattern "<.*>|$.*";
           }
           type uint32 {
             range "1 .. 4294967295";
           }
         }
       }
       leaf sa-type {
         description "Show IKE security association by type";
         type enumeration {
           enum "shortcut" {
             description "Show Shortcut SAs";
           }
         }
       }
     }
     output {
       choice output_c {
         case output-tag {
           leaf output {
             type string;
           }
         }
         case actual-tag {
           anyxml ike-security-associations-information;
         }
         case multichassis-tag {
           anyxml multi-routing-engine-results;
         }
       }
     }
   }
   rpc get-ike-active-peers-information {
     description "Show IKE active peers ";
     input {
       uses command-forwarding;
       leaf level {
         default "brief";
         type enumeration {
           enum "brief" {
             description "Display brief output";
           }
           enum "detail" {
             description "Display detailed output";
           }
         }
       }
       leaf peer-address {
         description "IP of peer";
         type jt:ipaddr;
       }
       leaf port {
         description "Port number of peer";
         type union {
           type string {
             pattern "<.*>|$.*";
           }
           type uint32 {
             range "1 .. 65535";
           }
         }
       }
       leaf ike-id {
         description "IKE ID";
         default "all";
         type string;
       }
       leaf aaa-username {
         description "AAA username";
         default "all";
         type string;
       }
       leaf debug {
         description "Show additional peer-entry debug information";
         type empty;
       }
     }
     output {
       choice output_c {
         case output-tag {
           leaf output {
             type string;
           }
         }
         case actual-tag {
           anyxml ike-active-peers-information;
         }
         case multichassis-tag {
           anyxml multi-routing-engine-results;
         }
       }
     }
   }
   rpc get-config-ike-debug {
     description "Show current enabled IKE debug information";
     output {
       choice output_c {
         case output-tag {
           leaf output {
             type string;
           }
         }
         case actual-tag {
           anyxml security-ike-debug-info;
         }
         case multichassis-tag {
           anyxml multi-routing-engine-results;
         }
       }
     }
   }
   rpc get-gvpn-security-associations-information {
     description "Show IPSec security association information";
     input {
       uses command-forwarding;
       leaf level {
         default "brief";
         type enumeration {
           enum "brief" {
             description "Display brief output";
           }
           enum "detail" {
             description "Display detailed output";
           }
         }
       }
       leaf show-gvpn-index-ipsec-security-association {
         description "Index of security association";
         default "0";
         type union {
           type uint32;
           type string {
             pattern "<.*>|$.*";
           }
         }
       }
       leaf group-id {
         description "Group VPN identification number";
         type union {
           type string {
             pattern "<.*>|$.*";
           }
           type uint32 {
             range "1 .. 4294967295";
           }
         }
       }
     }
     output {
       choice output_c {
         case output-tag {
           leaf output {
             type string;
           }
         }
         case actual-tag {
           anyxml ipsec-security-associations-information;
         }
         case multichassis-tag {
           anyxml multi-routing-engine-results;
         }
       }
     }
   }
   rpc get-gvpn-ipsec-statistics-information {
     description "Show IPSec statistics";
     input {
       uses command-forwarding;
       leaf show-gvpn-index-ipsec-statistics {
         description "Index of Security Association";
         default "0";
         type union {
           type uint32;
           type string {
             pattern "<.*>|$.*";
           }
         }
       }
     }
     output {
       choice output_c {
         case output-tag {
           leaf output {
             type string;
           }
         }
         case actual-tag {
           anyxml usp-ipsec-total-statistics-information;
         }
         case multichassis-tag {
           anyxml multi-routing-engine-results;
         }
       }
     }
   }
   rpc get-gvpn-inactive-tunnels {
     description "Inactive-tunnels";
     input {
       uses command-forwarding;
       leaf level {
         default "brief";
         type enumeration {
           enum "brief" {
             description "Display brief output";
           }
           enum "detail" {
             description "Display detailed output";
           }
         }
       }
       leaf group-id {
         description "Group VPN identification number";
         type union {
           type string {
             pattern "<.*>|$.*";
           }
           type uint32 {
             range "1 .. 4294967295";
           }
         }
       }
     }
     output {
       choice output_c {
         case output-tag {
           leaf output {
             type string;
           }
         }
         case actual-tag {
           anyxml ipsec-unestablished-tunnel-information;
         }
         case multichassis-tag {
           anyxml multi-routing-engine-results;
         }
       }
     }
   }
   rpc get-gvpn-ike-security-associations-information {
     description "Show IKE security association information";
     input {
       uses command-forwarding;
       leaf level {
         default "brief";
         type enumeration {
           enum "brief" {
             description "Show brief output (default)";
           }
           enum "detail" {
             description "Show detailed output";
           }
         }
       }
       leaf peer-address {
         description "IP address of the peer";
         type jt:ipaddr;
       }
       leaf index {
         description "Index of security association";
         default "0";
         type union {
           type uint32;
           type string {
             pattern "<.*>|$.*";
           }
         }
       }
     }
     output {
       choice output_c {
         case output-tag {
           leaf output {
             type string;
           }
         }
         case actual-tag {
           anyxml ike-security-associations-information;
         }
         case multichassis-tag {
           anyxml multi-routing-engine-results;
         }
       }
     }
   }
   rpc get-gvpn-kek-security-associations-information {
     description "Show KEK security association information";
     input {
       uses command-forwarding;
       leaf level {
         default "brief";
         type enumeration {
           enum "brief" {
             description "Show brief output (default)";
           }
           enum "detail" {
             description "Show detailed output";
           }
         }
       }
       leaf peer-address {
         description "IP address of the peer";
         type jt:ipaddr;
       }
       leaf index {
         description "Index of security association";
         default "0";
         type union {
           type uint32;
           type string {
             pattern "<.*>|$.*";
           }
         }
       }
       choice groupchoice {
         description "Specify a group by name or ID";
         case group-id {
           leaf group-id {
             description "Group VPN identification number";
             type union {
               type string {
                 pattern "<.*>|$.*";
               }
               type uint32 {
                 range "1 .. 4294967295";
               }
             }
           }
         }
         case vpn {
           leaf vpn {
             description "Group VPN Name";
             type string {
               length "1 .. 32";
             }
           }
         }
       }
     }
     output {
       choice output_c {
         case output-tag {
           leaf output {
             type string;
           }
         }
         case actual-tag {
           anyxml ike-security-associations-information;
         }
         case multichassis-tag {
           anyxml multi-routing-engine-results;
         }
       }
     }
   }
   rpc get-gvpn-policy-information {
     description "Show group vpn policies";
     input {
       uses command-forwarding;
       choice groupchoice {
         description "Specify a group by name or ID";
         case group-id {
           leaf group-id {
             description "Group VPN identification number";
             type union {
               type string {
                 pattern "<.*>|$.*";
               }
               type uint32 {
                 range "1 .. 4294967295";
               }
             }
           }
         }
         case vpn {
           leaf vpn {
             description "Group VPN Name";
             type string {
               length "1 .. 32";
             }
           }
         }
       }
     }
     output {
       choice output_c {
         case output-tag {
           leaf output {
             type string;
           }
         }
         case actual-tag {
           anyxml gvpn-policy-information;
         }
         case multichassis-tag {
           anyxml multi-routing-engine-results;
         }
       }
     }
   }
   rpc get-security-group-vpn-server-registered-members {
     description "Show group VPN registered members for group VPN server";
     input {
       uses command-forwarding;
       choice group_choice {
         description "Specify a group by name or id";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case peer-address {
           leaf peer-address {
             description "Peer IP address";
             type jt:ipaddr;
           }
         }
       }
       leaf level {
         default "brief";
         type enumeration {
           enum "brief" {
             description "Show brief output (default)";
           }
           enum "detail" {
             description "Show detailed output";
           }
         }
       }
     }
     output {
       choice output_c {
         case output-tag {
           leaf output {
             type string;
           }
         }
         case actual-tag {
           anyxml security-group-vpn-server-registered-members;
         }
         case multichassis-tag {
           anyxml multi-routing-engine-results;
         }
       }
     }
   }
   rpc get-security-group-vpn-server-kek-sa {
     description "Show KEK security association information";
     input {
       uses command-forwarding;
       leaf level {
         default "brief";
         type enumeration {
           enum "brief" {
             description "Show brief output (default)";
           }
           enum "detail" {
             description "Show detailed output";
           }
         }
       }
       choice group_index_choice {
         description "Specify peer-address, group, group-id or index filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case index {
           leaf index {
             description "Index of security association";
             type union {
               type uint32;
               type string {
                 pattern "<.*>|$.*";
               }
             }
           }
         }
       }
     }
     output {
       choice output_c {
         case output-tag {
           leaf output {
             type string;
           }
         }
         case actual-tag {
           anyxml security-group-vpn-server-kek-sa;
         }
         case multichassis-tag {
           anyxml multi-routing-engine-results;
         }
       }
     }
   }
   rpc get-security-group-vpn-server-security-information {
     description "Show IPSec security association information for group VPN server";
     input {
       uses command-forwarding;
       leaf level {
         default "brief";
         type enumeration {
           enum "brief" {
             description "Show brief output (default)";
           }
           enum "detail" {
             description "Show detailed output";
           }
         }
       }
       choice group_choice {
         description "Specify group or group-id filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
       }
     }
     output {
       choice output_c {
         case output-tag {
           leaf output {
             type string;
           }
         }
         case actual-tag {
           anyxml security-group-vpn-server-security-information;
         }
         case multichassis-tag {
           anyxml multi-routing-engine-results;
         }
       }
     }
   }
   rpc get-security-group-vpn-server-ike-security-associations-information {
     description "Show IKE security association information";
     input {
       uses command-forwarding;
       leaf level {
         default "brief";
         type enumeration {
           enum "brief" {
             description "Show brief output (default)";
           }
           enum "detail" {
             description "Show detailed output";
           }
         }
       }
       choice group_index_choice {
         description "Specify peer-address, group, group-id or index filter";
         case peer-address {
           leaf peer-address {
             description "Peer IP address";
             type jt:ipaddr;
           }
         }
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case index {
           leaf index {
             description "Index of security association";
             type union {
               type uint32;
               type string {
                 pattern "<.*>|$.*";
               }
             }
           }
         }
       }
     }
     output {
       choice output_c {
         case output-tag {
           leaf output {
             type string;
           }
         }
         case actual-tag {
           anyxml security-group-vpn-server-ike-security-associations-information;
         }
         case multichassis-tag {
           anyxml multi-routing-engine-results;
         }
       }
     }
   }
   rpc get-security-group-vpn-svr-svr-cluster-info {
     description "Show group vpn server cluster information";
     input {
       uses command-forwarding;
       leaf level {
         default "brief";
         type enumeration {
           enum "brief" {
             description "Show brief output (default)";
           }
           enum "detail" {
             description "Show detailed output";
           }
         }
       }
       choice group_cluster_index_choice {
         description "Specify group, group-id or peer gateway filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case peer-gateway {
           leaf peer-gateway {
             description "Show specified peer server gateway name";
             type string {
               length "1 .. 32";
             }
           }
         }
       }
     }
     output {
       choice output_c {
         case output-tag {
           leaf output {
             type string;
           }
         }
         case actual-tag {
           anyxml server-cluster-information;
         }
         case multichassis-tag {
           anyxml multi-routing-engine-results;
         }
       }
     }
   }
   rpc get-security-group-vpn-server-stats {
     description "Show group server statistics";
     input {
       uses command-forwarding;
       choice group_choice {
         description "Specify a group by name or id";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
       }
     }
     output {
       choice output_c {
         case output-tag {
           leaf output {
             type string;
           }
         }
         case actual-tag {
           anyxml security-group-vpn-server-stats;
         }
         case multichassis-tag {
           anyxml multi-routing-engine-results;
         }
       }
     }
   }
   rpc get-internal-security-association {
     description "Show internal security association";
     output {
       choice output_c {
         case output-tag {
           leaf output {
             type string;
           }
         }
         case actual-tag {
           anyxml internal-sa-information;
         }
         case multichassis-tag {
           anyxml multi-routing-engine-results;
         }
       }
     }
   }
   rpc get-eedebug-action-profile {
     description "Show current datapath-debug action profile";
     output {
       choice output_c {
         case output-tag {
           leaf output {
             type string;
           }
         }
         case actual-tag {
           anyxml eedebug-all-action-profile;
         }
         case multichassis-tag {
           anyxml multi-routing-engine-results;
         }
       }
     }
   }
   rpc get-eedebug-events {
     description "Show current registered data path events";
     output {
       choice output_c {
         case output-tag {
           leaf output {
             type string;
           }
         }
         case actual-tag {
           anyxml eedebug-all-events;
         }
         case multichassis-tag {
           anyxml multi-routing-engine-results;
         }
       }
     }
   }
   rpc get-eedebug-counters {
     description "Show datapath counters";
     output {
       choice output_c {
         case output-tag {
           leaf output {
             type string;
           }
         }
         case actual-tag {
           anyxml eedebug-all-counters;
         }
         case multichassis-tag {
           anyxml multi-routing-engine-results;
         }
       }
     }
   }
   rpc show-eedebug-capture {
     description "Show datapath debug capture file";
     output {
       choice output_c {
         case output-tag {
           leaf output {
             type string;
           }
         }
         case actual-tag {
           anyxml eedebug-capture-output;
         }
         case multichassis-tag {
           anyxml multi-routing-engine-results;
         }
       }
     }
   }
   rpc show-ds-lite-softwire-sc-infomation {
     description "Show softwire information";
     output {
       choice output_c {
         case output-tag {
           leaf output {
             type string;
           }
         }
         case actual-tag {
           anyxml ds-lite-softwire-sc-information;
         }
         case multichassis-tag {
           anyxml multi-routing-engine-results;
         }
       }
     }
   }
   rpc show-ds-lite-softwire-one-sc-information {
     description "Show Softwire Concentrator object";
     input {
       uses command-forwarding;
       leaf softwire-name-str {
         description "Softwire Name";
         type string;
         mandatory true;
       }
       leaf start-id {
         description "Show softwire initiator info from start identifier";
         type union {
           type string {
             pattern "<.*>|$.*";
           }
           type uint32 {
             range "1 .. 100000";
           }
         }
       }
       leaf count {
         description "Number of softwire initiator entries";
         type union {
           type string {
             pattern "<.*>|$.*";
           }
           type uint32 {
             range "1 .. 100000";
           }
         }
       }
     }
     output {
       choice output_c {
         case output-tag {
           leaf output {
             type string;
           }
         }
         case actual-tag {
           anyxml ds-lite-softwire-one-sc-information;
         }
         case multichassis-tag {
           anyxml multi-routing-engine-results;
         }
       }
     }
   }
   rpc get-firewall-dynamic-policies {
     description "Show security firewall dynamic policies";
     input {
       uses command-forwarding;
       leaf from-zone {
         description "Show the policy information matching the given source zone";
         type string;
       }
       leaf to-zone {
         description "Show the policy information matching the given destination zone";
         type string;
       }
       leaf detail {
         description "Show the detailed dynamic policy information";
         type empty;
       }
       leaf scope-id {
         description "Show the policy information matching the given scope policy id [4...MAX_POLICIES]";
         type union {
           type string {
             pattern "<.*>|$.*";
           }
           type uint32 {
             range "4 .. 4294967295";
           }
         }
       }
     }
     output {
       choice output_c {
         case output-tag {
           leaf output {
             type string;
           }
         }
         case actual-tag {
           anyxml security-dynamic-policies;
         }
         case multichassis-tag {
           anyxml multi-routing-engine-results;
         }
       }
     }
   }
   rpc get-flow-statistics-all {
     description "Show flow statistics";
     output {
       choice output_c {
         case output-tag {
           leaf output {
             type string;
           }
         }
         case actual-tag {
           anyxml flow-statistics-all;
         }
         case multichassis-tag {
           anyxml multi-routing-engine-results;
         }
       }
     }
   }
   rpc get-flow-status-all {
     description "Show flow status";
     output {
       choice output_c {
         case output-tag {
           leaf output {
             type string;
           }
         }
         case actual-tag {
           anyxml flow-status-all;
         }
         case multichassis-tag {
           anyxml multi-routing-engine-results;
         }
       }
     }
   }
   rpc get-flow-gate-information {
     description "Show gate information";
     input {
       uses command-forwarding;
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf family {
         description "Protocol family";
         type enumeration {
           enum "inet" {
             description "Show IPv4";
           }
           enum "inet6" {
             description "Show IPv6/IPv6-NATPT";
           }
         }
       }
       leaf level {
         default "brief";
         type enumeration {
           enum "summary" {
             description "Show output summary";
           }
           enum "brief" {
             description "Show brief output (default)";
           }
         }
       }
     }
     output {
       choice output_c {
         case output-tag {
           leaf output {
             type string;
           }
         }
         case actual-tag {
           anyxml flow-gate-information;
         }
         case multichassis-tag {
           anyxml multi-routing-engine-results;
         }
       }
     }
   }
   rpc get-flow-session-information {
     description "Show session table";
     input {
       uses command-forwarding;
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf level {
         default "brief";
         type enumeration {
           enum "summary" {
             description "Show output summary";
           }
           enum "brief" {
             description "Show brief output (default)";
           }
           enum "extensive" {
             description "Show detailed output";
           }
         }
       }
       leaf enc {
         type enumeration {
           enum "encrypted" {
             description "Show encrypted traffic";
           }
         }
       }
       leaf add-on {
         type enumeration {
           enum "idp" {
             description "IDP sessions";
           }
           enum "tunnel" {
             description "Tunnel sessions";
           }
           enum "nat" {
             description "Sessions with network address translation";
           }
           enum "services-offload" {
             description "Services-offload sessions";
           }
           enum "resource-manager" {
             description "Sessions with resource manager";
           }
           enum "application-firewall" {
             description "Show application-firewall sessions";
           }
           enum "application-traffic-control" {
             description "Show application-traffic-control sessions";
           }
           enum "security-intelligence" {
             description "Show security-intelligence sessions";
           }
           enum "advanced-anti-malware" {
             description "Show advanced-anti-malware sessions";
           }
         }
       }
       leaf application {
         description "Application protocol name";
         type enumeration {
           enum "dns" {
             description "Domain Name Service";
           }
           enum "ftp" {
             description "File Transfer Protocol";
           }
           enum "ignore" {
             description "Ignore application type";
           }
           enum "mgcp-ca" {
             description "MGCP-CA";
           }
           enum "mgcp-ua" {
             description "MGCP-UA";
           }
           enum "ms-rpc" {
             description "Microsoft RPC";
           }
           enum "pptp" {
             description "Point-to-Point Tunneling Protocol";
           }
           enum "sun-rpc" {
             description "Sun Microsystems RPC";
           }
           enum "q931" {
             description "Q.931";
           }
           enum "ras" {
             description "RAS";
           }
           enum "realaudio" {
             description "RealAudio";
           }
           enum "rsh" {
             description "Remote Shell";
           }
           enum "rtsp" {
             description "Real Time Streaming Protocol";
           }
           enum "sccp" {
             description "Skinny Client Control Protocol";
           }
           enum "sip" {
             description "Session Initiation Protocol";
           }
           enum "sqlnet-v2" {
             description "Oracle SQL*Net Version 2";
           }
           enum "talk" {
             description "Talk program";
           }
           enum "tftp" {
             description "Trivial File Transfer Protocol";
           }
           enum "http" {
             description "Hyper Text transfer protocol";
           }
           enum "https" {
             description "Secure HyperText Transfer Protocol";
           }
           enum "smtp" {
             description "Simple Mail Transfer Protocol";
           }
           enum "imap" {
             description "Internet Message Access Protocol";
           }
           enum "ssh" {
             description "Secure Shell";
           }
           enum "telnet" {
             description "Telnet Terminal Emulation Protocol";
           }
         }
       }
       leaf family {
         description "Protocol family";
         type enumeration {
           enum "inet" {
             description "Show IPv4";
           }
           enum "inet6" {
             description "Show IPv6/IPv6-NATPT";
           }
         }
       }
       leaf policy-id {
         description "Policy id value";
         type union {
           type string {
             pattern "<.*>|$.*";
           }
           type uint32 {
             range "1 .. 4294967295";
           }
         }
       }
       leaf interface {
         description "Name of incoming or outgoing interface";
         type string;
       }
       leaf application-firewall-rule-set {
         description "Show application-firewall session by rule-set";
         type string;
       }
       leaf dynamic-application {
         description "Dynamic application name";
         type string;
       }
       leaf dynamic-application-group {
         description "Dynamic application group name";
         type string;
       }
       leaf start-identifier {
         description "Show sessions from this start identifier";
         type union {
           type string {
             pattern "<.*>|$.*";
           }
           type uint32 {
             range "1 .. 4294967295";
           }
         }
       }
       leaf count {
         description "Number of entries to show";
         type union {
           type string {
             pattern "<.*>|$.*";
           }
           type uint32 {
             range "1 .. 4294967295";
           }
         }
       }
       leaf conn-tag {
         description "Session connection tag";
         type union {
           type string {
             pattern "<.*>|$.*";
           }
           type uint32 {
             range "0 .. 4294967295";
           }
         }
       }
     }
     output {
       choice output_c {
         case output-tag {
           leaf output {
             type string;
           }
         }
         case actual-tag {
           anyxml flow-session-information;
         }
         case multichassis-tag {
           anyxml multi-routing-engine-results;
         }
       }
     }
   }
   rpc get-flow-session-by-identifier {
     description "Show session with specified session identifier";
     input {
       uses command-forwarding;
       leaf session-identifier {
         description "Session identifier";
         type union {
           type string {
             pattern "<.*>|$.*";
           }
           type uint32 {
             range "1 .. 4294967295";
           }
         }
         mandatory true;
       }
     }
     output {
       choice output_c {
         case output-tag {
           leaf output {
             type string;
           }
         }
         case actual-tag {
           anyxml flow-session-information;
         }
         case multichassis-tag {
           anyxml multi-routing-engine-results;
         }
       }
     }
   }
   rpc get-flow-ipaction-information {
     description "Show ip-action table";
     input {
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf family {
         description "Protocol family";
         type enumeration {
           enum "inet" {
             description "Show IPv4";
           }
           enum "inet6" {
             description "Show IPv6/IPv6-NATPT";
           }
         }
       }
       leaf level {
         default "brief";
         type enumeration {
           enum "summary" {
             description "Show output summary";
           }
           enum "brief" {
             description "Show brief output (default)";
           }
         }
       }
     }
     output {
       choice output_c {
         case output-tag {
           leaf output {
             type string;
           }
         }
         case actual-tag {
           anyxml flow-ipaction-information;
         }
         case multichassis-tag {
           anyxml multi-routing-engine-results;
         }
       }
     }
   }
   rpc get-flow-ipaction-information-all {
     description "Show all ip-action entries";
     output {
       choice output_c {
         case output-tag {
           leaf output {
             type string;
           }
         }
         case actual-tag {
           anyxml flow-ipaction-information;
         }
         case multichassis-tag {
           anyxml multi-routing-engine-results;
         }
       }
     }
   }
   rpc get-forward-options-information {
     description "Show forward-options status";
     output {
       choice output_c {
         case output-tag {
           leaf output {
             type string;
           }
         }
         case actual-tag {
           anyxml forward-options-information;
         }
         case multichassis-tag {
           anyxml multi-routing-engine-results;
         }
       }
     }
   }
   rpc get-secure-wire-information {
     description "Show secure wire information";
     input {
       uses command-forwarding;
       leaf secure-wire-name {
         description "Display specified secure wire";
         type string;
       }
     }
     output {
       choice output_c {
         case output-tag {
           leaf output {
             type string;
           }
         }
         case actual-tag {
           anyxml secure-wire-information;
         }
         case multichassis-tag {
           anyxml multi-routing-engine-results;
         }
       }
     }
   }
   rpc get-mirror-filter {
     description "Show  mirror-filter with specified filter-name";
     input {
       uses command-forwarding;
       choice filter {
         case name {
           leaf get-mirror-filter-by-name {
             description "Mirror filter name";
             type string;
             mandatory true;
           }
         }
         case all {
           leaf get-mirror-filter-all {
             description "List all mirror filters Counter";
             type empty;
           }
         }
       }
     }
     output {
       choice output_c {
         case output-tag {
           leaf output {
             type string;
           }
         }
         case actual-tag {
           anyxml show-mirror-filter-entry;
         }
         case multichassis-tag {
           anyxml multi-routing-engine-results;
         }
       }
     }
   }
   rpc get-firewall-authentication-jims {
     description "Show JIMS information";
     input {
       choice filter {
         case statistics {
           leaf get-firewall-authentication-jims-statistics {
             description "Show firewall authentication JIMS statistics";
             type empty;
           }
         }
       }
     }
     output {
       choice output_c {
         case output-tag {
           leaf output {
             type string;
           }
         }
         case actual-tag {
           anyxml firewall-authentication-jims;
         }
         case multichassis-tag {
           anyxml multi-routing-engine-results;
         }
       }
     }
   }
   rpc get-firewall-authentication-users {
     description "Show current firewall authentication users";
     input {
       uses command-forwarding;
       choice filter {
         case identifier {
           leaf get-firewall-authentication-users-specific {
             description "Locate authentication entry by id";
             type union {
               type uint32;
               type string {
                 pattern "<.*>|$.*";
               }
             }
           }
         }
         case auth-type {
           leaf get-firewall-authentication-users {
             description "Show authentication entry matching the given auth-type";
             type enumeration {
               enum "user-firewall" {
                 description "User firewall authentication";
               }
               enum "pass-through" {
                 description "Pass-through authentication";
               }
               enum "web-authentication" {
                 description "Web firewall authentication";
               }
             }
           }
         }
         case address {
           leaf get-firewall-authentication-users-specific {
             description "Locate authentication entry by ip address";
             type jt:ipprefix;
           }
         }
         case from-zone {
           leaf from-zone {
             description "Show authentication entry matching the given source zone, null for web-auth and userfw-auth";
             type string;
           }
         }
         case to-zone {
           leaf to-zone {
             description "Show authentication entry matching the given destination zone, null for web-auth and userfw-auth";
             type string;
           }
         }
       }
     }
     output {
       choice output_c {
         case output-tag {
           leaf output {
             type string;
           }
         }
         case actual-tag {
           anyxml firewall-authentication-users;
         }
         case multichassis-tag {
           anyxml multi-routing-engine-results;
         }
       }
     }
   }
   rpc get-firewall-authentication-history {
     description "Show firewall authentication history";
     input {
       uses command-forwarding;
       choice filter {
         case identifier {
           leaf get-firewall-authentication-history-specific {
             description "Locate authentication history by id";
             type union {
               type uint32;
               type string {
                 pattern "<.*>|$.*";
               }
             }
           }
         }
         case address {
           leaf get-firewall-authentication-history-specific {
             description "Locate authentication history by ip address";
             type jt:ipprefix;
           }
         }
         case from-zone {
           leaf from-zone {
             description "Show authentication history matching the given source zone, null for web-auth and userfw-auth";
             type string;
           }
         }
         case to-zone {
           leaf to-zone {
             description "Show authentication history matching the given destination zone, null for web-auth and userfw-auth";
             type string;
           }
         }
       }
     }
     output {
       choice output_c {
         case output-tag {
           leaf output {
             type string;
           }
         }
         case actual-tag {
           anyxml firewall-authentication-history;
         }
         case multichassis-tag {
           anyxml multi-routing-engine-results;
         }
       }
     }
   }
   rpc get-security-screen-ids-data {
     description "Show screen data";
     output {
       choice output_c {
         case output-tag {
           leaf output {
             type string;
           }
         }
         case actual-tag {
           anyxml show-ids-data;
         }
         case multichassis-tag {
           anyxml multi-routing-engine-results;
         }
       }
     }
   }
   rpc get-security-screen-ids-whitelist {
     description "Show white list data";
     input {
       uses command-forwarding;
       leaf wlist-name {
         description "White list name";
         type string;
         mandatory true;
       }
     }
     output {
       choice output_c {
         case output-tag {
           leaf output {
             type string;
           }
         }
         case actual-tag {
           anyxml show-ids-whitelist;
         }
         case multichassis-tag {
           anyxml multi-routing-engine-results;
         }
       }
     }
   }
   rpc get-security-screen-ids-status {
     description "Show status of screen object";
     input {
       uses command-forwarding;
       leaf screen-name {
         description "Screen name";
         type string;
         mandatory true;
       }
     }
     output {
       choice output_c {
         case output-tag {
           leaf output {
             type string;
           }
         }
         case actual-tag {
           anyxml show-ids-status;
         }
         case multichassis-tag {
           anyxml multi-routing-engine-results;
         }
       }
     }
   }
   rpc get-ids-statistics {
     description "Show screen attack statistics information";
     input {
       uses command-forwarding;
       choice filter {
         case zone {
           leaf zone {
             description "IDS statistics zone";
             type string;
           }
         }
         case interface {
           leaf interface {
             description "IDS statistics interface";
             type string;
           }
         }
       }
       leaf ip {
         description "IDS statistics ip";
         type enumeration {
           enum "tunnel" {
             description "IDS statistics ip tunnel";
           }
         }
       }
     }
     output {
       choice output_c {
         case output-tag {
           leaf output {
             type string;
           }
         }
         case actual-tag {
           anyxml ids-statistics;
         }
         case multichassis-tag {
           anyxml multi-routing-engine-results;
         }
       }
     }
   }
   rpc get-interface-nat-ports-information {
     description "Show interface nat ports information";
     output {
       choice output_c {
         case output-tag {
           leaf output {
             type string;
           }
         }
         case actual-tag {
           anyxml interface-nat-ports-information;
         }
         case multichassis-tag {
           anyxml multi-routing-engine-results;
         }
       }
     }
   }
   rpc get-incoming-table-information {
     description "Show incoming table information";
     status deprecated;
     output {
       choice output_c {
         case output-tag {
           leaf output {
             type string;
           }
         }
         case actual-tag {
           anyxml incoming-table-information;
         }
         case multichassis-tag {
           anyxml multi-routing-engine-results;
         }
       }
     }
   }
   rpc get-firewall-policies {
     description "Show security firewall policies";
     input {
       uses command-forwarding;
       leaf from-zone {
         description "Show the policy information matching the given source zone";
         type string;
       }
       leaf to-zone {
         description "Show the policy information matching the given destination zone";
         type string;
       }
       leaf policy-name {
         description "Show the policy information matching the given policy name";
         type string;
       }
       leaf detail {
         description "Show the detailed information";
         type empty;
       }
       leaf zone-context {
         description "Show the count of policies in each context (from-zone and to-zone)";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       leaf application-firewall {
         description "Show the information of application-firewall";
         type empty;
       }
       leaf service-set {
         description "Name of service set";
         type string;
       }
       leaf interface {
         description "Name of adaptive services interface";
         type string;
       }
     }
     output {
       choice output_c {
         case output-tag {
           leaf output {
             type string;
           }
         }
         case actual-tag {
           anyxml security-policies;
         }
         case multichassis-tag {
           anyxml multi-routing-engine-results;
         }
       }
     }
   }
   rpc get-security-policies-hit-count {
     description "Show the hit count of policies";
     input {
       uses command-forwarding;
       leaf from-zone {
         description "Show the policy hit-count matching the given source zone";
         type string;
       }
       leaf to-zone {
         description "Show the policy hit-count matching the given destination zone";
         type string;
       }
       leaf order {
         description "Policy order";
         type enumeration {
           enum "ascending" {
             description "Ascending order";
           }
           enum "descending" {
             description "Descending order";
           }
         }
       }
       leaf less-than {
         description "Maximum hit-count ";
         type union {
           type string {
             pattern "<.*>|$.*";
           }
           type uint32 {
             range "0 .. 4294967295";
           }
         }
       }
       leaf greater-than {
         description "Minimum hit-count ";
         type union {
           type string {
             pattern "<.*>|$.*";
           }
           type uint32 {
             range "0 .. 4294967295";
           }
         }
       }
     }
     output {
       choice output_c {
         case output-tag {
           leaf output {
             type string;
           }
         }
         case actual-tag {
           anyxml policy-hit-count;
         }
         case multichassis-tag {
           anyxml multi-routing-engine-results;
         }
       }
     }
   }
   rpc get-global-firewall-policies {
     description "Show the policy information of global policies";
     input {
       uses command-forwarding;
       leaf policy-name {
         description "Show the policy information matching the given policy name";
         type string;
       }
       leaf detail {
         description "Show the detailed information";
         type empty;
       }
       leaf zone-context {
         description "Show the count of policies in each context (from-zone and to-zone)";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       leaf application-firewall {
         description "Show the information of application-firewall";
         type empty;
       }
     }
     output {
       choice output_c {
         case output-tag {
           leaf output {
             type string;
           }
         }
         case actual-tag {
           anyxml security-global-policies;
         }
         case multichassis-tag {
           anyxml multi-routing-engine-results;
         }
       }
     }
   }
   rpc unknown-source-identity-of-policies {
     description "Show the unknown-source-identity of policy";
     output {
       choice output_c {
         case output-tag {
           leaf output {
             type string;
           }
         }
         case actual-tag {
           anyxml unknown-source-identity;
         }
         case multichassis-tag {
           anyxml multi-routing-engine-results;
         }
       }
     }
   }
   rpc match-firewall-policies {
     description "Show security match policies";
     input {
       uses command-forwarding;
       leaf from-zone {
         description "Match policy for the given source zone (optional)";
         type string;
         mandatory true;
       }
       leaf to-zone {
         description "Match policy for the given destination zone (optional)";
         type string;
         mandatory true;
       }
       leaf source-ip {
         description "Match policy for the given source IP";
         type string;
         mandatory true;
       }
       leaf destination-ip {
         description "Match policy for the given destination IP";
         type string;
         mandatory true;
       }
       leaf source-port {
         description "Match policy for the given source port";
         type union {
           type string {
             pattern "<.*>|$.*";
           }
           type uint32 {
             range "1 .. 65535";
           }
         }
         mandatory true;
       }
       leaf destination-port {
         description "Match policy for the given destination port";
         type union {
           type string {
             pattern "<.*>|$.*";
           }
           type uint32 {
             range "1 .. 65535";
           }
         }
         mandatory true;
       }
       leaf protocol {
         description "Match policy for the given protocol";
         type string;
         mandatory true;
       }
       leaf dynamic-application {
         description "Match policy for the given dynamic application";
         type string;
       }
       leaf result-count {
         description "Expected results count (optional)";
         type union {
           type string {
             pattern "<.*>|$.*";
           }
           type uint32 {
             range "1 .. 16";
           }
         }
       }
       leaf source-identity {
         description "Match policy for the given roles (optional)";
         type string {
         }
       }
       leaf source-end-user-profile {
         description "Match policy for the given source-end-user-profile (optional)";
         type string;
       }
     }
     output {
       choice output_c {
         case output-tag {
           leaf output {
             type string;
           }
         }
         case actual-tag {
           anyxml security-policy-match;
         }
         case multichassis-tag {
           anyxml multi-routing-engine-results;
         }
       }
     }
   }
   rpc match-global-policies {
     description "Match global policy";
     input {
       uses command-forwarding;
       leaf source-ip {
         description "Match policy for the given source IP";
         type string;
         mandatory true;
       }
       leaf destination-ip {
         description "Match policy for the given destination IP";
         type string;
         mandatory true;
       }
       leaf source-port {
         description "Match policy for the given source port";
         type union {
           type string {
             pattern "<.*>|$.*";
           }
           type uint32 {
             range "1 .. 65535";
           }
         }
         mandatory true;
       }
       leaf destination-port {
         description "Match policy for the given destination port";
         type union {
           type string {
             pattern "<.*>|$.*";
           }
           type uint32 {
             range "1 .. 65535";
           }
         }
         mandatory true;
       }
       leaf protocol {
         description "Match policy for the given protocol";
         type string;
         mandatory true;
       }
       leaf dynamic-application {
         description "Match policy for the given dynamic application";
         type string;
       }
       leaf result-count {
         description "Expected results count (optional)";
         type union {
           type string {
             pattern "<.*>|$.*";
           }
           type uint32 {
             range "1 .. 16";
           }
         }
       }
       leaf source-identity {
         description "Match policy for the given roles (optional)";
         type string {
         }
       }
       leaf source-end-user-profile {
         description "Match policy for the given source-end-user-profile (optional)";
         type string;
       }
       leaf from-zone {
         description "Match policy for the given source zone (optional)";
         type string;
       }
       leaf to-zone {
         description "Match policy for the given destination zone (optional)";
         type string;
       }
     }
     output {
       choice output_c {
         case output-tag {
           leaf output {
             type string;
           }
         }
         case actual-tag {
           anyxml global-policy-match;
         }
         case multichassis-tag {
           anyxml multi-routing-engine-results;
         }
       }
     }
   }
   rpc get-firewall-policy-dns-cache {
     description "Show DNS cache of firewall policy";
     input {
       leaf dns-name {
         description "Show DNS cache matching the given DNS name";
         type string;
       }
     }
     output {
       choice output_c {
         case output-tag {
           leaf output {
             type string;
           }
         }
         case actual-tag {
           anyxml security-dns-cache;
         }
         case multichassis-tag {
           anyxml multi-routing-engine-results;
         }
       }
     }
   }
   rpc shadow-firewall-policies {
     description "Show security shadow policies";
     input {
       uses command-forwarding;
       leaf from-zone {
         description "Show shadow policy information for the given source zone";
         type string;
         mandatory true;
       }
       leaf to-zone {
         description "Show shadow policy information for the given destination zone";
         type string;
         mandatory true;
       }
       leaf policy {
         description "Show shadow policy information for the given policy";
         type string;
       }
       leaf reverse {
         description "Show the policies which shadows the given policy";
         type empty;
       }
     }
     output {
       choice output_c {
         case output-tag {
           leaf output {
             type string;
           }
         }
         case actual-tag {
           anyxml security-policy-shadow;
         }
         case multichassis-tag {
           anyxml multi-routing-engine-results;
         }
       }
     }
   }
   rpc shadow-global-policies {
     description "Shadow policy information for global policy";
     input {
       uses command-forwarding;
       leaf policy {
         description "Show shadow policy information for the given policy";
         type string;
       }
       leaf reverse {
         description "Show the policies which shadows the given policy";
         type empty;
       }
     }
     output {
       choice output_c {
         case output-tag {
           leaf output {
             type string;
           }
         }
         case actual-tag {
           anyxml global-policy-shadow;
         }
         case multichassis-tag {
           anyxml multi-routing-engine-results;
         }
       }
     }
   }
   rpc show-ragw-statistics {
     description "Show TCP encapsulation statistics";
     output {
       choice output_c {
         case output-tag {
           leaf output {
             type string;
           }
         }
         case actual-tag {
           anyxml ragw-statistics;
         }
         case multichassis-tag {
           anyxml multi-routing-engine-results;
         }
       }
     }
   }
   rpc show-ragw-connection {
     description "Show TCP encap session details";
     input {
       uses command-forwarding;
       leaf level {
         default "brief";
         type enumeration {
           enum "brief" {
             description "Display brief output";
           }
           enum "detail" {
             description "Display detailed output";
           }
         }
       }
       leaf show-sess-id-connection-details {
         description "Session id";
         type union {
           type string {
             pattern "<.*>|$.*";
           }
           type uint32 {
             range "1 .. 4294967295";
           }
         }
       }
     }
     output {
       choice output_c {
         case output-tag {
           leaf output {
             type string;
           }
         }
         case actual-tag {
           anyxml ragw-connection;
         }
         case multichassis-tag {
           anyxml multi-routing-engine-results;
         }
       }
     }
   }
   rpc get-resmgr-group-active {
     description "Show active resource manager group service information";
     input {
       uses command-forwarding;
       leaf group-number {
         description "Show active resource manager group";
         type union {
           type uint32;
           type string {
             pattern "<.*>|$.*";
           }
         }
       }
     }
     output {
       choice output_c {
         case output-tag {
           leaf output {
             type string;
           }
         }
         case actual-tag {
           anyxml resmgr-group-active;
         }
         case multichassis-tag {
           anyxml multi-routing-engine-results;
         }
       }
     }
   }
   rpc get-resmgr-resource-active {
     description "Show active resource manager resource service information";
     input {
       uses command-forwarding;
       leaf resource-number {
         description "Show active resource manager resource";
         type union {
           type uint32;
           type string {
             pattern "<.*>|$.*";
           }
         }
       }
     }
     output {
       choice output_c {
         case output-tag {
           leaf output {
             type string;
           }
         }
         case actual-tag {
           anyxml resmgr-resource-active;
         }
         case multichassis-tag {
           anyxml multi-routing-engine-results;
         }
       }
     }
   }
   rpc get-resmgr-settings {
     description "Show resource manager settings information";
     output {
       choice output_c {
         case output-tag {
           leaf output {
             type string;
           }
         }
         case actual-tag {
           anyxml resmgr-settings;
         }
         case multichassis-tag {
           anyxml multi-routing-engine-results;
         }
       }
     }
   }
   rpc get-resource-manager-summary {
     description "Show resource manager summary information";
     output {
       choice output_c {
         case output-tag {
           leaf output {
             type string;
           }
         }
         case actual-tag {
           anyxml resource-manager-summary-information;
         }
         case multichassis-tag {
           anyxml multi-routing-engine-results;
         }
       }
     }
   }
   rpc get-userfw-local-auth-table-all {
     description "Show the entire local user authentication table";
     input {
       uses command-forwarding;
       leaf level {
         default "brief";
         type enumeration {
           enum "brief" {
             description "Show brief output (default)";
           }
           enum "extensive" {
             description "Show extensive output";
           }
         }
       }
     }
     output {
       choice output_c {
         case output-tag {
           leaf output {
             type string;
           }
         }
         case actual-tag {
           anyxml user-identification;
         }
         case multichassis-tag {
           anyxml multi-routing-engine-results;
         }
       }
     }
   }
   rpc get-userfw-local-auth-table-ip {
     description "Show local user authentication information for the specified ip-address";
     input {
       uses command-forwarding;
       leaf ip-address {
         description "IP address";
         type jt:ipaddr;
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-local-auth-table-user {
     description "Show local user authentication information for the specified user";
     input {
       uses command-forwarding;
       leaf user-name {
         description "User name";
         type string {
           length "1 .. 64";
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-local-auth-table-role {
     description "Show local user authentication information for the specified role";
     input {
       uses command-forwarding;
       leaf role-name {
         description "Role name";
         type string {
           length "1 .. 63";
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-local-auth-table-start {
     description "Show local user authentication table information from a given position";
     input {
       uses command-forwarding;
       leaf start {
         type union {
           type string {
             pattern "<.*>|$.*";
           }
           type uint32 {
             range "1 .. 65535";
           }
         }
         mandatory true;
       }
       leaf count {
         description "Number of local user authentication table entries to show";
         type union {
           type string {
             pattern "<.*>|$.*";
           }
           type uint32 {
             range "1 .. 65535";
           }
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-role-info {
     description "Show all information";
     input {
       uses command-forwarding;
       leaf all {
         type empty;
       }
     }
     output {
       choice output_c {
         case output-tag {
           leaf output {
             type string;
           }
         }
         case actual-tag {
           anyxml user-identification;
         }
         case multichassis-tag {
           anyxml multi-routing-engine-results;
         }
       }
     }
   }
   rpc get-userfw-role-info-start {
     description "Show information from a given position";
     input {
       uses command-forwarding;
       leaf start {
         type union {
           type string {
             pattern "<.*>|$.*";
           }
           type uint32 {
             range "1 .. 65535";
           }
         }
         mandatory true;
       }
       leaf count {
         description "Number of entries to show";
         type union {
           type string {
             pattern "<.*>|$.*";
           }
           type uint32 {
             range "1 .. 65535";
           }
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-user-info {
     description "Show all information";
     input {
       uses command-forwarding;
       leaf all {
         type empty;
       }
     }
     output {
       choice output_c {
         case output-tag {
           leaf output {
             type string;
           }
         }
         case actual-tag {
           anyxml user-identification;
         }
         case multichassis-tag {
           anyxml multi-routing-engine-results;
         }
       }
     }
   }
   rpc get-userfw-user-info-start {
     description "Show information from a given position";
     input {
       uses command-forwarding;
       leaf start {
         type union {
           type string {
             pattern "<.*>|$.*";
           }
           type uint32 {
             range "1 .. 65535";
           }
         }
         mandatory true;
       }
       leaf count {
         description "Number of entries to show";
         type union {
           type string {
             pattern "<.*>|$.*";
           }
           type uint32 {
             range "1 .. 65535";
           }
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-source-identity-info {
     description "Show all information";
     input {
       uses command-forwarding;
       leaf all {
         type empty;
       }
     }
     output {
       choice output_c {
         case output-tag {
           leaf output {
             type string;
           }
         }
         case actual-tag {
           anyxml user-identification;
         }
         case multichassis-tag {
           anyxml multi-routing-engine-results;
         }
       }
     }
   }
   rpc get-userfw-source-identity-info-start {
     description "Show information from a given position";
     input {
       uses command-forwarding;
       leaf start {
         type union {
           type string {
             pattern "<.*>|$.*";
           }
           type uint32 {
             range "1 .. 65535";
           }
         }
         mandatory true;
       }
       leaf count {
         description "Number of entries to show";
         type union {
           type string {
             pattern "<.*>|$.*";
           }
           type uint32 {
             range "1 .. 65535";
           }
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-zones-information {
     description "Show security zone information";
     input {
       uses command-forwarding;
       choice filter {
         case name {
           leaf get-zones-named-information {
             description "Show information for a specified zone";
             type string;
           }
         }
         case type {
           leaf type {
             description "Show information for zones of a specified type";
             type enumeration {
               enum "functional" {
                 description "Show information for functional zones";
               }
               enum "security" {
                 description "Show information for security zones";
               }
             }
           }
         }
       }
       leaf level {
         default "detail";
         type enumeration {
           enum "terse" {
             description "Display terse output";
           }
           enum "detail" {
             description "Display detailed output (default)";
           }
         }
       }
     }
     output {
       choice output_c {
         case output-tag {
           leaf output {
             type string;
           }
         }
         case actual-tag {
           anyxml zones-information;
         }
         case multichassis-tag {
           anyxml multi-routing-engine-results;
         }
       }
     }
   }
   rpc get-mka-session-information {
     description "Show MKA sessions information";
     output {
       choice output_c {
         case output-tag {
           leaf output {
             type string;
           }
         }
         case actual-tag {
           anyxml mka-session-information;
         }
         case multichassis-tag {
           anyxml multi-routing-engine-results;
         }
       }
     }
   }
   rpc get-mka-session-interface-information {
     description "Show MKA session on this interface";
     input {
       leaf interface-name {
         description "Show MKA session for this interface";
         default "all";
         type union {
           type jt:interface-name;
           type string {
             pattern "<.*>|$.*";
           }
         }
       }
     }
     output {
       choice output_c {
         case output-tag {
           leaf output {
             type string;
           }
         }
         case actual-tag {
           anyxml mka-session-interface-information;
         }
         case multichassis-tag {
           anyxml multi-routing-engine-results;
         }
       }
     }
   }
   rpc get-mka-statistics {
     description "Show MKA statistics";
     output {
       choice output_c {
         case output-tag {
           leaf output {
             type string;
           }
         }
         case actual-tag {
           anyxml mka-statistics;
         }
         case multichassis-tag {
           anyxml multi-routing-engine-results;
         }
       }
     }
   }
   rpc get-mka-interface-statistics {
     description "Show MKA statistics on this interface";
     input {
       leaf interface-name {
         description "Show MKA statistics for this interface";
         default "all";
         type union {
           type jt:interface-name;
           type string {
             pattern "<.*>|$.*";
           }
         }
       }
     }
     output {
       choice output_c {
         case output-tag {
           leaf output {
             type string;
           }
         }
         case actual-tag {
           anyxml mka-interface-statistics;
         }
         case multichassis-tag {
           anyxml multi-routing-engine-results;
         }
       }
     }
   }
   rpc get-macsec-connection-information {
     description "Show MAC Security connections information";
     output {
       choice output_c {
         case output-tag {
           leaf output {
             type string;
           }
         }
         case actual-tag {
           anyxml macsec-connection-information;
         }
         case multichassis-tag {
           anyxml multi-routing-engine-results;
         }
       }
     }
   }
   rpc get-macsec-connection-interface-information {
     description "Show MAC security connections on this interface";
     input {
       leaf interface-name {
         description "Show MAC security connections for this interface";
         default "all";
         type union {
           type jt:interface-name;
           type string {
             pattern "<.*>|$.*";
           }
         }
       }
     }
     output {
       choice output_c {
         case output-tag {
           leaf output {
             type string;
           }
         }
         case actual-tag {
           anyxml macsec-connection-interface-information;
         }
         case multichassis-tag {
           anyxml multi-routing-engine-results;
         }
       }
     }
   }
   rpc get-macsec-statistics {
     description "Show MAC Security statistics";
     input {
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml macsec-statistics;
         }
         case multichassis-tag {
           anyxml multi-routing-engine-results;
         }
       }
     }
   }
   rpc get-macsec-interface-statistics {
     description "Show MAC security statistics on this interface";
     input {
       leaf verbosity_level {
         default "brief";
         type enumeration {
           enum "brief" {
             description "Display brief output (default)";
           }
           enum "detail" {
             description "Display detailed output";
           }
         }
       }
       leaf interface-name {
         description "Show MAC security statistics for this interface";
         default "all";
         type union {
           type jt:interface-name;
           type string {
             pattern "<.*>|$.*";
           }
         }
       }
     }
     output {
       choice output_c {
         case output-tag {
           leaf output {
             type string;
           }
         }
         case actual-tag {
           anyxml macsec-interface-statistics;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
