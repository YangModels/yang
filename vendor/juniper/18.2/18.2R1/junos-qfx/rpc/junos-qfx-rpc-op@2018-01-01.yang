/*
 * Copyright (c) 2018 Juniper Networks, Inc.
 * All rights reserved.
 */
 module junos-qfx-rpc-op {
   namespace "http://yang.juniper.net/junos-qfx/rpc/op";

   prefix op;

   import junos-common-types {
     prefix jt;
   }

   organization "Juniper Networks, Inc.";

   contact "yang-support@juniper.net";

   description "Junos RPC YANG module for op command(s)";

   revision 2018-01-01 {
     description "Junos: 18.2R1.9";
   }

   rpc op-script {
     description "Invoke an operation script";
     input {
       leaf script {
         description "Name of script to run";
         type string;
         mandatory true;
       }
       leaf detail {
         description "Display detailed output";
         type empty;
       }
       container argument {
         leaf name {
           description "Argument name";
           type string;
         }
         leaf value {
           description "Argument value";
           type string;
         }
       }
       leaf invoke-debugger {
         description "Invoke script in debugger mode";
         type enumeration {
           enum "cli" {
             description "Invoke debugger in cli";
           }
         }
       }
     }
     output {
       leaf output {
         type string;
       }
     }
   }
   rpc op-url {
     description "Execution of remote op script";
     input {
       leaf url-name {
         description "URL for script";
         type string;
         mandatory true;
       }
       leaf detail {
         description "Display detailed output";
         type empty;
       }
       leaf algorithm {
         type enumeration {
           enum "md5" {
             description "MD5";
           }
           enum "sha1" {
             description "SHA1";
           }
           enum "sha-256" {
             description "SHA-256";
           }
         }
       }
       leaf key-value {
         description "Checksum value";
         type string;
       }
       container argument {
         leaf name {
           description "Argument name";
           type string;
         }
         leaf value {
           description "Argument value";
           type string;
         }
       }
     }
     output {
       leaf output {
         type string;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
