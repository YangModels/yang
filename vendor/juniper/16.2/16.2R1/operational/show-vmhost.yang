/*
 * Copyright (c) 2017 Juniper Networks, Inc.
 * All rights reserved.
 */

 module show-vmhost {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-vmhost-staus {
     description "Show RE vmhost status";
   }
   rpc get-vmhost-information {
     description "Show RE vmhost information";
   }
   rpc get-vmhost-hardware {
     description "Show RE hardware";
   }
   rpc get-vmhost-resource-usage-information {
     description "Show RE vmhost resource usage";
     output {
       container sdk-vmmd-output {
         container output-compute-cluster {
           leaf output-compute-cluster-name {
             type string;
             description "Compute cluster name";
           }
           leaf output-compute-cluster-meta {
             type string;
             description "Compute cluster meta data";
           }
           container output-compute-node {
             leaf output-compute-node-name {
               type string;
               description "Compute node name";
             }
             leaf output-compute-node-note {
               type string;
               description "Compute node note message";
             }
             leaf output-compute-node-error {
               type string;
               description "Compute node error";
             }
             leaf output-compute-node-data {
               type string;
               description "Compute node data";
             }
           }
         }
       }
     }
   }
   rpc get-vmhost-processes-information {
     description "Show RE vmhost processes";
     output {
       container sdk-vmmd-output {
         container output-compute-cluster {
           leaf output-compute-cluster-name {
             type string;
             description "Compute cluster name";
           }
           leaf output-compute-cluster-meta {
             type string;
             description "Compute cluster meta data";
           }
           container output-compute-node {
             leaf output-compute-node-name {
               type string;
               description "Compute node name";
             }
             leaf output-compute-node-note {
               type string;
               description "Compute node note message";
             }
             leaf output-compute-node-error {
               type string;
               description "Compute node error";
             }
             leaf output-compute-node-data {
               type string;
               description "Compute node data";
             }
           }
         }
       }
     }
   }
   rpc get-vmhost-uptime {
     description "Show RE vmhost uptime and reboot reason ";
     output {
       container vmmd-host-uptime {
         leaf vmhost-current-time {
           type string;
           description "Vmhost node time detail";
         }
         leaf vmhost-uptime {
           type string;
           description "VMhost uptime detail";
         }
         leaf vmhost-reboot-reason {
           type string;
           description "VMhost reboot reason detail";
         }
       }
     }
   }
   rpc get-vmhost-netstat {
     description "Show RE vmhost netstat";
   }
   rpc get-vmhost-bridge-information {
     description "Show RE vmhost bridge";
     output {
       container sdk-vmmd-output {
         container output-compute-cluster {
           leaf output-compute-cluster-name {
             type string;
             description "Compute cluster name";
           }
           leaf output-compute-cluster-meta {
             type string;
             description "Compute cluster meta data";
           }
           container output-compute-node {
             leaf output-compute-node-name {
               type string;
               description "Compute node name";
             }
             leaf output-compute-node-note {
               type string;
               description "Compute node note message";
             }
             leaf output-compute-node-error {
               type string;
               description "Compute node error";
             }
             leaf output-compute-node-data {
               type string;
               description "Compute node data";
             }
           }
         }
       }
     }
   }
   rpc get-vmhost-crash-information {
     description "Show RE vmhost crash information";
     output {
       container sdk-vmmd-output {
         container output-compute-cluster {
           leaf output-compute-cluster-name {
             type string;
             description "Compute cluster name";
           }
           leaf output-compute-cluster-meta {
             type string;
             description "Compute cluster meta data";
           }
           container output-compute-node {
             leaf output-compute-node-name {
               type string;
               description "Compute node name";
             }
             leaf output-compute-node-note {
               type string;
               description "Compute node note message";
             }
             leaf output-compute-node-error {
               type string;
               description "Compute node error";
             }
             leaf output-compute-node-data {
               type string;
               description "Compute node data";
             }
           }
         }
       }
     }
   }
   rpc get-vmhost-logs-information {
     description "Show RE vmhost trace logs";
     output {
       container sdk-vmmd-output {
         container output-compute-cluster {
           leaf output-compute-cluster-name {
             type string;
             description "Compute cluster name";
           }
           leaf output-compute-cluster-meta {
             type string;
             description "Compute cluster meta data";
           }
           container output-compute-node {
             leaf output-compute-node-name {
               type string;
               description "Compute node name";
             }
             leaf output-compute-node-note {
               type string;
               description "Compute node note message";
             }
             leaf output-compute-node-error {
               type string;
               description "Compute node error";
             }
             leaf output-compute-node-data {
               type string;
               description "Compute node data";
             }
           }
         }
       }
     }
   }
   rpc get-vmhost-version-information {
     description "Show vmhost version information";
   }
   rpc get-vmhost-snapshot-information {
     description "Show vmhost snapshot information";
   }
   rpc get-vmhost-management-if-info {
     description "Display details of the host's management interface";
     output {
       container vmmd-management-if-info {
         leaf vmhost-management-if-admin-status {
           type string;
           description "Administrative status";
         }
         leaf vmhost-management-if-link-status {
           type string;
           description "Link status";
         }
         leaf vmhost-management-if-speed {
           type string;
           description "Link speed";
         }
         leaf vmhost-management-if-linkmode {
           type string;
           description "Link operational mode";
         }
       }
     }
   }
   rpc show-vmhost-hard-disk-test {
     description "Run smartd self tests on hard disks";
     input {
       container test-type {
         choice test-type_c {
           case status {
             leaf status {
               description "Display status of test";
               type empty;
             }
           }
         }
       }
       leaf disk {
         description "Name of hard disk";
         type string;
       }
     }
   }
 }
