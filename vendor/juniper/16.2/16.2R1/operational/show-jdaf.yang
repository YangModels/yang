/*
 * Copyright (c) 2017 Juniper Networks, Inc.
 * All rights reserved.
 */

 module show-jdaf {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-jdaf-command-server-stats {
     description "Show JDAF server side statistics";
     output {
       container jdaf-server-statistics {
         leaf srv-conn-requests {
           type uint32;
           description "Service connection requests received";
         }
         leaf srv-conn-accepts {
           type uint32;
           description "Service connections accpeted";
         }
         leaf srv-conn-rejects {
           type uint32;
           description "Service connections rejected";
         }
         leaf srv-conn-errors {
           type uint32;
           description "Service connection errors";
         }
         container listener-statistics {
           leaf routing-instance-id {
             type uint32;
             description "Routing instance id";
           }
           leaf srv-accepts {
             type uint32;
             description "Accepts on server socket";
           }
           leaf srv-accept-errors {
             type uint32;
             description "Errors while accept on server socket";
           }
         }
       }
     }
   }
   rpc get-jdaf-command-client-stats {
     description "Show JDAF client message statistics";
     output {
       container jdaf-clients-statistics {
         leaf error-msg {
           type string;
           description "Error message";
         }
         container jdaf-client-statistics {
           description "Client statistics";
           leaf client {
             type uint32;
             description "Service Client Id";
           }
           leaf rx-bytes {
             type uint32;
             description "Bytes received";
           }
           leaf tx-bytes {
             type uint32;
             description "Bytes transmitted";
           }
           leaf tx-queued {
             type uint32;
             description "Bytes queued for transmission";
           }
           leaf rx-msgs {
             type uint32;
             description "Messages received";
           }
           leaf rx-errors {
             type uint32;
             description "Errors on receive";
           }
           leaf tx-msgs {
             type uint32;
             description "Messages transmitted";
           }
           leaf tx-errors {
             type uint32;
             description "Errors on transmission";
           }
           container rpc-statistics {
             leaf name {
               type string;
               description "Message name";
             }
             leaf requests {
               type uint32;
               description "Service requests received";
             }
             leaf successes {
               type uint32;
               description "Service requests succeeded";
             }
             leaf failures {
               type uint32;
               description "Service requests failed";
             }
           }
           container notify-statistics {
             leaf name {
               type string;
               description "Message name";
             }
             leaf sent {
               type uint32;
               description "Service notifications sent";
             }
           }
         }
       }
     }
   }
   rpc get-jdaf-command-clients {
     description "Show JDAF client information";
     output {
       container jdaf-clients {
         container jdaf-client {
           description "Client information";
           leaf client {
             type uint32;
             description "Service Client Id";
           }
           leaf state {
             type string;
             description "State of the client";
           }
           leaf url {
             type string;
             description "Client URL";
           }
         }
       }
     }
   }
   rpc get-jdaf-config-server-stats {
     description "Show JDAF server side statistics";
     output {
       container jdaf-server-statistics {
         leaf srv-conn-requests {
           type uint32;
           description "Service connection requests received";
         }
         leaf srv-conn-accepts {
           type uint32;
           description "Service connections accpeted";
         }
         leaf srv-conn-rejects {
           type uint32;
           description "Service connections rejected";
         }
         leaf srv-conn-errors {
           type uint32;
           description "Service connection errors";
         }
         container listener-statistics {
           leaf routing-instance-id {
             type uint32;
             description "Routing instance id";
           }
           leaf srv-accepts {
             type uint32;
             description "Accepts on server socket";
           }
           leaf srv-accept-errors {
             type uint32;
             description "Errors while accept on server socket";
           }
         }
       }
     }
   }
   rpc get-jdaf-config-client-stats {
     description "Show JDAF client message statistics";
     output {
       container jdaf-clients-statistics {
         leaf error-msg {
           type string;
           description "Error message";
         }
         container jdaf-client-statistics {
           description "Client statistics";
           leaf client {
             type uint32;
             description "Service Client Id";
           }
           leaf rx-bytes {
             type uint32;
             description "Bytes received";
           }
           leaf tx-bytes {
             type uint32;
             description "Bytes transmitted";
           }
           leaf tx-queued {
             type uint32;
             description "Bytes queued for transmission";
           }
           leaf rx-msgs {
             type uint32;
             description "Messages received";
           }
           leaf rx-errors {
             type uint32;
             description "Errors on receive";
           }
           leaf tx-msgs {
             type uint32;
             description "Messages transmitted";
           }
           leaf tx-errors {
             type uint32;
             description "Errors on transmission";
           }
           container rpc-statistics {
             leaf name {
               type string;
               description "Message name";
             }
             leaf requests {
               type uint32;
               description "Service requests received";
             }
             leaf successes {
               type uint32;
               description "Service requests succeeded";
             }
             leaf failures {
               type uint32;
               description "Service requests failed";
             }
           }
           container notify-statistics {
             leaf name {
               type string;
               description "Message name";
             }
             leaf sent {
               type uint32;
               description "Service notifications sent";
             }
           }
         }
       }
     }
   }
   rpc get-jdaf-config-clients {
     description "Show JDAF client information";
     output {
       container jdaf-clients {
         container jdaf-client {
           description "Client information";
           leaf client {
             type uint32;
             description "Service Client Id";
           }
           leaf state {
             type string;
             description "State of the client";
           }
           leaf url {
             type string;
             description "Client URL";
           }
         }
       }
     }
   }
   rpc get-jdaf-firewall-server-stats {
     description "Show JDAF server side statistics";
     output {
       container jdaf-server-statistics {
         leaf srv-conn-requests {
           type uint32;
           description "Service connection requests received";
         }
         leaf srv-conn-accepts {
           type uint32;
           description "Service connections accpeted";
         }
         leaf srv-conn-rejects {
           type uint32;
           description "Service connections rejected";
         }
         leaf srv-conn-errors {
           type uint32;
           description "Service connection errors";
         }
         container listener-statistics {
           leaf routing-instance-id {
             type uint32;
             description "Routing instance id";
           }
           leaf srv-accepts {
             type uint32;
             description "Accepts on server socket";
           }
           leaf srv-accept-errors {
             type uint32;
             description "Errors while accept on server socket";
           }
         }
       }
     }
   }
   rpc get-jdaf-firewall-client-stats {
     description "Show JDAF client message statistics";
     input {
       leaf client-id {
         description "Client id";
         default "0";
         type uint32;
       }
     }
     output {
       container jdaf-clients-statistics {
         leaf error-msg {
           type string;
           description "Error message";
         }
         container jdaf-client-statistics {
           description "Client statistics";
           leaf client {
             type uint32;
             description "Service Client Id";
           }
           leaf rx-bytes {
             type uint32;
             description "Bytes received";
           }
           leaf tx-bytes {
             type uint32;
             description "Bytes transmitted";
           }
           leaf tx-queued {
             type uint32;
             description "Bytes queued for transmission";
           }
           leaf rx-msgs {
             type uint32;
             description "Messages received";
           }
           leaf rx-errors {
             type uint32;
             description "Errors on receive";
           }
           leaf tx-msgs {
             type uint32;
             description "Messages transmitted";
           }
           leaf tx-errors {
             type uint32;
             description "Errors on transmission";
           }
           container rpc-statistics {
             leaf name {
               type string;
               description "Message name";
             }
             leaf requests {
               type uint32;
               description "Service requests received";
             }
             leaf successes {
               type uint32;
               description "Service requests succeeded";
             }
             leaf failures {
               type uint32;
               description "Service requests failed";
             }
           }
           container notify-statistics {
             leaf name {
               type string;
               description "Message name";
             }
             leaf sent {
               type uint32;
               description "Service notifications sent";
             }
           }
         }
       }
     }
   }
   rpc get-jdaf-firewall-clients {
     description "Show JDAF client information";
     output {
       container jdaf-clients {
         container jdaf-client {
           description "Client information";
           leaf client {
             type uint32;
             description "Service Client Id";
           }
           leaf state {
             type string;
             description "State of the client";
           }
           leaf url {
             type string;
             description "Client URL";
           }
         }
       }
     }
   }
   rpc get-jdaf-interface-server-stats {
     description "Show JDAF server side statistics";
     output {
       container jdaf-server-statistics {
         leaf srv-conn-requests {
           type uint32;
           description "Service connection requests received";
         }
         leaf srv-conn-accepts {
           type uint32;
           description "Service connections accpeted";
         }
         leaf srv-conn-rejects {
           type uint32;
           description "Service connections rejected";
         }
         leaf srv-conn-errors {
           type uint32;
           description "Service connection errors";
         }
         container listener-statistics {
           leaf routing-instance-id {
             type uint32;
             description "Routing instance id";
           }
           leaf srv-accepts {
             type uint32;
             description "Accepts on server socket";
           }
           leaf srv-accept-errors {
             type uint32;
             description "Errors while accept on server socket";
           }
         }
       }
     }
   }
   rpc get-jdaf-interface-client-stats {
     description "Show JDAF client message statistics";
     input {
       leaf client-id {
         description "Client id";
         default "0";
         type uint32;
       }
     }
     output {
       container jdaf-clients-statistics {
         leaf error-msg {
           type string;
           description "Error message";
         }
         container jdaf-client-statistics {
           description "Client statistics";
           leaf client {
             type uint32;
             description "Service Client Id";
           }
           leaf rx-bytes {
             type uint32;
             description "Bytes received";
           }
           leaf tx-bytes {
             type uint32;
             description "Bytes transmitted";
           }
           leaf tx-queued {
             type uint32;
             description "Bytes queued for transmission";
           }
           leaf rx-msgs {
             type uint32;
             description "Messages received";
           }
           leaf rx-errors {
             type uint32;
             description "Errors on receive";
           }
           leaf tx-msgs {
             type uint32;
             description "Messages transmitted";
           }
           leaf tx-errors {
             type uint32;
             description "Errors on transmission";
           }
           container rpc-statistics {
             leaf name {
               type string;
               description "Message name";
             }
             leaf requests {
               type uint32;
               description "Service requests received";
             }
             leaf successes {
               type uint32;
               description "Service requests succeeded";
             }
             leaf failures {
               type uint32;
               description "Service requests failed";
             }
           }
           container notify-statistics {
             leaf name {
               type string;
               description "Message name";
             }
             leaf sent {
               type uint32;
               description "Service notifications sent";
             }
           }
         }
       }
     }
   }
   rpc get-jdaf-interface-clients {
     description "Show JDAF client information";
     output {
       container jdaf-clients {
         container jdaf-client {
           description "Client information";
           leaf client {
             type uint32;
             description "Service Client Id";
           }
           leaf state {
             type string;
             description "State of the client";
           }
           leaf url {
             type string;
             description "Client URL";
           }
         }
       }
     }
   }
   rpc get-jdaf-route-server-stats {
     description "Show JDAF server side statistics";
     output {
       container jdaf-server-statistics {
         leaf srv-conn-requests {
           type uint32;
           description "Service connection requests received";
         }
         leaf srv-conn-accepts {
           type uint32;
           description "Service connections accpeted";
         }
         leaf srv-conn-rejects {
           type uint32;
           description "Service connections rejected";
         }
         leaf srv-conn-errors {
           type uint32;
           description "Service connection errors";
         }
         container listener-statistics {
           leaf routing-instance-id {
             type uint32;
             description "Routing instance id";
           }
           leaf srv-accepts {
             type uint32;
             description "Accepts on server socket";
           }
           leaf srv-accept-errors {
             type uint32;
             description "Errors while accept on server socket";
           }
         }
       }
     }
   }
   rpc get-jdaf-route-client-stats {
     description "Show JDAF client message statistics";
     input {
       leaf client-id {
         description "Client id";
         default "0";
         type uint32;
       }
     }
     output {
       container jdaf-clients-statistics {
         leaf error-msg {
           type string;
           description "Error message";
         }
         container jdaf-client-statistics {
           description "Client statistics";
           leaf client {
             type uint32;
             description "Service Client Id";
           }
           leaf rx-bytes {
             type uint32;
             description "Bytes received";
           }
           leaf tx-bytes {
             type uint32;
             description "Bytes transmitted";
           }
           leaf tx-queued {
             type uint32;
             description "Bytes queued for transmission";
           }
           leaf rx-msgs {
             type uint32;
             description "Messages received";
           }
           leaf rx-errors {
             type uint32;
             description "Errors on receive";
           }
           leaf tx-msgs {
             type uint32;
             description "Messages transmitted";
           }
           leaf tx-errors {
             type uint32;
             description "Errors on transmission";
           }
           container rpc-statistics {
             leaf name {
               type string;
               description "Message name";
             }
             leaf requests {
               type uint32;
               description "Service requests received";
             }
             leaf successes {
               type uint32;
               description "Service requests succeeded";
             }
             leaf failures {
               type uint32;
               description "Service requests failed";
             }
           }
           container notify-statistics {
             leaf name {
               type string;
               description "Message name";
             }
             leaf sent {
               type uint32;
               description "Service notifications sent";
             }
           }
         }
       }
     }
   }
   rpc get-jdaf-route-clients {
     description "Show JDAF client information";
     output {
       container jdaf-clients {
         container jdaf-client {
           description "Client information";
           leaf client {
             type uint32;
             description "Service Client Id";
           }
           leaf state {
             type string;
             description "State of the client";
           }
           leaf url {
             type string;
             description "Client URL";
           }
         }
       }
     }
   }
 }
