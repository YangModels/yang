/*
 * Copyright (c) 2017 Juniper Networks, Inc.
 * All rights reserved.
 */

 module show-l2vpn {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-l2vpn-connection-information {
     description "Show Layer 2 VPN connections information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of Layer 2 VPN instance";
         default "all";
         type string;
       }
       leaf local-site {
         description "Name or ID of Layer 2 VPN local site";
         default "all";
         type string;
       }
       leaf remote-site {
         description "ID of Layer 2 VPN remote site";
         default "all";
         type string;
       }
       leaf state {
         default "up-down";
         type enumeration {
           enum "down" {
             description "Display nonoperational connections";
           }
           enum "up" {
             description "Display operational connections";
           }
           enum "up-down" {
             description "Display both non- and operational connections (default)";
           }
         }
       }
       leaf level {
         default "status";
         type enumeration {
           enum "brief" {
             description "Display one-line version of output";
           }
           enum "extensive" {
             description "Display connection status and history";
           }
           enum "history" {
             description "Display connection history";
           }
           enum "instance-history" {
             description "Display instance history";
           }
           enum "status" {
             description "Display connection and circuit status (default)";
           }
           enum "summary" {
             description "Display summary output";
           }
         }
       }
     }
     output {
       container l2vpn-connection-information {
         container instance {
           container normal {
             leaf instance-name {
               type string;
             }
             leaf instance-display-error {
               type string;
             }
             leaf edge-protection {
               type string;
             }
             leaf edge-protector {
               type string;
             }
             container reference-site {
               leaf automatic-site-name {
                 type string;
                 description "VPLS automatic site name";
               }
               leaf automatic-site-id-status {
                 type string;
                 description "VPLS automatic site identifier status";
               }
               leaf automatic-site-claim-id {
                 type int32;
                 description "Claim site identifier";
               }
               leaf automatic-site-collisions {
                 type int32;
                 description "Number of collisions";
               }
               leaf automatic-site-timer-status {
                 type string;
                 description "VPLS automatic site timer status";
               }
               leaf vpls-signaling-protocol-identifier {
                 type string;
               }
               leaf local-site-id {
                 type string;
               }
               leaf source-attachment-id {
                 type string;
                 description "Local source attachment identifier";
               }
               leaf vpls-id {
                 type int32;
                 description "VPLS instance identifier";
               }
               leaf l2vpn-id {
                 type string;
               }
               leaf local-id {
                 type ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               leaf target-attachment-id {
                 type string;
                 description "Remote target attachment identifier";
               }
               container mesh-group-interfaces {
                 description "Information about all interfaces associated with a mesh-group";
                 leaf mesh-group-name {
                   type string;
                   description "Name of mesh-group";
                 }
                 leaf mesh-group-state {
                   type string;
                   description "Mesh-group state";
                 }
                 leaf mesh-group-id {
                   type int32;
                   description "Mesh-group Identifier";
                 }
                 container interface {
                   leaf interface-name {
                     type string;
                     description "Name of interface";
                   }
                   leaf interface-description {
                     type string;
                   }
                   leaf interface-flags-description {
                     type string;
                   }
                   leaf interface-flags {
                     type int32;
                   }
                 }
               }
               container interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               container label-block {
                 leaf label-block.heading {
                   type string;
                 }
                 leaf label-block-base {
                   type int32;
                 }
                 leaf label-block-offset {
                   type int32;
                 }
                 leaf label-block-size {
                   type int32;
                 }
                 leaf label-block-range {
                   type int32;
                 }
                 leaf label-block-preference {
                   type int32;
                 }
                 leaf label-block-status-vector {
                   type string;
                 }
               }
               container connection {
                 leaf connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 leaf auto-sensed {
                   type empty;
                   description "Auto-sensed";
                 }
                 container local-interface {
                   leaf interface-name {
                     type string;
                     description "Name of interface";
                   }
                   leaf interface-status {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   description "Information about one or more VPLS RSVP-TE point-to-multipoint LSPs";
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container spe-info {
                   leaf spe-info.heading {
                     type string;
                   }
                   leaf local-ip-addr {
                     type ipaddr;
                   }
                   leaf remote-ip-addr {
                     type ipaddr;
                   }
                   leaf pw-status {
                     type string;
                   }
                 }
                 container history {
                   leaf history.category-heading {
                     type string;
                   }
                   leaf history.heading {
                     type string;
                   }
                   leaf log-time-stamp {
                     type string;
                   }
                   leaf log-event {
                     type string;
                   }
                   leaf changed-entity {
                     type string;
                   }
                 }
               }
               container mesh-group-connection {
                 description "Information about all vc-connections of a specific mesh-group";
                 leaf mesh-group-name {
                   type string;
                   description "Name of mesh-group";
                 }
                 container connection {
                   leaf connection.heading {
                     type string;
                   }
                   leaf connection-id {
                     type string;
                   }
                   leaf connection-type {
                     type string;
                   }
                   leaf connection-status {
                     type string;
                   }
                   leaf last-change {
                     type string;
                   }
                   leaf up-transitions {
                     type int32;
                   }
                   leaf remote-pe {
                     type ipaddr;
                   }
                   leaf control-word {
                     type string;
                   }
                   leaf control-word-type {
                     type string;
                   }
                   leaf interface-encapsulation {
                     type string;
                   }
                   leaf inbound-label {
                     type string;
                   }
                   leaf outbound-label {
                     type string;
                   }
                   leaf pw-status-tlv {
                     type string;
                   }
                   leaf local-pw-status-code {
                     type int32;
                   }
                   leaf remote-pw-status-code {
                     type int32;
                   }
                   leaf connection-protection {
                     type string;
                   }
                   leaf vc-flow-label-transmit {
                     type string;
                   }
                   leaf vc-flow-label-receive {
                     type string;
                   }
                   leaf auto-sensed {
                     type empty;
                     description "Auto-sensed";
                   }
                   container local-interface {
                     leaf interface-name {
                       type string;
                       description "Name of interface";
                     }
                     leaf interface-status {
                       type string;
                     }
                     leaf working-status {
                       type string;
                     }
                     leaf profile-name {
                       type string;
                     }
                     leaf profile-varset-name {
                       type string;
                     }
                     leaf interface-description {
                       type string;
                     }
                   }
                   container remote-interface {
                     leaf interface-name {
                       type string;
                       description "Name of interface";
                     }
                     leaf interface-status {
                       type string;
                     }
                     leaf interface-encapsulation {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
               container automatic-site-timers {
                 leaf automatic-site-timers.heading {
                   type string;
                 }
                 leaf automatic-site-startup-wait-time {
                   type string;
                 }
                 leaf automatic-site-new-site-wait-time {
                   type string;
                 }
                 leaf automatic-site-collision-detect-time {
                   type string;
                 }
                 leaf automatic-site-reclaim-wait-time {
                   type string;
                 }
               }
             }
             container ldp-vpls-reference-site {
               description "Information about LDP-VPLS";
               leaf vpls-signaling-protocol-identifier {
                 type string;
               }
               leaf local-site-id {
                 type string;
               }
               leaf vpls-id {
                 type int32;
                 description "VPLS instance identifier";
               }
               leaf l2vpn-id {
                 type string;
               }
               leaf local-id {
                 type ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               container mesh-group-interfaces {
                 description "Information about all interfaces associated with a mesh-group";
                 leaf mesh-group-name {
                   type string;
                   description "Name of mesh-group";
                 }
                 leaf mesh-group-state {
                   type string;
                   description "Mesh-group state";
                 }
                 leaf mesh-group-id {
                   type int32;
                   description "Mesh-group Identifier";
                 }
                 container interface {
                   leaf interface-name {
                     type string;
                     description "Name of interface";
                   }
                   leaf interface-description {
                     type string;
                   }
                   leaf interface-flags-description {
                     type string;
                   }
                   leaf interface-flags {
                     type int32;
                   }
                 }
               }
               container interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               container connection {
                 leaf connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 leaf auto-sensed {
                   type empty;
                   description "Auto-sensed";
                 }
                 container local-interface {
                   leaf interface-name {
                     type string;
                     description "Name of interface";
                   }
                   leaf interface-status {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   description "Information about one or more VPLS RSVP-TE point-to-multipoint LSPs";
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   leaf log-time-stamp {
                     type string;
                   }
                   leaf log-event {
                     type string;
                   }
                   leaf changed-entity {
                     type string;
                   }
                 }
               }
               container mesh-group-connection {
                 description "Information about all vc-connections of a specific mesh-group";
                 leaf mesh-group-name {
                   type string;
                   description "Name of mesh-group";
                 }
                 container connection {
                   leaf connection.heading {
                     type string;
                   }
                   leaf connection-id {
                     type string;
                   }
                   leaf connection-type {
                     type string;
                   }
                   leaf connection-status {
                     type string;
                   }
                   leaf last-change {
                     type string;
                   }
                   leaf up-transitions {
                     type int32;
                   }
                   leaf remote-pe {
                     type ipaddr;
                   }
                   leaf control-word {
                     type string;
                   }
                   leaf control-word-type {
                     type string;
                   }
                   leaf interface-encapsulation {
                     type string;
                   }
                   leaf inbound-label {
                     type string;
                   }
                   leaf outbound-label {
                     type string;
                   }
                   leaf pw-status-tlv {
                     type string;
                   }
                   leaf local-pw-status-code {
                     type int32;
                   }
                   leaf remote-pw-status-code {
                     type int32;
                   }
                   leaf connection-protection {
                     type string;
                   }
                   leaf vc-flow-label-transmit {
                     type string;
                   }
                   leaf vc-flow-label-receive {
                     type string;
                   }
                   leaf auto-sensed {
                     type empty;
                     description "Auto-sensed";
                   }
                   container local-interface {
                     leaf interface-name {
                       type string;
                       description "Name of interface";
                     }
                     leaf interface-status {
                       type string;
                     }
                     leaf working-status {
                       type string;
                     }
                     leaf profile-name {
                       type string;
                     }
                     leaf profile-varset-name {
                       type string;
                     }
                     leaf interface-description {
                       type string;
                     }
                   }
                   container remote-interface {
                     leaf interface-name {
                       type string;
                       description "Name of interface";
                     }
                     leaf interface-status {
                       type string;
                     }
                     leaf interface-encapsulation {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
             }
             container vpls-protocol-state {
               leaf vpls-signaling-protocol-identifier {
                 type string;
               }
               leaf num-local-interfaces {
                 type int32;
               }
               leaf num-local-interfaces-up {
                 type int32;
               }
               leaf irb-present {
                 type string;
               }
               leaf mesh-group-count {
                 type int32;
               }
               leaf mesh-group-up-count {
                 type int32;
               }
               container mesh-group-interfaces {
                 description "Information about all interfaces associated with a mesh-group";
                 container interface {
                   leaf interface-flags {
                     type int32;
                   }
                 }
               }
               container interface {
                 leaf interface-flags {
                   type int32;
                 }
               }
               container mesh-group-connection {
                 description "Information about all vc-connections of a specific mesh-group";
                 leaf mesh-group-name {
                   type string;
                   description "Name of mesh-group";
                 }
                 container connection {
                   leaf connection.heading {
                     type string;
                   }
                   leaf remote-pe {
                     type ipaddr;
                   }
                   leaf l2vpn-local-site-id {
                     type int32;
                     description "Local site identifier";
                   }
                   leaf l2vpn-remote-site-id {
                     type int32;
                     description "Remote site identifier";
                   }
                   leaf connection-status {
                     type string;
                   }
                   leaf last-change {
                     type string;
                   }
                   leaf inbound-label {
                     type string;
                   }
                   leaf outbound-label {
                     type string;
                   }
                   container local-interface {
                     leaf interface-name {
                       type string;
                       description "Name of interface";
                     }
                     leaf interface-status {
                       type string;
                     }
                     leaf interface-encapsulation {
                       type string;
                     }
                     leaf working-status {
                       type string;
                     }
                     leaf profile-name {
                       type string;
                     }
                     leaf profile-varset-name {
                       type string;
                     }
                     leaf interface-description {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
               container reference-site {
                 leaf automatic-site-name {
                   type string;
                   description "VPLS automatic site name";
                 }
                 leaf automatic-site-id-status {
                   type string;
                   description "VPLS automatic site identifier status";
                 }
                 leaf automatic-site-claim-id {
                   type int32;
                   description "Claim site identifier";
                 }
                 leaf automatic-site-collisions {
                   type int32;
                   description "Number of collisions";
                 }
                 leaf automatic-site-timer-status {
                   type string;
                   description "VPLS automatic site timer status";
                 }
                 leaf vpls-signaling-protocol-identifier {
                   type string;
                 }
                 leaf local-site-id {
                   type string;
                 }
                 leaf source-attachment-id {
                   type string;
                   description "Local source attachment identifier";
                 }
                 leaf vpls-id {
                   type int32;
                   description "VPLS instance identifier";
                 }
                 leaf l2vpn-id {
                   type string;
                 }
                 leaf local-id {
                   type ipaddr;
                 }
                 leaf num-local-interfaces {
                   type int32;
                 }
                 leaf num-local-interfaces-up {
                   type int32;
                 }
                 leaf irb-present {
                   type string;
                 }
                 leaf mesh-group-count {
                   type int32;
                 }
                 leaf mesh-group-up-count {
                   type int32;
                 }
                 leaf remote-site-id {
                   type string;
                 }
                 leaf target-attachment-id {
                   type string;
                   description "Remote target attachment identifier";
                 }
                 container mesh-group-interfaces {
                   description "Information about all interfaces associated with a mesh-group";
                   leaf mesh-group-name {
                     type string;
                     description "Name of mesh-group";
                   }
                   leaf mesh-group-state {
                     type string;
                     description "Mesh-group state";
                   }
                   leaf mesh-group-id {
                     type int32;
                     description "Mesh-group Identifier";
                   }
                   container interface {
                     leaf interface-name {
                       type string;
                       description "Name of interface";
                     }
                     leaf interface-description {
                       type string;
                     }
                     leaf interface-flags-description {
                       type string;
                     }
                     leaf interface-flags {
                       type int32;
                     }
                   }
                 }
                 container interface {
                   leaf interface-name {
                     type string;
                     description "Name of interface";
                   }
                   leaf interface-id {
                     type int32;
                   }
                   leaf interface-description {
                     type string;
                   }
                   leaf interface-flags-description {
                     type string;
                   }
                   leaf interface-flags {
                     type int32;
                   }
                 }
                 container connection {
                 }
                 container mesh-group-connection {
                   description "Information about all vc-connections of a specific mesh-group";
                   container connection {
                   }
                 }
               }
             }
             container vpls-rsvp-te-ingress-p2mp-lsp {
               leaf vpls-ingress-p2mp-lsp-name {
                 type string;
                 description "Name of ingress point-to-multipoint LSP";
               }
               leaf vpls-rsvp-te-p2mp-flood-nexthop-id {
                 type int32;
                 description "Identifier for VPLS RSVP traffic-engineering ingress flood next hop";
               }
             }
             container multihome {
               leaf multihome.heading {
                 type string;
               }
               container multihome-site {
                 leaf multihome-site-name {
                   type string;
                   description "Name of site";
                 }
                 leaf multihome-site-id {
                   type int32;
                   description "Site Identifier";
                 }
                 leaf multihome-site-preference {
                   type int32;
                   description "Site Preference";
                 }
                 leaf multihome-site-state {
                   type string;
                   description "Site state";
                 }
                 leaf multihome-num-interfaces {
                   type int32;
                 }
                 leaf multihome-num-interfaces-up {
                   type int32;
                 }
                 container interface {
                   leaf interface-name {
                     type string;
                     description "Name of interface";
                   }
                   leaf interface-id {
                     type int32;
                   }
                   leaf interface-description {
                     type string;
                   }
                   leaf interface-flags-description {
                     type string;
                   }
                   leaf interface-flags {
                     type int32;
                   }
                 }
                 container remote-advertisements {
                   leaf remote-advertisements.heading {
                     type string;
                   }
                   container remote-adv {
                     leaf remote-adv-addr {
                       type string;
                     }
                     leaf remote-adv-preference {
                       type int32;
                       description "Remote PE preference";
                     }
                     leaf remote-adv-ctrl-flag {
                       type int32;
                       description "Remote PE Control flags";
                     }
                     leaf remote-adv-ctrl-flag-description {
                       type string;
                       description "Control flags description";
                     }
                   }
                 }
               }
             }
             container history {
               leaf history.category-heading {
                 type string;
               }
               leaf history.heading {
                 type string;
               }
               leaf log-time-stamp {
                 type string;
               }
               leaf log-event {
                 type string;
               }
               leaf changed-entity {
                 type string;
               }
             }
           }
           container summary {
             leaf instance-name {
               type string;
             }
             leaf instance-display-error {
               type string;
             }
             leaf edge-protection {
               type string;
             }
             leaf edge-protector {
               type string;
             }
             container reference-site {
               leaf automatic-site-name {
                 type string;
                 description "VPLS automatic site name";
               }
               leaf automatic-site-id-status {
                 type string;
                 description "VPLS automatic site identifier status";
               }
               leaf automatic-site-claim-id {
                 type int32;
                 description "Claim site identifier";
               }
               leaf automatic-site-collisions {
                 type int32;
                 description "Number of collisions";
               }
               leaf automatic-site-timer-status {
                 type string;
                 description "VPLS automatic site timer status";
               }
               leaf vpls-signaling-protocol-identifier {
                 type string;
               }
               leaf local-site-id {
                 type string;
               }
               leaf source-attachment-id {
                 type string;
                 description "Local source attachment identifier";
               }
               leaf vpls-id {
                 type int32;
                 description "VPLS instance identifier";
               }
               leaf l2vpn-id {
                 type string;
               }
               leaf local-id {
                 type ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               leaf target-attachment-id {
                 type string;
                 description "Remote target attachment identifier";
               }
               container mesh-group-interfaces {
                 description "Information about all interfaces associated with a mesh-group";
                 container interface {
                   leaf interface-flags {
                     type int32;
                   }
                 }
               }
               container interface {
                 leaf interface-flags {
                   type int32;
                 }
               }
               container connection {
               }
               container mesh-group-connection {
                 description "Information about all vc-connections of a specific mesh-group";
                 container connection {
                 }
               }
               container connections-summary {
                 leaf vc-up-count {
                   type int32;
                 }
                 leaf vc-down-count {
                   type int32;
                 }
               }
             }
             container ldp-vpls-reference-site {
               description "Information about LDP-VPLS";
               leaf vpls-signaling-protocol-identifier {
                 type string;
               }
               leaf local-site-id {
                 type string;
               }
               leaf vpls-id {
                 type int32;
                 description "VPLS instance identifier";
               }
               leaf l2vpn-id {
                 type string;
               }
               leaf local-id {
                 type ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               container mesh-group-interfaces {
                 description "Information about all interfaces associated with a mesh-group";
                 container interface {
                   leaf interface-flags {
                     type int32;
                   }
                 }
               }
               container interface {
                 leaf interface-flags {
                   type int32;
                 }
               }
               container connection {
               }
               container mesh-group-connection {
                 description "Information about all vc-connections of a specific mesh-group";
                 container connection {
                 }
               }
               container connections-summary {
                 leaf vc-up-count {
                   type int32;
                 }
                 leaf vc-down-count {
                   type int32;
                 }
               }
             }
             container vpls-protocol-state {
               leaf vpls-signaling-protocol-identifier {
                 type string;
               }
               leaf num-local-interfaces {
                 type int32;
               }
               leaf num-local-interfaces-up {
                 type int32;
               }
               leaf irb-present {
                 type string;
               }
               leaf mesh-group-count {
                 type int32;
               }
               leaf mesh-group-up-count {
                 type int32;
               }
               container mesh-group-interfaces {
                 description "Information about all interfaces associated with a mesh-group";
                 container interface {
                   leaf interface-flags {
                     type int32;
                   }
                 }
               }
               container interface {
                 leaf interface-flags {
                   type int32;
                 }
               }
               container mesh-group-connection {
                 description "Information about all vc-connections of a specific mesh-group";
                 leaf mesh-group-name {
                   type string;
                   description "Name of mesh-group";
                 }
                 container connection {
                 }
                 container connections-summary {
                   leaf vc-up-count {
                     type int32;
                   }
                   leaf vc-down-count {
                     type int32;
                   }
                 }
               }
               container reference-site {
                 container mesh-group-interfaces {
                   description "Information about all interfaces associated with a mesh-group";
                   container interface {
                     leaf interface-flags {
                       type int32;
                     }
                   }
                 }
                 container interface {
                   leaf interface-flags {
                     type int32;
                   }
                 }
                 container connection {
                 }
                 container mesh-group-connection {
                   description "Information about all vc-connections of a specific mesh-group";
                   container connection {
                   }
                 }
               }
             }
             container multihome {
               container multihome-site {
                 container interface {
                   leaf interface-flags {
                     type int32;
                   }
                 }
                 container remote-advertisements {
                 }
               }
             }
           }
         }
       }
     }
   }
 }
