/*
 * Copyright (c) 2017 Juniper Networks, Inc.
 * All rights reserved.
 */

 module show-ike {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ike-security-associations-information {
     description "Show IKE security association information";
     input {
       leaf level {
         default "brief";
         type enumeration {
           enum "brief" {
             description "Show brief output (default)";
           }
           enum "detail" {
             description "Show detailed output";
           }
         }
       }
       leaf peer-address {
         description "Name of security association";
         type ipaddr;
       }
     }
     output {
       container ike-security-associations-information {
         container brief {
           container ike-security-associations {
             description "Information about a single security association";
             leaf ike-sa-remote-address {
               type ipaddr;
               description "Remote address";
             }
             leaf ike-sa-state {
               type string;
               description "Status of the SA";
             }
             leaf ike-sa-initiator-cookie {
               type string;
               description "IKE SA initiator cookie";
             }
             leaf ike-sa-responder-cookie {
               type string;
               description "IKE SA responder cookie";
             }
             leaf ike-sa-exchange-type {
               type string;
               description "Exchange type";
             }
             container ike-sa-algorithms {
               description "Algorithms used with the SA information";
               leaf ike-sa-sig-key-length {
                 type uint32;
                 description "Signature Key Length";
               }
             }
             container ike-sa-traffic-statistics {
               description "Number of packets and bytes received and transmitted on the SA";
               leaf ike-sa-output-invalid-spi-packets {
                 type int32;
                 description "Number of invalid SPI notifications send";
               }
               leaf ike-sa-input-invalid-spi-packets {
                 type int32;
                 description "Number of invalid SPI notifications received";
               }
             }
           }
           container ike-security-associations-block {
             description "Information about a single security association block";
             container ike-security-associations {
               description "Information about a single security association";
               container ike-sa-algorithms {
                 description "Algorithms used with the SA information";
                 leaf ike-sa-sig-key-length {
                   type uint32;
                   description "Signature Key Length";
                 }
               }
               container ike-sa-traffic-statistics {
                 description "Number of packets and bytes received and transmitted on the SA";
                 leaf ike-sa-output-invalid-spi-packets {
                   type int32;
                   description "Number of invalid SPI notifications send";
                 }
                 leaf ike-sa-input-invalid-spi-packets {
                   type int32;
                   description "Number of invalid SPI notifications received";
                 }
               }
             }
           }
         }
         container detail {
           container ike-security-associations {
             description "Information about a single security association";
             container ike-sa-algorithms {
               description "Algorithms used with the SA information";
               leaf ike-sa-sig-key-length {
                 type uint32;
                 description "Signature Key Length";
               }
             }
             container ike-sa-traffic-statistics {
               description "Number of packets and bytes received and transmitted on the SA";
               leaf ike-sa-output-invalid-spi-packets {
                 type int32;
                 description "Number of invalid SPI notifications send";
               }
               leaf ike-sa-input-invalid-spi-packets {
                 type int32;
                 description "Number of invalid SPI notifications received";
               }
             }
           }
           container ike-security-associations-block {
             description "Information about a single security association block";
             leaf ike-sa-remote-address {
               type ipaddr;
               description "Remote address";
             }
             container ike-security-associations {
               description "Information about a single security association";
               leaf ike-sa-role {
                 type string;
                 description "Role of our end";
               }
               leaf ike-sa-state {
                 type string;
                 description "Status of the SA";
               }
               leaf ike-sa-initiator-cookie {
                 type string;
                 description "IKE SA initiator cookie";
               }
               leaf ike-sa-responder-cookie {
                 type string;
                 description "IKE SA responder cookie";
               }
               leaf ike-sa-exchange-type {
                 type string;
                 description "Exchange type";
               }
               leaf ike-sa-authentication-method {
                 type string;
               }
               leaf ike-sa-local-gateway-interface {
                 type string;
                 description "Local gateway  interface";
               }
               leaf ike-sa-routing-instance {
                 type string;
                 description "Local-gateway routing instance";
               }
               leaf ike-sa-local-address {
                 type ipaddr;
                 description "Local address";
               }
               leaf ike-sa-local-port {
                 type int32;
                 description "Local port";
               }
               leaf ike-sa-remote-port {
                 type int32;
                 description "Remote port";
               }
               leaf ike-sa-lifetime {
                 type string;
                 description "Remaining lifetime before expiration, in seconds or kilobytes";
               }
               container ike-sa-algorithms {
                 description "Algorithms used with the SA information";
                 leaf ike-sa-authentication-algorithm {
                   type string;
                   description "Authentication algorithm";
                 }
                 leaf ike-sa-encryption-algorithm {
                   type string;
                   description "Encryption algorithm";
                 }
                 leaf ike-sa-prf-algorithm {
                   type string;
                   description "PRF algorithm";
                 }
                 leaf ike-sa-dhgroup {
                   type string;
                   description "DH group";
                 }
                 leaf ike-sa-sig-key-length {
                   type uint32;
                   description "Signature Key Length";
                 }
               }
               container ike-sa-traffic-statistics {
                 description "Number of packets and bytes received and transmitted on the SA";
                 leaf ike-sa-input-bytes {
                   type int32;
                   description "Input bytes, including retransmissions";
                 }
                 leaf ike-sa-output-bytes {
                   type int32;
                   description "Output bytes, including retransmissions";
                 }
                 leaf ike-sa-input-packets {
                   type int32;
                   description "Input packets, including retransmissions";
                 }
                 leaf ike-sa-output-packets {
                   type int32;
                   description "Output packets, including retransmissions";
                 }
                 leaf ike-sa-output-invalid-spi-packets {
                   type int32;
                   description "Number of invalid SPI notifications send";
                 }
                 leaf ike-sa-input-invalid-spi-packets {
                   type int32;
                   description "Number of invalid SPI notifications received";
                 }
               }
               container ike-sa-misc {
                 description "Miscellaneous IKE SA information";
                 leaf ike-sa-flags {
                   type string;
                   description "IKE SA flags";
                 }
                 leaf ike-sa-num-ipsec-sas-created {
                   type int32;
                   description "Number of IPSec SAs created using this SA";
                 }
                 leaf ike-sa-num-ipsec-sas-deleted {
                   type int32;
                   description "Number of IPSec SAs deleted using this SA";
                 }
                 leaf ike-sa-num-phase2-negotiations {
                   type int32;
                   description "Number of negotiations in progress on this SA";
                 }
               }
               container ike-sa-phase2-information {
                 description "Information about phase 2 negotiation";
                 leaf ike-sa-phase2-type {
                   type string;
                   description "Type of phase 2 negotiation";
                 }
                 leaf ike-sa-role {
                   type string;
                   description "Role of our end";
                 }
                 leaf ike-sa-msg-id {
                   type int32;
                   description "Message ID of the quick mode negotiation";
                 }
                 leaf ike-sa-local-address {
                   type ipaddr;
                   description "Local address";
                 }
                 leaf ike-sa-local-port {
                   type int32;
                   description "Local port";
                 }
                 leaf ike-sa-remote-address {
                   type ipaddr;
                   description "Remote address";
                 }
                 leaf ike-sa-remote-port {
                   type int32;
                   description "Remote port";
                 }
                 leaf ike-sa-local-id {
                   type string;
                   description "Local end identity in phase 2";
                 }
                 leaf ike-sa-remote-id {
                   type string;
                   description "Remote end identity in phase 2";
                 }
                 leaf ike-sa-flags {
                   type string;
                   description "IKE SA flags";
                 }
               }
             }
           }
         }
       }
     }
   }
 }
