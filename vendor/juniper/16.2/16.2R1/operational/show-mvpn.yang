/*
 * Copyright (c) 2017 Juniper Networks, Inc.
 * All rights reserved.
 */

 module show-mvpn {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-mvpn-instance-information {
     description "Show MVPN instance";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf display-tunnel-name {
         description "Display ingress provider tunnel name instead of attribute";
         type empty;
       }
       leaf instance-name {
         description "Name of MVPN instance";
         default "all";
         type string;
       }
       leaf family {
         description "MVPN instance address family";
         type enumeration {
           enum "inet" {
             description "Display IPv4 instance";
           }
           enum "inet6" {
             description "Display IPv6 instance";
           }
         }
       }
       leaf level {
         type enumeration {
           enum "summary" {
             description "Display summary output";
           }
           enum "extensive" {
             description "Display detailed version of output";
           }
         }
       }
     }
     output {
       container mvpn-instance-information {
         container mvpn-instance {
           container normal {
             container instance-family {
               leaf address-family {
                 type string;
               }
               container instance-entry {
                 leaf instance-name {
                   type string;
                 }
                 leaf ngen-mvpn-mode {
                   type string;
                   description "MVPN mode of operation";
                 }
                 leaf ngen-mvpn-hmcnh-usage {
                   type string;
                   description "Forwarding Entry hierarchical nh usage";
                 }
                 leaf ngen-mvpn-sel-tun-nh-shared {
                   type string;
                   description "Forwarding Entry for selective tunnel nh share usage";
                 }
                 leaf instance-display-error {
                   type string;
                 }
                 leaf sender-based-rpf-status {
                   type string;
                   description "Sender-Based RPF status";
                 }
                 leaf hot-root-standby-status {
                   type string;
                   description "Hot Root Standby status";
                 }
                 container provider-tunnel {
                   leaf provider-tunnel-id {
                     type string;
                     description "Provider tunnel identifier";
                   }
                 }
                 container neighbor {
                   container neighbor-entry {
                     leaf neighbor-identifier {
                       type string;
                       description "Neighbor IPv4 address";
                     }
                     leaf provider-tunnel-id {
                       type string;
                       description "Provider tunnel identifier";
                     }
                     leaf neighbor-property {
                       type string;
                       description "Special properties of the neighbor";
                     }
                   }
                 }
                 container c-multicast-ipv4 {
                   container c-multicast-ipv4-entry {
                     leaf c-multicast-address {
                       type string;
                       description "Address of the c-multicast route";
                     }
                     leaf provider-tunnel-id {
                       type string;
                       description "Provider tunnel identifier";
                     }
                     leaf c-multicast-property {
                       type string;
                       description "Special properties of the c-multicast route";
                     }
                     leaf c-multicast-fwd-nh {
                       type string;
                       description "C-multicast route Forwarding NH Id";
                     }
                     leaf backup-provider-tunnel-id {
                       type string;
                       description "Backup Provider tunnel identifier";
                     }
                     leaf c-backup-multicast-fwd-nh {
                       type string;
                       description "C-multicast route Forwarding NH Id for backup ptnl";
                     }
                   }
                 }
                 container c-multicast-ipv6 {
                   container c-multicast-ipv6-entry {
                     leaf c-multicast-address {
                       type string;
                       description "Address of the c-multicast route";
                     }
                     leaf provider-tunnel-id {
                       type string;
                       description "Provider tunnel identifier";
                     }
                     leaf c-multicast-property {
                       type string;
                       description "Special properties of the c-multicast route";
                     }
                     leaf c-multicast-fwd-nh {
                       type string;
                       description "C-multicast route Forwarding NH Id";
                     }
                     leaf backup-provider-tunnel-id {
                       type string;
                       description "Backup Provider tunnel identifier";
                     }
                     leaf c-backup-multicast-fwd-nh {
                       type string;
                       description "C-multicast route Forwarding NH Id for backup ptnl";
                     }
                   }
                 }
               }
               container instance-entry-summary {
                 leaf sender-based-rpf-status {
                   type string;
                   description "Sender-Based RPF status";
                 }
                 leaf hot-root-standby-status {
                   type string;
                   description "Hot Root Standby status";
                 }
               }
             }
           }
           container summary {
             container instance-family {
               leaf address-family {
                 type string;
               }
               container instance-entry {
                 leaf instance-name {
                   type string;
                 }
                 leaf instance-display-error {
                   type string;
                 }
                 leaf sender-based-rpf-status {
                   type string;
                   description "Sender-Based RPF status";
                 }
                 leaf hot-root-standby-status {
                   type string;
                   description "Hot Root Standby status";
                 }
                 container neighbor {
                   container neighbor-entry {
                     leaf neighbor-property {
                       type string;
                       description "Special properties of the neighbor";
                     }
                   }
                 }
                 container c-multicast-ipv4 {
                 }
                 container c-multicast-ipv6 {
                 }
               }
               container instance-entry-summary {
                 leaf sender-based-rpf-status {
                   type string;
                   description "Sender-Based RPF status";
                 }
                 leaf hot-root-standby-status {
                   type string;
                   description "Hot Root Standby status";
                 }
                 container neighbor-summary {
                   leaf neighbor-summary-count {
                     type int32;
                     description "Number of neighbors in the instance";
                   }
                 }
                 container c-multicast-summary {
                   leaf c-multicast-ipv4-count {
                     type int32;
                     description "Number of c-multicast IPv4 routes in the instance";
                   }
                 }
                 container c-multicast-ipv6-summary {
                   leaf c-multicast-ipv6-count {
                     type int32;
                     description "Number of c-multicast IPv6 routes in the instance";
                   }
                 }
               }
             }
           }
         }
         container mvpn-instance-src-pe {
           container normal {
             container instance-family {
               leaf address-family {
                 type string;
               }
               container instance-entry {
                 leaf instance-name {
                   type string;
                 }
                 leaf ngen-mvpn-mode {
                   type string;
                   description "MVPN mode of operation";
                 }
                 leaf instance-display-error {
                   type string;
                 }
                 container neighbor {
                   container neighbor-entry {
                     leaf neighbor-property {
                       type string;
                       description "Special properties of the neighbor";
                     }
                   }
                 }
                 container c-multicast-ipv4 {
                 }
                 container c-multicast-source-pe-cmcast-addr {
                   leaf c-multicast-address {
                     type string;
                     description "Address of the c-multicast route";
                   }
                 }
                 container c-multicast-source-pe {
                   leaf mvpn-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-pim-source-pe {
                   leaf pim-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-ipv6 {
                 }
               }
               container instance-entry-summary {
                 leaf sender-based-rpf-status {
                   type string;
                   description "Sender-Based RPF status";
                 }
                 leaf hot-root-standby-status {
                   type string;
                   description "Hot Root Standby status";
                 }
               }
             }
           }
           container summary {
             container instance-family {
               leaf address-family {
                 type string;
               }
               container instance-entry {
                 leaf instance-name {
                   type string;
                 }
                 leaf ngen-mvpn-mode {
                   type string;
                   description "MVPN mode of operation";
                 }
                 leaf instance-display-error {
                   type string;
                 }
                 container neighbor {
                   container neighbor-entry {
                     leaf neighbor-property {
                       type string;
                       description "Special properties of the neighbor";
                     }
                   }
                 }
                 container c-multicast-ipv4 {
                 }
                 container c-multicast-source-pe-cmcast-addr {
                   leaf c-multicast-address {
                     type string;
                     description "Address of the c-multicast route";
                   }
                 }
                 container c-multicast-source-pe {
                   leaf mvpn-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-pim-source-pe {
                   leaf pim-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-ipv6 {
                 }
               }
               container instance-entry-summary {
                 leaf sender-based-rpf-status {
                   type string;
                   description "Sender-Based RPF status";
                 }
                 leaf hot-root-standby-status {
                   type string;
                   description "Hot Root Standby status";
                 }
               }
             }
           }
         }
         container instance-family {
           container instance-entry {
             container neighbor {
               container neighbor-entry {
                 leaf neighbor-property {
                   type string;
                   description "Special properties of the neighbor";
                 }
               }
             }
             container c-multicast-ipv4 {
             }
             container c-multicast-ipv6 {
             }
           }
           container instance-entry-summary {
             leaf sender-based-rpf-status {
               type string;
               description "Sender-Based RPF status";
             }
             leaf hot-root-standby-status {
               type string;
               description "Hot Root Standby status";
             }
           }
         }
       }
     }
   }
   rpc get-mvpn-neighbor-information {
     description "Show MVPN neighbor";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf neighbor-address {
         description "Address of MVPN neighbor";
         default "all";
         type string;
       }
       leaf instance-name {
         description "Name of MVPN instance";
         default "all";
         type string;
       }
       leaf family {
         description "MVPN neighbor address family";
         type enumeration {
           enum "inet" {
             description "Display IPv4 neighbor";
           }
           enum "inet6" {
             description "Display IPv6 neighbor";
           }
         }
       }
       leaf level {
         type enumeration {
           enum "summary" {
             description "Display summary output";
           }
           enum "extensive" {
             description "Display detailed version of output";
           }
         }
       }
     }
     output {
       container mvpn-instance-information {
         container mvpn-instance {
           container normal {
             container instance-family {
               leaf address-family {
                 type string;
               }
               container instance-entry {
                 leaf instance-name {
                   type string;
                 }
                 leaf ngen-mvpn-mode {
                   type string;
                   description "MVPN mode of operation";
                 }
                 leaf ngen-mvpn-hmcnh-usage {
                   type string;
                   description "Forwarding Entry hierarchical nh usage";
                 }
                 leaf ngen-mvpn-sel-tun-nh-shared {
                   type string;
                   description "Forwarding Entry for selective tunnel nh share usage";
                 }
                 leaf instance-display-error {
                   type string;
                 }
                 leaf sender-based-rpf-status {
                   type string;
                   description "Sender-Based RPF status";
                 }
                 leaf hot-root-standby-status {
                   type string;
                   description "Hot Root Standby status";
                 }
                 container provider-tunnel {
                   leaf provider-tunnel-id {
                     type string;
                     description "Provider tunnel identifier";
                   }
                 }
                 container neighbor {
                   container neighbor-entry {
                     leaf neighbor-identifier {
                       type string;
                       description "Neighbor IPv4 address";
                     }
                     leaf provider-tunnel-id {
                       type string;
                       description "Provider tunnel identifier";
                     }
                     leaf neighbor-property {
                       type string;
                       description "Special properties of the neighbor";
                     }
                   }
                 }
                 container c-multicast-ipv4 {
                   container c-multicast-ipv4-entry {
                     leaf c-multicast-address {
                       type string;
                       description "Address of the c-multicast route";
                     }
                     leaf provider-tunnel-id {
                       type string;
                       description "Provider tunnel identifier";
                     }
                     leaf c-multicast-property {
                       type string;
                       description "Special properties of the c-multicast route";
                     }
                     leaf c-multicast-fwd-nh {
                       type string;
                       description "C-multicast route Forwarding NH Id";
                     }
                     leaf backup-provider-tunnel-id {
                       type string;
                       description "Backup Provider tunnel identifier";
                     }
                     leaf c-backup-multicast-fwd-nh {
                       type string;
                       description "C-multicast route Forwarding NH Id for backup ptnl";
                     }
                   }
                 }
                 container c-multicast-ipv6 {
                   container c-multicast-ipv6-entry {
                     leaf c-multicast-address {
                       type string;
                       description "Address of the c-multicast route";
                     }
                     leaf provider-tunnel-id {
                       type string;
                       description "Provider tunnel identifier";
                     }
                     leaf c-multicast-property {
                       type string;
                       description "Special properties of the c-multicast route";
                     }
                     leaf c-multicast-fwd-nh {
                       type string;
                       description "C-multicast route Forwarding NH Id";
                     }
                     leaf backup-provider-tunnel-id {
                       type string;
                       description "Backup Provider tunnel identifier";
                     }
                     leaf c-backup-multicast-fwd-nh {
                       type string;
                       description "C-multicast route Forwarding NH Id for backup ptnl";
                     }
                   }
                 }
               }
               container instance-entry-summary {
                 leaf sender-based-rpf-status {
                   type string;
                   description "Sender-Based RPF status";
                 }
                 leaf hot-root-standby-status {
                   type string;
                   description "Hot Root Standby status";
                 }
               }
             }
           }
           container summary {
             container instance-family {
               leaf address-family {
                 type string;
               }
               container instance-entry {
                 leaf instance-name {
                   type string;
                 }
                 leaf instance-display-error {
                   type string;
                 }
                 leaf sender-based-rpf-status {
                   type string;
                   description "Sender-Based RPF status";
                 }
                 leaf hot-root-standby-status {
                   type string;
                   description "Hot Root Standby status";
                 }
                 container neighbor {
                   container neighbor-entry {
                     leaf neighbor-property {
                       type string;
                       description "Special properties of the neighbor";
                     }
                   }
                 }
                 container c-multicast-ipv4 {
                 }
                 container c-multicast-ipv6 {
                 }
               }
               container instance-entry-summary {
                 leaf sender-based-rpf-status {
                   type string;
                   description "Sender-Based RPF status";
                 }
                 leaf hot-root-standby-status {
                   type string;
                   description "Hot Root Standby status";
                 }
                 container neighbor-summary {
                   leaf neighbor-summary-count {
                     type int32;
                     description "Number of neighbors in the instance";
                   }
                 }
                 container c-multicast-summary {
                   leaf c-multicast-ipv4-count {
                     type int32;
                     description "Number of c-multicast IPv4 routes in the instance";
                   }
                 }
                 container c-multicast-ipv6-summary {
                   leaf c-multicast-ipv6-count {
                     type int32;
                     description "Number of c-multicast IPv6 routes in the instance";
                   }
                 }
               }
             }
           }
         }
         container mvpn-instance-src-pe {
           container normal {
             container instance-family {
               leaf address-family {
                 type string;
               }
               container instance-entry {
                 leaf instance-name {
                   type string;
                 }
                 leaf ngen-mvpn-mode {
                   type string;
                   description "MVPN mode of operation";
                 }
                 leaf instance-display-error {
                   type string;
                 }
                 container neighbor {
                   container neighbor-entry {
                     leaf neighbor-property {
                       type string;
                       description "Special properties of the neighbor";
                     }
                   }
                 }
                 container c-multicast-ipv4 {
                 }
                 container c-multicast-source-pe-cmcast-addr {
                   leaf c-multicast-address {
                     type string;
                     description "Address of the c-multicast route";
                   }
                 }
                 container c-multicast-source-pe {
                   leaf mvpn-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-pim-source-pe {
                   leaf pim-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-ipv6 {
                 }
               }
               container instance-entry-summary {
                 leaf sender-based-rpf-status {
                   type string;
                   description "Sender-Based RPF status";
                 }
                 leaf hot-root-standby-status {
                   type string;
                   description "Hot Root Standby status";
                 }
               }
             }
           }
           container summary {
             container instance-family {
               leaf address-family {
                 type string;
               }
               container instance-entry {
                 leaf instance-name {
                   type string;
                 }
                 leaf ngen-mvpn-mode {
                   type string;
                   description "MVPN mode of operation";
                 }
                 leaf instance-display-error {
                   type string;
                 }
                 container neighbor {
                   container neighbor-entry {
                     leaf neighbor-property {
                       type string;
                       description "Special properties of the neighbor";
                     }
                   }
                 }
                 container c-multicast-ipv4 {
                 }
                 container c-multicast-source-pe-cmcast-addr {
                   leaf c-multicast-address {
                     type string;
                     description "Address of the c-multicast route";
                   }
                 }
                 container c-multicast-source-pe {
                   leaf mvpn-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-pim-source-pe {
                   leaf pim-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-ipv6 {
                 }
               }
               container instance-entry-summary {
                 leaf sender-based-rpf-status {
                   type string;
                   description "Sender-Based RPF status";
                 }
                 leaf hot-root-standby-status {
                   type string;
                   description "Hot Root Standby status";
                 }
               }
             }
           }
         }
         container instance-family {
           container instance-entry {
             container neighbor {
               container neighbor-entry {
                 leaf neighbor-property {
                   type string;
                   description "Special properties of the neighbor";
                 }
               }
             }
             container c-multicast-ipv4 {
             }
             container c-multicast-ipv6 {
             }
           }
           container instance-entry-summary {
             leaf sender-based-rpf-status {
               type string;
               description "Sender-Based RPF status";
             }
             leaf hot-root-standby-status {
               type string;
               description "Hot Root Standby status";
             }
           }
         }
       }
     }
   }
   rpc get-mvpn-c-multicasti-route {
     description "Show MVPN c-multicast route";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf display-tunnel-name {
         description "Display ingress provider tunnel name instead of attribute";
         type empty;
       }
       leaf source-pe {
         description "Display source PE information";
         type empty;
       }
       leaf instance-name {
         description "Name of MVPN instance";
         default "all";
         type string;
       }
       leaf family {
         description "MVPN c-multicast route address family";
         type enumeration {
           enum "inet" {
             description "Display IPv4 c-multicast route";
           }
           enum "inet6" {
             description "Display IPv6 c-multicast route";
           }
         }
       }
       leaf level {
         type enumeration {
           enum "summary" {
             description "Display summary output";
           }
           enum "extensive" {
             description "Display detailed version of output";
           }
         }
       }
     }
     output {
       container mvpn-instance-information {
         container mvpn-instance {
           container normal {
             container instance-family {
               leaf address-family {
                 type string;
               }
               container instance-entry {
                 leaf instance-name {
                   type string;
                 }
                 leaf ngen-mvpn-mode {
                   type string;
                   description "MVPN mode of operation";
                 }
                 leaf ngen-mvpn-hmcnh-usage {
                   type string;
                   description "Forwarding Entry hierarchical nh usage";
                 }
                 leaf ngen-mvpn-sel-tun-nh-shared {
                   type string;
                   description "Forwarding Entry for selective tunnel nh share usage";
                 }
                 leaf instance-display-error {
                   type string;
                 }
                 leaf sender-based-rpf-status {
                   type string;
                   description "Sender-Based RPF status";
                 }
                 leaf hot-root-standby-status {
                   type string;
                   description "Hot Root Standby status";
                 }
                 container provider-tunnel {
                   leaf provider-tunnel-id {
                     type string;
                     description "Provider tunnel identifier";
                   }
                 }
                 container neighbor {
                   container neighbor-entry {
                     leaf neighbor-identifier {
                       type string;
                       description "Neighbor IPv4 address";
                     }
                     leaf provider-tunnel-id {
                       type string;
                       description "Provider tunnel identifier";
                     }
                     leaf neighbor-property {
                       type string;
                       description "Special properties of the neighbor";
                     }
                   }
                 }
                 container c-multicast-ipv4 {
                   container c-multicast-ipv4-entry {
                     leaf c-multicast-address {
                       type string;
                       description "Address of the c-multicast route";
                     }
                     leaf provider-tunnel-id {
                       type string;
                       description "Provider tunnel identifier";
                     }
                     leaf c-multicast-property {
                       type string;
                       description "Special properties of the c-multicast route";
                     }
                     leaf c-multicast-fwd-nh {
                       type string;
                       description "C-multicast route Forwarding NH Id";
                     }
                     leaf backup-provider-tunnel-id {
                       type string;
                       description "Backup Provider tunnel identifier";
                     }
                     leaf c-backup-multicast-fwd-nh {
                       type string;
                       description "C-multicast route Forwarding NH Id for backup ptnl";
                     }
                   }
                 }
                 container c-multicast-ipv6 {
                   container c-multicast-ipv6-entry {
                     leaf c-multicast-address {
                       type string;
                       description "Address of the c-multicast route";
                     }
                     leaf provider-tunnel-id {
                       type string;
                       description "Provider tunnel identifier";
                     }
                     leaf c-multicast-property {
                       type string;
                       description "Special properties of the c-multicast route";
                     }
                     leaf c-multicast-fwd-nh {
                       type string;
                       description "C-multicast route Forwarding NH Id";
                     }
                     leaf backup-provider-tunnel-id {
                       type string;
                       description "Backup Provider tunnel identifier";
                     }
                     leaf c-backup-multicast-fwd-nh {
                       type string;
                       description "C-multicast route Forwarding NH Id for backup ptnl";
                     }
                   }
                 }
               }
               container instance-entry-summary {
                 leaf sender-based-rpf-status {
                   type string;
                   description "Sender-Based RPF status";
                 }
                 leaf hot-root-standby-status {
                   type string;
                   description "Hot Root Standby status";
                 }
               }
             }
           }
           container summary {
             container instance-family {
               leaf address-family {
                 type string;
               }
               container instance-entry {
                 leaf instance-name {
                   type string;
                 }
                 leaf instance-display-error {
                   type string;
                 }
                 leaf sender-based-rpf-status {
                   type string;
                   description "Sender-Based RPF status";
                 }
                 leaf hot-root-standby-status {
                   type string;
                   description "Hot Root Standby status";
                 }
                 container neighbor {
                   container neighbor-entry {
                     leaf neighbor-property {
                       type string;
                       description "Special properties of the neighbor";
                     }
                   }
                 }
                 container c-multicast-ipv4 {
                 }
                 container c-multicast-ipv6 {
                 }
               }
               container instance-entry-summary {
                 leaf sender-based-rpf-status {
                   type string;
                   description "Sender-Based RPF status";
                 }
                 leaf hot-root-standby-status {
                   type string;
                   description "Hot Root Standby status";
                 }
                 container neighbor-summary {
                   leaf neighbor-summary-count {
                     type int32;
                     description "Number of neighbors in the instance";
                   }
                 }
                 container c-multicast-summary {
                   leaf c-multicast-ipv4-count {
                     type int32;
                     description "Number of c-multicast IPv4 routes in the instance";
                   }
                 }
                 container c-multicast-ipv6-summary {
                   leaf c-multicast-ipv6-count {
                     type int32;
                     description "Number of c-multicast IPv6 routes in the instance";
                   }
                 }
               }
             }
           }
         }
         container mvpn-instance-src-pe {
           container normal {
             container instance-family {
               leaf address-family {
                 type string;
               }
               container instance-entry {
                 leaf instance-name {
                   type string;
                 }
                 leaf ngen-mvpn-mode {
                   type string;
                   description "MVPN mode of operation";
                 }
                 leaf instance-display-error {
                   type string;
                 }
                 container neighbor {
                   container neighbor-entry {
                     leaf neighbor-property {
                       type string;
                       description "Special properties of the neighbor";
                     }
                   }
                 }
                 container c-multicast-ipv4 {
                 }
                 container c-multicast-source-pe-cmcast-addr {
                   leaf c-multicast-address {
                     type string;
                     description "Address of the c-multicast route";
                   }
                 }
                 container c-multicast-source-pe {
                   leaf mvpn-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-pim-source-pe {
                   leaf pim-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-ipv6 {
                 }
               }
               container instance-entry-summary {
                 leaf sender-based-rpf-status {
                   type string;
                   description "Sender-Based RPF status";
                 }
                 leaf hot-root-standby-status {
                   type string;
                   description "Hot Root Standby status";
                 }
               }
             }
           }
           container summary {
             container instance-family {
               leaf address-family {
                 type string;
               }
               container instance-entry {
                 leaf instance-name {
                   type string;
                 }
                 leaf ngen-mvpn-mode {
                   type string;
                   description "MVPN mode of operation";
                 }
                 leaf instance-display-error {
                   type string;
                 }
                 container neighbor {
                   container neighbor-entry {
                     leaf neighbor-property {
                       type string;
                       description "Special properties of the neighbor";
                     }
                   }
                 }
                 container c-multicast-ipv4 {
                 }
                 container c-multicast-source-pe-cmcast-addr {
                   leaf c-multicast-address {
                     type string;
                     description "Address of the c-multicast route";
                   }
                 }
                 container c-multicast-source-pe {
                   leaf mvpn-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-pim-source-pe {
                   leaf pim-src-pe-string {
                     type string;
                     description "Name of interface";
                   }
                   leaf extended-community {
                     type string;
                     description "Extended community";
                   }
                   leaf route-distinguisher {
                     type string;
                   }
                   leaf as-number {
                     type int32;
                   }
                   leaf mvpn-interface-name {
                     type string;
                     description "Name of interface";
                   }
                   leaf mvpn-interface-index {
                     type int32;
                     description "Index of interface";
                   }
                 }
                 container c-multicast-ipv6 {
                 }
               }
               container instance-entry-summary {
                 leaf sender-based-rpf-status {
                   type string;
                   description "Sender-Based RPF status";
                 }
                 leaf hot-root-standby-status {
                   type string;
                   description "Hot Root Standby status";
                 }
               }
             }
           }
         }
         container instance-family {
           container instance-entry {
             container neighbor {
               container neighbor-entry {
                 leaf neighbor-property {
                   type string;
                   description "Special properties of the neighbor";
                 }
               }
             }
             container c-multicast-ipv4 {
             }
             container c-multicast-ipv6 {
             }
           }
           container instance-entry-summary {
             leaf sender-based-rpf-status {
               type string;
               description "Sender-Based RPF status";
             }
             leaf hot-root-standby-status {
               type string;
               description "Hot Root Standby status";
             }
           }
         }
       }
     }
   }
   rpc get-mvpn-suppressed-information {
     description "Show suppressed MVPN forwarding prefixes";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf general {
         description "Display suppressed general entries";
         type empty;
       }
       leaf mvpn-rpt {
         description "Display suppressed MVPN (*,G) entries";
         type empty;
       }
       leaf instance {
         description "Name of instance";
         type string;
         mandatory true;
       }
       leaf family {
         description "Address family";
         type enumeration {
           enum "inet" {
             description "Display IPv4 suppressed prefixes";
           }
           enum "inet6" {
             description "Display IPv6 suppressed prefixes";
           }
         }
       }
       leaf level {
         type enumeration {
           enum "summary" {
             description "Display summary output";
           }
         }
       }
     }
     output {
       container mvpn-suppressed-information {
         container mvpn-suppressed {
           leaf mvpn-suppressed-instance {
             type string;
             description "MVPN Instance";
           }
           leaf mvpn-suppressed-family {
             type string;
             description "MVPN address family";
           }
           container summary {
             container mvpn-suppressed-prefix {
               leaf c-multicast-address {
                 type string;
                 description "Address of the c-multicast route";
               }
               leaf suppress-reason {
                 type string;
                 description "Reason prefix was suppressed by MVPN";
               }
             }
             container mvpn-suppressed-summary {
               leaf suppressed-general-count {
                 type int32;
                 description "Number of general suppressed MVPN forwarding cache entries";
               }
               leaf suppressed-mvpn-rpt-count {
                 type int32;
                 description "Number of RPT suppressed MVPN forwarding cache entries";
               }
             }
           }
           container normal {
             leaf mvpn-suppressed-instance {
               type string;
               description "MVPN Instance";
             }
             leaf mvpn-suppressed-family {
               type string;
               description "MVPN address family";
             }
             container mvpn-suppressed-prefix {
               leaf c-multicast-address {
                 type string;
                 description "Address of the c-multicast route";
               }
               leaf suppress-reason {
                 type string;
                 description "Reason prefix was suppressed by MVPN";
               }
             }
             container mvpn-suppressed-summary {
               leaf suppressed-general-count {
                 type int32;
                 description "Number of general suppressed MVPN forwarding cache entries";
               }
               leaf suppressed-mvpn-rpt-count {
                 type int32;
                 description "Number of RPT suppressed MVPN forwarding cache entries";
               }
             }
           }
         }
       }
     }
   }
 }
