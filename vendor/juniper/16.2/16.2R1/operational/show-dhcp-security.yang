/*
 * Copyright (c) 2017 Juniper Networks, Inc.
 * All rights reserved.
 */

 module show-dhcp-security {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-dhcp-security-statistics {
     description "Show DHCP security statistics";
     output {
       container dhcp-security-statistics {
         leaf total {
           type int32;
         }
         leaf discover {
           type int32;
         }
         leaf offer {
           type int32;
         }
         leaf request {
           type int32;
         }
         leaf decline {
           type int32;
         }
         leaf ack {
           type int32;
         }
         leaf nack {
           type int32;
         }
         leaf release {
           type int32;
         }
         leaf inform {
           type int32;
         }
         leaf force-renew {
           type int32;
         }
         leaf renew {
           type int32;
         }
         leaf rebind {
           type int32;
         }
         leaf total-dropped {
           type int32;
         }
         leaf no-cfg {
           type int32;
         }
         leaf no-vlan {
           type int32;
         }
         leaf no-ifl {
           type int32;
         }
         leaf request-on-trusted-port {
           type int32;
         }
         leaf first-packet-time {
           type string;
         }
         leaf last-packet-time {
           type string;
         }
         leaf process-time-in-seconds {
           type int32;
         }
         leaf first-client-time {
           type string;
         }
         leaf last-client-time {
           type string;
         }
         leaf client-process-time-in-seconds {
           type int32;
         }
         leaf total-ce-mac-mismatch {
           type int32;
         }
         leaf total-trans-stale-timer_expiry {
           type int32;
         }
         leaf succ-updated-snoop-binding {
           type int32;
         }
         leaf total-current-transient-ce {
           type int32;
         }
       }
     }
   }
 }
