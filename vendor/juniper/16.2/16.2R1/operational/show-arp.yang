/*
 * Copyright (c) 2017 Juniper Networks, Inc.
 * All rights reserved.
 */

 module show-arp {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-arp-table-information {
     description "Show system Address Resolution Protocol table entries";
     input {
       leaf hostname {
         description "Name of host";
         type string;
       }
       leaf interface {
         description "Name of the interface";
         type string;
       }
       leaf no-resolve {
         description "Don't attempt to print addresses symbolically";
         type empty;
       }
       leaf expiration-time {
         description "Show seconds remaining before expiration";
         type empty;
       }
       leaf vpn {
         description "Name of VPN routing table";
         type string;
       }
       leaf logical-system {
         description "Name of logical system";
         type string;
       }
     }
     output {
       container arp-table-information {
         container normal {
           description "Information about one or more entries in the ARP table";
           container arp-table-entry {
             description "Information about an entry in the ARP table";
             leaf mac-address {
               type mac-addr;
               description "Hardware MAC address associated with the ARP entry";
             }
             leaf ip-address {
               type ipaddr;
               description "IP address of the ARP entry";
             }
             leaf hostname {
               type string;
               description "Resolved hostname of the ARP entry";
             }
             leaf interface-name {
               type string;
               description "Name of the interface associated with the ARP entry";
             }
             container arp-table-entry-flags {
               description "One or more status flags for the ARP entry";
               leaf none {
                 type empty;
                 description "ARP entry has no flags";
               }
               leaf permanent {
                 type empty;
                 description "ARP entry is permanent";
               }
               leaf published {
                 type empty;
                 description "ARP entry is published";
               }
               leaf dead {
                 type empty;
                 description "ARP entry is dead";
               }
               leaf free {
                 type empty;
                 description "ARP entry is free";
               }
               leaf virtual-gateway-address {
                 type empty;
                 description "ARP entry is for virtual gateway address";
               }
               leaf remotely-learnt-address {
                 type empty;
                 description "ARP entry learnt from remote and installed by protocol";
               }
             }
           }
         }
         container normal-with-tte {
           description "Information about one or more entries in the ARP table";
           container arp-table-entry {
             description "Information about an entry in the ARP table";
             leaf mac-address {
               type mac-addr;
               description "Hardware MAC address associated with the ARP entry";
             }
             leaf ip-address {
               type ipaddr;
               description "IP address of the ARP entry";
             }
             leaf hostname {
               type string;
               description "Resolved hostname of the ARP entry";
             }
             leaf interface-name {
               type string;
               description "Name of the interface associated with the ARP entry";
             }
             leaf time-to-expire {
               type string;
               description "Seconds remaining until the entry expires";
             }
             container arp-table-entry-flags {
               description "One or more status flags for the ARP entry";
               leaf none {
                 type empty;
                 description "ARP entry has no flags";
               }
               leaf permanent {
                 type empty;
                 description "ARP entry is permanent";
               }
               leaf published {
                 type empty;
                 description "ARP entry is published";
               }
               leaf dead {
                 type empty;
                 description "ARP entry is dead";
               }
               leaf free {
                 type empty;
                 description "ARP entry is free";
               }
               leaf virtual-gateway-address {
                 type empty;
                 description "ARP entry is for virtual gateway address";
               }
               leaf remotely-learnt-address {
                 type empty;
                 description "ARP entry learnt from remote and installed by protocol";
               }
             }
           }
         }
         container no-resolve {
           description "Information about one or more entries in the ARP table";
           container arp-table-entry {
             description "Information about an entry in the ARP table";
             leaf mac-address {
               type mac-addr;
               description "Hardware MAC address associated with the ARP entry";
             }
             leaf ip-address {
               type ipaddr;
               description "IP address of the ARP entry";
             }
             leaf interface-name {
               type string;
               description "Name of the interface associated with the ARP entry";
             }
             container arp-table-entry-flags {
               description "One or more status flags for the ARP entry";
               leaf none {
                 type empty;
                 description "ARP entry has no flags";
               }
               leaf permanent {
                 type empty;
                 description "ARP entry is permanent";
               }
               leaf published {
                 type empty;
                 description "ARP entry is published";
               }
               leaf dead {
                 type empty;
                 description "ARP entry is dead";
               }
               leaf free {
                 type empty;
                 description "ARP entry is free";
               }
               leaf virtual-gateway-address {
                 type empty;
                 description "ARP entry is for virtual gateway address";
               }
               leaf remotely-learnt-address {
                 type empty;
                 description "ARP entry learnt from remote and installed by protocol";
               }
             }
           }
         }
         container no-resolve-with-tte {
           description "Information about one or more entries in the ARP table";
           container arp-table-entry {
             description "Information about an entry in the ARP table";
             leaf mac-address {
               type mac-addr;
               description "Hardware MAC address associated with the ARP entry";
             }
             leaf ip-address {
               type ipaddr;
               description "IP address of the ARP entry";
             }
             leaf interface-name {
               type string;
               description "Name of the interface associated with the ARP entry";
             }
             leaf time-to-expire {
               type string;
               description "Seconds remaining until the entry expires";
             }
             container arp-table-entry-flags {
               description "One or more status flags for the ARP entry";
               leaf none {
                 type empty;
                 description "ARP entry has no flags";
               }
               leaf permanent {
                 type empty;
                 description "ARP entry is permanent";
               }
               leaf published {
                 type empty;
                 description "ARP entry is published";
               }
               leaf dead {
                 type empty;
                 description "ARP entry is dead";
               }
               leaf free {
                 type empty;
                 description "ARP entry is free";
               }
               leaf virtual-gateway-address {
                 type empty;
                 description "ARP entry is for virtual gateway address";
               }
               leaf remotely-learnt-address {
                 type empty;
                 description "ARP entry learnt from remote and installed by protocol";
               }
             }
           }
         }
       }
     }
   }
 }
