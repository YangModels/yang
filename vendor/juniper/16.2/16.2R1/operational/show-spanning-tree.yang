/*
 * Copyright (c) 2017 Juniper Networks, Inc.
 * All rights reserved.
 */

 module show-spanning-tree {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-stp-bridge-information {
     description "Show STP bridge parameters";
     input {
       leaf verbosity_level {
         default "brief";
         type enumeration {
           enum "brief" {
             description "Display brief output (default)";
           }
           enum "detail" {
             description "Display detailed output";
           }
         }
       }
       leaf logical-system {
         description "Name of logical system";
         type string {
           junos:posix-pattern "^[a-zA-Z0-9_-]{1,63}$";
           junos:pattern-message "Logical-system name is a string consisting of up to 63 letters, numbers, dashes and underscores";
         }
       }
       container msti-vlan {
         choice msti-vlan_c {
           case msti {
             leaf msti {
               description "MSTP instance ID";
               type int32 {
                 range "0 .. 4094";
               }
             }
           }
           case vlan-id {
             leaf vlan-id {
               description "VLAN ID";
               type int32 {
                 range "1 .. 4094";
               }
             }
           }
         }
       }
       leaf routing-instance {
         description "Name of routing instance";
         type string;
       }
     }
   }
   rpc get-stp-interface-information {
     description "Show STP interface parameters";
     input {
       leaf verbosity_level {
         default "brief";
         type enumeration {
           enum "brief" {
             description "Display brief output (default)";
           }
           enum "detail" {
             description "Display detailed output";
           }
         }
       }
       leaf logical-system {
         description "Name of logical system";
         type string {
           junos:posix-pattern "^[a-zA-Z0-9_-]{1,63}$";
           junos:pattern-message "Logical-system name is a string consisting of up to 63 letters, numbers, dashes and underscores";
         }
       }
       leaf interface-name {
         description "Name of interface";
         type interface-device;
       }
       container msti-vlan {
         choice msti-vlan_c {
           case msti {
             leaf msti {
               description "MSTP instance ID";
               type int32 {
                 range "0 .. 4094";
               }
             }
           }
           case vlan-id {
             leaf vlan-id {
               description "VLAN ID";
               type int32 {
                 range "1 .. 4094";
               }
             }
           }
         }
       }
       leaf routing-instance {
         description "Name of routing instance";
         type string;
       }
     }
     output {
       container stp-interface-information {
         container stp-instance {
           container stp-interfaces {
             description "Information about one or more Spanning Tree Protocol interfaces";
             container brief {
               description "Information about one or more Spanning Tree Protocol interfaces";
               container stp-interface-entry {
                 description "Information about Spanning Tree Protocol interface";
                 leaf interface-name {
                   type string;
                   description "Name of interface";
                 }
                 leaf port-number {
                   type int32;
                   description "Port number";
                 }
                 leaf designated-port-number {
                   type int32;
                   description "Designated port number";
                 }
                 leaf designated-bridge-mac {
                   type string;
                   description "Media access control address of bridge";
                 }
                 leaf port-cost {
                   type uint32;
                   description "Port cost";
                 }
                 leaf port-state {
                   type string;
                   description "Port state";
                 }
                 leaf port-role {
                   type string;
                   description "Role of port";
                 }
               }
             }
             container detail {
               description "Information about one or more Spanning Tree Protocol interfaces";
               container stp-interface-entry {
                 description "Information about Spanning Tree Protocol interface";
                 leaf interface-name {
                   type string;
                   description "Name of interface";
                 }
                 leaf port-priority {
                   type int32;
                   description "Port priority";
                 }
                 leaf port-number {
                   type int32;
                   description "Port number";
                 }
                 leaf designated-port-priority {
                   type int32;
                   description "Designated port priority";
                 }
                 leaf designated-port-number {
                   type int32;
                   description "Designated port number";
                 }
                 leaf port-cost {
                   type uint32;
                   description "Port cost";
                 }
                 leaf port-state {
                   type string;
                   description "Port state";
                 }
                 leaf designated-bridge-priority {
                   type int32;
                   description "Bridge priority";
                 }
                 leaf designated-bridge-mac {
                   type string;
                   description "Media access control address of bridge";
                 }
                 leaf port-role {
                   type string;
                   description "Role of port";
                 }
                 leaf link-type {
                   type string;
                   description "Type of link";
                 }
                 leaf port-migrated-protocol {
                   type string;
                   description "Migrated protocol for port";
                 }
                 leaf boundary-port {
                   type string;
                   description "STP boundary port";
                 }
               }
             }
           }
         }
       }
     }
   }
   rpc get-mstp-configuration-information {
     description "Show MSTP configuration";
     input {
       leaf verbosity_level {
         default "brief";
         type enumeration {
           enum "brief" {
             description "Display brief output (default)";
           }
           enum "detail" {
             description "Display detailed output";
           }
         }
       }
       leaf logical-system {
         description "Name of logical system";
         type string {
           junos:posix-pattern "^[a-zA-Z0-9_-]{1,63}$";
           junos:pattern-message "Logical-system name is a string consisting of up to 63 letters, numbers, dashes and underscores";
         }
       }
       leaf routing-instance {
         description "Name of routing instance";
         type string;
       }
     }
   }
   rpc get-stp-interface-statistics {
     description "Show STP interface statistics";
     input {
       leaf verbosity_level {
         default "brief";
         type enumeration {
           enum "brief" {
             description "Display brief output (default)";
           }
           enum "detail" {
             description "Display detailed output";
           }
         }
       }
       leaf logical-system {
         description "Name of logical system";
         type string {
           junos:posix-pattern "^[a-zA-Z0-9_-]{1,63}$";
           junos:pattern-message "Logical-system name is a string consisting of up to 63 letters, numbers, dashes and underscores";
         }
       }
       leaf interface-name {
         description "Name of interface";
         type interface-device;
       }
       leaf routing-instance {
         description "Name of routing instance";
         type string;
       }
     }
     output {
       container stp-interface-statistics {
         container stp-interface-statistics-entry {
           description "Spanning Tree Protocol interface statistics";
           leaf interface-name {
             type string;
             description "Name of interface";
           }
           leaf total-bpdus-sent {
             type int32;
             description "Total number of BPDUs sent out";
           }
           leaf total-bpdus-received {
             type int32;
             description "Total number of BPDUs received";
           }
           leaf next-bpdu-time {
             type int32;
             description "Next bpdu send time in the steady state in seconds";
           }
           leaf total-tcn-bpdus-sent-received {
             type string;
             description "Total number of TCN BPDUs sent/received";
           }
           leaf total-proposal-bpdus-sent-received {
             type string;
             description "Total number of Proposal BPDUs sent/received";
           }
           leaf total-agreement-bpdus-sent-received {
             type string;
             description "Total number of Agreement BPDUs sent/received";
           }
         }
         container vstp-interface-statistics {
           description "Statistics information about one or more VLAN STP interfaces";
           container stp-interface-statistics-entry {
             description "Spanning Tree Protocol interface statistics";
             leaf interface-name {
               type string;
               description "Name of interface";
             }
             leaf total-bpdus-sent {
               type int32;
               description "Total number of BPDUs sent out";
             }
             leaf total-bpdus-received {
               type int32;
               description "Total number of BPDUs received";
             }
             leaf next-bpdu-time {
               type int32;
               description "Next bpdu send time in the steady state in seconds";
             }
             leaf total-tcn-bpdus-sent-received {
               type string;
               description "Total number of TCN BPDUs sent/received";
             }
             leaf total-proposal-bpdus-sent-received {
               type string;
               description "Total number of Proposal BPDUs sent/received";
             }
             leaf total-agreement-bpdus-sent-received {
               type string;
               description "Total number of Agreement BPDUs sent/received";
             }
           }
         }
       }
     }
   }
   rpc get-stp-routing-instance-statistics {
     description "Show STP routing instance statistics";
     input {
       leaf verbosity_level {
         default "brief";
         type enumeration {
           enum "brief" {
             description "Display brief output (default)";
           }
           enum "detail" {
             description "Display detailed output";
           }
         }
       }
       leaf logical-system {
         description "Name of logical system";
         type string {
           junos:posix-pattern "^[a-zA-Z0-9_-]{1,63}$";
           junos:pattern-message "Logical-system name is a string consisting of up to 63 letters, numbers, dashes and underscores";
         }
       }
       leaf routing-instance-name {
         description "Name of routing instance";
         type string;
       }
     }
   }
 }
