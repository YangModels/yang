/*
 * Copyright (c) 2017 Juniper Networks, Inc.
 * All rights reserved.
 */

 module show-validation {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-validation-statistics-information {
     description "Show route validation statistics";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Name of route validation instance";
         type string;
       }
     }
     output {
       container rv-statistics-information {
         container rv-statistics {
           leaf rv-record-count {
             type uint32;
           }
           leaf rv-replication-record-count {
             type uint32;
           }
           leaf rv-prefix-count {
             type uint32;
           }
           leaf rv-origin-as-count {
             type uint32;
           }
           leaf rv-memory-utilization {
             type string;
           }
           leaf rv-policy-origin-validation-requests {
             type uint32;
           }
           leaf rv-policy-origin-validation-results-valid {
             type uint32;
           }
           leaf rv-policy-origin-validation-results-invalid {
             type uint32;
           }
           leaf rv-policy-origin-validation-results-unknown {
             type uint32;
           }
           leaf rv-bgp-import-policy-reevaluations {
             type uint32;
           }
           leaf rv-bgp-import-policy-rib-name {
             type uint32;
           }
           leaf rv-bgp-import-policy-rib-reevaluations {
             type uint32;
           }
         }
       }
     }
   }
   rpc get-validation-group-information {
     description "Show route validation redundancy groups";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Name of route validation instance";
         type string;
       }
     }
     output {
       container rv-group-information {
         container rv-group {
           leaf instance-name {
             type string;
           }
           leaf group-name {
             type string;
           }
           leaf maximum-sessions {
             type uint32;
           }
           leaf ip-address {
             type ipaddr;
           }
           leaf session-state {
             type string;
             description "State of the session session";
           }
           leaf preference {
             type int32;
             description "Preference for the route";
           }
         }
       }
     }
   }
   rpc get-validation-session-information {
     description "Show route validation session information";
     input {
       leaf logical-system {
         description "Name of logical system";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf destination {
         description "IP address of session";
         type ipaddr;
       }
       leaf instance {
         description "Name of route validation instance";
         type string;
       }
     }
     output {
       container rv-session-information {
         container brief {
           description "RV session information";
           container rv-session {
             leaf ip-address {
               type ipaddr;
             }
             leaf session-state {
               type string;
               description "State of the session session";
             }
             leaf session-flaps {
               type uint32;
             }
             leaf session-uptime {
               type string;
             }
             leaf ip-prefix-count {
               type uint32;
             }
             leaf ip6-prefix-count {
               type uint32;
             }
           }
         }
         container detail {
           description "RV session information";
           container rv-session {
             leaf ip-address {
               type ipaddr;
             }
             leaf session-state {
               type string;
               description "State of the session session";
             }
             leaf session-index {
               type uint32;
             }
             leaf group-name {
               type string;
             }
             leaf preference {
               type int32;
               description "Preference for the route";
             }
             leaf local-ip-address {
               type ipaddr;
             }
             leaf port {
               type uint32;
             }
             leaf local-cache {
               type string;
             }
             leaf refresh-time {
               type uint32;
             }
             leaf hold-time {
               type uint32;
             }
             leaf record-life-time {
               type uint32;
             }
             leaf serial-full {
               type uint32;
             }
             leaf serial-incremental {
               type uint32;
             }
             leaf connect-retry-time {
               type uint32;
             }
             leaf session-flaps {
               type uint32;
             }
             leaf session-uptime {
               type string;
             }
             leaf last-update {
               type string;
             }
             leaf ip-prefix-count {
               type uint32;
             }
             leaf ip6-prefix-count {
               type uint32;
             }
           }
         }
       }
     }
   }
   rpc get-validation-database-information {
     description "Show contents of route validation database";
     input {
       leaf logical-system {
         description "Name of logical system";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf record {
         description "Filter by record";
         type ipprefix;
       }
       leaf origin-autonomous-system {
         description "Filter by Origin Autonomous System";
         type uint32;
       }
       leaf session {
         description "Filter by Session IP Address";
         type ipaddr;
       }
       leaf mismatch {
         description "Filter by mismatched Origin Autonomous System";
         type empty;
       }
       leaf instance {
         description "Name of route validation instance";
         type string;
       }
     }
     output {
       container rv-database-information {
         container rv-database {
           leaf instance-name {
             type string;
           }
           leaf ip-prefix-count {
             type uint32;
           }
           leaf ip6-prefix-count {
             type uint32;
           }
           container rv-database-entry {
             leaf ip-prefix {
               type ipprefix;
             }
             leaf maximum-length {
               type uint32;
             }
             leaf origin-as {
               type uint32;
             }
             leaf ip-address {
               type ipaddr;
             }
             leaf validation-state {
               type string;
             }
             leaf validation-mismatch {
               type string;
             }
             leaf last-update {
               type string;
             }
           }
         }
       }
     }
   }
   rpc get-validation-replication-database-information {
     description "Show contents of route validation replication database";
     input {
       leaf logical-system {
         description "Name of logical system";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf record {
         description "Filter by record";
         type ipprefix;
       }
       leaf origin-autonomous-system {
         description "Filter by Origin Autonomous System";
         type uint32;
       }
       leaf session {
         description "Filter by Session IP Address";
         type ipaddr;
       }
       leaf instance {
         description "Name of route validation instance";
         type string;
       }
     }
     output {
       container rv-replication-database-information {
         container rv-replication-database {
           leaf instance-name {
             type string;
           }
           leaf ip-prefix-count {
             type uint32;
           }
           leaf ip6-prefix-count {
             type uint32;
           }
           container rv-replication-database-entry {
             leaf ip-prefix {
               type ipprefix;
             }
             leaf maximum-length {
               type uint32;
             }
             leaf origin-as {
               type uint32;
             }
             leaf ip-address {
               type ipaddr;
             }
             leaf validation-state {
               type string;
             }
             leaf last-update {
               type string;
             }
           }
         }
       }
     }
   }
 }
