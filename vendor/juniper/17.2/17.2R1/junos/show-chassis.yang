/*
 * Copyright (c) 2017 Juniper Networks, Inc.
 * All rights reserved.
 */
 module show-chassis {
  namespace "http://yang.juniper.net/yang/1.1/jrpc/show-chassis/junos/17.2R1.13";
  prefix show-chassis;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-personality-information {
     description "Show chassis's current personality";
   }
   rpc get-uft-information {
     description "Show member's current UFT configuration";
     output {
       container uft-information {
         uses uft-information-block;
       }
     }
   }
   rpc get-system-mode-information {
     description "Show member's current system-mode configuration";
     output {
       container system-mode-information {
         uses system-mode-information-block;
       }
     }
   }
   rpc get-power-usage-information {
     description "Show Chassis Power Usages";
     output {
       container power-usage-information {
         uses power-usage-information-block;
       }
     }
   }
   rpc get-power-usage-information-detail {
     description "Show chassis power usage detail";
   }
   rpc get-fru-power-on-sequence {
     description "Show chassis fru power on sequence";
     output {
       container fru-power-on-sequence {
         uses fru-power-on-sequence-block;
       }
     }
   }
   rpc get-alarm-information {
     description "Show alarm status";
     output {
       container alarm-information {
         uses alarm-information-block;
       }
     }
   }
   rpc get-chassis-alarm-satellite-information {
     description "Show alarm status for satellite devices";
     input {
       leaf fpc-slot {
         description "Satellite slot number";
         type uint16 {
           range "65 .. 254";
         }
       }
     }
   }
   rpc get-jam-test-information {
     description "Show Jam API test result";
     input {
       leaf detail {
         description "Display detailed output";
         type empty;
       }
       leaf fpc-slot {
         description "FPC slot number";
         type uint32 {
           range "0 .. 63";
         }
       }
     }
   }
   rpc get-chassis-beacon-information {
     description "Show beacon status";
     input {
       container which-arg {
         choice which-arg_c {
           case all {
             leaf all {
               description "Beacons in ON/OFF state";
               type enumeration {
                 enum "off" {
                   description "Beacons in OFF state";
                 }
                 enum "on" {
                   description "Beacons in ON state";
                 }
               }
             }
           }
           case fpc {
             leaf fpc {
               description "Flexible PIC Controller slot number";
               type uint32 {
                 range "0 .. 63";
               }
             }
           }
           case cb {
           }
           case service-node {
             leaf service-node {
               description "Service Node slot number";
               type uint32 {
                 range "0 .. 1";
               }
             }
           }
         }
       }
       leaf pic-slot {
         description "PIC slot number";
         type uint32 {
           range "0 .. 3";
         }
       }
       container port-num {
         choice port-num_c {
           case port {
             leaf port {
               description "Port number";
               type uint32 {
                 range "0 .. 127";
               }
             }
           }
           case port-range {
             leaf port-range {
               description "Port range";
               type empty;
             }
           }
         }
       }
       leaf lower-limit {
         description "Port range lower limit";
         type uint32 {
           range "0 .. 127";
         }
       }
       leaf upper-limit {
         description "Port range upper limit";
         type uint32 {
           range "0 .. 127";
         }
       }
     }
     output {
       container chassis-beacon-information {
         uses chassis-beacon-information-block;
       }
     }
   }
   rpc network-services {
     description "Show chassis network services";
     output {
       container network-services {
         uses network-services-block;
       }
     }
   }
   rpc ambient-temperature {
     description "Show chassis ambient temperature";
     output {
       container ambient-temperature {
         uses ambient-temperature-block;
       }
     }
   }
   rpc get-clock-synchronization-information {
     description "Show clock synchronization information";
     input {
       leaf interface {
         description "Name of physical interface";
         type string;
       }
       leaf extensive {
         description "Show clock synchronization information in detail";
         type empty;
       }
     }
     output {
       container clock-synchronization-information {
         uses clock-synchronization-information-block;
       }
     }
   }
   rpc get-craft-information {
     description "Show craft interface status";
     output {
       container craft-information {
         uses craft-information-block;
       }
     }
   }
   rpc get-ethernet-switch-information {
     description "Show Ethernet switch information";
   }
   rpc get-feb-redundancy-information {
     description "Show Forwarding Engine Board redundancy information";
     output {
       container feb-redundancy-information {
         uses feb-redundancy-information-block;
       }
     }
   }
   rpc get-feb-redundancy-error-information {
     description "Show error information";
     output {
       container feb-redundancy-error-information {
         uses feb-redundancy-error-information-block;
       }
     }
   }
   rpc get-feb-redundancy-group-information {
     description "Show FEB redundancy group information";
     input {
       leaf group {
         description "Name of FEB redundancy group";
         type string;
         mandatory true;
       }
       leaf errors {
         description "Include error information";
         type empty;
       }
     }
   }
   rpc get-fpc-feb-connectivity-information {
     description "Show connectivity between Flexible PIC Concentrators and Forwarding Engine boards";
     output {
       container fpc-feb-connectivity {
         uses fpc-feb-connectivity-block;
       }
     }
   }
   rpc get-chassis-zones-information {
     description "Show chassis cooling zones information";
     input {
       leaf detail {
         description "Display detailed output";
         type empty;
       }
     }
     output {
       container chassis-zones-information {
         uses chassis-zones-information-block;
       }
     }
   }
   rpc get-environment-information {
     description "Show component status and temperature, cooling system speeds";
     input {
       leaf monitored {
         description "Show items whose temperatures are monitored";
         type empty;
       }
     }
     output {
       container environment-information {
         uses environment-information-block;
       }
     }
   }
   rpc get-environment-sib-information {
     description "Show Switch Interface Board information";
     input {
       leaf sib-slot {
         description "SIB slot number";
         type uint32 {
           range "0 .. 15";
         }
       }
     }
     output {
       container environment-component-information {
         uses environment-component-information-block;
       }
     }
   }
   rpc get-environment-fan-information {
     description "Show fan status";
     input {
       leaf slot {
         description "Fantray slot number";
         type uint32 {
           range "0 .. 6";
         }
       }
     }
     output {
       container fan-information {
         uses fan-information-block;
       }
     }
   }
   rpc get-environment-fpc-information {
     description "Show Flexible PIC Concentrator information";
     input {
       leaf fpc-slot {
         description "FPC slot number";
         type uint32 {
           range "0 .. 63";
         }
       }
     }
     output {
       container environment-component-information {
         uses environment-component-information-block;
       }
     }
   }
   rpc get-chassis-environment-fpc-satellite-info {
     description "Show environment FPC details";
     input {
       leaf fpc-slot {
         description "Satellite slot number";
         type uint16 {
           range "65 .. 254";
         }
       }
       leaf device-alias {
         description "Device alias";
         type string;
       }
     }
   }
   rpc get-environment-fpm-information {
     description "Show craft interface information";
     output {
       container environment-component-information {
         uses environment-component-information-block;
       }
     }
   }
   rpc get-environment-mcs-information {
     description "Show Miscellaneous Control Subsystem information";
     input {
       leaf slot {
         description "MCS slot number";
         type uint32 {
           range "0 .. 1";
         }
       }
     }
     output {
       container environment-component-information {
         uses environment-component-information-block;
       }
     }
   }
   rpc get-environment-pcg-information {
     description "Show Packet Forwarding Engine Clock Generator information";
     input {
       leaf slot {
         description "PCG slot number";
         type uint32 {
           range "0 .. 1";
         }
       }
     }
     output {
       container environment-component-information {
         uses environment-component-information-block;
       }
     }
   }
   rpc get-environment-scg-information {
     description "Show SONET Clock Generator information";
     input {
       leaf slot {
         description "SCG slot number";
         type uint32 {
           range "0 .. 1";
         }
       }
     }
     output {
       container environment-component-information {
         uses environment-component-information-block;
       }
     }
   }
   rpc get-environment-ccg-information {
     description "Show clock generator information";
     input {
       leaf slot {
         description "CCG slot number";
         type uint32 {
           range "0 .. 1";
         }
       }
     }
     output {
       container environment-component-information {
         uses environment-component-information-block;
       }
     }
   }
   rpc get-environment-cb-information {
     description "Show Control Board information";
     input {
       leaf slot {
         description "CB slot number";
         type uint32 {
           range "0 .. 2";
         }
       }
     }
     output {
       container environment-component-information {
         uses environment-component-information-block;
       }
     }
   }
   rpc get-environment-power-supply-unit-information {
     description "Show power supply unit information";
     input {
       leaf slot {
         description "FPC slot number";
         type uint32 {
           range "0 .. 63";
         }
       }
     }
     output {
       container environment-component-information {
         uses environment-component-information-block;
       }
     }
   }
   rpc get-environment-pem-information {
     description "Show Power Entry Module information";
     input {
       leaf slot {
         description "PEM slot number";
         type uint32 {
           range "0 .. 63";
         }
       }
     }
     output {
       container environment-component-information {
         uses environment-component-information-block;
       }
     }
   }
   rpc get-chassis-environment-pem-satellite-info {
     description "Show environment PEM details";
     input {
       leaf fpc-slot {
         description "Satellite slot number";
         type uint16 {
           range "65 .. 254";
         }
       }
       leaf device-alias {
         description "Device alias";
         type string;
       }
     }
   }
   rpc get-environment-psm-information {
     description "Show Power Supply Module information";
     input {
       leaf slot {
         description "PSM slot number";
         type uint32 {
           range "0 .. 17";
         }
       }
     }
     output {
       container environment-component-information {
         uses environment-component-information-block;
       }
     }
   }
   rpc get-environment-sfb-information {
     description "Show SFB status";
     input {
       leaf sfb-slot {
         description "SFB slot number";
         type uint32 {
           range "0 .. 7";
         }
       }
     }
     output {
       container sfb-information {
         uses sfb-information-block;
       }
     }
   }
   rpc get-environment-adc-information {
     description "Show adc status";
     input {
       leaf adc-slot {
         description "ADC slot number";
         type uint32 {
           range "0 .. 63";
         }
       }
     }
     output {
       container sfb-information {
         uses sfb-information-block;
       }
     }
   }
   rpc get-environment-pdu-information {
     description "Show Power Distribution Unit information";
     input {
       leaf slot {
         description "PDU slot number";
         type uint32 {
           range "0 .. 3";
         }
       }
     }
     output {
       container environment-component-information {
         uses environment-component-information-block;
       }
     }
   }
   rpc get-environment-re-information {
     description "Show Routing Engine information";
     input {
       leaf slot {
         description "Routing Engine slot number";
         type uint32 {
           range "0 .. 32";
         }
       }
     }
     output {
       container environment-component-information {
         uses environment-component-information-block;
       }
     }
   }
   rpc get-chassis-environment-re-satellite-info {
     description "Show environment routing engine details";
     input {
       leaf fpc-slot {
         description "Satellite slot number";
         type uint16 {
           range "65 .. 254";
         }
       }
       leaf device-alias {
         description "Device alias";
         type string;
       }
     }
   }
   rpc get-environment-sfm-information {
     description "Show Switching and Forwarding Module information";
     input {
       leaf sfm_plane {
         description "SFM slot number";
         type uint32 {
           range "0 .. 5";
         }
       }
     }
     output {
       container environment-component-information {
         uses environment-component-information-block;
       }
     }
   }
   rpc get-environment-feb-information {
     description "Show Forwarding Engine Board information";
     input {
       leaf slot {
         description "FEB slot number";
         type uint32 {
           range "0 .. 5";
         }
       }
     }
     output {
       container environment-component-information {
         uses environment-component-information-block;
       }
     }
   }
   rpc get-environment-cip-information {
     description "Show Connector Interface Panel Information";
     input {
       leaf slot {
         description "CIP slot number";
         type uint32 {
           range "0 .. 1";
         }
       }
     }
     output {
       container environment-component-information {
         uses environment-component-information-block;
       }
     }
   }
   rpc get-environment-service-node-information {
     description "Show Compute Node Environment information";
     input {
       leaf slot {
         description "Service node slot number";
         type uint32 {
           range "0 .. 1";
         }
       }
     }
     output {
       container environment-component-information {
         uses environment-component-information-block;
       }
     }
   }
   rpc get-chassis-environment-satellite-information {
     description "Show environment details";
     input {
       leaf fpc-slot {
         description "Satellite slot number";
         type uint16 {
           range "65 .. 254";
         }
       }
       leaf device-alias {
         description "Device alias";
         type string;
       }
     }
   }
   rpc get-firmware-information {
     description "Show firmware and operating system version for components";
     output {
       container firmware-information {
         uses firmware-information-block;
       }
     }
   }
   rpc get-firmware-information-detail {
     description "Show detailed output";
     output {
       container hardware-version-information {
         uses hardware-version-information-block;
       }
     }
   }
   rpc get-chassis-firmware-satellite-information {
     description "Show FPC firmware details";
     input {
       leaf fpc-slot {
         description "Satellite slot number";
         type uint16 {
           range "65 .. 254";
         }
       }
       leaf device-alias {
         description "Device alias";
         type string;
       }
     }
   }
   rpc get-usb-storage-status {
     description "Show USB storage status";
   }
   rpc get-fpc-information {
     description "Show Flexible PIC Concentrator status";
     input {
       leaf detail {
         description "Display detailed output";
         type empty;
       }
       leaf fpc-slot {
         description "FPC slot number";
         type uint32 {
           range "0 .. 63";
         }
       }
     }
     output {
       container fpc-information {
         uses fpc-information-block;
       }
     }
   }
   rpc get-pic-information {
     description "Show Physical Interface Cards installed in FPC";
     input {
       leaf slot {
         description "FPC slot number";
         type uint32 {
           range "0 .. 63";
         }
       }
     }
     output {
       container fpc-information {
         uses fpc-information-block;
       }
     }
   }
   rpc get-fpc-port-information {
     description "Show Port status installed in FPC";
     input {
       leaf slot {
         description "FPC slot number";
         type uint32 {
           range "0 .. 63";
         }
       }
     }
     output {
       container fpc-port-information {
         uses fpc-port-information-block;
       }
     }
   }
   rpc get-fpc-error-information {
     description "Show ASIC errors on all the FPC's";
     output {
       container fpc-error-information {
         uses fpc-error-information-block;
       }
     }
   }
   rpc get-fpc-error-i2c {
     description "Display I2C error statistics";
   }
   rpc get-fpc-optical-information {
     description "Show optical properties of the card";
     output {
       container fpc-optical-information {
         uses fpc-optical-information-block;
       }
     }
   }
   rpc get-fpc-optical-mfg-info-information {
     description "Show mfg-info of optical module";
     input {
       leaf fpc-slot {
         description "FPC slot number";
         type uint32 {
           range "0 .. 63";
         }
         mandatory true;
       }
     }
   }
   rpc get-fpc-optical-status-information {
     description "Show status of optical module";
     input {
       leaf fpc-slot {
         description "FPC slot number";
         type uint32 {
           range "0 .. 63";
         }
         mandatory true;
       }
     }
   }
   rpc get-fpc-optical-alarms-information {
     description "Show alarms of optical module";
     input {
       leaf fpc-slot {
         description "FPC slot number";
         type uint32 {
           range "0 .. 63";
         }
         mandatory true;
       }
     }
   }
   rpc get-fpc-optical-edfa-information {
     description "Show edfa of optical module";
     input {
       leaf fpc-slot {
         description "FPC slot number";
         type uint32 {
           range "0 .. 63";
         }
         mandatory true;
       }
     }
   }
   rpc get-fpc-optical-ocm-information {
     description "Show ocm of optical module";
     input {
       leaf fpc-slot {
         description "FPC slot number";
         type uint32 {
           range "0 .. 63";
         }
         mandatory true;
       }
     }
   }
   rpc get-fpc-optical-wss-information {
     description "Show wss of optical module";
     input {
       leaf fpc-slot {
         description "FPC slot number";
         type uint32 {
           range "0 .. 63";
         }
         mandatory true;
       }
     }
   }
   rpc get-fpc-optical-pm-current-information {
     description "Show pm-current of optical module";
     input {
       leaf fpc-slot {
         description "FPC slot number";
         type uint32 {
           range "0 .. 63";
         }
         mandatory true;
       }
     }
   }
   rpc get-fpc-optical-pm-interval-information {
     description "Show pm-interval of optical module";
     input {
       leaf fpc-slot {
         description "FPC slot number";
         type uint32 {
           range "0 .. 63";
         }
         mandatory true;
       }
     }
   }
   rpc get-fpc-optical-pm-currentday-information {
     description "Show pm-currentday of optical module";
     input {
       leaf fpc-slot {
         description "FPC slot number";
         type uint32 {
           range "0 .. 63";
         }
         mandatory true;
       }
     }
   }
   rpc get-fpc-optical-pm-previousday-information {
     description "Show pm-previousday of optical module";
     input {
       leaf fpc-slot {
         description "FPC slot number";
         type uint32 {
           range "0 .. 63";
         }
         mandatory true;
       }
     }
   }
   rpc get-fpc-optical-amplifier-topology-information {
     description "Show amplifier-topology of optical module";
     input {
       leaf fpc-slot {
         description "FPC slot number";
         type uint32 {
           range "0 .. 63";
         }
         mandatory true;
       }
     }
   }
   rpc get-fpc-optical-topology-information {
     description "Show IPLC Topology Information";
     input {
       leaf fpc-slot {
         description "FPC slot number";
         type uint32 {
           range "0 .. 63";
         }
         mandatory true;
       }
       leaf detail {
         description "Show IPLC Topology Detailed Information";
         type empty;
       }
     }
   }
   rpc get-fpc-optical-amplifier-chain-information {
     description "Show in-line amplifier amplifier-chain information";
   }
   rpc get-fpc-optical-ila-summary-information {
     description "Show summary of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-edfa-information {
     description "Show edfa of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-osc-information {
     description "Show osc of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-voa-information {
     description "Show voa of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-alarms-information {
     description "Show alarms of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-pm-current-information {
     description "Show pm-current of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-pm-interval-information {
     description "Show pm-interval of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-pm-currentday-information {
     description "Show pm-currentday of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-pm-previousday-information {
     description "Show pm-previousday of ila module";
     input {
       leaf fpc-slot {
         description "FPC slot number";
         type uint32 {
           range "0 .. 63";
         }
         mandatory true;
       }
       leaf ila-number {
         description "In-line amplifier number";
         type uint32;
         mandatory true;
       }
     }
   }
   rpc get-adc-information {
     description "Show ADC status";
     output {
       container adc-information {
         uses adc-information-block;
       }
     }
   }
   rpc get-pic-detail {
     description "Show Physical Interface Card state, type, and uptime";
     input {
       leaf fpc-slot {
         description "Slot number of FPC that houses PIC";
         type uint32 {
           range "0 .. 63";
         }
       }
       leaf pic-slot {
         description "PIC slot number";
         type int32 {
           range "0 .. 3";
         }
         mandatory true;
       }
     }
     output {
       container fpc-information {
         uses fpc-information-block;
       }
     }
   }
   rpc get-pic-transport-information {
     description "Show Physical Interface Card transport information";
     input {
       leaf fpc-slot {
         description "Slot number of FPC that houses PIC";
         type uint32 {
           range "0 .. 63";
         }
         mandatory true;
       }
       leaf pic-slot {
         description "PIC slot number";
         type int32 {
           range "0 .. 3";
         }
         mandatory true;
       }
     }
   }
   rpc get-spmb-information {
     description "Show Switch Processor Mezzanine Board status";
     output {
       container spmb-information {
         uses spmb-information-block;
       }
     }
   }
   rpc get-spmb-sib-information {
     description "Show Switch Interface Board status";
     output {
       container sib-information {
         uses sib-information-block;
       }
     }
   }
   rpc get-spmb-error-information {
     description "Show errors on SPMB";
     output {
       container spmb-error-information {
         uses spmb-error-information-block;
       }
     }
   }
   rpc get-sib-information {
     description "Show Switch Interface Board status";
     input {
       leaf detail {
         description "Display detailed output";
         type empty;
       }
       leaf slot {
         description "SIB slot number";
         type uint32 {
           range "0 .. 15";
         }
       }
     }
     output {
       container sib-information {
         uses sib-information-block;
       }
     }
   }
   rpc get-sibs-errors {
     description "Show ASIC errors on sib";
     input {
       leaf sib-slot {
         description "SIB slot number";
         type uint32 {
           range "0 .. 15";
         }
       }
     }
     output {
       container sib-information {
         uses sib-information-block;
       }
     }
   }
   rpc get-sfb-information {
     description "Show Switch Fabric Board status";
     input {
       leaf slot {
         description "SFB slot number";
         type uint32 {
           range "0 .. 7";
         }
       }
     }
     output {
       container sfb-information {
         uses sfb-information-block;
       }
     }
   }
   rpc get-fru-information {
     description "Show Line Card Chassis (LCC) status";
     output {
       container fru-information {
         uses fru-information-block;
       }
     }
   }
   rpc get-chassis-lcc-mode-information {
     description "Show chassis lcc mode information";
     input {
       leaf lcc {
         description "LCC number";
         type uint32 {
           range "0 .. 7";
         }
       }
     }
     output {
       container chassis-lcc-mode-information {
         uses chassis-lcc-mode-information-block;
       }
     }
   }
   rpc get-psd-information {
     description "Show Protected System Domain (PSD) status";
     output {
       container psd-information {
         uses psd-information-block;
       }
     }
   }
   rpc get-gnf-information {
     description "Show Network Slices status";
     output {
       container gnf-information {
         uses gnf-information-block;
       }
     }
   }
   rpc get-gnf-fpcs-information {
     description "Show FPCs assigned to GNFs";
     output {
       container gnf-fpcs-information {
         uses gnf-fpcs-information-block;
       }
     }
   }
   rpc get-fm-fpc-state-information {
     description "Show summary fabric management FPC state from Routing Engine";
     input {
       leaf slot {
         description "FPC slot number";
         type uint32 {
           range "0 .. 63";
         }
       }
       leaf mode {
         type enumeration {
           enum "extended" {
             description "Show all 24 planes in output";
           }
         }
       }
     }
     output {
       container fm-fpc-state-information {
         uses fm-fpc-state-information-block;
       }
     }
   }
   rpc get-fm-degradation-information {
     description "Show FPC fabric bandwidth degradation information";
   }
   rpc get-fm-degradation-information-details {
     description "Show fpc fabric degradation action history";
   }
   rpc get-fm-fabric-destinations-state {
     description "Show fabric destinations state for all FPCs";
     input {
       leaf fpc {
         description "FPC slot number";
         type uint32 {
           range "0 .. 63";
         }
       }
       leaf mode {
         type enumeration {
           enum "extended" {
             description "Show all 24 planes in output";
           }
         }
       }
     }
     output {
       container fm-fabric-destinations-state {
         uses fm-fabric-destinations-state-block;
       }
     }
   }
   rpc get-fm-plane-location-information {
     description "Show fabric plane location";
     output {
       container fm-plane-location-information {
         uses fm-plane-location-information-block;
       }
     }
   }
   rpc get-fm-topology {
     description "Show fabric topology for plane";
     input {
       leaf plane {
         description "Fabric plane number";
         type uint32 {
           range "0 .. 21";
         }
       }
     }
     output {
       container fm-topology {
         uses fm-topology-block;
       }
     }
   }
   rpc get-fm-optical-links-state-information {
     description "Show state of fabric management optical links";
     input {
       leaf lcc {
         description "Lcc number";
         type uint32 {
           range "0 .. 7";
         }
       }
       leaf detail {
         description "Display detailed output";
         type empty;
       }
     }
     output {
       container fm-optical-links-state-information {
         uses fm-optical-links-state-information-block;
       }
     }
   }
   rpc get-fm-optics-port-information {
     description "Show info of fabric optical ports";
     input {
       leaf display {
         type enumeration {
           enum "brief" {
             description "Show brief output";
           }
           enum "detail" {
             description "Show detailed output";
           }
         }
       }
       leaf sib-slot {
         description "SIB slot number";
         type uint32 {
           range "0 .. 15";
         }
       }
     }
     output {
       container fm-optics-port-information {
         uses fm-optics-port-information-block;
       }
     }
   }
   rpc get-fm-plane-state-information {
     description "Show state of fabric management plane";
     input {
       leaf display {
         type enumeration {
           enum "terse" {
             description "Show terse output";
           }
           enum "detail" {
             description "Show detail output";
           }
           enum "extensive" {
             description "Show extensive output";
           }
         }
       }
       leaf number {
         description "Fabric plane number";
         type uint32 {
           range "0 .. 4";
         }
       }
       leaf mode {
         type enumeration {
           enum "extended" {
             description "Show all 24 planes in output";
           }
         }
       }
     }
     output {
       container fm-plane-state-information {
         uses fm-plane-state-information-block;
       }
     }
   }
   rpc get-fm-state-information {
     description "Show summary fabric management state";
     output {
       container fm-state-information {
         uses fm-state-information-block;
       }
     }
   }
   rpc get-fm-ext-state-information {
     description "Show extended summary fabric management state";
     output {
       container fm-ext-state-information {
         uses fm-ext-state-information-block;
       }
     }
   }
   rpc get-fm-state-legend {
     description "Show legend of fabric management states";
     output {
       container fm-state-legend {
         uses fm-state-legend-block;
       }
     }
   }
   rpc get-fm-sib-state-information {
     description "Show summary fabric management SIB state from Routing Engine";
     input {
       leaf slot {
         description "SIB slot number";
         type uint32 {
           range "0 .. 15";
         }
       }
     }
     output {
       container fm-sib-state-information {
         uses fm-sib-state-information-block;
       }
     }
   }
   rpc get-chassis-fabric-topology-information {
     description "Show fabric topology information";
     input {
       leaf sib-slot {
         description "SIB slot number";
         type uint32 {
           range "0 .. 15";
         }
       }
     }
     output {
       container chassis-fabric-information {
         uses chassis-fabric-information-block;
       }
     }
   }
   rpc get-fm-topo-tracepath-link {
     description "Show info of fabric path";
     input {
       leaf hsl2link {
         description "HSL2 Link Name as in topology command";
         type string;
         mandatory true;
       }
       leaf lcc {
         description "Lcc number. Default is 0";
         default "0";
         type uint32 {
           range "0 .. 7";
         }
       }
     }
     output {
       container fm-topo-tracepath-link {
         uses fm-topo-tracepath-link-block;
       }
     }
   }
   rpc get-fm-topo-tracepath-fpc {
     description "Show info of fabric path";
     input {
       leaf fpcstr {
         description "FPC/PFE String as in topology cmd - e.g. FPC7PFE1";
         type string;
         mandatory true;
       }
       leaf lcc {
         description "Lcc number.";
         type uint32 {
           range "0 .. 7";
         }
         mandatory true;
       }
       leaf plane {
         description "Fabric Plane - 0/1/2/3/4 and 5=all-active-planes(Default)";
         default "5";
         type uint32 {
           range "0 .. 5";
         }
       }
     }
     output {
       container fm-topo-tracepath-fpc {
         uses fm-topo-tracepath-fpc-block;
       }
     }
   }
   rpc get-fm-unreachable-dest-information {
     description "Show unreachable destinations on all active planes";
     output {
       container fm-unreachable-dest-information {
         uses fm-unreachable-dest-information-block;
       }
     }
   }
   rpc get-fm-fabric-reachability-information {
     description "Show current status of fabric reachability";
     input {
       leaf detail {
         description "Show reachability output in detail";
         type empty;
       }
       leaf extended {
         description "Show all 24 planes in output";
         type empty;
       }
     }
     output {
       container fm-fabric-reachability-information {
         uses fm-fabric-reachability-information-block;
       }
     }
   }
   rpc get-fm-degraded-fabric-state-information {
     description "Show degraded fabric state on all active planes";
     output {
       container fm-degraded-fabric-state-information {
         uses fm-degraded-fabric-state-information-block;
       }
     }
   }
   rpc get-fm-sib-errors {
     description "Show Switch Interface Board errors";
     input {
       leaf sib-slot {
         description "SIB slot number";
         type uint32 {
           range "0 .. 15";
         }
         mandatory true;
       }
     }
     output {
       container fm-fru-errors {
         uses fm-fru-errors-block;
       }
     }
   }
   rpc get-fm-fpc-errors {
     description "Show Flexible PIC Controller errors";
     input {
       leaf slot {
         description "FPC slot number";
         type uint32 {
           range "0 .. 63";
         }
         mandatory true;
       }
     }
     output {
       container fm-fru-errors {
         uses fm-fru-errors-block;
       }
     }
   }
   rpc get-fm-plane-autoheal-errors {
     description "Show Planes autoheal state";
     output {
       container fm-fru-errors {
         uses fm-fru-errors-block;
       }
     }
   }
   rpc get-chassis-inventory {
     description "Show installed hardware components";
     input {
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
     output {
       container chassis-inventory {
         uses chassis-inventory-block;
       }
     }
   }
   rpc get-chassis-hardware-satellite-information {
     description "Show hardware details";
     input {
       leaf fpc-slot {
         description "Satellite slot number";
         type uint16 {
           range "65 .. 254";
         }
       }
       leaf device-alias {
         description "Device alias";
         type string;
       }
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
   }
   rpc get-power-budget-information {
     description "Show power budget chassis information";
     output {
       container power-budget-information {
         uses power-budget-information-block;
       }
     }
   }
   rpc get-chassis-mac-addresses {
     description "Show media access control addresses";
     output {
       container chassis-mac-addresses {
         uses chassis-mac-addresses-block;
       }
     }
   }
   rpc get-route-engine-information {
     description "Show Routing Engine status";
     input {
       leaf slot {
         description "Routing Engine slot number";
         type uint32 {
           range "0 .. 32";
         }
       }
     }
     output {
       container route-engine-information {
         uses route-engine-information-block;
       }
     }
   }
   rpc get-bios-version-information {
     description "Show BIOS firmware version";
   }
   rpc get-chassis-routing-engine-bios-satellite-info {
     description "Show routing engine bios details";
     input {
       leaf fpc-slot {
         description "Satellite slot number";
         type uint16 {
           range "65 .. 254";
         }
       }
       leaf device-alias {
         description "Device alias";
         type string;
       }
     }
   }
   rpc get-chassis-routing-engine-errors {
     description "Show re errors";
   }
   rpc get-chassis-routing-engine-satellite-information {
     description "Show routing engine details";
     input {
       leaf fpc-slot {
         description "Satellite slot number";
         type uint16 {
           range "65 .. 254";
         }
       }
       leaf device-alias {
         description "Device alias";
         type string;
       }
     }
   }
   rpc get-service-node-information {
     description "Show service node information";
     input {
       leaf version {
         description "Show service-node version information";
         type empty;
       }
       leaf slot {
         description "Service node slot number";
         type uint32 {
           range "0 .. 1";
         }
       }
     }
     output {
       container service-node-information {
         uses service-node-information-block;
       }
     }
   }
   rpc get-ssb-information {
     description "Show System and Switch Board status";
     input {
       leaf slot {
         description "SSB slot number";
         type uint32 {
           range "0 .. 1";
         }
       }
     }
     output {
       container scb-information {
         uses scb-information-block;
       }
     }
   }
   rpc get-scb-information {
     description "Show System Control Board status";
     output {
       container scb-information {
         uses scb-information-block;
       }
     }
   }
   rpc get-fwdd-information {
     description "Show forwarding process (fwdd) status";
     output {
       container scb-information {
         uses scb-information-block;
       }
     }
   }
   rpc get-sfm-information {
     description "Show Switching and Forwarding Module status";
     output {
       container scb-information {
         uses scb-information-block;
       }
     }
   }
   rpc get-feb-brief-information {
     description "Show Forwarding Engine Board status";
     output {
       container scb-information {
         uses scb-information-block;
       }
     }
   }
   rpc get-feb-information {
     description "Show detailed output";
     input {
       leaf feb_slot {
         description "FEB slot number";
         type uint32 {
           range "0 .. 5";
         }
       }
     }
     output {
       container scb-information {
         uses scb-information-block;
       }
     }
   }
   rpc get-cfeb-information {
     description "Show Compact Forwarding Engine Board status";
     output {
       container scb-information {
         uses scb-information-block;
       }
     }
   }
   rpc get-afeb-information {
     description "Show Compact Forwarding Engine Board status";
     output {
       container scb-information {
         uses scb-information-block;
       }
     }
   }
   rpc get-tfeb-information {
     description "Show Compact Forwarding Engine Board status";
     output {
       container scb-information {
         uses scb-information-block;
       }
     }
   }
   rpc get-chassis-fan-satellite-information {
     description "Show fan details";
     input {
       leaf fpc-slot {
         description "Satellite slot number";
         type uint16 {
           range "65 .. 254";
         }
       }
       leaf device-alias {
         description "Device alias";
         type string;
       }
     }
   }
   rpc get-chassis-location {
     description "Show physical location of chassis";
     output {
       container chassis-location {
         uses chassis-location-block;
       }
     }
   }
   rpc get-interface-location-name-information {
     description "Show physical location given interface name";
     input {
       leaf interface-name {
         description "Interface name";
         type string;
         mandatory true;
       }
     }
     output {
       container interface-location-name-information {
         uses interface-location-name-information-block;
       }
     }
   }
   rpc get-interface-location-information {
     description "Show interface name given location";
     input {
       leaf lcc {
         description "LCC number";
         type uint32 {
           range "0 .. 3";
         }
         mandatory true;
       }
       leaf fpc {
         description "FPC number";
         type uint32 {
           range "0 .. 63";
         }
         mandatory true;
       }
     }
     output {
       container interface-location-slot-information {
         uses interface-location-slot-information-block;
       }
     }
   }
   rpc get-temperature-threshold-information {
     description "Show chassis temperature threshold settings";
     output {
       container temperature-threshold-information {
         uses temperature-threshold-information-block;
       }
     }
   }
   rpc get-chassis-temp-thresholds-satellite-info {
     description "Show temperature thresholds details";
     input {
       leaf fpc-slot {
         description "Satellite slot number";
         type uint16 {
           range "65 .. 254";
         }
       }
       leaf device-alias {
         description "Device alias";
         type string;
       }
     }
   }
   rpc get-power-management {
     description "Show power ratings for the router";
     output {
       container power-management-information {
         uses power-management-information-block;
       }
     }
   }
   rpc get-nonstop-upgrade-status {
     description "Show nonstop upgrade status";
     output {
       container in-service-upgrade-status {
         uses in-service-upgrade-status-block;
       }
     }
   }
   rpc get-chassis-oss-map {
     description "Show Operation Supported System's translated model";
     output {
       container chassis-oss-map {
         uses chassis-oss-map-block;
       }
     }
   }
   rpc get-lcd-information {
     description "Show LCD display";
     output {
       container craft-lcd-led-information {
         uses craft-lcd-led-information-block;
       }
     }
   }
   rpc get-lcd-fpc-information {
     description "Show LCD display for FPC slot number";
     input {
       leaf fpc-slot {
         description "FPC slot number";
         type uint32 {
           range "0 .. 63";
         }
       }
     }
     output {
       container craft-lcd-led-information {
         uses craft-lcd-led-information-block;
       }
     }
   }
   rpc get-lcd-menu-information {
     description "Show active LCD menu items";
   }
   rpc get-led-information {
     description "Show LED status";
     output {
       container craft-lcd-led-information {
         uses craft-lcd-led-information-block;
       }
     }
   }
   rpc get-led-fpc-information {
     description "Show LED status for FPC slot number";
     input {
       leaf fpc-slot {
         description "FPC slot number";
         type uint32 {
           range "0 .. 63";
         }
       }
     }
     output {
       container craft-lcd-led-information {
         uses craft-lcd-led-information-block;
       }
     }
   }
   rpc get-chassis-led-satellite-information {
     description "Show led details";
     input {
       leaf fpc-slot {
         description "Satellite slot number";
         type uint16 {
           range "65 .. 254";
         }
       }
       leaf device-alias {
         description "Device alias";
         type string;
       }
     }
   }
   rpc get-chassis-satellite-information {
     description "Show Satellite Devices information";
     input {
       container arg {
         choice arg_c {
           case fpc-slot {
             leaf fpc-slot {
               description "Satellite slot number";
               type uint32 {
                 range "65 .. 254";
               }
             }
           }
           case device-alias {
             leaf device-alias {
               description "Device alias";
               type string;
             }
           }
         }
       }
       leaf cluster {
         description "Cluster name";
         type string;
       }
       leaf since {
         description "Show history since YYYY-MM-DD.HH:MM:SS";
         type time;
       }
       leaf level {
         default "brief";
         type enumeration {
           enum "terse" {
             description "Display terse output";
           }
           enum "brief" {
             description "Display brief output (default)";
           }
           enum "detail" {
             description "Display detailed output";
           }
           enum "extensive" {
             description "Display extensive output";
           }
         }
       }
     }
     output {
       container satellite-information {
         uses satellite-information-block;
       }
     }
   }
   rpc get-chassis-satellite-unprovision-information {
     description "Display unprovisioned satellites";
     input {
       leaf system-id {
         description "Satellite system id";
         type mac-addr;
       }
       leaf since {
         description "Show history since YYYY-MM-DD.HH:MM:SS";
         type time;
       }
       leaf level {
         default "brief";
         type enumeration {
           enum "brief" {
             description "Display brief output (default)";
           }
           enum "detail" {
             description "Display detailed output";
           }
           enum "extensive" {
             description "Display extensive output";
           }
         }
       }
     }
     output {
       container satellite-information {
         uses satellite-information-block;
       }
     }
   }
   rpc get-chassis-satellite-statistics {
     description "Display device statistics information";
     input {
       container arg {
         choice arg_c {
           case fpc-slot {
             leaf fpc-slot {
               description "Satellite slot number";
               type uint32 {
                 range "65 .. 254";
               }
             }
           }
           case device-alias {
             leaf device-alias {
               description "Device alias";
               type string;
             }
           }
         }
       }
       leaf cluster {
         description "Cluster name";
         type string;
       }
     }
   }
   rpc get-chassis-satellite-redundancy-group-info {
     description "Display multi-chassis cluster information";
     input {
       leaf since {
         description "Show history since YYYY-MM-DD.HH:MM:SS";
         type time;
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       container multi-chassis-cluster-information {
         uses multi-chassis-cluster-information-block;
       }
     }
   }
   rpc get-chassis-satellite-redundacy-grp-devices-info {
     description "Display satellite device information";
     input {
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       container multi-chassis-cluster-device-information {
         uses multi-chassis-cluster-device-information-block;
       }
     }
   }
   rpc get-chassis-satellite-redundancy-grp-dev-history {
     description "Display device history information";
     input {
       leaf verbosity_level {
         default "brief";
         type enumeration {
           enum "brief" {
             description "Display brief output (default)";
           }
           enum "detail" {
             description "Display detailed output";
           }
           enum "extensive" {
             description "Display extensive output";
           }
         }
       }
       leaf serial-number {
         description "Device Serial Number";
         type string;
       }
       leaf global {
         description "Global history";
         type empty;
       }
     }
   }
   rpc get-chassis-satellite-extended-port-information {
     description "Display extended-port information";
     input {
       leaf interface-name {
         description "Interface name";
         type string;
       }
       leaf since {
         description "Show history since YYYY-MM-DD.HH:MM:SS";
         type time;
       }
       leaf fpc-slot {
         description "Satellite slot number";
         type uint32 {
           range "65 .. 254";
         }
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       container extended-port-information {
         uses extended-port-information-block;
       }
     }
   }
   rpc get-chassis-satellite-upgrade-group-information {
     description "Display upgrade group information";
     input {
       leaf level {
         default "terse";
         type enumeration {
           enum "terse" {
             description "Display terse output (default)";
           }
           enum "brief" {
             description "Display brief output";
           }
           enum "detail" {
             description "Display detailed output";
           }
           enum "extensive" {
             description "Display extensive output";
           }
         }
       }
       leaf group-name {
         description "Upgrade group name";
         type string;
       }
     }
     output {
       container upgrade-group-information {
         uses upgrade-group-information-block;
       }
     }
   }
   rpc get-chassis-satellite-neighbor-information {
     description "Display satellite adjacency information";
     input {
       leaf interface-name {
         description "Name of interface";
         type string;
       }
       leaf since {
         description "Show history since YYYY-MM-DD.HH:MM:SS";
         type time;
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       container adjacency-information {
         uses adjacency-information-block;
       }
     }
   }
   rpc get-chassis-satellite-neighbor-statistics {
     description "Display adjacency statistics information";
     input {
       leaf interface-name {
         description "Name of interface";
         type string;
       }
     }
     output {
       container adjacency-statistics {
         uses adjacency-statistics-block;
       }
     }
   }
   rpc get-chassis-satellite-interface-information {
     description "Display satellite protocol interface information";
     input {
       leaf verbosity_level {
         default "brief";
         type enumeration {
           enum "brief" {
             description "Display brief output (default)";
           }
           enum "detail" {
             description "Display detailed output";
           }
           enum "extensive" {
             description "Display extensive output";
           }
         }
       }
       leaf interface-name {
         description "Name of interface";
         type string;
       }
       leaf since {
         description "Show history since YYYY-MM-DD.HH:MM:SS";
         type time;
       }
     }
     output {
       container satellite-interface-information {
         uses satellite-interface-information-block;
       }
     }
   }
   rpc get-satellite-management-software-information {
     description "Show satellite software installed";
     input {
       leaf level {
         default "brief";
         type enumeration {
           enum "brief" {
             description "Display brief output (default)";
           }
           enum "detail" {
             description "Display detailed output";
           }
         }
       }
     }
     output {
       container satellite-software-information {
         uses satellite-software-information-block;
       }
     }
   }
   rpc get-power-budget-information {
     description "Show power budget chassis satellite information";
     input {
       leaf fpc-slot {
         description "Satellite slot number";
         type uint16 {
           range "65 .. 254";
         }
       }
     }
     output {
       container power-budget-information {
         uses power-budget-information-block;
       }
     }
   }
   rpc get-chassis-satellite-cluster-information {
     description "Show Satellite Cluster information";
     input {
       leaf cluster {
         description "Cluster name";
         type string;
       }
       leaf level {
         default "brief";
         type enumeration {
           enum "terse" {
             description "Display terse output";
           }
           enum "brief" {
             description "Display brief output (default)";
           }
           enum "detail" {
             description "Display detailed output";
           }
           enum "extensive" {
             description "Display extensive output";
           }
         }
       }
     }
     output {
       container satellite-cluster-information {
         uses satellite-cluster-information-block;
       }
     }
   }
   rpc get-chassis-satellite-cluster-route {
     description "Display cluster route information";
     input {
       leaf cluster {
         description "Cluster name";
         type string;
       }
       leaf fpc-slot {
         description "Satellite slot number";
         type uint32 {
           range "65 .. 254";
         }
       }
     }
   }
   rpc get-chassis-satellite-cluster-statistics {
     description "Display cluster statistics information";
     input {
       leaf cluster {
         description "Cluster name";
         type string;
       }
       leaf fpc-slot {
         description "Satellite slot number";
         type uint32 {
           range "65 .. 254";
         }
       }
     }
   }
 grouping uft-information-block {
   container uft {
   }
   container ft {
     leaf uft {
       type string;
     }
   }
 }
 grouping system-mode-information-block {
   leaf system-mode {
     type string;
   }
   leaf system-mode-warning {
     type string;
   }
 }
 grouping power-usage-information-block {
   container power-usage-item {
     leaf name {
       type string;
       description "Name of this component";
     }
     leaf status {
       type string;
       description "Status of clock synchronization source";
     }
     leaf state {
       type string;
       description "Status of the component";
     }
     container ac-input-detail {
       leaf ac-input {
         type string;
         description "AC input state";
       }
       leaf ac-expect-feed {
         type uint32;
         description "Expect power input feed";
       }
       leaf ac-actual-feed {
         type uint32;
         description "Actual power input feed";
       }
     }
     container ac-input-detail2 {
       leaf ac-input_status {
         type string;
         description "AC input status";
       }
       leaf str-ac-expect-feed {
         type string;
         description "Expect power input feed";
       }
       leaf str-ac-actual-feed {
         type string;
         description "Actual power input feed";
       }
     }
     container dc-input-detail {
       leaf dc-input {
         type string;
         description "DC input state";
       }
       leaf dc-expect-feed {
         type uint32;
         description "Expect power input feed";
       }
       leaf dc-actual-feed {
         type uint32;
         description "Actual power input feed";
       }
       leaf reference-voltage {
         type string;
         description "Voltage of the item in Volts";
       }
       leaf actual-voltage {
         type int32;
         description "Voltage of the item in mVlots";
       }
     }
     container dc-input-detail2 {
       leaf dc-input-status {
         type string;
         description "DC input status";
       }
       leaf str-dc-expect-feed {
         type string;
         description "Expect power input feed";
       }
       leaf str-dc-actual-feed {
         type string;
         description "Actual power input feed";
       }
     }
     container dc-output-detail {
       leaf dc-power {
         type uint32;
       }
       leaf zone {
         type uint32;
         description "Power zone";
       }
       leaf dc-current {
         type uint32;
       }
       leaf dc-voltage {
         type uint32;
       }
       leaf dc-load {
         type uint32;
       }
     }
     container dc-output-detail2 {
       leaf str-dc-power {
         type string;
       }
       leaf str-zone {
         type string;
         description "Power zone";
       }
       leaf str-dc-current {
         type string;
       }
       leaf str-dc-voltage {
         type string;
       }
       leaf str-dc-load {
         type string;
       }
     }
     container dc-output-detail3 {
       leaf str2-dc-power {
         type string;
       }
       leaf str2-dc-current {
         type string;
       }
       leaf str2-dc-voltage {
         type string;
       }
       leaf str2-dc-load {
         type string;
       }
     }
     container pem-capacity-detail {
       leaf capacity-actual {
         type uint32;
         description "Actual capacity in volt";
       }
       leaf capacity-max {
         type uint32;
         description "Maximum capacity in volt";
       }
     }
   }
   container power-usage-system {
     leaf capacity-res-power {
       type uint32;
     }
     leaf capacity-sys-actual {
       type uint32;
     }
     leaf capacity-sys-max {
       type uint32;
     }
     leaf capacity-sys-remaining {
       type uint32;
     }
     container power-usage-zone-information {
       leaf zone {
         type uint32;
         description "Power zone";
       }
       leaf str-zone {
         type string;
         description "Power zone";
       }
       leaf capacity-actual {
         type uint32;
         description "Actual capacity in volt";
       }
       leaf capacity-max {
         type uint32;
         description "Maximum capacity in volt";
       }
       leaf capacity-allocated {
         type uint32;
         description "Allocated capacity in volt";
       }
       leaf capacity-remaining {
         type uint32;
         description "Remaining capacity in volt";
       }
       leaf capacity-actual-usage {
         type uint32;
         description "Actual usage in volt";
       }
     }
   }
   container power-usage-system2 {
     container power-usage-zone-information2 {
       leaf capacity-actual {
         type uint32;
         description "Actual capacity in volt";
       }
       leaf capacity-max {
         type uint32;
         description "Maximum capacity in volt";
       }
       leaf capacity-allocated {
         type uint32;
         description "Allocated capacity in volt";
       }
       leaf capacity-remaining {
         type uint32;
         description "Remaining capacity in volt";
       }
       leaf capacity-actual-usage {
         type uint32;
         description "Actual usage in volt";
       }
     }
   }
   container power-usage-total {
     leaf dc-power {
       type uint32;
     }
   }
   container power-usage-voltage-total {
     leaf dc-power {
       type uint32;
     }
   }
   container power-usage-pdu-item {
     leaf slot {
       type int32;
     }
     leaf dc-power {
       type uint32;
     }
     container power-usage-psm-item {
       container power-usage-psm-input {
         leaf name {
           type string;
           description "Name of this component";
         }
         leaf dc-voltage {
           type uint32;
         }
       }
     }
   }
   container power-usage-psm-item1 {
     leaf slot {
       type int32;
     }
     container power-usage-psm-input1 {
       leaf name {
         type string;
         description "Name of this component";
       }
       leaf dc-voltage {
         type uint32;
       }
       leaf dc-power {
         type uint32;
       }
     }
   }
   container power-usage-fru-item {
     leaf name {
       type string;
       description "Name of this component";
     }
     leaf dc-power {
       type uint32;
     }
   }
 }
 grouping fru-power-on-sequence-block {
   leaf sequence {
     type string;
   }
 }
 grouping alarm-information-block {
   container alarm-summary {
     description "Number of alarms currently active";
     leaf active-alarm-count {
       type int32;
       description "Number of active alarms";
     }
     leaf no-active-alarms {
       type empty;
       description "No active alarms";
     }
     container satellite {
       description "Number of alarms currently active";
       leaf active-fpc-slot {
         type int32;
         description "FPC slot with active alarms";
       }
     }
   }
   list alarm-detail {
     description "Detailed information about an active alarm";
     leaf alarm-time {
       type string;
       description "Time of the alarm";
     }
     leaf alarm-class {
       type string;
       description "Class of the alarm";
     }
     leaf alarm-description {
       type string;
       description "Description of the alarm";
     }
   }
 }
 grouping chassis-beacon-information-block {
   container chassis-beacon-item {
     leaf beacon-name {
       type string;
     }
     leaf beacon-state {
       type string;
     }
   }
 }
 grouping network-services-block {
   container network-services-information {
     leaf name {
       type string;
       description "Name of this component";
     }
   }
 }
 grouping ambient-temperature-block {
   container ambient-temperature-information {
     leaf name {
       type string;
       description "Name of this component";
     }
   }
 }
 grouping clock-synchronization-information-block {
   list clock-synchronization {
     leaf clock-fru {
       type string;
       description "FRU on which clock module is present";
     }
     leaf mastership-state {
       type string;
       description "Current state of mastership on this Routing Engine";
     }
     leaf signal-type {
       type string;
       description "Frequency for provided reference clocks";
     }
     leaf switching-mode {
       type string;
       description "Should system revert to higher priority valid source";
     }
     leaf line-termination {
       type string;
       description "How external signal is wired to redundant CBs";
     }
     leaf transmit {
       type string;
       description "Control whether diagnostic timing signal is transmitted";
     }
     leaf validation-interval {
       type uint32;
       description "Time between successive frequency measurements";
     }
     leaf automatic-switching {
       type string;
       description "Clock synchronization source switching: manual or automatic";
     }
     container marked-as-failed-source-list {
       list marked-as-failed-source {
         leaf source-name {
           type string;
           description "Name of clock synchronization source";
         }
       }
     }
     container synchronization-source-list {
       container current-source {
         leaf clock-state {
           type string;
           description "State of the clock synchronization source";
         }
         leaf up-time {
           type string;
           description "Length of time this component has been operational";
         }
         leaf active-time {
           type string;
           description "Time since clock synchronization source is in use";
         }
         leaf deviation {
           type string;
           description "Frequency deviation of clock synchronization source";
         }
         leaf last-deviation {
           type string;
           description "Frequency deviation measured last";
         }
       }
       container configured-source-list {
         list configured-source {
           leaf source-name {
             type string;
             description "Name of clock synchronization source";
           }
           leaf source-priority {
             type string;
             description "Priority of clock synchronization source";
           }
           leaf deviation {
             type string;
             description "Frequency deviation of clock synchronization source";
           }
           leaf last-deviation {
             type string;
             description "Frequency deviation measured last";
           }
           leaf status {
             type string;
             description "Status of clock synchronization source";
           }
         }
       }
     }
   }
 }
 grouping craft-information-block {
   leaf output {
     type string;
     description "Formatted ASCII output displayed by the CLI";
   }
   container front-panel {
     description "Information from the craft interface";
     container display-panel {
       description "Text currently appearing on the craft interface display";
     }
     container re-panel {
       description "State of status LEDs on the craft interface for one or more Routing Engines. The front panel of each Routing Engine has the same LEDs.";
       container re {
         description "State of status LEDs on the craft interface for a Routing Engine. The front panel of the Routing Engine has the same LEDs.";
       }
     }
     container alarm-indicators {
       description "Information about alarms from the craft interface";
     }
     container fpc-panel {
       description "State of status LEDs on the craft interface for Flexible PIC Concentrators";
       list fpc {
         container pic-detail {
           container port-information {
           }
           container package-information {
             container package {
             }
           }
           container port-speed-information {
           }
         }
       }
     }
     container sib-panel {
       description "State of the status LEDs on the faceplate of one or more Switch Interface Boards. Some of the LEDs also appear on the craft interface.";
       container sib {
       }
     }
     container ccg-panel {
       description "State of the status LEDs on the faceplate of one or more SONET ClockGenerators";
       container ccg {
         description "State of the CCG status LEDs on the craft interface";
       }
     }
     container fan-tray-panel {
       description "State of status LEDs on the craft interface for Fan Trays";
       container fan-tray {
         description "State of the status LEDs on the craft interface for a fan tray";
       }
     }
     container power-supply-panel {
       description "State of the status LEDs on the faceplate of one or more power supplies";
       container power-supply {
         description "State of the status LEDs on the faceplate of a power supply";
       }
       container pdu {
         description "State of the PDU status LEDs on the craft interface";
         container psm {
           description "State of the PSM status LEDs on the craft interface";
         }
       }
     }
   }
   container recb-panel {
     description "Information about LEDs from the craft interface";
     container ha-led {
       description "State of the HA LED on the craft interface";
     }
     container rps-led {
       description "State of the RPS LED on the craft interface";
     }
     container mpim1-led {
       description "State of the MPIM1 LED on the craft interface";
     }
     container mpim2-led {
       description "State of the MPIM2 LED on the craft interface";
     }
     container storage-led {
       description "State of the external storage LED on the craft interface";
     }
     container sfb-led {
       description "State of the SFB LED on the craft interface";
     }
     container cfm-ok-fail-led {
       description "State of the CFM Ok/Fail LED on the craft interface";
     }
     container cfm-service-led {
       description "State of the CFM Service LED on the craft interface";
     }
     container sysio-status-led {
       description "State of the SYSIO Status LED on the craft interface";
     }
   }
   container mcs-panel {
     description "State of the status LEDs on the faceplate of one or more Miscellaneous Control Subsystems";
     container mcs {
       description "State of the status LEDs on the faceplate of a Miscellaneous Control Subsystem";
     }
   }
   container sfm-panel {
     description "State of the status LEDs on the faceplate of one or more Switching and Forwarding Modules";
     container sfm {
       description "State of the status LEDs on the faceplate of a Switching andForwarding Module";
     }
   }
   container pcg-panel {
     description "State of the status LEDs on the faceplate of one or more Packet Forwarding Engine Clock Generators";
     container pcg {
       description "State of the status LEDs on the faceplate of a Packet Forwarding Engine Clock Generator";
     }
   }
   container cb-panel {
     description "State of status LEDs on one or more Control Boards";
     container cb {
       description "State of status LEDs on a Control Board";
     }
   }
   container sib-panel {
     description "State of the status LEDs on the faceplate of one or more Switch Interface Boards. Some of the LEDs also appear on the craft interface.";
     container sib {
     }
   }
   container scg-panel {
     description "State of the status LEDs on the faceplate of one or more SONET ClockGenerators";
     container scg {
       description "State of the status LEDs on the faceplate of a SONET Clock Generator";
     }
   }
   container feb-panel {
     description "State of the status LEDs on the faceplate of one or more Forwarding Engine Boards";
     container feb {
       description "State of the status LEDs on the faceplate of a Forwarding Engine Board";
     }
   }
   container power-supply-panel {
     description "State of the status LEDs on the faceplate of one or more power supplies";
     container power-supply {
       description "State of the status LEDs on the faceplate of a power supply";
     }
     container pdu {
       description "State of the PDU status LEDs on the craft interface";
       container psm {
         description "State of the PSM status LEDs on the craft interface";
       }
     }
   }
   container fan-tray-panel {
     description "State of status LEDs on the craft interface for Fan Trays";
     container fan-tray {
       description "State of the status LEDs on the craft interface for a fan tray";
     }
   }
 }
 grouping feb-redundancy-information-block {
   list feb-redundancy-group-information {
     description "FEB redundancy information for a redundancy group";
     container feb-redundancy-group-information-item {
       description "FEB redundancy information for a FEB";
       leaf feb-slot {
         type int32;
         description "FEB slot";
       }
       leaf feb-state {
         type string;
         description "FEB state";
       }
       leaf redundancy-priority {
         type string;
         description "FEB redundancy priority";
       }
       leaf connected-fpcs {
         type string;
         description "List of FPCs connected to the FEB in printable form";
       }
       leaf redundancy-state {
         type string;
         description "Redundancy state";
       }
       leaf redundancy-state-description {
         type string;
         description "Description of redundancy state";
       }
     }
   }
 }
 grouping feb-redundancy-error-information-block {
   list feb-redundancy-group-errors {
     description "FEB redundancy error information for a FEB group";
     container feb-redundancy-group-feb-errors {
       description "FEB redundancy error information for a FEB";
       leaf feb-slot {
         type int32;
         description "FEB slot";
       }
       leaf feb-state {
         type string;
         description "FEB state";
       }
       leaf feb-harderror-state {
         type string;
         description "FEB hard error state";
       }
       list feb-redundancy-group-feb-fpc-errors {
         description "FEB redundancy error information for an FPC";
         leaf fpc-slot {
           type int32;
           description "FPC slot";
         }
         leaf fpc-link-status {
           type string;
           description "FPC link status";
         }
       }
       list feb-redundancy-group-feb-fabric-plane-errors {
         description "FEB redundancy error information for a fabric plane";
         leaf fabric-plane-number {
           type int32;
           description "Fabric plane number";
         }
         leaf fabric-plane-status {
           type int32;
           description "Fabric plane status";
         }
       }
     }
   }
 }
 grouping fpc-feb-connectivity-block {
   list fpc-feb-connectivity-item {
     description "FEB connectivity information for an FPC";
     leaf fpc-slot {
       type int32;
       description "FPC slot";
     }
     leaf fpc-type {
       type string;
       description "FPC type";
     }
     leaf fpc-state {
       type string;
       description "FPC state";
     }
     leaf feb-slot {
       type int32;
       description "FEB slot";
     }
     leaf no-feb-slot {
       type empty;
     }
     leaf feb-state {
       type string;
       description "FEB state";
     }
     leaf fpc-link-status {
       type string;
       description "FPC link status";
     }
   }
 }
 grouping chassis-zones-information-block {
   leaf name {
     type string;
     description "Name of this component";
   }
   leaf driving-fru-name {
     type string;
   }
   leaf temperature {
     type string;
     description "Temperature of the item";
   }
   leaf zone-status {
     type string;
   }
   leaf comment {
     type string;
   }
   leaf fan-missing-cnt {
     type uint32;
   }
   leaf fan-failed-cnt {
     type uint32;
   }
   leaf fan-dutycycle {
     type uint32;
   }
   leaf fru-name {
     type string;
   }
   leaf fru-temp-status {
     type string;
   }
   leaf fru-temperature {
     type string;
   }
   leaf cooling-fru-name {
     type string;
   }
   leaf fru-fan-status {
     type string;
   }
   leaf fru-comment {
     type string;
   }
 }
 grouping environment-information-block {
   list environment-item {
     leaf class {
       type string;
     }
     leaf status {
       type string;
       description "Status of clock synchronization source";
     }
   }
 }
 grouping environment-component-information-block {
   list environment-component-item {
     description "Chassis environment component";
     leaf name {
       type string;
       description "Name of this component";
     }
     leaf state {
       type string;
       description "Status of the component";
     }
     leaf bus-revision {
       type int32;
       description "Bus revision";
     }
     leaf cmb-revision {
       type int32;
       description "CMB revision";
     }
     leaf fpga-revision {
       type int32;
       description "FPGA revision";
     }
     leaf ac-feed0-voltage {
       type string;
       description "AC feed0 voltage";
     }
     leaf ac-feed0-current {
       type string;
       description "AC feed0 current";
     }
     leaf ac-feed0-power {
       type string;
       description "AC feed0 power";
     }
     leaf ac-feed1-voltage {
       type string;
       description "AC feed1 voltage";
     }
     leaf ac-feed1-current {
       type string;
       description "AC feed1 current";
     }
     leaf ac-feed1-power {
       type string;
       description "AC feed1 power";
     }
     leaf reason {
       type string;
       description "Reason";
     }
     leaf frequency {
       type string;
       description "Frequency";
     }
     leaf slave-revision {
       type uint32;
       description "Slave revision";
     }
     leaf load {
       type string;
       description "Load";
     }
     leaf time-used {
       type string;
       description "Length of time this component has been used";
     }
     container temperature-reading {
       leaf temperature-name {
         type string;
       }
       leaf temperature {
         type string;
         description "Temperature of the item";
       }
     }
     container fan-speed-reading {
       leaf fan-name {
         type string;
       }
       leaf fan-speed {
         type string;
         description "Fan speed in RPM";
       }
     }
     container fpga-revision-detail {
       description "FPGA revision in detail";
       leaf fpga-revision-name {
         type string;
       }
       leaf fpga-revision-value {
         type string;
       }
     }
     container revision {
       leaf revision-name {
         type string;
         description "Revision Name";
       }
       leaf revision-number {
         type uint32;
         description "Revision Number";
       }
     }
     container slave-registers-information {
       leaf slave-registers-title {
         type string;
         description "Title for the dump of slave registers";
       }
       container slave-registers {
         description "Slave register values";
       }
     }
     container cowra-registers-information {
       leaf cowra-registers-title {
         type string;
         description "Title for the dump of cowra registers";
       }
       container cowra-registers {
         description "Cowra register values";
       }
     }
     container fpga-registers {
       description "FPGA register values";
       leaf fpga-registers-type {
         type string;
       }
       leaf fpga-registers-name {
         type string;
       }
       leaf fpga-registers-value {
         type string;
       }
     }
     list firmware {
       description "Firmware version";
       leaf firmware-name {
         type string;
         description "Name of this component";
       }
       leaf firmware-version {
         type string;
         description "Firmware version string for this component";
       }
     }
     container power-information {
       leaf voltage-title {
         type string;
         description "Title for the display of voltage";
       }
       leaf max-power-consumption-ambient-temp {
         type int32;
       }
       leaf psm-hours-used {
         type uint32;
         description "Hours used for this component";
       }
       container power-title {
       }
       container voltage {
       }
       container current {
       }
       container voltage-power {
       }
     }
     container pcg-frequency {
       description "PCG Frequency";
       leaf pcg-frequency-setting {
         type string;
       }
       leaf pcg-frequency-measurement {
         type string;
       }
     }
     container dc-information {
       leaf dc-feed0-voltage {
         type string;
         description "DC feed0 voltage";
       }
       leaf dc-feed0-current {
         type string;
         description "DC feed0 current";
       }
       leaf dc-feed0-power {
         type string;
         description "DC feed0 power";
       }
       leaf dc-feed1-voltage {
         type string;
         description "DC feed1 voltage";
       }
       leaf dc-feed1-current {
         type string;
         description "DC feed1 current";
       }
       leaf dc-feed1-power {
         type string;
         description "DC feed1 power";
       }
       leaf dc-input {
         type string;
         description "DC input state";
       }
       leaf dc-output {
         type string;
         description "DC output state";
       }
       leaf ac-input {
         type string;
         description "AC input state";
       }
       leaf ac-output {
         type string;
         description "AC output state";
       }
       container dc-detail {
         description "Detailed DC information";
       }
       container dc-in-detail2 {
         description "Detailed DC input information";
       }
       container dc-detail2 {
         description "Detailed DC information";
       }
     }
     container pmbus-table {
       container pmbus-table-entry {
         description "Power Management Bus Device information";
       }
     }
     container airflow-direction {
       leaf airflow {
         type string;
       }
       leaf direction {
         type string;
         description "Airflow direction";
       }
     }
     container input-voltage {
       leaf voltage-name {
         type string;
         description "Input voltage";
       }
       leaf voltage-value {
         type uint32;
       }
     }
     container output-detail {
       description "Detailed power output information";
       leaf output-voltage {
         type uint32;
       }
       leaf output-current {
         type uint32;
         description "Output Current in Ampere(A)";
       }
     }
     container pdu-information {
       leaf hours-used {
         type uint32;
         description "Hours used for this component";
       }
       container efuse {
         description "PDU efuse information";
         leaf name {
           type string;
           description "Name of this component";
         }
         leaf state {
           type string;
           description "Status of the component";
         }
       }
       container pdu-firmware {
         description "PDU firmware information";
         leaf firmware-name {
           type string;
           description "Name of this component";
         }
         leaf firmware-version {
           type string;
           description "Firmware version string for this component";
         }
       }
       container pdu-component {
         description "PDU specific component information";
         leaf component-name {
           type string;
           description "PDU component name";
         }
         leaf component-state {
           type string;
           description "PDU component state";
         }
       }
     }
     container psm-information {
       leaf temperature {
         type string;
         description "Temperature of the item";
       }
       leaf hours-used {
         type uint32;
         description "Hours used for this component";
       }
       leaf firmware-version {
         type string;
         description "Firmware version string for this component";
       }
       container psm-status {
         leaf psm-health-check-status {
           type string;
           description "Show health check status of all PSMs";
         }
         leaf fans {
           type string;
           description "Fan status for this component";
         }
         leaf dc-input {
           type string;
           description "DC input state";
         }
         leaf dc-input1 {
           type string;
           description "DC input1 state";
         }
         leaf dc-input2 {
           type string;
           description "DC input2 state";
         }
         leaf ac-input {
           type string;
           description "AC input state";
         }
         leaf ac-input1 {
           type string;
           description "AC input1 state";
         }
         leaf ac-input2 {
           type string;
           description "AC input2 state";
         }
         leaf check-input1-alarm {
           type string;
           description "Check input1 alarm";
         }
         leaf check-input2-alarm {
           type string;
           description "Check input2 alarm";
         }
         leaf dc-output {
           type string;
           description "DC output state";
         }
         leaf ac-output {
           type string;
           description "AC output state";
         }
       }
     }
     container pem-information {
       leaf fpc-slot {
         type int32;
         description "FPC slot";
       }
       leaf pem-slot {
         type uint32;
       }
       leaf pem-state {
         type string;
         description "State of power supply unit";
       }
       leaf pem-temperature {
         type uint32;
         description "Temperature in (C)";
       }
       leaf input-current {
         type uint32;
         description "Input Current in Ampere(A)";
       }
       leaf input-volt {
         type uint32;
         description "Input Volt in Volt(V)";
       }
       leaf input-power {
         type uint32;
         description "Input Power in Watt(W)";
       }
       leaf output-current {
         type uint32;
         description "Output Current in Ampere(A)";
       }
       leaf output-volt {
         type uint32;
         description "Output Volt in Volt(V)";
       }
       leaf output-power {
         type uint32;
         description "Output Power in Watt(W)";
       }
     }
   }
 }
 grouping fan-information-block {
   container rpm {
     container fan-information-rpm-item {
       leaf name {
         type string;
         description "Name of this component";
       }
       leaf status {
         type string;
         description "Status of clock synchronization source";
       }
       leaf comment {
         type string;
       }
     }
   }
   container percent-rpm {
     container fan-information-percent-rpm-item {
       leaf name {
         type string;
         description "Name of this component";
       }
       leaf status {
         type string;
         description "Status of clock synchronization source";
       }
       leaf rpm-percent {
         type string;
         description "Fan speed in % RPM";
       }
       leaf comment {
         type string;
       }
     }
   }
 }
 grouping sfb-information-block {
   container brief {
     container sfb {
       leaf slot {
         type int32;
       }
       leaf state {
         type string;
         description "Status of the component";
       }
       leaf up-time {
         type string;
         description "Length of time this component has been operational";
       }
       leaf comment {
         type string;
       }
     }
   }
 }
 grouping firmware-information-block {
   container chassis {
     description "Hardware inventory of this chassis";
     container inventory {
       description "Hardware inventory of this chassis";
       leaf name {
         type string;
         description "Name of this component";
       }
       leaf version {
         type string;
         description "Version of this component";
       }
       leaf part-number {
         type string;
         description "Part number of this component";
       }
       leaf serial-number {
         type string;
         description "Serial number of this component";
       }
       leaf description {
         type string;
         description "Description of this component";
       }
       leaf hardware-incomplete {
         type empty;
       }
       container i2c-information {
         leaf jedec-code {
           type string;
         }
         leaf eeprom-version {
           type string;
         }
         leaf assembly-identifier {
           type string;
         }
         leaf assembly-version {
           type string;
         }
         leaf manufacture-date {
           type string;
           description "Date this component was manufactured";
         }
         leaf assembly-flags {
           type string;
         }
         leaf i2c-version {
           type string;
         }
         leaf clei-code {
           type string;
           description "Common Language Equipment Identifier code of this component";
         }
         leaf i2c-identifier {
           type string;
         }
         leaf model-number {
           type string;
           description "Model number of this component";
         }
         leaf board-information-record {
           type string;
           description "Hex dump of board information record";
         }
         leaf i2c-data {
           type string;
           description "Hex dump of I2C data";
         }
       }
       list chassis-module {
         leaf name {
           type string;
           description "Name of this component";
         }
         leaf version {
           type string;
           description "Version of this component";
         }
         leaf part-number {
           type string;
           description "Part number of this component";
         }
         leaf serial-number {
           type string;
           description "Serial number of this component";
         }
         leaf description {
           type string;
           description "Description of this component";
         }
         leaf ir-mode {
           type string;
           description "R/IR mode configured";
         }
         leaf license-mode {
           type string;
           description "PTX R/IR mode configured";
         }
         container i2c-information {
           leaf jedec-code {
             type string;
           }
           leaf eeprom-version {
             type string;
           }
           leaf assembly-identifier {
             type string;
           }
           leaf assembly-version {
             type string;
           }
           leaf manufacture-date {
             type string;
             description "Date this component was manufactured";
           }
           leaf assembly-flags {
             type string;
           }
           leaf i2c-version {
             type string;
           }
           leaf clei-code {
             type string;
             description "Common Language Equipment Identifier code of this component";
           }
           leaf i2c-identifier {
             type string;
           }
           leaf model-number {
             type string;
             description "Model number of this component";
           }
           leaf board-information-record {
             type string;
             description "Hex dump of board information record";
           }
           leaf i2c-data {
             type string;
             description "Hex dump of I2C data";
           }
         }
         list chassis-sub-module {
           leaf name {
             type string;
             description "Name of this component";
           }
           leaf version {
             type string;
             description "Version of this component";
           }
           leaf part-number {
             type string;
             description "Part number of this component";
           }
           leaf serial-number {
             type string;
             description "Serial number of this component";
           }
           leaf description {
             type string;
             description "Description of this component";
           }
           container i2c-information {
             leaf jedec-code {
               type string;
             }
             leaf eeprom-version {
               type string;
             }
             leaf assembly-identifier {
               type string;
             }
             leaf assembly-version {
               type string;
             }
             leaf manufacture-date {
               type string;
               description "Date this component was manufactured";
             }
             leaf assembly-flags {
               type string;
             }
             leaf i2c-version {
               type string;
             }
             leaf clei-code {
               type string;
               description "Common Language Equipment Identifier code of this component";
             }
             leaf i2c-identifier {
               type string;
             }
             leaf model-number {
               type string;
               description "Model number of this component";
             }
             leaf board-information-record {
               type string;
               description "Hex dump of board information record";
             }
             leaf i2c-data {
               type string;
               description "Hex dump of I2C data";
             }
           }
           list chassis-sub-sub-module {
             leaf name {
               type string;
               description "Name of this component";
             }
             leaf version {
               type string;
               description "Version of this component";
             }
             leaf part-number {
               type string;
               description "Part number of this component";
             }
             leaf serial-number {
               type string;
               description "Serial number of this component";
             }
             leaf description {
               type string;
               description "Description of this component";
             }
             list chassis-sub-sub-sub-module {
             }
           }
         }
         list chassis-re-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
         list chassis-re-usb-module {
           leaf name {
             type string;
             description "Name of this component";
           }
           leaf product {
             type string;
           }
           leaf product-number {
             type int32;
           }
           leaf vendor {
             type string;
           }
           leaf description {
             type string;
             description "Description of this component";
           }
         }
         list chassis-re-dimm-module {
           leaf name {
             type string;
             description "Name of this component";
           }
           leaf part-number {
             type string;
             description "Part number of this component";
           }
           leaf die-rev {
             type string;
             description " DIE revision of the DIMM";
           }
           leaf pcb-rev {
             type string;
             description "PCB revision ";
           }
           leaf mfr-id {
             type string;
             description "Manufacture Id of the DIMM";
           }
         }
         list chassis-compute-node-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
       }
     }
     container model-inventory {
       description "Hardware inventory of this chassis";
       list chassis-module {
         leaf name {
           type string;
           description "Name of this component";
         }
         leaf version {
           type string;
           description "Version of this component";
         }
         leaf part-number {
           type string;
           description "Part number of this component";
         }
         leaf serial-number {
           type string;
           description "Serial number of this component";
         }
         leaf model-number {
           type string;
           description "Model number of this component";
         }
         list chassis-sub-module {
           list chassis-sub-sub-module {
             list chassis-sub-sub-sub-module {
             }
           }
         }
       }
     }
     container clei-model-inventory {
       description "Hardware inventory of this chassis";
       list chassis-module {
         leaf name {
           type string;
           description "Name of this component";
         }
         leaf version {
           type string;
           description "Version of this component";
         }
         leaf part-number {
           type string;
           description "Part number of this component";
         }
         leaf clei-code {
           type string;
           description "Common Language Equipment Identifier code of this component";
         }
         leaf model-number {
           type string;
           description "Model number of this component";
         }
         list chassis-sub-module {
           list chassis-sub-sub-module {
             list chassis-sub-sub-sub-module {
             }
           }
         }
       }
     }
     container firmware {
       description "Hardware inventory of this chassis";
       list chassis-module {
         leaf name {
           type string;
           description "Name of this component";
         }
         list chassis-sub-module {
           list chassis-sub-sub-module {
             list chassis-sub-sub-sub-module {
             }
           }
         }
       }
     }
   }
 }
 grouping hardware-version-information-block {
   list chassis-version {
     leaf component-name {
       type string;
       description "PDU component name";
     }
     leaf component-version {
       type string;
     }
     list chassis-module-version {
       list chassis-module-sub-version {
         list chassis-module-sub-sub-version {
         }
       }
     }
   }
 }
 grouping fpc-information-block {
   list terse {
     list fpc {
       leaf slot {
         type int32;
       }
       leaf state {
         type string;
         description "Status of the component";
       }
       leaf comment {
         type string;
       }
       leaf temperature {
         type string;
         description "Temperature of the item";
       }
       container pic-detail {
         container port-information {
         }
         container package-information {
           container package {
           }
         }
         container port-speed-information {
         }
       }
     }
   }
   list brief {
     leaf fpc-slot {
       type int32;
       description "FPC slot";
     }
     leaf fpc-status {
       type string;
       description "FPC status";
     }
     leaf fpc-power-limit {
       type string;
       description "FPC power limit";
     }
     leaf fpc-power {
       type string;
       description "Total FPC power consumption";
     }
     leaf fpc-priority {
       type string;
       description "Priority options";
     }
     leaf fpc-firmware-version {
       type string;
       description "POE firmware version";
     }
     list fpc {
       leaf slot {
         type int32;
       }
       leaf state {
         type string;
         description "Status of the component";
       }
       leaf comment {
         type string;
       }
       leaf temperature {
         type string;
         description "Temperature of the item";
       }
       leaf cpu-total {
         type int32;
         description "Percentage of CPU utilized";
       }
       leaf cpu-interrupt {
         type int32;
         description "Percentage of CPU utilized by interrupt processing";
       }
       leaf cpu-1min-avg {
         type int32;
         description "Percentage of one min average CPU utilized";
       }
       leaf cpu-5min-avg {
         type int32;
         description "Percentage of five min average CPU utilized";
       }
       leaf cpu-15min-avg {
         type int32;
         description "Percentage of fifteen min average CPU utilized";
       }
       leaf memory-dram-size {
         type int32;
         description "DRAM";
       }
       leaf memory-heap-utilization {
         type int32;
         description "Percentage of heap memory utilized";
       }
       leaf memory-buffer-utilization {
         type int32;
         description "Percentage of buffer memory utilized";
       }
       container pic-detail {
         container port-information {
         }
         container package-information {
           container package {
           }
         }
         container port-speed-information {
         }
       }
     }
   }
   list brief-bsys {
     list fpc {
       leaf slot {
         type int32;
       }
       leaf state {
         type string;
         description "Status of the component";
       }
       leaf comment {
         type string;
       }
       leaf temperature {
         type string;
         description "Temperature of the item";
       }
       leaf cpu-total {
         type int32;
         description "Percentage of CPU utilized";
       }
       leaf cpu-interrupt {
         type int32;
         description "Percentage of CPU utilized by interrupt processing";
       }
       leaf cpu-1min-avg {
         type int32;
         description "Percentage of one min average CPU utilized";
       }
       leaf cpu-5min-avg {
         type int32;
         description "Percentage of five min average CPU utilized";
       }
       leaf cpu-15min-avg {
         type int32;
         description "Percentage of fifteen min average CPU utilized";
       }
       leaf memory-dram-size {
         type int32;
         description "DRAM";
       }
       leaf memory-heap-utilization {
         type int32;
         description "Percentage of heap memory utilized";
       }
       leaf memory-buffer-utilization {
         type int32;
         description "Percentage of buffer memory utilized";
       }
       leaf gnf-id {
         type string;
       }
       container pic-detail {
         container port-information {
         }
         container package-information {
           container package {
           }
         }
         container port-speed-information {
         }
       }
     }
   }
   list verbose {
     list fpc {
       leaf slot {
         type int32;
       }
       leaf state {
         type string;
         description "Status of the component";
       }
       leaf error-code {
         type int32;
         description "Code resulting from major or minor error";
       }
       leaf logical-slot {
         type int32;
       }
       leaf temperature {
         type string;
         description "Temperature of the item";
       }
       leaf cpu-less-info-str {
         type string;
         description "Flexible PIC Concentrator (FPC) without CPU";
       }
       leaf memory-dram-size {
         type int32;
         description "DRAM";
       }
       leaf memory-sram-size {
         type int32;
         description "SRAM";
       }
       leaf memory-sdram-size {
         type int32;
         description "SDRAM";
       }
       leaf memory-notification-sdram-size {
         type int32;
         description "Notification SDRAM";
       }
       leaf memory-rldram-size {
         type int32;
         description "RLDRAM";
       }
       leaf memory-xr2-size {
         type int32;
         description "XR2";
       }
       leaf memory-ddr-dram-size {
         type int32;
         description "DDR DRAM";
       }
       leaf asic-information {
         type string;
       }
       leaf start-time {
         type string;
         description "Time this component was started";
       }
       leaf up-time {
         type string;
         description "Length of time this component has been operational";
       }
       leaf comment {
         type string;
       }
       leaf max-power-consumption {
         type int32;
       }
       leaf max-mpc-base-power-consumption {
         type int32;
         description "Max MPC base power consumption";
       }
       leaf max-mic0-power-consumption {
         type int32;
         description "Max MIC0 power consumption";
       }
       leaf max-mic1-power-consumption {
         type int32;
         description "Max MIC1 power consumption";
       }
       leaf max-mpc-total-power-consumption {
         type int32;
         description "Max MPC total power consumption";
       }
       container pic-detail {
         container port-information {
         }
         container package-information {
           container package {
           }
         }
         container port-speed-information {
         }
       }
     }
   }
   list pic-style {
     list fpc {
       leaf slot {
         type int32;
       }
       leaf state {
         type string;
         description "Status of the component";
       }
       leaf description {
         type string;
         description "Description of this component";
       }
       leaf gnf-id {
         type string;
       }
       list pic {
         leaf pic-slot {
           type int32;
         }
         leaf pic-state {
           type string;
         }
         leaf pic-type {
           type string;
         }
         leaf comment {
           type string;
         }
       }
       container pic-detail {
         container port-information {
         }
         container package-information {
           container package {
           }
         }
         container port-speed-information {
         }
       }
     }
   }
   list pic-style-detail {
     list fpc {
       container pic-detail {
         leaf slot {
           type int32;
         }
         leaf pic-slot {
           type int32;
         }
         leaf pic-type {
           type string;
         }
         leaf comment {
           type string;
         }
         leaf asic-type {
           type string;
           description "Type of ASIC on the PIC";
         }
         leaf account-layer2-overhead {
           type string;
           description "Account Layer2 Overhead Knob Status";
         }
         leaf state {
           type string;
           description "Status of the component";
         }
         leaf pic-version {
           type string;
           description "PIC hardware version";
         }
         leaf cpu-sw-version {
           type string;
           description "Version of operating system running on the PIC";
         }
         leaf cpu-rom-version {
           type string;
           description "PIC ROM version";
         }
         leaf cpu-total {
           type int32;
           description "Percentage of CPU utilized";
         }
         leaf cpu-interrupt {
           type int32;
           description "Percentage of CPU utilized by interrupt processing";
         }
         leaf memory-dram-size {
           type int32;
           description "DRAM";
         }
         leaf memory-buffer-utilization {
           type int32;
           description "Percentage of buffer memory utilized";
         }
         leaf memory-heap-utilization {
           type int32;
           description "Percentage of heap memory utilized";
         }
         leaf up-time {
           type string;
           description "Length of time this component has been operational";
         }
         leaf pic-package {
           type string;
         }
         leaf pic-clock-sync {
           type string;
           description "PIC Clock Synchronization";
         }
         leaf pic-multirate-mode {
           type string;
         }
         leaf pic-channelization-mode {
           type string;
           description "PIC Channelization Mode";
         }
         leaf configured-mode {
           type string;
         }
         leaf control-cores {
           type int32;
         }
         leaf data-cores {
           type int32;
         }
         leaf object-cache-size {
           type int32;
         }
         leaf policy-db-size {
           type int32;
         }
         leaf forwarding-db-size {
           type int32;
         }
         leaf wired-process-mem-size {
           type int32;
         }
         leaf wired-max-processes {
           type int32;
         }
         container port-information {
           container port {
             leaf port-number {
               type int32;
               description "Port number on the PIC";
             }
             leaf cable-type {
               type string;
               description "Port cable type";
             }
             leaf fiber-mode {
               type string;
               description "Single or multi-mode";
             }
             leaf sfp-vendor-name {
               type string;
               description "SFP vendor name";
             }
             leaf sfp-vendor-pno {
               type string;
               description "SFP vendor part number";
             }
             leaf wavelength {
               type string;
               description "Wavelength of the optical transceiver";
             }
             leaf sfp-vendor-fw-ver {
               type string;
               description "Vendor firmware version";
             }
           }
         }
         container pic-transport-information {
           leaf pic-transport-admin-state {
             type string;
           }
           leaf pic-transport-oper-state {
             type string;
           }
         }
         container package-information {
           container package {
           }
         }
         container port-speed-information {
           container port {
             leaf port-number1 {
               type int32;
               description "PIC port number";
             }
             leaf speed-capability {
               type string;
               description "Port speed capabilities";
             }
           }
         }
       }
     }
   }
   list detail {
     leaf fpc-slot {
       type int32;
       description "FPC slot";
     }
     leaf fpc-status {
       type string;
       description "FPC status";
     }
     leaf fpc-power-limit {
       type string;
       description "FPC power limit";
     }
     leaf fpc-power {
       type string;
       description "Total FPC power consumption";
     }
     leaf fpc-priority {
       type string;
       description "Priority options";
     }
     leaf fpc-firmware-version {
       type string;
       description "POE firmware version";
     }
     list fpc {
       container pic-detail {
         container port-information {
         }
         container package-information {
           container package {
           }
         }
         container port-speed-information {
         }
       }
     }
   }
 }
 grouping fpc-port-information-block {
   container brief {
     description "Display the port stats for FPC";
     list fpc {
       leaf slot {
         type int32;
       }
       leaf port-num {
         type int32;
       }
       leaf port-config-map {
         type string;
       }
       leaf port-map {
         type string;
       }
       container pic-detail {
         container port-information {
         }
         container package-information {
           container package {
           }
         }
         container port-speed-information {
         }
       }
     }
   }
 }
 grouping fpc-error-information-block {
   container brief {
     description "Display the ASIC error stats for FPC";
     list fpc {
       leaf slot {
         type int32;
       }
       leaf minor-level-occured {
         type uint32;
       }
       leaf minor-level-cleared {
         type uint32;
       }
       leaf minor-level-threshold {
         type uint32;
       }
       leaf minor-level-action-taken {
         type uint32;
       }
       leaf minor-level-action {
         type string;
       }
       leaf major-level-occured {
         type uint32;
       }
       leaf major-level-cleared {
         type uint32;
       }
       leaf major-level-threshold {
         type uint32;
       }
       leaf major-level-action-taken {
         type uint32;
       }
       leaf major-level-action {
         type string;
       }
       leaf fatal-level-occured {
         type uint32;
       }
       leaf fatal-level-cleared {
         type uint32;
       }
       leaf fatal-level-threshold {
         type uint32;
       }
       leaf fatal-level-action-taken {
         type uint32;
       }
       leaf fatal-level-action {
         type string;
       }
       leaf fpc-pfe-state {
         type string;
       }
       container pic-detail {
         container port-information {
         }
         container package-information {
           container package {
           }
         }
         container port-speed-information {
         }
       }
     }
   }
 }
 grouping fpc-optical-information-block {
   container mfg {
     leaf fpc-optical-prod-mb {
       type string;
       description "Optical module main board product name";
     }
     leaf fpc-optical-prod-edfa {
       type string;
       description "Optical module EDFA product name";
     }
     leaf fpc-optical-prod-wss {
       type string;
       description "Optical module WSS product name";
     }
     leaf fpc-optical-prod-ocm {
       type string;
       description "Optical module OCM product name";
     }
     leaf fpc-optical-mod-mb {
       type string;
       description "Optical module main board module type";
     }
     leaf fpc-optical-mod-edfa {
       type string;
       description "Optical module EDFA module type";
     }
     leaf fpc-optical-mod-wss {
       type string;
       description "Optical module WSS module type";
     }
     leaf fpc-optical-mod-ocm {
       type string;
       description "Optical module OCM module type";
     }
     leaf fpc-optical-boot-edfa {
       type string;
       description "Optical module EDFA boot version";
     }
     leaf fpc-optical-boot-ocm {
       type string;
       description "Optical module OCM boot version";
     }
     leaf fpc-optical-sw-mb {
       type string;
       description "Optical module main board software version";
     }
     leaf fpc-optical-fw-mb {
       type string;
       description "Optical module main board firmware version";
     }
     leaf fpc-optical-fw-edfa {
       type string;
       description "Optical module EDFA firmware version";
     }
     leaf fpc-optical-fw-wss {
       type string;
       description "Optical module WSS firmware version";
     }
     leaf fpc-optical-fw-ocm {
       type string;
       description "Optical module OCM firmware version";
     }
     leaf fpc-optical-fpga-mb {
       type string;
       description "Optical module main board FPGA version";
     }
     leaf fpc-optical-fpga-edfa {
       type string;
       description "Optical module EDFA FPGA version";
     }
     leaf fpc-optical-cpld-mb {
       type string;
       description "Optical module main board CPLD version";
     }
     leaf fpc-optical-hw-mb {
       type string;
       description "Optical module main board hardware version";
     }
     leaf fpc-optical-hw-edfa {
       type string;
       description "Optical module EDFA hardware version";
     }
     leaf fpc-optical-hw-wss {
       type string;
       description "Optical module WSS hardware version";
     }
     leaf fpc-optical-hw-ocm {
       type string;
       description "Optical module OCM hardware version";
     }
     leaf fpc-optical-pcb-mb {
       type string;
       description "Optical module main board PCB revision";
     }
     leaf fpc-optical-pcb-edfa {
       type string;
       description "Optical module EDFA PCB revision";
     }
     leaf fpc-optical-pcb-wss {
       type string;
       description "Optical module WSS PCB revision";
     }
     leaf fpc-optical-pcb-ocm {
       type string;
       description "Optical module OCM PCB revision";
     }
     leaf fpc-optical-pn-mb {
       type string;
       description "Optical module main board part number";
     }
     leaf fpc-optical-pn-edfa {
       type string;
       description "Optical module EDFA part number";
     }
     leaf fpc-optical-pn-wss {
       type string;
       description "Optical module WSS part number";
     }
     leaf fpc-optical-pn-ocm {
       type string;
       description "Optical module OCM part number";
     }
     leaf fpc-optical-sn-mb {
       type string;
       description "Optical module main board serial number";
     }
     leaf fpc-optical-sn-edfa {
       type string;
       description "Optical module EDFA serial number";
     }
     leaf fpc-optical-sn-wss {
       type string;
       description "Optical module WSS serial number";
     }
     leaf fpc-optical-sn-ocm {
       type string;
       description "Optical module OCM serial number";
     }
     leaf fpc-optical-mdate-mb {
       type string;
       description "Optical module main board manufacture date";
     }
     leaf fpc-optical-mdate-edfa {
       type string;
       description "Optical module EDFA manufacture date";
     }
     leaf fpc-optical-mdate-wss {
       type string;
       description "Optical module WSS manufacture date";
     }
     leaf fpc-optical-mdate-ocm {
       type string;
       description "Optical module OCM manufacture date";
     }
     leaf fpc-optical-cdate-mb {
       type string;
       description "Optical module main board calibration date";
     }
     leaf fpc-optical-cdate-edfa {
       type string;
       description "Optical module EDFA calibration date";
     }
     leaf fpc-optical-cdate-wss {
       type string;
       description "Optical module WSS calibration date";
     }
     leaf fpc-optical-cdate-ocm {
       type string;
       description "Optical module OCM calibration date";
     }
   }
   container status {
     leaf fpc-optical-status-uptime {
       type string;
       description "Optical module operational uptime";
     }
     leaf fpc-optical-status-edfa1-temp {
       type string;
       description "Optical module operational EDFA 1 case temperature";
     }
     leaf fpc-optical-status-edfa1-pump {
       type string;
       description "Optical module operational EDFA 1 pump temperature";
     }
     leaf fpc-optical-status-edfa1-coil {
       type string;
       description "Optical module operational EDFA 1 coil temperature";
     }
     leaf fpc-optical-status-edfa2-temp {
       type string;
       description "Optical module operational EDFA 2 case temperature";
     }
     leaf fpc-optical-status-edfa2-pump {
       type string;
       description "Optical module operational EDFA 2 pump temperature";
     }
     leaf fpc-optical-status-edfa2-coil {
       type string;
       description "Optical module operational EDFA 2 coil temperature";
     }
     leaf fpc-optical-status-wss-vol {
       type string;
       description "Optical module operational WSS voltage";
     }
     leaf fpc-optical-status-wss-temp {
       type string;
       description "Optical module operational WSS temperature";
     }
     leaf fpc-optical-status-ocm-temp {
       type string;
       description "Optical module operational OCM temperature";
     }
     leaf fpc-optical-status-osc-status {
       type string;
       description "Optical module operational OSC status";
     }
   }
   container alarm {
     leaf fpc-optical-alarm {
       type string;
       description "Optical module alarm status";
     }
     leaf fpc-optical-alarm-edfa1 {
       type string;
       description "Optical module EDFA1 alarm status";
     }
     leaf fpc-optical-alarm-edfa2 {
       type string;
       description "Optical module EDFA2 alarm status";
     }
     leaf fpc-optical-alarm-wss {
       type string;
       description "Optical module WSS alarm status";
     }
   }
   container edfa {
     leaf fpc-optical-edfa1-gains {
       type string;
       description "Optical module EDFA1 gain setting save";
     }
     leaf fpc-optical-edfa2-gains {
       type string;
       description "Optical module EDFA2 gain setting save";
     }
     leaf fpc-optical-edfa1-tilt {
       type string;
       description "Optical module EDFA1 gain tilt";
     }
     leaf fpc-optical-edfa2-tilt {
       type string;
       description "Optical module EDFA2 gain tilt";
     }
     leaf fpc-optical-edfa1-ilos-ut {
       type string;
       description "Optical module EDFA1 input LOS upper threshold";
     }
     leaf fpc-optical-edfa2-ilos-ut {
       type string;
       description "Optical module EDFA2 input LOS upper threshold";
     }
     leaf fpc-optical-edfa1-ilos-lt {
       type string;
       description "Optical module EDFA1 input LOS lower threshold";
     }
     leaf fpc-optical-edfa2-ilos-lt {
       type string;
       description "Optical module EDFA2 input LOS lower threshold";
     }
     leaf fpc-optical-edfa1-olos-ut {
       type string;
       description "Optical module EDFA1 output LOS upper threshold";
     }
     leaf fpc-optical-edfa2-olos-ut {
       type string;
       description "Optical module EDFA2 output LOS upper threshold";
     }
     leaf fpc-optical-edfa1-olos-lt {
       type string;
       description "Optical module EDFA1 output LOS lower threshold";
     }
     leaf fpc-optical-edfa2-olos-lt {
       type string;
       description "Optical module EDFA2 output LOS lower threshold";
     }
     leaf fpc-optical-edfa1-gain {
       type string;
       description "Optical module EDFA1 gain setting";
     }
     leaf fpc-optical-edfa2-gain {
       type string;
       description "Optical module EDFA2 gain setting";
     }
     leaf fpc-optical-edfa1-output {
       type string;
       description "Optical module EDFA1 output enable";
     }
     leaf fpc-optical-edfa2-output {
       type string;
       description "Optical module EDFA2 output enable";
     }
     leaf fpc-optical-edfa1-autolos {
       type string;
       description "Optical module EDFA1 auto LOS enable";
     }
     leaf fpc-optical-edfa2-autolos {
       type string;
       description "Optical module EDFA2 auto LOS enable";
     }
     leaf fpc-optical-edfa1-mode {
       type string;
       description "Optical module EDFA1 mode";
     }
     leaf fpc-optical-edfa2-mode {
       type string;
       description "Optical module EDFA2 mode";
     }
     leaf fpc-optical-edfa1-plim {
       type string;
       description "Optical module EDFA1 plim power";
     }
     leaf fpc-optical-edfa2-plim {
       type string;
       description "Optical module EDFA2 plim power";
     }
     leaf fpc-optical-ila-edfa-info {
       type string;
       description "Optical ila edfa information";
     }
     leaf fpc-optical-ila-edfa-index {
       type string;
       description "Optical ila edfa index";
     }
     leaf fpc-optical-ila-edfa-mfg-info {
       type string;
       description "Optical ila edfa manufacture info";
     }
     leaf fpc-optical-ila-edfa-module-type {
       type string;
       description "Optical ila edfa module type";
     }
     leaf fpc-optical-ila-edfa-part-number {
       type string;
       description "Optical ila edfa part number";
     }
     leaf fpc-optical-ila-edfa-serial-number {
       type string;
       description "Optical ila edfa serial number";
     }
     leaf fpc-optical-ila-edfa-mfg-date {
       type string;
       description "Optical ila edfa manufacture date";
     }
     leaf fpc-optical-ila-edfa-cali-date {
       type string;
       description "Optical ila edfa calibration date";
     }
     leaf fpc-optical-ila-edfa-firmware-ver {
       type string;
       description "Optical ila edfa firmware version";
     }
     leaf fpc-optical-ila-edfa-hardware-ver {
       type string;
       description "Optical ila edfa hardware version";
     }
     leaf fpc-optical-ila-edfa-mode {
       type string;
       description "Optical ila edfa mode";
     }
     leaf fpc-optical-ila-edfa-gain-setting {
       type string;
       description "Optical ila edfa gain setting";
     }
     leaf fpc-optical-ila-edfa-tilt {
       type string;
       description "Optical ila edfa tilt";
     }
     leaf fpc-optical-ila-edfa-work-status {
       type string;
       description "Optical ila edfa work status";
     }
     leaf fpc-optical-ila-edfa-apr-enable {
       type string;
       description "Optical ila edfa apr enable";
     }
     leaf fpc-optical-ila-edfa-work-range {
       type string;
       description "Optical ila edfa work range";
     }
     leaf fpc-optical-ila-edfa-actual-gain {
       type string;
       description "Optical ila edfa actual gain";
     }
     leaf fpc-optical-ila-edfa-case-temp {
       type string;
       description "Optical ila edfa case temperature";
     }
     leaf fpc-optical-ila-edfa-pump-temp {
       type string;
       description "Optical ila edfa pump temperature";
     }
     leaf fpc-optical-ila-edfa-asc {
       type string;
       description "Optical ila edfa asc";
     }
     leaf fpc-optical-ila-edfa-upstream-output-power {
       type string;
       description "Optical ila edfa upstream output power";
     }
     leaf fpc-optical-ila-edfa-input-power {
       type string;
       description "Optical ila edfa input power";
     }
     leaf fpc-optical-ila-edfa-output-power {
       type string;
       description "Optical ila edfa output power";
     }
     leaf fpc-optical-ila-edfa-downstream-input-power {
       type string;
       description "Optical ila edfa downstream input power";
     }
     leaf fpc-optical-ila-edfa-input-los-threshold {
       type string;
       description "Optical ila edfa input los threshold";
     }
     leaf fpc-optical-ila-edfa-output-los-threshold {
       type string;
       description "Optical ila edfa output los threshold";
     }
   }
   container ocm {
     leaf fpc-optical-topology-wavelength {
       type string;
       description "Optical module topology";
     }
     leaf fpc-optical-port {
       type string;
       description "Optical module WSS port";
     }
     leaf fpc-optical-frequency {
       type string;
       description "Optical module frequency";
     }
     leaf fpc-optical-ocm-lout {
       type string;
       description "Optical module OCM channel 0 line out port power";
     }
   }
   container wss {
     leaf fpc-optical-topology-wavelength {
       type string;
       description "Optical module topology";
     }
     leaf fpc-optical-port {
       type string;
       description "Optical module WSS port";
     }
     leaf fpc-optical-frequency {
       type string;
       description "Optical module frequency";
     }
     leaf fpc-optical-wss-port {
       type string;
       description "Optical module WSS channel 0 port";
     }
     leaf fpc-optical-wss-attn {
       type string;
       description "Optical module WSS channel 0 attenuation";
     }
   }
   container pm {
     leaf fpc-optical-pm-slot {
       type string;
       description "Optical module PM FPC slot";
     }
     leaf fpc-optical-pm-timestamp {
       type string;
       description "Optical module PM timestamp";
     }
     leaf fpc-optical-pm-suspect-flag {
       type string;
       description "Optical module PM suspect flag";
     }
     leaf fpc-optical-pm-suspect-reason {
       type string;
       description "Optical module PM suspect reason";
     }
     leaf fpc-optical-pm-osc-txpwr-cur {
       type string;
       description "Optical module PM OSC Tx power current";
     }
     leaf fpc-optical-pm-osc-txpwr-min {
       type string;
       description "Optical module PM OSC Tx power min";
     }
     leaf fpc-optical-pm-osc-txpwr-max {
       type string;
       description "Optical module PM OSC Tx power max";
     }
     leaf fpc-optical-pm-osc-txpwr-avg {
       type string;
       description "Optical module PM OSC Tx power avg";
     }
     leaf fpc-optical-pm-osc-txpwr-min-tca-th {
       type string;
       description "Optical module PM OSC Tx power TCA min threshold";
     }
     leaf fpc-optical-pm-osc-txpwr-max-tca-th {
       type string;
       description "Optical module PM OSC Tx power TCA max threshold";
     }
     leaf fpc-optical-pm-osc-txpwr-min-tca-en {
       type string;
       description "Optical module PM OSC Tx power TCA min enable";
     }
     leaf fpc-optical-pm-osc-txpwr-max-tca-en {
       type string;
       description "Optical module PM OSC Tx power TCA max enable";
     }
     leaf fpc-optical-pm-osc-txpwr-min-tca-state {
       type string;
       description "Optical module PM OSC Tx power TCA min state";
     }
     leaf fpc-optical-pm-osc-txpwr-max-tca-state {
       type string;
       description "Optical module PM OSC Tx power TCA max state";
     }
     leaf fpc-optical-pm-osc-rxpwr-cur {
       type string;
       description "Optical module PM OSC Rx power current";
     }
     leaf fpc-optical-pm-osc-rxpwr-min {
       type string;
       description "Optical module PM OSC Rx power min";
     }
     leaf fpc-optical-pm-osc-rxpwr-max {
       type string;
       description "Optical module PM OSC Rx power max";
     }
     leaf fpc-optical-pm-osc-rxpwr-avg {
       type string;
       description "Optical module PM OSC Rx power avg";
     }
     leaf fpc-optical-pm-osc-rxpwr-min-tca-th {
       type string;
       description "Optical module PM OSC Rx power TCA min threshold";
     }
     leaf fpc-optical-pm-osc-rxpwr-max-tca-th {
       type string;
       description "Optical module PM OSC Rx power TCA max threshold";
     }
     leaf fpc-optical-pm-osc-rxpwr-min-tca-en {
       type string;
       description "Optical module PM OSC Rx power TCA min enable";
     }
     leaf fpc-optical-pm-osc-rxpwr-max-tca-en {
       type string;
       description "Optical module PM OSC Rx power TCA max enable";
     }
     leaf fpc-optical-pm-osc-rxpwr-min-tca-state {
       type string;
       description "Optical module PM OSC Rx power TCA min state";
     }
     leaf fpc-optical-pm-osc-rxpwr-max-tca-state {
       type string;
       description "Optical module PM OSC Rx power TCA max state";
     }
     leaf fpc-optical-pm-osc-los-cur {
       type string;
       description "Optical module PM OSC LOS current";
     }
     leaf fpc-optical-pm-osc-los-min {
       type string;
       description "Optical module PM OSC LOS min";
     }
     leaf fpc-optical-pm-osc-los-max {
       type string;
       description "Optical module PM OSC LOS max";
     }
     leaf fpc-optical-pm-osc-los-avg {
       type string;
       description "Optical module PM OSC LOS avg";
     }
     leaf fpc-optical-pm-osc-los-min-tca-th {
       type string;
       description "Optical module PM OSC LOS TCA min threshold";
     }
     leaf fpc-optical-pm-osc-los-max-tca-th {
       type string;
       description "Optical module PM OSC LOS TCA max threshold";
     }
     leaf fpc-optical-pm-osc-los-min-tca-en {
       type string;
       description "Optical module PM OSC LOS TCA min enable";
     }
     leaf fpc-optical-pm-osc-los-max-tca-en {
       type string;
       description "Optical module PM OSC LOS TCA max enable";
     }
     leaf fpc-optical-pm-osc-los-min-tca-state {
       type string;
       description "Optical module PM OSC LOS TCA min state";
     }
     leaf fpc-optical-pm-osc-los-max-tca-state {
       type string;
       description "Optical module PM OSC LOS TCA max state";
     }
     leaf fpc-optical-pm-lout-voa-cur {
       type string;
       description "Optical module PM LOUT VOA attenuation current";
     }
     leaf fpc-optical-pm-lout-voa-min {
       type string;
       description "Optical module PM LOUT VOA attenuation min";
     }
     leaf fpc-optical-pm-lout-voa-max {
       type string;
       description "Optical module PM LOUT VOA attenuation max";
     }
     leaf fpc-optical-pm-lout-voa-avg {
       type string;
       description "Optical module PM LOUT VOA attenuation avg";
     }
     leaf fpc-optical-pm-lout-voa-min-tca-th {
       type string;
       description "Optical module PM LOUT VOA attenuation TCA min threshold";
     }
     leaf fpc-optical-pm-lout-voa-max-tca-th {
       type string;
       description "Optical module PM LOUT VOA attenuation TCA max threshold";
     }
     leaf fpc-optical-pm-lout-voa-min-tca-en {
       type string;
       description "Optical module PM LOUT VOA attenuation TCA min enable";
     }
     leaf fpc-optical-pm-lout-voa-max-tca-en {
       type string;
       description "Optical module PM LOUT VOA attenuation TCA max enable";
     }
     leaf fpc-optical-pm-lout-voa-min-tca-state {
       type string;
       description "Optical module PM LOUT VOA attenuation TCA min state";
     }
     leaf fpc-optical-pm-lout-voa-max-tca-state {
       type string;
       description "Optical module PM LOUT VOA attenuation TCA max state";
     }
     leaf fpc-optical-pm-edfa1-inpwr-cur {
       type string;
       description "Optical module PM EDFA1 input power current";
     }
     leaf fpc-optical-pm-edfa1-inpwr-min {
       type string;
       description "Optical module PM EDFA1 input power min";
     }
     leaf fpc-optical-pm-edfa1-inpwr-max {
       type string;
       description "Optical module PM EDFA1 input power max";
     }
     leaf fpc-optical-pm-edfa1-inpwr-avg {
       type string;
       description "Optical module PM EDFA1 input power avg";
     }
     leaf fpc-optical-pm-edfa1-inpwr-min-tca-th {
       type string;
       description "Optical module PM EDFA1 input power TCA min threshold";
     }
     leaf fpc-optical-pm-edfa1-inpwr-max-tca-th {
       type string;
       description "Optical module PM EDFA1 input power TCA max threshold";
     }
     leaf fpc-optical-pm-edfa1-inpwr-min-tca-en {
       type string;
       description "Optical module PM EDFA1 input power TCA min enable";
     }
     leaf fpc-optical-pm-edfa1-inpwr-max-tca-en {
       type string;
       description "Optical module PM EDFA1 input power TCA max enable";
     }
     leaf fpc-optical-pm-edfa1-inpwr-min-tca-state {
       type string;
       description "Optical module PM EDFA1 input power TCA min state";
     }
     leaf fpc-optical-pm-edfa1-inpwr-max-tca-state {
       type string;
       description "Optical module PM EDFA1 input power TCA max state";
     }
     leaf fpc-optical-pm-edfa1-outpwr-cur {
       type string;
       description "Optical module PM EDFA1 output power current";
     }
     leaf fpc-optical-pm-edfa1-outpwr-min {
       type string;
       description "Optical module PM EDFA1 output power min";
     }
     leaf fpc-optical-pm-edfa1-outpwr-max {
       type string;
       description "Optical module PM EDFA1 output power max";
     }
     leaf fpc-optical-pm-edfa1-outpwr-avg {
       type string;
       description "Optical module PM EDFA1 output power avg";
     }
     leaf fpc-optical-pm-edfa1-outpwr-min-tca-th {
       type string;
       description "Optical module PM EDFA1 output power TCA min threshold";
     }
     leaf fpc-optical-pm-edfa1-outpwr-max-tca-th {
       type string;
       description "Optical module PM EDFA1 output power TCA max threshold";
     }
     leaf fpc-optical-pm-edfa1-outpwr-min-tca-en {
       type string;
       description "Optical module PM EDFA1 output power TCA min enable";
     }
     leaf fpc-optical-pm-edfa1-outpwr-max-tca-en {
       type string;
       description "Optical module PM EDFA1 output power TCA max enable";
     }
     leaf fpc-optical-pm-edfa1-outpwr-min-tca-state {
       type string;
       description "Optical module PM EDFA1 output power TCA min state";
     }
     leaf fpc-optical-pm-edfa1-outpwr-max-tca-state {
       type string;
       description "Optical module PM EDFA1 output power TCA max state";
     }
     leaf fpc-optical-pm-edfa1-sigpwr-cur {
       type string;
       description "Optical module PM EDFA1 signal power current";
     }
     leaf fpc-optical-pm-edfa1-sigpwr-min {
       type string;
       description "Optical module PM EDFA1 signal power min";
     }
     leaf fpc-optical-pm-edfa1-sigpwr-max {
       type string;
       description "Optical module PM EDFA1 signal power max";
     }
     leaf fpc-optical-pm-edfa1-sigpwr-avg {
       type string;
       description "Optical module PM EDFA1 signal power avg";
     }
     leaf fpc-optical-pm-edfa1-sigpwr-min-tca-th {
       type string;
       description "Optical module PM EDFA1 signal power TCA min threshold";
     }
     leaf fpc-optical-pm-edfa1-sigpwr-max-tca-th {
       type string;
       description "Optical module PM EDFA1 signal power TCA max threshold";
     }
     leaf fpc-optical-pm-edfa1-sigpwr-min-tca-en {
       type string;
       description "Optical module PM EDFA1 signal power TCA min enable";
     }
     leaf fpc-optical-pm-edfa1-sigpwr-max-tca-en {
       type string;
       description "Optical module PM EDFA1 signal power TCA max enable";
     }
     leaf fpc-optical-pm-edfa1-sigpwr-min-tca-state {
       type string;
       description "Optical module PM EDFA1 signal power TCA min state";
     }
     leaf fpc-optical-pm-edfa1-sigpwr-max-tca-state {
       type string;
       description "Optical module PM EDFA1 signal power TCA max state";
     }
     leaf fpc-optical-pm-edfa1-pump-cur {
       type string;
       description "Optical module PM EDFA1 pump current current";
     }
     leaf fpc-optical-pm-edfa1-pump-min {
       type string;
       description "Optical module PM EDFA1 pump current min";
     }
     leaf fpc-optical-pm-edfa1-pump-max {
       type string;
       description "Optical module PM EDFA1 pump current max";
     }
     leaf fpc-optical-pm-edfa1-pump-avg {
       type string;
       description "Optical module PM EDFA1 pump current avg";
     }
     leaf fpc-optical-pm-edfa1-pump-min-tca-th {
       type string;
       description "Optical module PM EDFA1 pump current TCA min threshold";
     }
     leaf fpc-optical-pm-edfa1-pump-max-tca-th {
       type string;
       description "Optical module PM EDFA1 pump current TCA max threshold";
     }
     leaf fpc-optical-pm-edfa1-pump-min-tca-en {
       type string;
       description "Optical module PM EDFA1 pump current TCA min enable";
     }
     leaf fpc-optical-pm-edfa1-pump-max-tca-en {
       type string;
       description "Optical module PM EDFA1 pump current TCA max enable";
     }
     leaf fpc-optical-pm-edfa1-pump-min-tca-state {
       type string;
       description "Optical module PM EDFA1 pump current TCA min state";
     }
     leaf fpc-optical-pm-edfa1-pump-max-tca-state {
       type string;
       description "Optical module PM EDFA1 pump current TCA max state";
     }
     leaf fpc-optical-pm-edfa2-inpwr-cur {
       type string;
       description "Optical module PM EDFA2 input power current";
     }
     leaf fpc-optical-pm-edfa2-inpwr-min {
       type string;
       description "Optical module PM EDFA2 input power min";
     }
     leaf fpc-optical-pm-edfa2-inpwr-max {
       type string;
       description "Optical module PM EDFA2 input power max";
     }
     leaf fpc-optical-pm-edfa2-inpwr-avg {
       type string;
       description "Optical module PM EDFA2 input power avg";
     }
     leaf fpc-optical-pm-edfa2-inpwr-min-tca-th {
       type string;
       description "Optical module PM EDFA2 input power TCA min threshold";
     }
     leaf fpc-optical-pm-edfa2-inpwr-max-tca-th {
       type string;
       description "Optical module PM EDFA2 input power TCA max threshold";
     }
     leaf fpc-optical-pm-edfa2-inpwr-min-tca-en {
       type string;
       description "Optical module PM EDFA2 input power TCA min enable";
     }
     leaf fpc-optical-pm-edfa2-inpwr-max-tca-en {
       type string;
       description "Optical module PM EDFA2 input power TCA max enable";
     }
     leaf fpc-optical-pm-edfa2-inpwr-min-tca-state {
       type string;
       description "Optical module PM EDFA2 input power TCA min state";
     }
     leaf fpc-optical-pm-edfa2-inpwr-max-tca-state {
       type string;
       description "Optical module PM EDFA2 input power TCA max state";
     }
     leaf fpc-optical-pm-edfa2-outpwr-cur {
       type string;
       description "Optical module PM EDFA2 output power current";
     }
     leaf fpc-optical-pm-edfa2-outpwr-min {
       type string;
       description "Optical module PM EDFA2 output power min";
     }
     leaf fpc-optical-pm-edfa2-outpwr-max {
       type string;
       description "Optical module PM EDFA2 output power max";
     }
     leaf fpc-optical-pm-edfa2-outpwr-avg {
       type string;
       description "Optical module PM EDFA2 output power avg";
     }
     leaf fpc-optical-pm-edfa2-outpwr-min-tca-th {
       type string;
       description "Optical module PM EDFA2 output power TCA min threshold";
     }
     leaf fpc-optical-pm-edfa2-outpwr-max-tca-th {
       type string;
       description "Optical module PM EDFA2 output power TCA max threshold";
     }
     leaf fpc-optical-pm-edfa2-outpwr-min-tca-en {
       type string;
       description "Optical module PM EDFA2 output power TCA min enable";
     }
     leaf fpc-optical-pm-edfa2-outpwr-max-tca-en {
       type string;
       description "Optical module PM EDFA2 output power TCA max enable";
     }
     leaf fpc-optical-pm-edfa2-outpwr-min-tca-state {
       type string;
       description "Optical module PM EDFA2 output power TCA min state";
     }
     leaf fpc-optical-pm-edfa2-outpwr-max-tca-state {
       type string;
       description "Optical module PM EDFA2 output power TCA max state";
     }
     leaf fpc-optical-pm-edfa2-sigpwr-cur {
       type string;
       description "Optical module PM EDFA2 signal power current";
     }
     leaf fpc-optical-pm-edfa2-sigpwr-min {
       type string;
       description "Optical module PM EDFA2 signal power min";
     }
     leaf fpc-optical-pm-edfa2-sigpwr-max {
       type string;
       description "Optical module PM EDFA2 signal power max";
     }
     leaf fpc-optical-pm-edfa2-sigpwr-avg {
       type string;
       description "Optical module PM EDFA2 signal power avg";
     }
     leaf fpc-optical-pm-edfa2-sigpwr-min-tca-th {
       type string;
       description "Optical module PM EDFA2 signal power TCA min threshold";
     }
     leaf fpc-optical-pm-edfa2-sigpwr-max-tca-th {
       type string;
       description "Optical module PM EDFA2 signal power TCA max threshold";
     }
     leaf fpc-optical-pm-edfa2-sigpwr-min-tca-en {
       type string;
       description "Optical module PM EDFA2 signal power TCA min enable";
     }
     leaf fpc-optical-pm-edfa2-sigpwr-max-tca-en {
       type string;
       description "Optical module PM EDFA2 signal power TCA max enable";
     }
     leaf fpc-optical-pm-edfa2-sigpwr-min-tca-state {
       type string;
       description "Optical module PM EDFA2 signal power TCA min state";
     }
     leaf fpc-optical-pm-edfa2-sigpwr-max-tca-state {
       type string;
       description "Optical module PM EDFA2 signal power TCA max state";
     }
     leaf fpc-optical-pm-edfa2-pump-cur {
       type string;
       description "Optical module PM EDFA2 pump current current";
     }
     leaf fpc-optical-pm-edfa2-pump-min {
       type string;
       description "Optical module PM EDFA2 pump current min";
     }
     leaf fpc-optical-pm-edfa2-pump-max {
       type string;
       description "Optical module PM EDFA2 pump current max";
     }
     leaf fpc-optical-pm-edfa2-pump-avg {
       type string;
       description "Optical module PM EDFA2 pump current avg";
     }
     leaf fpc-optical-pm-edfa2-pump-min-tca-th {
       type string;
       description "Optical module PM EDFA2 pump current TCA min threshold";
     }
     leaf fpc-optical-pm-edfa2-pump-max-tca-th {
       type string;
       description "Optical module PM EDFA2 pump current TCA max threshold";
     }
     leaf fpc-optical-pm-edfa2-pump-min-tca-en {
       type string;
       description "Optical module PM EDFA2 pump current TCA min enable";
     }
     leaf fpc-optical-pm-edfa2-pump-max-tca-en {
       type string;
       description "Optical module PM EDFA2 pump current TCA max enable";
     }
     leaf fpc-optical-pm-edfa2-pump-min-tca-state {
       type string;
       description "Optical module PM EDFA2 pump current TCA min state";
     }
     leaf fpc-optical-pm-edfa2-pump-max-tca-state {
       type string;
       description "Optical module PM EDFA2 pump current TCA max state";
     }
     leaf fpc-optical-pm-powermon-awg-cur {
       type string;
       description "Optical module PM power monitor AWG port current";
     }
     leaf fpc-optical-pm-powermon-awg-min {
       type string;
       description "Optical module PM power monitor AWG port min";
     }
     leaf fpc-optical-pm-powermon-awg-max {
       type string;
       description "Optical module PM power monitor AWG port max";
     }
     leaf fpc-optical-pm-powermon-awg-avg {
       type string;
       description "Optical module PM power monitor AWG port avg";
     }
     leaf fpc-optical-pm-powermon-awg-min-tca-th {
       type string;
       description "Optical module PM power monitor AWG port TCA min threshold";
     }
     leaf fpc-optical-pm-powermon-awg-max-tca-th {
       type string;
       description "Optical module PM power monitor AWG port TCA max threshold";
     }
     leaf fpc-optical-pm-powermon-awg-min-tca-en {
       type string;
       description "Optical module PM power monitor AWG port TCA min enable";
     }
     leaf fpc-optical-pm-powermon-awg-max-tca-en {
       type string;
       description "Optical module PM power monitor AWG port TCA max enable";
     }
     leaf fpc-optical-pm-powermon-awg-min-tca-state {
       type string;
       description "Optical module PM power monitor AWG port TCA min state";
     }
     leaf fpc-optical-pm-powermon-awg-max-tca-state {
       type string;
       description "Optical module PM power monitor AWG port TCA max state";
     }
     leaf fpc-optical-pm-powermon-expin-cur {
       type string;
       description "Optical module PM power monitor Express In port current";
     }
     leaf fpc-optical-pm-powermon-expin-min {
       type string;
       description "Optical module PM power monitor Express In port min";
     }
     leaf fpc-optical-pm-powermon-expin-max {
       type string;
       description "Optical module PM power monitor Express In port max";
     }
     leaf fpc-optical-pm-powermon-expin-avg {
       type string;
       description "Optical module PM power monitor Express In port avg";
     }
     leaf fpc-optical-pm-powermon-expin-min-tca-th {
       type string;
       description "Optical module PM power monitor Express In port TCA min threshold";
     }
     leaf fpc-optical-pm-powermon-expin-max-tca-th {
       type string;
       description "Optical module PM power monitor Express In port TCA max threshold";
     }
     leaf fpc-optical-pm-powermon-expin-min-tca-en {
       type string;
       description "Optical module PM power monitor Express In port TCA min enable";
     }
     leaf fpc-optical-pm-powermon-expin-max-tca-en {
       type string;
       description "Optical module PM power monitor Express In port TCA max enable";
     }
     leaf fpc-optical-pm-powermon-expin-min-tca-state {
       type string;
       description "Optical module PM power monitor Express In port TCA min state";
     }
     leaf fpc-optical-pm-powermon-expin-max-tca-state {
       type string;
       description "Optical module PM power monitor Express In port TCA max state";
     }
     leaf fpc-optical-channel-lout {
       type string;
       description "Optical module OCM channel LOUT";
     }
     leaf fpc-optical-ocm-lout {
       type string;
       description "Optical module OCM channel 0 line out port power";
     }
     leaf fpc-optical-pm-ocm-lout-min {
       type string;
       description "Optical module OCM channel 0 min power";
     }
     leaf fpc-optical-pm-ocm-lout-max {
       type string;
       description "Optical module OCM channel 0 max power";
     }
     leaf fpc-optical-pm-ocm-lout-avg {
       type string;
       description "Optical module OCM channel 0 avg power";
     }
     leaf fpc-optical-pm-ocm-lout-min-tca-th {
       type string;
       description "Optical module OCM channel 0 min TCA threshold";
     }
     leaf fpc-optical-pm-ocm-lout-max-tca-th {
       type string;
       description "Optical module OCM channel 0 max TCA threshold";
     }
     leaf fpc-optical-pm-ocm-lout-min-tca-en {
       type string;
       description "Optical module OCM channel 0 min TCA enable";
     }
     leaf fpc-optical-pm-ocm-lout-max-tca-en {
       type string;
       description "Optical module OCM channel 0 max TCA enable";
     }
     leaf fpc-optical-pm-ocm-lout-min-tca-state {
       type string;
       description "Optical module OCM channel 0 min TCA state";
     }
     leaf fpc-optical-pm-ocm-lout-max-tca-state {
       type string;
       description "Optical module OCM channel 0 max TCA state";
     }
   }
   container topology {
     leaf fpc-optical-topology-express-in-state {
       type string;
       description "Optical module topology state";
     }
     leaf fpc-optical-topology-express-in-connected-to {
       type string;
       description "Optical module topology state";
     }
     leaf fpc-optical-topology-expansion-state {
       type string;
       description "Optical module topology state";
     }
     leaf fpc-optical-topology-expansion-connected-to {
       type string;
       description "Optical module topology connected-to";
     }
     leaf fpc-optical-topology-wavelength {
       type string;
       description "Optical module topology";
     }
     leaf fpc-optical-port {
       type string;
       description "Optical module WSS port";
     }
     leaf fpc-optical-frequency {
       type string;
       description "Optical module frequency";
     }
     leaf fpc-optical-topology-wavelength-state {
       type string;
       description "Optical module topology state";
     }
     leaf fpc-optical-topology-wavelength-connected-to {
       type string;
       description "Optical module topology state";
     }
   }
   container amplifier-topology {
     leaf fpc-optical-amplifier-topology-name {
       type string;
       description "Optical module amplifier topology name";
     }
     leaf fpc-optical-amplifier-topology-ipaddr {
       type string;
       description "Optical module amplifier topology ip address";
     }
     leaf fpc-optical-amplifier-topology-reachable {
       type string;
       description "Optical module amplifier topology reachability";
     }
     leaf fpc-optical-amplifier-topology-connected-to {
       type string;
       description "Optical module amplifier topology connected-to";
     }
   }
   container summary {
     leaf fpc-optical-ila-summary-ila-num {
       type string;
       description "Optical module ila summary ila number";
     }
     leaf fpc-optical-ila-summary-ila-name {
       type string;
       description "Optical module ila summary ila name";
     }
     leaf fpc-optical-ila-summary-position {
       type string;
       description "Optical module ila summary ila position";
     }
     leaf fpc-optical-ila-summary-ip-address {
       type string;
       description "Optical module ila summary ila ip address";
     }
     leaf fpc-optical-ila-summary-mfg-name {
       type string;
       description "Optical module ila summary ila manufactory name";
     }
     leaf fpc-optical-ila-summary-mfg-date {
       type string;
       description "Optical module ila summary ila manufactory date";
     }
     leaf fpc-optical-ila-summary-part-num {
       type string;
       description "Optical module ila summary ila part number";
     }
     leaf fpc-optical-ila-summary-serial-num {
       type string;
       description "Optical module ila summary ila serial number";
     }
     leaf fpc-optical-ila-summary-calibration-date {
       type string;
       description "Optical module ila summary ila calibration date";
     }
     leaf fpc-optical-ila-summary-firmware-ver {
       type string;
       description "Optical module ila summary ila firmware version";
     }
     leaf fpc-optical-ila-summary-hardware-ver {
       type string;
       description "Optical module ila summary ila hardware version";
     }
     leaf fpc-optical-ila-summary-fpga-ver {
       type string;
       description "Optical module ila summary ila fpga version";
     }
     leaf fpc-optical-ila-summary-x86cpld-ver {
       type string;
       description "Optical module ila summary ila x86cpld version";
     }
     leaf fpc-optical-ila-summary-board-cpld-ver {
       type string;
       description "Optical module ila summary ila board cpld version";
     }
     leaf fpc-optical-ila-summary-system-date {
       type string;
       description "Optical module ila summary ila system date";
     }
     leaf fpc-optical-ila-summary-system-time {
       type string;
       description "Optical module ila summary system time";
     }
     leaf fpc-optical-ila-summary-up-time {
       type string;
       description "Optical module ila summary ila up time";
     }
     leaf fpc-optical-ila-summary-ipv4-info {
       type string;
       description "Optical module ila summary ipv4 address/mask/gateway";
     }
     leaf fpc-optical-ila-summary-mac-address {
       type string;
       description "Optical module ila summary ila MAC address";
     }
     leaf fpc-optical-ila-summary-board-temp {
       type string;
       description "Optical module ila summary board temperature";
     }
     leaf fpc-optical-ila-summary-temp-thre {
       type string;
       description "Optical module ila summary temperature threshold";
     }
     leaf fpc-optical-ila-summary-pwr-fan-plug-status {
       type string;
       description "Optical module ila summary power fan plug status";
     }
     leaf fpc-optical-ila-summary-fan-speed {
       type string;
       description "Optical module ila summary fan speed";
     }
     leaf fpc-optical-ila-summary-system-mode {
       type string;
       description "Optical module ila summary system mode";
     }
     leaf fpc-optical-ila-summary-firmware-upgrade-status {
       type string;
       description "Optical module ila summary firmware upgrade status";
     }
   }
   container voa {
     leaf fpc-optical-ila-voa-info {
       type string;
       description "Optical module ila voa information";
     }
     leaf fpc-optical-ila-voa-index {
       type string;
       description "Optical module ila voa index";
     }
     leaf fpc-optical-ila-voa-attenuation {
       type string;
       description "Optical module ila voa index";
     }
   }
   container osc {
     leaf fpc-optical-ila-osc-info {
       type string;
       description "Optical module ila osc information";
     }
     leaf fpc-optical-ila-osc-index {
       type string;
       description "Optical module ila osc index";
     }
     leaf fpc-optical-ila-osc-mfg-node {
       type string;
       description "Optical ila OSC manufacture node";
     }
     leaf fpc-optical-ila-osc-enable {
       type string;
       description "Optical ila OSC enable";
     }
     leaf fpc-optical-ila-osc-add-power-value {
       type string;
       description "Optical ila OSC add power value";
     }
     leaf fpc-optical-ila-osc-drop-power-value {
       type string;
       description "Optical ila OSC drop power value";
     }
     leaf fpc-optical-ila-osc-add-los-thr {
       type string;
       description "Optical ila OSC add los threshold";
     }
     leaf fpc-optical-ila-osc-drop-los-thr {
       type string;
       description "Optical ila OSC drop los threshold";
     }
   }
   container ila-alarm {
     leaf fpc-optical-ila-alarm-board-temp-abnormal {
       type string;
       description "Optical ila alarm board temperatur abnormal";
     }
     leaf fpc-optical-ila-alarm-communication-abnormal {
       type string;
       description "Optical ila alarm communication abnormal";
     }
     leaf fpc-optical-ila-alarm-fan0-online-abnormal {
       type string;
       description "Optical ila alarm fan0 online abnormal";
     }
     leaf fpc-optical-ila-alarm-fan1-online-abnormal {
       type string;
       description "Optical ila alarm fan1 online abnormal";
     }
     leaf fpc-optical-ila-alarm-fan2-online-abnormal {
       type string;
       description "Optical ila alarm fan2 online abnormal";
     }
     leaf fpc-optical-ila-alarm-fan0-speed-abnormal {
       type string;
       description "Optical ila alarm fan0 speed abnormal";
     }
     leaf fpc-optical-ila-alarm-fan1-speed-abnormal {
       type string;
       description "Optical ila alarm fan1 speed abnormal";
     }
     leaf fpc-optical-ila-alarm-fan2-speed-abnormal {
       type string;
       description "Optical ila alarm fan2 speed abnormal";
     }
     leaf fpc-optical-ila-alarm-software-version-abnormal {
       type string;
       description "Optical ila alarm software version abnormal";
     }
     leaf fpc-optical-ila-alarm-ac-power-abnormal {
       type string;
       description "Optical ila alarm ac power abnormal";
     }
     leaf fpc-optical-ila-alarm-dc-power-abnormal {
       type string;
       description "Optical ila alarm dc power abnormal";
     }
     leaf fpc-optical-ila-alarm-table-err {
       type string;
       description "Optical ila alarm table error";
     }
     leaf fpc-optical-ila-alarm-edfa-ab-case-temp {
       type string;
       description "Optical ila alarm edfa ab case temperature";
     }
     leaf fpc-optical-ila-alarm-edfa-ab-rfl {
       type string;
       description "Optical ila alarm edfa ab RFL";
     }
     leaf fpc-optical-ila-alarm-edfa-ab-oop {
       type string;
       description "Optical ila alarm edfa ab OOP";
     }
     leaf fpc-optical-ila-alarm-edfa-ab-oog {
       type string;
       description "Optical ila alarm edfa ab OOG";
     }
     leaf fpc-optical-ila-alarm-edfa-ab-pump0-eol {
       type string;
       description "Optical ila alarm edfa ab pump 0 EOL";
     }
     leaf fpc-optical-ila-alarm-edfa-ab-pump1-eol {
       type string;
       description "Optical ila alarm edfa ab pump 1 EOL";
     }
     leaf fpc-optical-ila-alarm-edfa-ab-pump0-temp-abnormal {
       type string;
       description "Optical ila alarm edfa ab pump 0 temp abmornal";
     }
     leaf fpc-optical-ila-alarm-edfa-ab-pump1-temp-abnormal {
       type string;
       description "Optical ila alarm edfa ab pump 1 temp abmornal";
     }
     leaf fpc-optical-ila-alarm-edfa-ab-input-los {
       type string;
       description "Optical ila alarm edfa ab input LOS";
     }
     leaf fpc-optical-ila-alarm-edfa-ab-output-alarm {
       type string;
       description "Optical ila alarm edfa ab output alarm";
     }
     leaf fpc-optical-ila-alarm-edfa-ab-cali-tbl-err {
       type string;
       description "Optical ila alarm edfa ab cali table error";
     }
     leaf fpc-optical-ila-alarm-edfa-ba-case-temp {
       type string;
       description "Optical ila alarm edfa ba case temperature";
     }
     leaf fpc-optical-ila-alarm-edfa-ba-rfl {
       type string;
       description "Optical ila alarm edfa ba RFL";
     }
     leaf fpc-optical-ila-alarm-edfa-ba-oop {
       type string;
       description "Optical ila alarm edfa ba OOP";
     }
     leaf fpc-optical-ila-alarm-edfa-ba-oog {
       type string;
       description "Optical ila alarm edfa ba OOG";
     }
     leaf fpc-optical-ila-alarm-edfa-ba-pump0-eol {
       type string;
       description "Optical ila alarm edfa ba pump 0 EOL";
     }
     leaf fpc-optical-ila-alarm-edfa-ba-pump1-eol {
       type string;
       description "Optical ila alarm edfa ba pump 1 EOL";
     }
     leaf fpc-optical-ila-alarm-edfa-ba-pump0-temp-abnormal {
       type string;
       description "Optical ila alarm edfa ba pump 0 temp abmornal";
     }
     leaf fpc-optical-ila-alarm-edfa-ba-pump1-temp-abnormal {
       type string;
       description "Optical ila alarm edfa ba pump 1 temp abmornal";
     }
     leaf fpc-optical-ila-alarm-edfa-ba-input-los {
       type string;
       description "Optical ila alarm edfa ba input LOS";
     }
     leaf fpc-optical-ila-alarm-edfa-ba-output-alarm {
       type string;
       description "Optical ila alarm edfa ba output alarm";
     }
     leaf fpc-optical-ila-alarm-edfa-ba-cali-tbl-err {
       type string;
       description "Optical ila alarm edfa ba cali table error";
     }
     leaf fpc-optical-ila-alarm-osc-a-add-power-alarm {
       type string;
       description "Optical ila alarm osc a add power alarm";
     }
     leaf fpc-optical-ila-alarm-osc-a-drop-power-alarm {
       type string;
       description "Optical ila alarm osc a drop power alarm";
     }
     leaf fpc-optical-ila-alarm-osc-b-add-power-alarm {
       type string;
       description "Optical ila alarm osc b add power alarm";
     }
     leaf fpc-optical-ila-alarm-osc-b-drop-power-alarm {
       type string;
       description "Optical ila alarm osc b drop power alarm";
     }
   }
 }
 grouping adc-information-block {
   container terse {
     list adc {
       leaf slot {
         type int32;
       }
       leaf state {
         type string;
         description "Status of the component";
       }
     }
   }
   container brief {
     list adc {
       leaf slot {
         type int32;
       }
       leaf state {
         type string;
         description "Status of the component";
       }
       leaf comment {
         type string;
       }
       leaf up-time {
         type string;
         description "Length of time this component has been operational";
       }
       leaf use-cli-info {
         type string;
       }
     }
   }
   container brief-bsys {
     list adc {
       leaf slot {
         type int32;
       }
       leaf state {
         type string;
         description "Status of the component";
       }
       leaf comment {
         type string;
       }
       leaf up-time {
         type string;
         description "Length of time this component has been operational";
       }
       leaf gnf-id {
         type string;
       }
       leaf use-cli-info {
         type string;
       }
     }
   }
   container verbose {
     list adc {
       leaf slot {
         type int32;
       }
       leaf state {
         type string;
         description "Status of the component";
       }
       leaf comment {
         type string;
       }
     }
   }
 }
 grouping spmb-information-block {
   container verbose {
     list spmb {
       leaf slot {
         type int32;
       }
       leaf state {
         type string;
         description "Status of the component";
       }
       leaf cpu-total {
         type int32;
         description "Percentage of CPU utilized";
       }
       leaf cpu-interrupt {
         type int32;
         description "Percentage of CPU utilized by interrupt processing";
       }
       leaf memory-heap-utilization {
         type int32;
         description "Percentage of heap memory utilized";
       }
       leaf memory-buffer-utilization {
         type int32;
         description "Percentage of buffer memory utilized";
       }
       leaf start-time {
         type string;
         description "Time this component was started";
       }
       leaf up-time {
         type string;
         description "Length of time this component has been operational";
       }
     }
   }
 }
 grouping sib-information-block {
   container brief {
     leaf use-cli-info {
       type string;
     }
     container sib {
       leaf slot {
         type int32;
       }
       leaf state {
         type string;
         description "Status of the component";
       }
       leaf link-error {
         type string;
         description "Link error count";
       }
       leaf destination-error {
         type string;
         description "Destination error count";
       }
       leaf up-time {
         type string;
         description "Length of time this component has been operational";
       }
       leaf comment {
         type string;
       }
     }
   }
   container brief_cable_error {
     leaf use-cli-info {
       type string;
     }
     container sib {
       leaf slot {
         type int32;
       }
       leaf state {
         type string;
         description "Status of the component";
       }
       leaf sib-cable-errors {
         type string;
         description "SIB cable errors";
       }
       leaf link-error {
         type string;
         description "Link error count";
       }
       leaf destination-error {
         type string;
         description "Destination error count";
       }
       leaf up-time {
         type string;
         description "Length of time this component has been operational";
       }
       leaf comment {
         type string;
       }
     }
   }
   container detail {
     container sib {
       leaf slot-type {
         type string;
       }
       leaf state {
         type string;
         description "Status of the component";
       }
       leaf sib-type {
         type string;
       }
       leaf link-error {
         type string;
         description "Link error count";
       }
       leaf destination-error {
         type string;
         description "Destination error count";
       }
       leaf up-time {
         type string;
         description "Length of time this component has been operational";
       }
       leaf comment {
         type string;
       }
     }
   }
   container detail_cable_error {
     container sib {
       leaf slot-type {
         type string;
       }
       leaf state {
         type string;
         description "Status of the component";
       }
       leaf sib-type {
         type string;
       }
       leaf sib-cable-errors {
         type string;
         description "SIB cable errors";
       }
       leaf link-error {
         type string;
         description "Link error count";
       }
       leaf destination-error {
         type string;
         description "Destination error count";
       }
       leaf up-time {
         type string;
         description "Length of time this component has been operational";
       }
       leaf comment {
         type string;
       }
     }
   }
   container brief1 {
     container sib {
       leaf slot {
         type int32;
       }
       leaf state {
         type string;
         description "Status of the component";
       }
       leaf sib-link-state {
         type string;
         description "SIB fabric link state";
       }
       leaf sib-link-errors {
         type string;
         description "SIB fabric link errors";
       }
     }
   }
   container verbose1 {
     container sib {
       leaf slot {
         type int32;
       }
       leaf state {
         type string;
         description "Status of the component";
       }
       leaf temperature {
         type string;
         description "Temperature of the item";
       }
       leaf start-time {
         type string;
         description "Time this component was started";
       }
       leaf up-time {
         type string;
         description "Length of time this component has been operational";
       }
       leaf sib-link-state {
         type string;
         description "SIB fabric link state";
       }
       leaf sib-errors {
         type string;
         description "SIB errors";
       }
       leaf comment {
         type string;
       }
     }
   }
 }
 grouping spmb-error-information-block {
   container brief {
     description "Display the ASIC error stats for SPMB";
     list spmb {
       leaf slot {
         type int32;
       }
       leaf minor-level-occured {
         type uint32;
       }
       leaf minor-level-cleared {
         type uint32;
       }
       leaf minor-level-threshold {
         type uint32;
       }
       leaf minor-level-action-taken {
         type uint32;
       }
       leaf minor-level-action {
         type string;
       }
       leaf major-level-occured {
         type uint32;
       }
       leaf major-level-cleared {
         type uint32;
       }
       leaf major-level-threshold {
         type uint32;
       }
       leaf major-level-action-taken {
         type uint32;
       }
       leaf major-level-action {
         type string;
       }
       leaf fatal-level-occured {
         type uint32;
       }
       leaf fatal-level-cleared {
         type uint32;
       }
       leaf fatal-level-threshold {
         type uint32;
       }
       leaf fatal-level-action-taken {
         type uint32;
       }
       leaf fatal-level-action {
         type string;
       }
     }
   }
 }
 grouping fru-information-block {
   container brief {
     container fru {
       leaf slot {
         type int32;
       }
       leaf state {
         type string;
         description "Status of the component";
       }
       leaf up-time {
         type string;
         description "Length of time this component has been operational";
       }
       leaf comment {
         type string;
       }
       list error-module {
         container device-entry {
         }
       }
     }
   }
 }
 grouping chassis-lcc-mode-information-block {
   container brief {
     container lcc-mode-information {
       leaf slot {
         type int32;
       }
       leaf lcc-mode {
         type string;
         description "LCC mode";
       }
     }
   }
 }
 grouping psd-information-block {
   container brief {
     container psd {
       leaf slot {
         type int32;
       }
       leaf description {
         type string;
         description "Description of this component";
       }
       leaf state {
         type string;
         description "Status of the component";
       }
       leaf up-time {
         type string;
         description "Length of time this component has been operational";
       }
       leaf comment {
         type string;
       }
     }
   }
 }
 grouping gnf-information-block {
   container brief {
     container gnf {
       leaf slot {
         type int32;
       }
       leaf description {
         type string;
         description "Description of this component";
       }
       leaf state {
         type string;
         description "Status of the component";
       }
       leaf up-time {
         type string;
         description "Length of time this component has been operational";
       }
       leaf comment {
         type string;
       }
     }
   }
 }
 grouping gnf-fpcs-information-block {
   container brief {
     container gnf-fpc {
       leaf slot {
         type int32;
       }
       leaf gnf-fpcs {
         type string;
       }
     }
   }
 }
 grouping fm-fpc-state-information-block {
   container brief1 {
     list fm-fpc-ln {
       list fm-pfe-ln {
         list fm-sib-ln {
         }
       }
     }
     list fm-fpc-ln1 {
       leaf fpc-slot1 {
         type int32;
       }
       list fm-pfe-ln1 {
         list fm-pfe-core-ln {
         }
       }
     }
   }
   container brief {
     list fm-fpc-ln {
       leaf slot {
         type int32;
       }
       list fm-pfe-ln {
         list fm-sib-ln {
         }
       }
     }
     list fm-fpc-ln1 {
       list fm-pfe-ln1 {
         list fm-pfe-core-ln {
         }
       }
     }
   }
   container terse {
     leaf comment {
       type string;
     }
     list fm-fpc-ln {
       leaf slot {
         type int32;
       }
       list fm-pfe-ln {
         container fm-plane-ln {
         }
       }
     }
     list fm-fpc-ln1 {
       list fm-pfe-ln1 {
         list fm-pfe-core-ln {
         }
       }
     }
   }
   container link {
     list fm-fpc-ln {
       leaf slot {
         type int32;
       }
       list fm-pfe-ln {
         container fm-link-ln {
         }
       }
     }
     list fm-fpc-ln1 {
       list fm-pfe-ln1 {
         list fm-pfe-core-ln {
         }
       }
     }
   }
 }
 grouping fm-fabric-destinations-state-block {
   container terse {
     description "Fabric destinations state information";
     list fm-dest-fpc-ln {
       description "Fabric destinations state for fpc";
       leaf fm-slot {
         type uint32;
         description "FPC slot";
       }
       list fm-dest-pfe-ln {
         description "Fabric destinations state for pfe";
         list fm-dest-plane-ln {
           description "Fabric destinations state for plane";
           container fm-dest-fabric-destinations-ln {
           }
         }
       }
     }
   }
 }
 grouping fm-plane-location-information-block {
   container fm-plane-location {
     leaf plane {
       type string;
       description "Plane information";
     }
     leaf sib-f13-slot {
       type string;
       description "F13 SIB information";
     }
     leaf sib-f2-slot {
       type string;
       description "F2 SIB information";
     }
     leaf sib-l-slot {
       type string;
       description "LCC SIB information";
     }
     leaf plane-slot {
       type uint32;
     }
     leaf cb-slot {
       type uint32;
     }
     leaf sfb-plane {
       type uint32;
     }
     leaf sfb-slot {
       type uint32;
     }
     leaf sib-slot {
       type int32;
       description "SIB slot number";
     }
     leaf planes {
       type string;
       description "Planes associated with the SIB";
     }
     leaf plane-number {
       type uint32;
       description "Planes number";
     }
     list fab-fru-slot-ln {
     }
   }
 }
 grouping fm-topology-block {
   container fm-topo-link-src-des {
     leaf fm-topo-link-msg {
       type string;
     }
     container fm-topo-link-src {
       leaf fm-topo-link-src-in {
         type string;
       }
       leaf fm-topo-link-src-out {
         type string;
       }
       leaf hsl2-state-src {
         type string;
       }
     }
     container fm-topo-link-des {
       leaf fm-topo-link-des-in {
         type string;
       }
       leaf fm-topo-link-des-out {
         type string;
       }
       leaf hsl2-state-des {
         type string;
       }
     }
   }
   container fm-topo-link-io {
     leaf fm-topo-link-header-message {
       type string;
       description "Header messages for this command";
     }
     container fm-topo-link-sib {
       leaf fm-topo-link-sibnum {
         type int32;
         description "SIB number";
       }
       leaf fm-topo-link-sib-message {
         type string;
         description "SIB messages";
       }
       container fm-topo-link-fchip {
         container fm-topo-link-fcore {
           container fm-topo-link-source {
           }
           container fm-topo-link-destination {
           }
         }
       }
     }
   }
   container fm-topo-link {
     container detail {
       container fm-topo-link-details {
         container fm-topo-link-in-out {
           leaf fm-topo-link-type {
             type string;
             description "Type of the link";
           }
         }
         container fm-topo-link-details-head-lcc {
           leaf fm-topo-sib-source {
             type string;
             description "Source sib";
           }
           leaf fm-topo-sib-dest {
             type string;
             description "Destination sib";
           }
         }
         container fm-topo-link-details-lcc {
           leaf source-pfe-xc-link {
             type string;
             description "Source pfe link";
           }
           leaf dest-pfe-xc-link {
             type string;
             description "Destination pfe link";
           }
           leaf vcsel-status {
             type string;
             description "VCSEL status";
           }
           leaf hsl2-channel {
             type string;
             description "HSL2 channel number";
           }
           leaf hsl2-status {
             type string;
             description "HSL2 channel status";
           }
         }
         container fm-topo-link-details-head-sfc {
           leaf fm-topo-sib-source {
             type string;
             description "Source sib";
           }
           leaf fm-topo-sib-dest {
             type string;
             description "Destination sib";
           }
         }
         container fm-topo-link-details-sfc {
           leaf source-pfe-xc-link {
             type string;
             description "Source pfe link";
           }
           leaf dest-pfe-xc-link {
             type string;
             description "Destination pfe link";
           }
           leaf vcsel-status {
             type string;
             description "VCSEL status";
           }
           leaf hsl2-channel {
             type string;
             description "HSL2 channel number";
           }
           leaf hsl2-status {
             type string;
             description "HSL2 channel status";
           }
         }
       }
       container fm-topo-link-information {
         leaf fm-topo-sib {
           type string;
           description "SIB information";
         }
         leaf fm-topo-dbl-line {
           type string;
           description "Under line of the header";
         }
         container fm-topo-link-fail {
           leaf fm-topo-fail-msg {
             type string;
             description "Details of the failure";
           }
         }
         container fm-topo-link-details {
           container fm-topo-link-in-out {
             leaf fm-topo-link-type {
               type string;
               description "Type of the link";
             }
           }
           container fm-topo-link-details-head-lcc {
             leaf fm-topo-sib-source {
               type string;
               description "Source sib";
             }
             leaf fm-topo-sib-dest {
               type string;
               description "Destination sib";
             }
           }
           container fm-topo-link-details-lcc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
           container fm-topo-link-details-head-sfc {
             leaf fm-topo-sib-source {
               type string;
               description "Source sib";
             }
             leaf fm-topo-sib-dest {
               type string;
               description "Destination sib";
             }
           }
           container fm-topo-link-details-sfc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
         }
       }
       container fm-topo-link-information-sgl {
         container fm-topo-link-fail-sgl {
           leaf fm-topo-sib {
             type string;
             description "SIB information";
           }
           leaf fm-topo-fail-msg {
             type string;
             description "Details of the failure";
           }
         }
         container fm-topo-link-details {
           container fm-topo-link-in-out {
             leaf fm-topo-link-type {
               type string;
               description "Type of the link";
             }
           }
           container fm-topo-link-details-head-lcc {
             leaf fm-topo-sib-source {
               type string;
               description "Source sib";
             }
             leaf fm-topo-sib-dest {
               type string;
               description "Destination sib";
             }
           }
           container fm-topo-link-details-lcc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
           container fm-topo-link-details-head-sfc {
             leaf fm-topo-sib-source {
               type string;
               description "Source sib";
             }
             leaf fm-topo-sib-dest {
               type string;
               description "Destination sib";
             }
           }
           container fm-topo-link-details-sfc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
         }
       }
     }
   }
   container fm-topo-map {
     container fm-topo-map-ln {
       leaf fm-fpc-slot {
         type uint32;
       }
       leaf fm-pfe-slot {
         type uint32;
         description "PFE slot";
       }
       leaf fm-cb-slot {
         type uint32;
       }
       leaf port {
         type uint32;
       }
       leaf link-state {
         type string;
       }
     }
   }
 }
 grouping fm-optical-links-state-information-block {
   container brief {
     container fm-optical-links-state {
       leaf lcc-opt-name {
         type string;
         description "Lcc optics name";
       }
       leaf opt-link-state {
         type string;
       }
       leaf sc-opt-name {
         type string;
         description "Sc optics name";
       }
       leaf opt-link-state-str {
         type string;
       }
       leaf opt-link-mandatory-str {
         type string;
         description "Cable mandatory or non-mandatory";
       }
     }
   }
   container detail {
     container fm-optical-links-state {
       leaf lcc-opt-name {
         type string;
         description "Lcc optics name";
       }
       leaf opt-link-state {
         type string;
       }
       leaf sc-opt-name {
         type string;
         description "Sc optics name";
       }
       leaf opt-link-state-str {
         type string;
       }
       leaf opt-link-mandatory-str {
         type string;
         description "Cable mandatory or non-mandatory";
       }
       leaf cbl-mapped-fpcs {
         type string;
         description "Fpcs mapped to this cable";
       }
       leaf cbl-chan-hsl-state {
         type string;
         description "Cable chan hsl state";
       }
       leaf cbl-misconn-info {
         type string;
         description "Cable Misconnected Info details if cable is misconnected";
       }
     }
   }
 }
 grouping fm-optics-port-information-block {
   container brief {
     container fm-optics-port-info-state {
       leaf optics-sib-name {
         type string;
         description "SIB name";
       }
       leaf optics-port {
         type uint32;
         description "Port";
       }
       leaf optics-cable-state {
         type string;
         description "Cable State";
       }
       leaf optics-cable-type {
         type string;
         description "Module Type";
       }
       leaf optics-cbl-fault-reason {
         type string;
         description "Optics Fault reason";
       }
     }
   }
   container detail {
     leaf optics-header {
       type string;
       description "Optics header";
     }
     container fm-optics-port-info-state {
       leaf optics-sib-name {
         type string;
         description "SIB name";
       }
       leaf optics-port {
         type uint32;
         description "Port";
       }
       leaf optics-cable-state {
         type string;
         description "Cable State";
       }
       leaf optics-cbl-fault-reason {
         type string;
         description "Optics Fault reason";
       }
       leaf optics-vendor-name {
         type string;
         description "Optics Vendor Name";
       }
       leaf optics-fw-ver {
         type string;
         description "Optics Firmware Version";
       }
       leaf optics-cable-type {
         type string;
         description "Module Type";
       }
       leaf optics-port-tx-rx {
         type string;
         description "Tx or Rx side";
       }
       leaf optics-module-alarm-info {
         type string;
         description "Optics Module Alarms Info";
       }
       leaf optics-temp-source {
         type string;
         description "Temperature monitor source";
       }
       leaf optics-temp {
         type int32;
         description "Temperature";
       }
       leaf optics-volt-source {
         type string;
         description "Voltage monitor source";
       }
       leaf optics-volt {
         type string;
         description "Voltage";
       }
       leaf optics-chan-name {
         type string;
         description "Channel name";
       }
       leaf optics-chan-alarm-info {
         type string;
         description "Optics Channel Alarms Info";
       }
       leaf optics-chan-bias-current {
         type string;
         description "Channel Bias current";
       }
       leaf optics-chan-power {
         type string;
         description "Channel optical power";
       }
     }
   }
 }
 grouping fm-plane-state-information-block {
   container terse {
     leaf comment {
       type string;
     }
     container fmp-plane {
       leaf slot {
         type int32;
       }
       leaf state {
         type string;
         description "Status of the component";
       }
       leaf fru-name {
         type string;
       }
       leaf fru-slot {
         type int32;
         description "FRU slot number";
       }
       leaf pfe-slot {
         type int32;
       }
       leaf pfe-link-status {
         type string;
         description "PFE link status information";
       }
     }
   }
   container brief {
     leaf fabric-header {
       type string;
       description "Fabric header";
     }
     leaf comment {
       type string;
     }
     container fmp-plane {
       leaf slot {
         type int32;
       }
       leaf state {
         type string;
         description "Status of the component";
       }
       leaf link-error {
         type string;
         description "Link error count";
       }
       leaf destination-error {
         type string;
         description "Destination error count";
       }
       leaf up-time {
         type string;
         description "Length of time this component has been operational";
       }
     }
   }
   container brief_cable_error {
     leaf fabric-header {
       type string;
       description "Fabric header";
     }
     leaf comment {
       type string;
     }
     container fmp-plane {
       leaf slot {
         type int32;
       }
       leaf state {
         type string;
         description "Status of the component";
       }
       leaf plane-cable-errors {
         type string;
         description "Number of cable errors in the plane";
       }
       leaf link-error {
         type string;
         description "Link error count";
       }
       leaf destination-error {
         type string;
         description "Destination error count";
       }
       leaf up-time {
         type string;
         description "Length of time this component has been operational";
       }
     }
   }
   container detail {
     leaf fabric-header {
       type string;
       description "Fabric header";
     }
     leaf comment {
       type string;
     }
     container fmp-plane {
       leaf slot {
         type int32;
       }
       leaf plane-state {
         type string;
         description "Plane state information";
       }
       leaf sib-name {
         type string;
         description "SIB name";
       }
       leaf sibs-slot {
         type string;
         description "Chassis SIB slot number";
       }
       leaf state {
         type string;
         description "Status of the component";
       }
     }
   }
   container extensive {
     leaf fabric-header {
       type string;
       description "Fabric header";
     }
     leaf comment {
       type string;
     }
     container fmp-plane {
       leaf slot {
         type int32;
       }
       leaf plane-state {
         type string;
         description "Plane state information";
       }
       leaf sib-name {
         type string;
         description "SIB name";
       }
       leaf sibs-slot {
         type string;
         description "Chassis SIB slot number";
       }
       leaf state {
         type string;
         description "Status of the component";
       }
       leaf sib-f13-name {
         type string;
         description "F13 SIB name";
       }
       leaf f13-slot {
         type int32;
         description "F13 slot number";
       }
       leaf even-odd {
         type string;
         description "Even or Odd part of SIB F13";
       }
       leaf lcc-slot {
         type int32;
         description "LCC slot number";
       }
       leaf sibl-slot {
         type int32;
         description "LCC SIB slot number";
       }
       leaf sibl-link-state {
         type string;
         description "LCC SIB link state information";
       }
       leaf sgasic-number {
         type int32;
         description "SG number on SFC";
       }
       leaf sgasic-port-number {
         type int32;
         description "SG port number on SFC";
       }
       leaf sgasic-port-link-state {
         type string;
         description "SG port link status on SFC";
       }
       leaf sibs-lcc-pfe-slot {
         type int32;
         description "SFC PFE slot number";
       }
       leaf sibs-lcc-pfe-link-state {
         type string;
         description "SFC PFE link state information";
       }
       leaf sib-f2-name {
         type string;
         description "F2 SIB name";
       }
       leaf sibs2-slot {
         type string;
         description "Chassis F2 SIB slot number";
       }
       leaf f2-link-state {
         type string;
         description "F2 link state information";
       }
       leaf lcc-sib-link-state {
         type string;
         description "LCC SIB link state information";
       }
       leaf lcc-sgasic-number {
         type int32;
         description "SG number on LCC";
       }
       leaf lcc-sgasic-port-number {
         type int32;
         description "SG port number on LCC";
       }
       leaf lcc-sgasic-port-link-state {
         type string;
         description "SG port link status on LCC";
       }
       leaf sibl-lcc-pfe-slot {
         type int32;
         description "LCC PFE slot number";
       }
       leaf sibl-lcc-pfe-link-state {
         type string;
         description "LCC PFE link state information";
       }
       leaf lcc-fpc-slot {
         type int32;
         description "FPC slot number";
       }
       leaf lcc-pfe-slot {
         type int32;
         description "PFE slot number";
       }
       leaf lcc-pfe-link-state {
         type string;
         description "PFE link state information";
       }
     }
   }
 }
 grouping fm-state-information-block {
   leaf comment {
     type string;
   }
   container fm-state-item {
     leaf plane-slot {
       type uint32;
     }
     leaf state {
       type string;
       description "Status of the component";
     }
     leaf up-time {
       type string;
       description "Length of time this component has been operational";
     }
   }
 }
 grouping fm-ext-state-information-block {
   leaf comment {
     type string;
   }
   container fm-ext-state-item {
     leaf plane-slot {
       type uint32;
     }
     leaf state {
       type string;
       description "Status of the component";
     }
     leaf link-error {
       type string;
       description "Link error count";
     }
     leaf link-tf {
       type string;
       description "Count of training failure links";
     }
     leaf destination-error {
       type string;
       description "Destination error count";
     }
     leaf up-time {
       type string;
       description "Length of time this component has been operational";
     }
   }
 }
 grouping fm-state-legend-block {
   leaf comment {
     type string;
   }
 }
 grouping fm-sib-state-information-block {
   container brief1 {
     list fms-sib-ln {
       leaf sib-slot {
         type int32;
         description "SIB slot number";
       }
       leaf sib-fms-state1 {
         type string;
       }
       list fms-core-ln {
         list fms-core-fpc-ln {
           list fms-core-pfe-ln {
           }
         }
       }
     }
     list fms-sib-ln1 {
       leaf sib-slot {
         type int32;
         description "SIB slot number";
       }
       leaf sib-fms-state1 {
         type string;
       }
       list fms-core-ln {
         list fms-core-fpc-ln {
           list fms-core-pfe-ln {
           }
         }
       }
     }
   }
   container brief {
     list fms-sib-ln {
       leaf sib-slot {
         type int32;
         description "SIB slot number";
       }
       leaf sib-fm-state {
         type string;
       }
       list fms-fpc-ln {
         list fms-pfe-ln {
         }
       }
       list fms-lcc-ln {
       }
       container fms-scc-ln {
       }
     }
     list fms-sib-ln1 {
       list fms-core-ln {
         list fms-core-fpc-ln {
           list fms-core-pfe-ln {
           }
         }
       }
     }
   }
 }
 grouping chassis-fabric-information-block {
   leaf device-id {
     type string;
     description "Device ID";
   }
   leaf chassis-type {
     type string;
     description "Chassis type";
   }
   leaf management-status {
     type string;
     description "Management status";
   }
   leaf hw-status {
     type string;
     description "Hardware status";
   }
   list chassis-fabric-links-header {
     leaf fm-space-tab {
       type string;
       description "Space tab";
     }
   }
   list chassis-fabric-ccpc-incoming-links-header {
     leaf card-detail {
       type string;
       description "Card detail";
     }
     leaf card-slot-num {
       type string;
       description "Card slot number";
     }
   }
   list chassis-fabric-ccpc-outgoing-links-header {
     leaf card-detail {
       type string;
       description "Card detail";
     }
     leaf card-slot-num {
       type string;
       description "Card slot number";
     }
   }
   list chassis-fabric-tor-incoming-links-header {
     leaf fm-space-tab {
       type string;
       description "Space tab";
     }
   }
   list chassis-fabric-tor-outgoing-links-header {
     leaf fm-space-tab {
       type string;
       description "Space tab";
     }
   }
   container chassis-fabric-links {
     list link-by-link-information {
       leaf src-link {
         type string;
         description "Source link";
       }
       leaf dst-link {
         type string;
         description "Destination link";
       }
       leaf hw-status {
         type string;
         description "Hardware status";
       }
     }
   }
   list chassis-fabric-information-internal {
     leaf chassis-id {
       type uint32;
       description "Chassis ID";
     }
     leaf min-chip-id {
       type uint32;
       description "Minimum chip ID";
     }
     leaf max-chip-id {
       type uint32;
       description "Maximum chip ID";
     }
   }
   list chassis-fabric-card-information-internal {
     leaf card-pos {
       type string;
       description "Card position";
     }
     leaf card-slot {
       type uint32;
       description "Card slot";
     }
     leaf card-type {
       type string;
       description "Card type";
     }
     leaf management-status {
       type string;
       description "Management status";
     }
     leaf hw-status {
       type string;
       description "Hardware status";
     }
     leaf min-chip-id {
       type uint32;
       description "Minimum chip ID";
     }
     leaf max-chip-id {
       type uint32;
       description "Maximum chip ID";
     }
   }
   list chassis-fabric-chip-information-internal {
     leaf chip-id {
       type uint32;
       description "Chip ID";
     }
     leaf chip-type {
       type string;
       description "Chip type";
     }
     leaf management-status {
       type string;
       description "Management status";
     }
     leaf hw-status {
       type string;
       description "Hardware status";
     }
   }
   list chassis-fabric-chip-in-links-internal {
     leaf src-chip {
       type uint32;
       description "Source chip";
     }
     leaf src-port {
       type uint32;
       description "Source port";
     }
     leaf dst-chip {
       type uint32;
       description "Destination chip";
     }
     leaf dst-port {
       type uint32;
       description "Destination port";
     }
     leaf management-status {
       type string;
       description "Management status";
     }
     leaf hw-status {
       type string;
       description "Hardware status";
     }
   }
   list chassis-fabric-chip-out-links-internal {
     leaf src-chip {
       type uint32;
       description "Source chip";
     }
     leaf src-port {
       type uint32;
       description "Source port";
     }
     leaf dst-chip {
       type uint32;
       description "Destination chip";
     }
     leaf dst-port {
       type uint32;
       description "Destination port";
     }
     leaf management-status {
       type string;
       description "Management status";
     }
     leaf hw-status {
       type string;
       description "Hardware status";
     }
   }
   list chassis-fabric-chip-up-links-internal {
     leaf src-chip {
       type uint32;
       description "Source chip";
     }
     leaf src-port {
       type uint32;
       description "Source port";
     }
     leaf dst-chip {
       type uint32;
       description "Destination chip";
     }
     leaf dst-port {
       type uint32;
       description "Destination port";
     }
   }
   list chassis-fabric-chip-down-links-internal {
     leaf src-chip {
       type uint32;
       description "Source chip";
     }
     leaf src-port {
       type uint32;
       description "Source port";
     }
     leaf dst-chip {
       type uint32;
       description "Destination chip";
     }
     leaf dst-port {
       type uint32;
       description "Destination port";
     }
   }
   list chassis-fabric-chip-error-links-internal {
     leaf src-chip {
       type uint32;
       description "Source chip";
     }
     leaf src-port {
       type uint32;
       description "Source port";
     }
     leaf dst-chip {
       type uint32;
       description "Destination chip";
     }
     leaf dst-port {
       type uint32;
       description "Destination port";
     }
   }
 }
 grouping fm-topo-tracepath-link-block {
   container brief {
     container fm-topo-tracepath-link-output {
       leaf link-tracepath {
         type string;
         description "Tracepath Output";
       }
     }
   }
 }
 grouping fm-topo-tracepath-fpc-block {
   container brief {
     container fm-topo-tracepath-fpc-output {
       leaf fpc-tracepath {
         type string;
         description "Tracepath Output";
       }
     }
   }
 }
 grouping fm-unreachable-dest-information-block {
   container brief {
     description "Display unreachable destinations on all active planes";
     leaf slot {
       type int32;
     }
     list fm-fpc-line {
       description "Fabric reachability state for FPC";
       leaf pfe-slot {
         type int32;
       }
       list fm-pfe-line {
         description "Fabric reachability state for PFE";
       }
     }
   }
 }
 grouping fm-fabric-reachability-information-block {
   leaf fab-reach-status {
     type string;
   }
   leaf fab-reach-resolute {
     type string;
   }
   container fab-reachability-detect {
     leaf unreach-dests {
       type string;
     }
     leaf detect-time {
       type string;
       description "Time of unreachability detection";
     }
     leaf unreachability-reason {
       type string;
     }
   }
   container fab-reachability-action {
     leaf current-act {
       type string;
     }
     leaf act-reason {
       type string;
     }
     leaf init-phase {
       type string;
     }
     leaf current-phase {
       type string;
     }
     leaf current-phase-status {
       type string;
     }
     leaf act-start-time {
       type string;
       description "Fabric reachability action started";
     }
     leaf act-end-time {
       type string;
       description "Time fabric reachability action completed";
     }
     container plane-restart-phase {
       leaf plane-restart-phase-status {
         type string;
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
     }
     container sib-restart-phase {
       leaf plane-restart-phase-status {
         type string;
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
     }
     container plane-fpc-restart-phase {
       leaf plane-fpc-restart-phase-status {
         type string;
       }
       leaf plane-fpc-restart-start-time {
         type string;
         description "Plane and FPC restart phase start time";
       }
       leaf fpc-offline-start-time {
         type string;
         description "Offline FPC stage start time";
       }
       leaf fpc-action-list {
         type string;
       }
       leaf fpc-offline-timeout-list {
         type string;
         description "FPCs timed out on offline event";
       }
       leaf fpc-offline-current {
         type int32;
       }
       leaf fpc-offline-time {
         type string;
         description "Time FPC made offline";
       }
       leaf fpc-offline-end-time {
         type string;
         description "Offline FPC stage end time";
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
       leaf fpc-online-start-time {
         type string;
         description "FPC online stage start time";
       }
       leaf fpc-online-list {
         type string;
       }
       leaf fpc-online-timeout-list {
         type string;
         description "FPCs timed out on online event";
       }
       leaf fpc-online-current {
         type int32;
       }
       leaf fpc-online-time {
         type string;
         description "Time FPC made online";
       }
       leaf fpc-online-end-time {
         type string;
         description "FPC online stage end time";
       }
       leaf fpc-restart-list {
         type string;
         description "FPCs restart list";
       }
       leaf fpc-restart-time {
         type string;
         description "FPC restart time";
       }
       leaf plane-fpc-restart-phase-end-time {
         type string;
         description "Plane and FPC restart phase end time";
       }
     }
     container sib-fpc-restart-phase {
       leaf plane-fpc-restart-phase-status {
         type string;
       }
       leaf plane-fpc-restart-start-time {
         type string;
         description "Plane and FPC restart phase start time";
       }
       leaf fpc-offline-start-time {
         type string;
         description "Offline FPC stage start time";
       }
       leaf fpc-offline-list {
         type string;
       }
       leaf fpc-offline-timeout-list {
         type string;
         description "FPCs timed out on offline event";
       }
       leaf fpc-offline-current {
         type int32;
       }
       leaf fpc-offline-time {
         type string;
         description "Time FPC made offline";
       }
       leaf fpc-offline-end-time {
         type string;
         description "Offline FPC stage end time";
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
       leaf fpc-online-start-time {
         type string;
         description "FPC online stage start time";
       }
       leaf fpc-online-list {
         type string;
       }
       leaf fpc-online-timeout-list {
         type string;
         description "FPCs timed out on online event";
       }
       leaf fpc-online-current {
         type int32;
       }
       leaf fpc-online-time {
         type string;
         description "Time FPC made online";
       }
       leaf fpc-online-end-time {
         type string;
         description "FPC online stage end time";
       }
       leaf fpc-restart-list {
         type string;
         description "FPCs restart list";
       }
       leaf fpc-restart-time {
         type string;
         description "FPC restart time";
       }
       leaf plane-fpc-restart-phase-end-time {
         type string;
         description "Plane and FPC restart phase end time";
       }
     }
     container fpc-offline-phase {
       leaf fpc-offline-phase-status {
         type string;
       }
       leaf fpc-offline-phase-start-time {
         type string;
         description "FPC offline phase start time";
       }
       leaf fpc-offline-start-time {
         type string;
         description "Offline FPC stage start time";
       }
       leaf fpc-action-list {
         type string;
       }
       leaf fpc-offline-timeout-list {
         type string;
         description "FPCs timed out on offline event";
       }
       leaf fpc-offline-current {
         type int32;
       }
       leaf fpc-offline-time {
         type string;
         description "Time FPC made offline";
       }
       leaf fpc-offline-end-time {
         type string;
         description "Offline FPC stage end time";
       }
       leaf fpc-offline-phase-end-time {
         type string;
         description "FPC offline phase end time";
       }
     }
   }
 }
 grouping fm-degraded-fabric-state-information-block {
   container brief {
     description "Fabric state information";
     list fm-fpc-line {
       description "Fabric reachability state for FPC";
       leaf deg-fpc-slot {
         type int32;
         description "FPC slot";
       }
       list fm-pfe-line {
         description "Fabric reachability state for PFE";
         list fm-pfe-sib-line {
           description "Fabric state for FE per SIB/Plane";
         }
       }
     }
   }
 }
 grouping fm-fru-errors-block {
   container verbose {
     leaf fm-fru-first-error-header {
       type int32;
       description "First error logs header";
     }
     leaf fm-fru-last-error-header {
       type int32;
       description "Last error logs header";
     }
     list fm-first-error-ln {
       leaf fm-first-error-time {
         type string;
       }
       leaf fm-first-error-detail {
         type string;
       }
     }
     list fm-last-error-ln {
       leaf fm-last-error-time {
         type string;
       }
       leaf fm-last-error-detail {
         type string;
       }
     }
   }
 }
 grouping chassis-inventory-block {
   container chassis {
     description "Hardware inventory of this chassis";
     container inventory {
       description "Hardware inventory of this chassis";
       leaf name {
         type string;
         description "Name of this component";
       }
       leaf version {
         type string;
         description "Version of this component";
       }
       leaf part-number {
         type string;
         description "Part number of this component";
       }
       leaf serial-number {
         type string;
         description "Serial number of this component";
       }
       leaf description {
         type string;
         description "Description of this component";
       }
       leaf hardware-incomplete {
         type empty;
       }
       container i2c-information {
         leaf jedec-code {
           type string;
         }
         leaf eeprom-version {
           type string;
         }
         leaf assembly-identifier {
           type string;
         }
         leaf assembly-version {
           type string;
         }
         leaf manufacture-date {
           type string;
           description "Date this component was manufactured";
         }
         leaf assembly-flags {
           type string;
         }
         leaf i2c-version {
           type string;
         }
         leaf clei-code {
           type string;
           description "Common Language Equipment Identifier code of this component";
         }
         leaf i2c-identifier {
           type string;
         }
         leaf model-number {
           type string;
           description "Model number of this component";
         }
         leaf board-information-record {
           type string;
           description "Hex dump of board information record";
         }
         leaf i2c-data {
           type string;
           description "Hex dump of I2C data";
         }
       }
       list chassis-module {
         leaf name {
           type string;
           description "Name of this component";
         }
         leaf version {
           type string;
           description "Version of this component";
         }
         leaf part-number {
           type string;
           description "Part number of this component";
         }
         leaf serial-number {
           type string;
           description "Serial number of this component";
         }
         leaf description {
           type string;
           description "Description of this component";
         }
         leaf ir-mode {
           type string;
           description "R/IR mode configured";
         }
         leaf license-mode {
           type string;
           description "PTX R/IR mode configured";
         }
         container i2c-information {
           leaf jedec-code {
             type string;
           }
           leaf eeprom-version {
             type string;
           }
           leaf assembly-identifier {
             type string;
           }
           leaf assembly-version {
             type string;
           }
           leaf manufacture-date {
             type string;
             description "Date this component was manufactured";
           }
           leaf assembly-flags {
             type string;
           }
           leaf i2c-version {
             type string;
           }
           leaf clei-code {
             type string;
             description "Common Language Equipment Identifier code of this component";
           }
           leaf i2c-identifier {
             type string;
           }
           leaf model-number {
             type string;
             description "Model number of this component";
           }
           leaf board-information-record {
             type string;
             description "Hex dump of board information record";
           }
           leaf i2c-data {
             type string;
             description "Hex dump of I2C data";
           }
         }
         list chassis-sub-module {
           leaf name {
             type string;
             description "Name of this component";
           }
           leaf version {
             type string;
             description "Version of this component";
           }
           leaf part-number {
             type string;
             description "Part number of this component";
           }
           leaf serial-number {
             type string;
             description "Serial number of this component";
           }
           leaf description {
             type string;
             description "Description of this component";
           }
           container i2c-information {
             leaf jedec-code {
               type string;
             }
             leaf eeprom-version {
               type string;
             }
             leaf assembly-identifier {
               type string;
             }
             leaf assembly-version {
               type string;
             }
             leaf manufacture-date {
               type string;
               description "Date this component was manufactured";
             }
             leaf assembly-flags {
               type string;
             }
             leaf i2c-version {
               type string;
             }
             leaf clei-code {
               type string;
               description "Common Language Equipment Identifier code of this component";
             }
             leaf i2c-identifier {
               type string;
             }
             leaf model-number {
               type string;
               description "Model number of this component";
             }
             leaf board-information-record {
               type string;
               description "Hex dump of board information record";
             }
             leaf i2c-data {
               type string;
               description "Hex dump of I2C data";
             }
           }
           list chassis-sub-sub-module {
             leaf name {
               type string;
               description "Name of this component";
             }
             leaf version {
               type string;
               description "Version of this component";
             }
             leaf part-number {
               type string;
               description "Part number of this component";
             }
             leaf serial-number {
               type string;
               description "Serial number of this component";
             }
             leaf description {
               type string;
               description "Description of this component";
             }
             list chassis-sub-sub-sub-module {
             }
           }
         }
         list chassis-re-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
         list chassis-re-usb-module {
           leaf name {
             type string;
             description "Name of this component";
           }
           leaf product {
             type string;
           }
           leaf product-number {
             type int32;
           }
           leaf vendor {
             type string;
           }
           leaf description {
             type string;
             description "Description of this component";
           }
         }
         list chassis-re-dimm-module {
           leaf name {
             type string;
             description "Name of this component";
           }
           leaf part-number {
             type string;
             description "Part number of this component";
           }
           leaf die-rev {
             type string;
             description " DIE revision of the DIMM";
           }
           leaf pcb-rev {
             type string;
             description "PCB revision ";
           }
           leaf mfr-id {
             type string;
             description "Manufacture Id of the DIMM";
           }
         }
         list chassis-compute-node-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
       }
     }
     container model-inventory {
       description "Hardware inventory of this chassis";
       list chassis-module {
         leaf name {
           type string;
           description "Name of this component";
         }
         leaf version {
           type string;
           description "Version of this component";
         }
         leaf part-number {
           type string;
           description "Part number of this component";
         }
         leaf serial-number {
           type string;
           description "Serial number of this component";
         }
         leaf model-number {
           type string;
           description "Model number of this component";
         }
         list chassis-sub-module {
           list chassis-sub-sub-module {
             list chassis-sub-sub-sub-module {
             }
           }
         }
       }
     }
     container clei-model-inventory {
       description "Hardware inventory of this chassis";
       list chassis-module {
         leaf name {
           type string;
           description "Name of this component";
         }
         leaf version {
           type string;
           description "Version of this component";
         }
         leaf part-number {
           type string;
           description "Part number of this component";
         }
         leaf clei-code {
           type string;
           description "Common Language Equipment Identifier code of this component";
         }
         leaf model-number {
           type string;
           description "Model number of this component";
         }
         list chassis-sub-module {
           list chassis-sub-sub-module {
             list chassis-sub-sub-sub-module {
             }
           }
         }
       }
     }
     container firmware {
       description "Hardware inventory of this chassis";
       list chassis-module {
         leaf name {
           type string;
           description "Name of this component";
         }
         list chassis-sub-module {
           list chassis-sub-sub-module {
             list chassis-sub-sub-sub-module {
             }
           }
         }
       }
     }
   }
 }
 grouping power-budget-information-block {
   container brief {
     leaf psu-slot {
       type int32;
       description "PSU slot";
     }
     leaf psu-type {
       type string;
       description "PSU type";
     }
     leaf power-supplied-psu {
       type int32;
       description "Power supplied by that PSU";
     }
     leaf power-supply-state {
       type string;
       description "State of PSU";
     }
     leaf total-power-supplied {
       type int32;
       description "Total Power supplied by all Online PSUs";
     }
     leaf psu-redundancy-config {
       type string;
       description "PSU redundancy Config";
     }
     leaf base-power {
       type int32;
       description "Reserved Power for the chassis";
     }
     leaf line-card-slot {
       type int32;
       description "Line card slot";
     }
     leaf line-card-type {
       type string;
       description "Line card type";
     }
     leaf line-card-power {
       type int32;
       description "Power used by that line card";
     }
     leaf line-card-poe-power {
       type int32;
       description "Power allocated for PoE per FPC";
     }
     leaf line-card-priority {
       type int32;
       description "Priority of the FPC";
     }
     leaf actual-power-used {
       type int32;
       description "Actual Power consumed by the chassis";
     }
     leaf total-poe-power-allocated {
       type int32;
       description "Total power allocated for Power over Ethernet(PoE)";
     }
     leaf power-available-redundant-case {
       type int32;
       description "Power available for use in redundant (N+1) case";
     }
     leaf total-power-available {
       type int32;
       description "Power available for use in non redundant (N) case";
     }
   }
   container detail {
     leaf psu-slot {
       type int32;
       description "PSU slot";
     }
     leaf psu-type {
       type string;
       description "PSU type";
     }
     leaf power-supplied-psu {
       type int32;
       description "Power supplied by that PSU";
     }
     leaf power-supply-state {
       type string;
       description "State of PSU";
     }
     leaf total-power-supplied {
       type int32;
       description "Total Power supplied by all Online PSUs";
     }
     leaf psu-redundancy-config {
       type string;
       description "PSU redundancy Config";
     }
     leaf base-power {
       type int32;
       description "Reserved Power for the chassis";
     }
     leaf fan-tray-slot {
       type int32;
       description "Fan Tray slot";
     }
     leaf fan-tray-type {
       type string;
       description "Fan Tray type";
     }
     leaf fan-tray-base-power {
       type int32;
       description "Fan Tray base power";
     }
     leaf fan-tray-actual-power {
       type empty;
       description "Actual Power consumed by Fan Tray";
     }
     leaf line-card-slot {
       type int32;
       description "Line card slot";
     }
     leaf line-card-type {
       type string;
       description "Line card type";
     }
     leaf line-card-power {
       type int32;
       description "Power used by that line card";
     }
     leaf line-card-actual-power {
       type empty;
       description "Power actually used by that line card";
     }
     leaf line-card-poe-power {
       type int32;
       description "Power allocated for PoE per FPC";
     }
     leaf line-card-priority {
       type int32;
       description "Priority of the FPC";
     }
     leaf actual-power-used {
       type int32;
       description "Actual Power consumed by the chassis";
     }
     leaf total-poe-power-allocated {
       type int32;
       description "Total power allocated for Power over Ethernet(PoE)";
     }
     leaf power-available-redundant-case {
       type int32;
       description "Power available for use in redundant (N+1) case";
     }
     leaf total-power-available {
       type int32;
       description "Power available for use in non redundant (N) case";
     }
   }
   container terse {
     leaf line-card-slot {
       type int32;
       description "Line card slot";
     }
     leaf psu-slot {
       type int32;
       description "PSU slot";
     }
     leaf psu-type {
       type string;
       description "PSU type";
     }
     leaf power-supplied-psu {
       type int32;
       description "Power supplied by that PSU";
     }
     leaf power-supply-state {
       type string;
       description "State of PSU";
     }
     leaf psu-redundancy-config {
       type string;
       description "PSU redundancy Config";
     }
     leaf total-power-supplied {
       type int32;
       description "Total Power supplied by all Online PSUs";
     }
     leaf base-power {
       type int32;
       description "Reserved Power for the chassis";
     }
     leaf actual-power-used {
       type int32;
       description "Actual Power consumed by the chassis";
     }
     leaf total-poe-power-allocated {
       type int32;
       description "Total power allocated for Power over Ethernet(PoE)";
     }
     leaf actual-poe-power-used {
       type int32;
       description "Power used for Power over Ethernet (PoE)";
     }
     leaf total-poe-power-available {
       type int32;
       description "Total power available for Power over Ethernet (PoE)";
     }
   }
 }
 grouping chassis-mac-addresses-block {
   list chassis-mac-addresses-edge-info {
     container re-mac-address {
       leaf re-fc-mac-base {
         type string;
       }
       leaf re-fc-mac-count {
         type string;
       }
       leaf re-vlan-mac {
         type string;
       }
     }
     list fpc-mac-address {
       leaf name {
         type string;
         description "Name of this component";
       }
       leaf fpc-mac-base {
         type string;
       }
       leaf fpc-mac-count {
         type string;
       }
     }
   }
   list mac-address-information {
     leaf public-base-address {
       type string;
     }
     leaf public-count {
       type string;
     }
     leaf private-base-address {
       type string;
     }
     leaf private-count {
       type string;
     }
   }
   container external-mac-address-information {
     leaf external-base-address {
       type string;
     }
     leaf external-count {
       type string;
     }
     leaf external-available {
       type string;
     }
   }
 }
 grouping route-engine-information-block {
   list route-engine {
     leaf slot {
       type int32;
     }
     leaf physical-slot {
       type int32;
     }
     leaf mastership-state {
       type string;
       description "Current state of mastership on this Routing Engine";
     }
     leaf mastership-priority {
       type string;
       description "Configured priority for mastership on this Routing Engine";
     }
     leaf temperature {
       type string;
       description "Temperature of the item";
     }
     leaf cpu-temperature {
       type string;
     }
     leaf memory-dram-size {
       type int32;
       description "DRAM";
     }
     leaf memory-installed-size {
       type string;
       description "Installed RAM";
     }
     leaf memory-buffer-utilization {
       type int32;
       description "Percentage of buffer memory utilized";
     }
     leaf memory-system-total {
       type int32;
       description "Display the total system memory";
     }
     leaf memory-system-total-used {
       type int32;
       description "Display overall utilization of system memory";
     }
     leaf memory-system-total-util {
       type int32;
       description "Display overall %utilization of system memory";
     }
     leaf memory-control-plane {
       type int32;
       description "Display the total memory with control plane";
     }
     leaf memory-control-plane-used {
       type int32;
       description "Display the memory utilization of control plane mem";
     }
     leaf memory-control-plane-util {
       type int32;
       description "Display the %memory utilization of control plane mem";
     }
     leaf memory-data-plane {
       type int32;
       description "Display the total memory preallocated for data plane";
     }
     leaf memory-data-plane-used {
       type int32;
       description "Display the memory utilization of data plane mem";
     }
     leaf memory-data-plane-util {
       type int32;
       description "Display the %memory utilization of data plane mem";
     }
     leaf control-plane-cpu-count {
       type int32;
       description "Display the number of CPUS dedicated for control-plane";
     }
     leaf data-plane-cpu-count {
       type int32;
       description "Display the number of CPUS dedicated for data-plane";
     }
     leaf cpu-user {
       type int32;
       description "Percentage of CPU utilized by user processes";
     }
     leaf cpu-real-time {
       type int32;
       description "Percentage of CPU utilized by real-time threads";
     }
     leaf cpu-background {
       type int32;
       description "Percentage of CPU utilized by background processes";
     }
     leaf cpu-system {
       type int32;
       description "Percentage of CPU utilized by the kernel";
     }
     leaf cpu-interrupt {
       type int32;
       description "Percentage of CPU utilized by interrupt processing";
     }
     leaf cpu-idle {
       type int32;
       description "Percentage of CPU idle time";
     }
     leaf cpu-user1 {
       type int32;
       description "Percentage of CPU utilized by user processes";
     }
     leaf cpu-background1 {
       type int32;
       description "Percentage of CPU utilized by background processes";
     }
     leaf cpu-system1 {
       type int32;
       description "Percentage of CPU utilized by the kernel";
     }
     leaf cpu-interrupt1 {
       type int32;
       description "Percentage of CPU utilized by the Interrupt";
     }
     leaf cpu-idle1 {
       type int32;
       description "Percentage of CPU idle time";
     }
     leaf cpu-user2 {
       type int32;
       description "Percentage of CPU utilized by user processes";
     }
     leaf cpu-background2 {
       type int32;
       description "Percentage of CPU utilized by background processes";
     }
     leaf cpu-system2 {
       type int32;
       description "Percentage of CPU utilized by the kernel";
     }
     leaf cpu-interrupt2 {
       type int32;
       description "Percentage of CPU utilized by the Interrupt";
     }
     leaf cpu-idle2 {
       type int32;
       description "Percentage of CPU idle time";
     }
     leaf cpu-user3 {
       type int32;
       description "Percentage of CPU utilized by user processes";
     }
     leaf cpu-background3 {
       type int32;
       description "Percentage of CPU utilized by background processes";
     }
     leaf cpu-system3 {
       type int32;
       description "Percentage of CPU utilized by the kernel";
     }
     leaf cpu-interrupt3 {
       type int32;
       description "Percentage of CPU utilized by the Interrupt";
     }
     leaf cpu-idle3 {
       type int32;
       description "Percentage of CPU idle time";
     }
     leaf model {
       type string;
     }
     leaf serial-number {
       type string;
       description "Serial number of this component";
     }
     leaf start-time {
       type string;
       description "Time this component was started";
     }
     leaf up-time {
       type string;
       description "Length of time this component has been operational";
     }
     leaf last-reboot-reason {
       type string;
       description "Last reboot reason of routinge engine";
     }
     leaf load-average-one {
       type string;
     }
     leaf load-average-five {
       type string;
     }
     leaf load-average-fifteen {
       type string;
     }
     leaf bios-version {
       type string;
       description "Routing engine BIOS version";
     }
     leaf bios-date {
       type string;
       description "Routing engine BIOS date";
     }
     leaf bios-id {
       type string;
       description "Routing engine BIOS ID";
     }
     leaf loader-name {
       type string;
       description "Routing engine Loader name";
     }
     leaf loader-version {
       type string;
       description "Routing engine Loader version";
     }
     leaf icrt-version {
       type string;
       description "Routing engine iCRT version";
     }
   }
 }
 grouping service-node-information-block {
   list service-node {
     leaf slot {
       type int32;
     }
     leaf status {
       type string;
       description "Status of clock synchronization source";
     }
     leaf cpu-total {
       type int32;
       description "Percentage of CPU utilized";
     }
     leaf memory-dram-size {
       type int32;
       description "DRAM";
     }
     leaf memory-heap-utilization {
       type int32;
       description "Percentage of heap memory utilized";
     }
     leaf start-time {
       type string;
       description "Time this component was started";
     }
     leaf up-time {
       type string;
       description "Length of time this component has been operational";
     }
     list psu-module {
       leaf psu-slot {
         type int32;
         description "PSU slot";
       }
       leaf model {
         type string;
       }
       leaf serial-number {
         type string;
         description "Serial number of this component";
       }
       leaf psu-rev {
         type string;
       }
       leaf psu-type {
         type string;
         description "PSU type";
       }
     }
     list service-node-version {
       leaf slot {
         type int32;
       }
       leaf version {
         type string;
         description "Version of this component";
       }
     }
   }
 }
 grouping scb-information-block {
   container brief {
     leaf cross-connect {
       type string;
     }
     leaf packet-scheduling {
       type string;
       description "Packet scheduling knob status";
     }
     list scb {
       leaf slot {
         type int32;
       }
       leaf state {
         type string;
         description "Status of the component";
       }
       leaf comment {
         type string;
       }
       leaf temperature {
         type string;
         description "Temperature of the item";
       }
       leaf cpu-total {
         type int32;
         description "Percentage of CPU utilized";
       }
       leaf cpu-interrupt {
         type int32;
         description "Percentage of CPU utilized by interrupt processing";
       }
       leaf memory-dram-size {
         type int32;
         description "DRAM";
       }
       leaf memory-heap-utilization {
         type int32;
         description "Percentage of heap memory utilized";
       }
       leaf memory-buffer-utilization {
         type int32;
         description "Percentage of buffer memory utilized";
       }
     }
   }
   container verbose {
     leaf cross-connect {
       type string;
     }
     leaf packet-scheduling {
       type string;
       description "Packet scheduling knob status";
     }
     leaf scb-type {
       type string;
     }
     list scb {
       leaf slot {
         type int32;
       }
       leaf state {
         type string;
         description "Status of the component";
       }
       leaf failover-count {
         type int32;
       }
       leaf temperature {
         type string;
         description "Temperature of the item";
       }
       leaf intake-temperature {
         type string;
       }
       leaf exhaust-temperature {
         type string;
       }
       leaf exhaust-a-temperature {
         type string;
         description "Exhaust A temperature";
       }
       leaf exhaust-b-temperature {
         type string;
         description "Exhaust B temperature";
       }
       leaf spp-temperature {
         type string;
       }
       leaf spr-temperature {
         type string;
       }
       leaf cpu-total {
         type int32;
         description "Percentage of CPU utilized";
       }
       leaf cpu-total-ukern {
         type int32;
       }
       leaf cpu-total-rt {
         type int32;
       }
       leaf cpu-interrupt {
         type int32;
         description "Percentage of CPU utilized by interrupt processing";
       }
       leaf memory-heap-utilization {
         type int32;
         description "Percentage of heap memory utilized";
       }
       leaf memory-buffer-utilization {
         type int32;
         description "Percentage of buffer memory utilized";
       }
       leaf memory-dram-size {
         type int32;
         description "DRAM";
       }
       leaf memory-sram-size {
         type int32;
         description "SRAM";
       }
       leaf memory-rldram-size {
         type int32;
         description "RLDRAM";
       }
       leaf memory-xr2-size {
         type int32;
         description "XR2";
       }
       leaf memory-ddr-dram-size {
         type int32;
         description "DDR DRAM";
       }
       leaf asic-name {
         type string;
       }
       leaf asic-information {
         type string;
       }
       leaf start-time {
         type string;
         description "Time this component was started";
       }
       leaf up-time {
         type string;
         description "Length of time this component has been operational";
       }
       leaf comment {
         type string;
       }
       leaf activate-count {
         type int32;
       }
       leaf reset-count {
         type int32;
       }
       leaf max-power-consumption {
         type int32;
       }
       leaf configured-bandwidth {
         type int32;
       }
       leaf operating-bandwidth {
         type int32;
       }
     }
   }
 }
 grouping chassis-location-block {
   list chassis-location-information {
     leaf country-code {
       type string;
       description "Country code";
     }
     leaf postal-code {
       type string;
       description "Postal code";
     }
     leaf npa-nxx {
       type string;
       description "Six digits of the phone number";
     }
     leaf altitude {
       type int32;
       description "Feet above (or below) sea level";
     }
     leaf lata {
       type string;
       description "Long distance service area";
     }
     leaf latitude {
       type string;
       description "Latitude";
     }
     leaf longitude {
       type string;
       description "Longitude";
     }
     leaf vcoord {
       type string;
       description "Bellcore vertical coordinate";
     }
     leaf hcoord {
       type string;
       description "Bellcore horizontal coordinate";
     }
     leaf building {
       type string;
       description "Building information";
     }
     leaf floor {
       type uint32;
       description "Floor in building";
     }
     leaf rack {
       type uint32;
       description "Rack";
     }
   }
 }
 grouping interface-location-name-information-block {
   list location-name-information {
     leaf interface-name {
       type string;
       description "Interface name";
     }
     leaf lcc-number {
       type int32;
       description "LCC Chassis number";
     }
     leaf fpc-number {
       type int32;
       description "FPC number";
     }
   }
 }
 grouping interface-location-slot-information-block {
   list location-slot-information {
     leaf global-fpc-number {
       type int32;
       description "Global FPC number";
     }
   }
 }
 grouping temperature-threshold-information-block {
   list temperature-threshold {
     description "Temperature threshold information for a component on the routing platform.";
   }
 }
 grouping power-management-information-block {
   list power-management {
     description "Information about JSeries Power Management";
     leaf power-mgmt-device {
       type string;
       description "Type of device";
     }
     leaf power-mgmt-low-power {
       type int32;
       description "Low power Rating tokens";
     }
     leaf power-mgmt-high-power {
       type int32;
       description "High power Rating tokens";
     }
     leaf power-mgmt-heat {
       type int32;
       description "Heat Rating tokens";
     }
     leaf power-mgmt-state {
       type string;
       description "Ratings exceed Chassis limits or not";
     }
   }
 }
 grouping in-service-upgrade-status-block {
   list in-service-upgrade-fru-status {
     description "In-Service Software Upgrade status for chassis";
     leaf fru-name {
       type string;
     }
     leaf fru-status {
       type string;
     }
     leaf fru-reason {
       type string;
     }
     list in-service-upgrade-pic-status {
     }
   }
 }
 grouping chassis-oss-map-block {
   leaf chassis-model {
     type string;
     description "Actual chassis model";
   }
   leaf oss-map {
     type string;
     description "Configured OSS chassis model";
   }
 }
 grouping craft-lcd-led-information-block {
   list front-panel-lcd {
     description "Information from the LCD-LED interfaces";
     container front-panel-title {
       leaf name {
         type string;
         description "Name of this component";
       }
       leaf delimiter {
         type string;
       }
     }
     container display-panel-lcd {
       description "Text currently appearing on the LCD interface display";
       leaf display-row-1 {
         type string;
       }
       leaf display-row-2 {
         type string;
       }
     }
     container system-led {
       description "State of system LEDs on the front panel";
       list system-led-display {
         leaf name {
           type string;
           description "Name of this component";
         }
         leaf led-status {
           type string;
         }
       }
     }
     container pic-status-led {
       description "State of QIC STATUS LEDs";
       list pic-status-led-display {
         leaf pic-name {
           type string;
         }
         leaf led-status {
           type string;
         }
       }
     }
     container interface-led {
       description "State of the Interface LEDs on the front panel";
       container two-column {
         description "State of the Interface LEDs on the front panel";
         leaf interface-display-title {
           type string;
         }
         list interface-led-display {
           leaf interface-name {
             type string;
           }
           leaf led-status {
             type string;
           }
         }
       }
       container three-column {
         description "State of the Interface LEDs on the front panel";
         list interface-led-display {
           leaf interface-name {
             type string;
           }
           leaf led-status {
             type string;
           }
           leaf activity-led {
             type string;
             description "State of the Port Activity LED";
           }
         }
       }
       container three-column-mgmt {
         description "State of the Interface LEDs on the front panel";
         list interface-led-display {
           leaf interface-name {
             type string;
           }
           leaf led-status {
             type string;
           }
           leaf activity-led {
             type string;
             description "State of the Port Activity LED";
           }
         }
       }
     }
   }
 }
 grouping satellite-information-block {
   container terse {
     description "Satellite Information";
     list satellite {
       leaf slot-id {
         type int32;
       }
       leaf operation-state {
         type string;
       }
       leaf product-model {
         type string;
       }
       leaf number-of-extended-ports {
         type int32;
       }
       leaf number-of-extended-ports-up {
         type int32;
       }
       leaf version {
         type string;
       }
       list connectivity {
       }
     }
   }
   container unprovision-brief {
     description "Satellite Information";
     list satellite {
       leaf system-id {
         type string;
       }
       leaf serial-number {
         type string;
       }
       leaf operation-state {
         type string;
       }
       list connectivity {
       }
     }
   }
   container brief {
     description "Satellite Information";
     list satellite {
       leaf satellite-alias {
         type string;
       }
       leaf slot-id {
         type int32;
       }
       leaf operation-state {
         type string;
       }
       leaf number-of-extended-ports {
         type int32;
       }
       leaf number-of-extended-ports-up {
         type int32;
       }
       list connectivity {
       }
     }
   }
   container detail {
     description "Satellite Information";
     list satellite {
       leaf satellite-alias {
         type string;
       }
       leaf slot-id {
         type int32;
       }
       leaf operation-state {
         type string;
       }
       leaf reachability {
         type string;
       }
       leaf product-model {
         type string;
       }
       leaf product-family {
         type string;
       }
       leaf serial-number {
         type string;
       }
       leaf system-id {
         type string;
       }
       leaf version {
         type string;
       }
       leaf host-sw-version {
         type string;
       }
       leaf downloaded-sw-version {
         type string;
       }
       leaf management-address {
         type string;
       }
       leaf ufd-config-state {
         type string;
       }
       leaf minimum-link {
         type int32;
       }
       leaf holddown-timer {
         type int32;
       }
       leaf ufd-operation-state {
         type string;
       }
       leaf uplink-port-pinning-state {
         type string;
       }
       leaf local-port-mirror-state {
         type string;
       }
       leaf mode-change-state {
         type string;
       }
       leaf extended-ports-template {
         type string;
       }
       leaf sw-incompatibility-reason {
         type string;
       }
       list connectivity {
         list peer-adjacency {
         }
       }
       list process {
       }
       list uplink-interface-list {
       }
     }
   }
   container extensive {
     description "Satellite Information";
     list satellite {
       leaf satellite-alias {
         type string;
       }
       leaf slot-id {
         type int32;
       }
       leaf operation-state {
         type string;
       }
       leaf number-of-extended-ports {
         type int32;
       }
       leaf number-of-extended-ports-up {
         type int32;
       }
       list connectivity {
       }
       list event-history {
       }
     }
   }
   container unprovision_extensive {
     description "Satellite Information";
     list satellite {
       leaf system-id {
         type string;
       }
       leaf serial-number {
         type string;
       }
       leaf operation-state {
         type string;
       }
       list connectivity {
       }
       list event-history {
       }
     }
   }
 }
 grouping multi-chassis-cluster-information-block {
   list multi-chassis-cluster {
     leaf multi-chassis-cluster-name {
       type string;
     }
     leaf multi-chassis-cluster-state {
       type string;
     }
     leaf peer-chassis-id {
       type int32;
     }
     leaf peer-chassis-serial-number {
       type string;
     }
     leaf local-chassis-id {
       type int32;
     }
     leaf peer-num-of-provisioning-devices {
       type int32;
     }
     leaf num-of-local-online-devices {
       type string;
     }
     leaf peer-num-of-online-devices {
       type int32;
     }
     list event-history {
     }
   }
 }
 grouping multi-chassis-cluster-device-information-block {
   list multi-chassis-cluster-device {
     leaf multi-chassis-cluster-name {
       type string;
     }
     leaf slot-id {
       type int32;
     }
     leaf local-state {
       type string;
     }
     leaf peer-state {
       type string;
     }
     leaf out-of-sync-cause {
       type string;
     }
     list event-history {
     }
   }
 }
 grouping extended-port-information-block {
   list extended-port {
     leaf extended-port-name {
       type string;
     }
     leaf extended-port-state {
       type string;
     }
     leaf recv-request-state {
       type string;
     }
     leaf sent-request-state {
       type string;
     }
     leaf admin-state {
       type string;
     }
     leaf operation-state {
       type string;
     }
     leaf interface-index {
       type int32;
     }
     leaf port-channel-id {
       type int32;
     }
     list event-history {
     }
   }
 }
 grouping upgrade-group-information-block {
   container brief {
     description "Software upgrade group information";
     list upgrade-group {
       leaf group-name {
         type string;
       }
       leaf version {
         type string;
       }
       leaf state {
         type string;
       }
       list upgrade-group-satellite-information {
       }
     }
   }
   container detail {
     description "Software upgrade group information";
     list upgrade-group {
       leaf group-name {
         type string;
       }
       leaf version {
         type string;
       }
       leaf previous-version {
         type string;
       }
       leaf force-host {
         type string;
       }
       list upgrade-group-satellite-information {
       }
     }
   }
 }
 grouping adjacency-information-block {
   list adjacency-entry {
     leaf interface-name {
       type string;
     }
     leaf protocol-state {
       type string;
     }
     leaf port-information {
       type string;
     }
     leaf system-name {
       type string;
     }
     leaf product-model {
       type string;
     }
     leaf version {
       type string;
     }
     container adjacency-peer-entry {
     }
     container link-keepalive {
     }
     list adjacency-down-history {
     }
     list local-assigned-primary-address {
     }
     list event-history {
     }
   }
 }
 grouping adjacency-statistics-block {
   container adjacency-statistics-entry {
     leaf interface-name {
       type string;
     }
     list interface-statistics {
     }
     list general-statistics {
     }
   }
 }
 grouping satellite-interface-information-block {
   list interface-entry {
     leaf interface-name {
       type string;
     }
     leaf interface-state {
       type string;
     }
     leaf interface-type {
       type string;
     }
     list operation-address-list {
     }
     list event-history {
     }
   }
 }
 grouping satellite-software-information-block {
   container brief {
     description "Satellite software installed";
     list satellite-package {
       leaf version {
         type string;
       }
       leaf package-targets {
         type string;
       }
       leaf group-name {
         type string;
       }
       list package-platform {
       }
     }
   }
   container detail {
     description "Satellite software installed";
     list satellite-package {
       leaf version {
         type string;
       }
       leaf package-targets {
         type string;
       }
       leaf group-name {
         type string;
       }
       leaf previous-group-name {
         type string;
       }
       list package-platform {
         list model-list {
         }
       }
     }
   }
 }
 grouping satellite-cluster-information-block {
   container terse {
     description "Satellite Cluster Information";
     list satellite-cluster {
       list cluster-info {
       }
       list cluster-device-info {
       }
     }
   }
   container brief {
     description "Satellite Cluster Information";
     list satellite-cluster {
       list cluster-info {
       }
       list cluster-device-info {
         container transit-slot {
         }
         list cluster-connectivity {
         }
       }
     }
   }
   container detail {
     description "Satellite Cluster Information";
     list satellite-cluster {
       list cluster-info {
       }
       list cluster-device-info {
         container transit-slot {
         }
         list cluster-connectivity {
         }
       }
     }
   }
   container extensive {
     description "Satellite Cluster Information";
     list satellite-cluster {
       list cluster-info {
       }
       list cluster-device-info {
         container transit-slot {
         }
         list cluster-connectivity {
         }
       }
       list event-history {
       }
     }
   }
 }
 }
