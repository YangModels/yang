/*
 * Copyright (c) 2017 Juniper Networks, Inc.
 * All rights reserved.
 */
 module show-amt {
  namespace "http://yang.juniper.net/yang/1.1/jrpc/show-amt/junos/17.2R1.13";
  prefix show-amt;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-amt-tunnel-information {
     description "Show AMT tunnel parameters";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "brief" {
             description "Display brief output (default)";
           }
           enum "detail" {
             description "Display detailed output";
           }
         }
       }
     }
     output {
       container amt-tunnel-information {
         uses amt-tunnel-information-block;
       }
     }
   }
   rpc get-amt-tunnel-interface {
     description "AMT tunnel interface";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "brief" {
             description "Display brief output (default)";
           }
           enum "detail" {
             description "Display detailed output";
           }
         }
       }
       leaf interface {
         description "Name of the interface";
         type string;
         mandatory true;
       }
     }
     output {
       container amt-tunnel-information {
         uses amt-tunnel-information-block;
       }
     }
   }
   rpc get-amt-tunnel-gateway-address {
     description "AMT tunnel gateway address";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "brief" {
             description "Display brief output (default)";
           }
           enum "detail" {
             description "Display detailed output";
           }
         }
       }
       leaf address {
         description "IP address of the gateway";
         type string;
         mandatory true;
       }
       leaf port {
         description "UDP port of the gateway";
         type uint16 {
           range "1 .. 65535";
         }
       }
     }
     output {
       container amt-tunnel-information {
         uses amt-tunnel-information-block;
       }
     }
   }
   rpc get-amt-summary {
     description "Show AMT configuration summary";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
     }
     output {
       container amt-summary {
         uses amt-summary-block;
       }
     }
   }
   rpc get-amt-statistics {
     description "Show AMT statistics summary";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
     }
     output {
       container amt-instance-statistics {
         uses amt-instance-statistics-block;
       }
     }
   }
 grouping amt-tunnel-information-block {
   list amt-tunnel {
     description "Display AMT tunnel information";
     list brief {
       description "Display AMT tunnel information";
       leaf amt-tunnel-gateway-address {
         type string;
         description "AMT gateway address for the tunnel";
       }
       leaf amt-tunnel-gateway-port {
         type int32;
         description "AMT gateway UDP port for the tunnel";
       }
       leaf amt-tunnel-interface {
         type string;
         description "AMT tunnel logical interface";
       }
       leaf amt-tunnel-state {
         type string;
         description "AMT tunnel logical interface";
       }
       leaf amt-inactivity-timeout {
         type int32;
         description "AMT tunnel inactivity timeout";
       }
       leaf amt-tunnel-gateway-nonce {
         type int32;
         description "AMT membership request nonce";
       }
       leaf amt-tunnel-gateway-mac {
         type string;
         description "AMT membership request mac";
       }
       leaf amt-tunnel-multicast-groups {
         type int32;
         description "Number of active multicast groups on this AMT tunnel";
       }
       list mgm-group {
         list igmp-terse {
           leaf multicast-group-address {
             type ipaddr;
             description "Group address";
           }
           leaf mgm-group-mode-type {
             type string;
             description "Group operational mode (Include/Exclude).";
           }
           leaf multicast-source-address {
             type ipaddr;
             description "Source address";
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list igmp {
           leaf multicast-group-address {
             type ipaddr;
             description "Group address";
           }
           leaf mgm-group-mode-type {
             type string;
             description "Group operational mode (Include/Exclude).";
           }
           leaf multicast-source-address {
             type ipaddr;
             description "Source address";
           }
           leaf last-address {
             type ipaddr;
           }
           leaf mgm-timeout {
             type int32;
           }
           leaf mgm-type {
             type string;
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list igmp-detail {
           leaf multicast-group-address {
             type ipaddr;
             description "Group address";
           }
           leaf mgm-group-mode-type {
             type string;
             description "Group operational mode (Include/Exclude).";
           }
           leaf multicast-source-address {
             type ipaddr;
             description "Source address";
           }
           leaf mgm-source-timeout {
             type int32;
             description "Amount of time for which the traffic from source is forwarded.";
           }
           leaf last-address {
             type ipaddr;
           }
           leaf mgm-timeout {
             type int32;
           }
           leaf mgm-type {
             type string;
           }
           leaf mgm-type-instance {
             type string;
           }
           leaf mgm-group-output-interface {
             type string;
             description "Group output interface";
           }
           leaf mgm-output-interface-status {
             type string;
             description "Group output interface status";
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list mld-terse {
           leaf multicast-group-address {
             type ipaddr;
             description "Group address";
           }
           leaf mgm-group-mode-type {
             type string;
             description "Group operational mode (Include/Exclude).";
           }
           leaf multicast-source-address {
             type ipaddr;
             description "Source address";
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list mld {
           leaf multicast-group-address {
             type ipaddr;
             description "Group address";
           }
           leaf mgm-group-mode-type {
             type string;
             description "Group operational mode (Include/Exclude).";
           }
           leaf multicast-source-address {
             type ipaddr;
             description "Source address";
           }
           leaf last-address {
             type ipaddr;
           }
           leaf mgm-timeout {
             type int32;
           }
           leaf mgm-type {
             type string;
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list mld-detail {
           leaf multicast-group-address {
             type ipaddr;
             description "Group address";
           }
           leaf mgm-group-mode-type {
             type string;
             description "Group operational mode (Include/Exclude).";
           }
           leaf multicast-source-address {
             type ipaddr;
             description "Source address";
           }
           leaf mgm-source-timeout {
             type int32;
             description "Amount of time for which the traffic from source is forwarded.";
           }
           leaf last-address {
             type ipaddr;
           }
           leaf mgm-timeout {
             type int32;
           }
           leaf mgm-type {
             type string;
           }
           leaf mgm-group-output-interface {
             type string;
             description "Group output interface";
           }
           leaf mgm-output-interface-status {
             type string;
             description "Group output interface status";
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
       }
       container amt-tunnel-message-count {
         description "Control packets received from the gateway";
         leaf amt-request-message {
           type int32;
           description "Number of AMT membership request messages received";
         }
         leaf amt-membership-update-message {
           type int32;
           description "Number of AMT membership updates received";
         }
       }
     }
     list detail {
       description "Display AMT tunnel information";
       leaf amt-tunnel-gateway-address {
         type string;
         description "AMT gateway address for the tunnel";
       }
       leaf amt-tunnel-gateway-port {
         type int32;
         description "AMT gateway UDP port for the tunnel";
       }
       leaf amt-tunnel-interface {
         type string;
         description "AMT tunnel logical interface";
       }
       leaf amt-tunnel-state {
         type string;
         description "AMT tunnel logical interface";
       }
       leaf amt-inactivity-timeout {
         type int32;
         description "AMT tunnel inactivity timeout";
       }
       leaf amt-tunnel-gateway-nonce {
         type int32;
         description "AMT membership request nonce";
       }
       leaf amt-tunnel-gateway-mac {
         type string;
         description "AMT membership request mac";
       }
       leaf amt-tunnel-multicast-groups {
         type int32;
         description "Number of active multicast groups on this AMT tunnel";
       }
       list mgm-group {
         leaf multicast-group-address {
           type ipaddr;
           description "Group address";
         }
         leaf mgm-group-mode-type {
           type string;
           description "Group operational mode (Include/Exclude).";
         }
         leaf multicast-source-address {
           type ipaddr;
           description "Source address";
         }
         list igmp-terse {
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list igmp {
           leaf multicast-group-address {
             type ipaddr;
             description "Group address";
           }
           leaf mgm-group-mode-type {
             type string;
             description "Group operational mode (Include/Exclude).";
           }
           leaf multicast-source-address {
             type ipaddr;
             description "Source address";
           }
           leaf last-address {
             type ipaddr;
           }
           leaf mgm-timeout {
             type int32;
           }
           leaf mgm-type {
             type string;
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list igmp-detail {
           leaf multicast-group-address {
             type ipaddr;
             description "Group address";
           }
           leaf mgm-group-mode-type {
             type string;
             description "Group operational mode (Include/Exclude).";
           }
           leaf multicast-source-address {
             type ipaddr;
             description "Source address";
           }
           leaf mgm-source-timeout {
             type int32;
             description "Amount of time for which the traffic from source is forwarded.";
           }
           leaf last-address {
             type ipaddr;
           }
           leaf mgm-timeout {
             type int32;
           }
           leaf mgm-type {
             type string;
           }
           leaf mgm-type-instance {
             type string;
           }
           leaf mgm-group-output-interface {
             type string;
             description "Group output interface";
           }
           leaf mgm-output-interface-status {
             type string;
             description "Group output interface status";
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list mld-terse {
           leaf multicast-group-address {
             type ipaddr;
             description "Group address";
           }
           leaf mgm-group-mode-type {
             type string;
             description "Group operational mode (Include/Exclude).";
           }
           leaf multicast-source-address {
             type ipaddr;
             description "Source address";
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list mld {
           leaf multicast-group-address {
             type ipaddr;
             description "Group address";
           }
           leaf mgm-group-mode-type {
             type string;
             description "Group operational mode (Include/Exclude).";
           }
           leaf multicast-source-address {
             type ipaddr;
             description "Source address";
           }
           leaf last-address {
             type ipaddr;
           }
           leaf mgm-timeout {
             type int32;
           }
           leaf mgm-type {
             type string;
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
         list mld-detail {
           leaf multicast-group-address {
             type ipaddr;
             description "Group address";
           }
           leaf mgm-group-mode-type {
             type string;
             description "Group operational mode (Include/Exclude).";
           }
           leaf multicast-source-address {
             type ipaddr;
             description "Source address";
           }
           leaf mgm-source-timeout {
             type int32;
             description "Amount of time for which the traffic from source is forwarded.";
           }
           leaf last-address {
             type ipaddr;
           }
           leaf mgm-timeout {
             type int32;
           }
           leaf mgm-type {
             type string;
           }
           leaf mgm-group-output-interface {
             type string;
             description "Group output interface";
           }
           leaf mgm-output-interface-status {
             type string;
             description "Group output interface status";
           }
           list host-record {
             leaf record-type {
               type string;
             }
             leaf receiver {
               type ipaddr;
             }
             leaf record-timeout {
               type int32;
             }
           }
           list reverse-oif {
             leaf oif-name {
               type string;
               description "Reverse OIF name";
             }
             leaf host-count {
               type int32;
               description "Host reference count";
             }
           }
         }
       }
       container amt-tunnel-message-count {
         description "Control packets received from the gateway";
         leaf amt-request-message {
           type int32;
           description "Number of AMT membership request messages received";
         }
         leaf amt-membership-update-message {
           type int32;
           description "Number of AMT membership updates received";
         }
       }
     }
   }
 }
 grouping amt-summary-block {
   leaf amt-anycast-prefix {
     type string;
     description "AMT anycast prefix";
   }
   leaf amt-anycast-address {
     type string;
     description "AMT anycast address";
   }
   leaf amt-local-address {
     type string;
     description "AMT local address";
   }
   leaf amt-tunnel-limit {
     type int32;
     description "Maximum number of AMT tunnels";
   }
   leaf amt-active-tunnels {
     type int32;
     description "Number of currently active AMT tunnels";
   }
   leaf amt-unicast-stream-limit {
     type int32;
     description "Maximum number of unicast streams";
   }
   leaf amt-active-unicast-streams {
     type int32;
     description "Number of currently active AMT unicast streams";
   }
 }
 grouping amt-instance-statistics-block {
   leaf amt-relay-discovery-messages {
     type int32;
     description "Number of AMT relay discovery messages received";
   }
   leaf amt-membership-request-messages {
     type int32;
     description "Number of AMT membership request messages received";
   }
   leaf amt-membership-update-messages {
     type int32;
     description "Number of AMT membership update messages received";
   }
   leaf amt-relay-advertisement-messages {
     type int32;
     description "Number of AMT relay advertisement messages sent";
   }
   leaf amt-membership-query-messages {
     type int32;
     description "Number of AMT membership query messages sent";
   }
   leaf amt-incomplete-packet {
     type int32;
     description "Number of incomplete AMT messages received";
   }
   leaf amt-invalid-mac {
     type int32;
     description "Number of AMT membership update messages received with invalid MAC";
   }
   leaf amt-unexpected-type {
     type int32;
     description "Number of AMT messages received with unexpected messages type";
   }
   leaf amt-relay-discovery-invalid-address {
     type int32;
     description "Number of AMT relay discovery messages received with invalid address";
   }
   leaf amt-membership-request-invalid-address {
     type int32;
     description "Number of AMT membership request messages received with invalid address";
   }
   leaf amt-membership-update-invalid-address {
     type int32;
     description "Number of AMT membership update messages received with invalid address";
   }
   leaf amt-incomplete-relay-discovery {
     type int32;
     description "Number of incomplete AMT relay discovery messages";
   }
   leaf amt-incomplete-membership-request {
     type int32;
     description "Number of incomplete AMT membership request messages";
   }
   leaf amt-incomplete-membership-update {
     type int32;
     description "Number of incomplete AMT membership update messages";
   }
   leaf amt-no-active-gateway {
     type int32;
     description "Number AMT membership update messages received with no active gateway";
   }
   leaf amt-invalid-inner-packet-checksum {
     type int32;
     description "Number of AMT packets with invalid inner packet checksum";
   }
   leaf amt-gateways-timed-out {
     type int32;
     description "Number of AMT gateways that have timed out due to inactivity";
   }
   container normal {
     description "Display a summary of AMT instance statistics";
   }
 }
 }
