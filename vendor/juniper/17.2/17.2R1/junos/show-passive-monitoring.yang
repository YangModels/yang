/*
 * Copyright (c) 2017 Juniper Networks, Inc.
 * All rights reserved.
 */
 module show-passive-monitoring {
  namespace "http://yang.juniper.net/yang/1.1/jrpc/show-passive-monitoring/junos/17.2R1.13";
  prefix show-passive-monitoring;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-passive-monitoring-information {
     description "Show information about passive monitoring";
     output {
       container passive-monitoring-information {
         uses passive-monitoring-information-block;
       }
     }
   }
   rpc get-passive-monitoring-usage-information {
     description "Show CPU utilization";
     input {
       leaf interface-name {
         description "Name of monitoring interface, wildcard, or 'all'";
         type string;
         mandatory true;
       }
     }
   }
   rpc get-passive-monitoring-memory-information {
     description "Show memory utilization";
     input {
       leaf interface-name {
         description "Name of monitoring interface, wildcard, or 'all'";
         type string;
         mandatory true;
       }
     }
   }
   rpc get-passive-monitoring-flow-information {
     description "Show flow statistics";
     input {
       leaf interface-name {
         description "Name of monitoring interface, wildcard, or 'all'";
         type string;
         mandatory true;
       }
     }
   }
   rpc get-passive-monitoring-error-information {
     description "Show error statistics";
     input {
       leaf interface-name {
         description "Name of monitoring interface, wildcard, or 'all'";
         type string;
         mandatory true;
       }
     }
   }
   rpc get-passive-monitoring-status-information {
     description "Show status information";
     input {
       leaf interface-name {
         description "Name of monitoring interface, wildcard, or 'all'";
         type string;
         mandatory true;
       }
     }
   }
 grouping passive-monitoring-information-block {
   leaf interface-name {
     type string;
     description "Physical interface name";
   }
   leaf local-index {
     type int32;
     description "Local physical interface index";
   }
   leaf pic-status {
     type string;
     description "Current interface state";
   }
   container usage-information {
     description "Passive monitoring CPU utilization";
     leaf uptime {
       type int32;
       description "CPU uptime, in milliseconds";
     }
     leaf inttime {
       type int32;
       description "CPU interrupt time, in microseconds";
     }
     leaf five-second-load {
       type int32;
       description "5-second load";
     }
     leaf one-minute-load {
       type int32;
       description "1-minute load";
     }
   }
   container memory-information {
     description "Passive monitoring memory utilization";
     leaf allocation-count {
       type int32;
       description "Flow record allocations";
     }
     leaf free-count {
       type int32;
       description "Flow record frees";
     }
     leaf maximum-allocated {
       type int32;
       description "Maximum flow records allocated";
     }
     leaf allocations-per-second {
       type int32;
       description "Flow record allocations per second";
     }
     leaf frees-per-second {
       type int32;
       description "Flow record frees per second";
     }
     leaf memory-used {
       type int32;
       description "Total memory used";
     }
     leaf memory-free {
       type int32;
       description "Total memory free";
     }
   }
   container flow-information {
     description "Passive monitoring flow information";
     leaf flow-packets {
       type int32;
       description "Flow packets";
     }
     leaf flow-bytes {
       type int32;
       description "Flow bytes";
     }
     leaf flow-packets-ten-second-rate {
       type int32;
       description "Flow packets 10-second rate";
     }
     leaf flow-bytes-ten-second-rate {
       type int32;
       description "Flow bytes 10-second rate";
     }
     leaf active-flows {
       type int32;
       description "Active flows";
     }
     leaf flows {
       type int32;
       description "Flows";
     }
     leaf flows-exported {
       type int32;
       description "Flows exported";
     }
     leaf flow-packets-exported {
       type int32;
       description "Flows packets exported";
     }
     leaf flows-expired {
       type int32;
       description "Flows inactive timed out";
     }
     leaf flows-aged {
       type int32;
       description "Flows active timed out";
     }
   }
   container error-information {
     description "Passive monitoring error information";
     leaf error-packets-dropped-no-memory {
       type int32;
       description "Number of packets dropped because memory is exhausted";
     }
     leaf error-packets-dropped-not-ip {
       type int32;
       description "Number of packets dropped because they are not IP";
     }
     leaf error-packets-dropped-not-ipv4 {
       type int32;
       description "Number of packets dropped because they are not IPv4";
     }
     leaf error-packets-too-small {
       type int32;
       description "Number of packets dropped because their header is too small";
     }
     leaf error-allocation-failures {
       type int32;
       description "Number of failed attempts to allocate memory";
     }
     leaf error-free-failures {
       type int32;
       description "Number of failed attempts to free memory";
     }
     leaf error-free-list-failures {
       type int32;
       description "Number of operations that failed because free list memory is exhausted";
     }
     leaf error-memory-warning {
       type string;
       description "Reached low memory condition";
     }
     leaf error-memory-overload {
       type string;
       description "Whether memory is exhausted";
     }
     leaf error-packets-per-second-overload {
       type string;
       description "Whether the number of incoming packets exceeds the designed per-second limit";
     }
     leaf error-bytes-per-second-overload {
       type string;
       description "Whether the number of incoming bytes exceeds the designed per-second limit";
     }
   }
   container status-information {
     description "Passive monitoring status information";
     leaf status-group-index {
       type int32;
       description "Group index";
     }
     leaf status-export-interval {
       type int32;
       description "Export interval, in seconds";
     }
     leaf status-export-format {
       type int32;
       description "Export format";
     }
     leaf status-proto {
       type string;
       description "Protocol";
     }
     leaf status-engine-type {
       type int32;
       description "Engine type";
     }
     leaf status-engine-id {
       type int32;
       description "Engine ID";
     }
     leaf status-route-record-count {
       type int32;
       description "Route record count";
     }
     leaf status-ifl-snmp-map-count {
       type int32;
       description "Local index to SNMP index count";
     }
     leaf status-as-count {
       type int32;
       description "Autonomous system number count";
     }
     leaf status-monitor-time-set {
       type string;
       description "Time set on PIC";
     }
     leaf status-monitor-config-set {
       type string;
       description "Configuration set on PIC";
     }
     leaf status-monitor-route-record-set {
       type string;
       description "Route records set on PIC";
     }
     leaf status-monitor-ifl-snmp-set {
       type string;
       description "Local index to SNMP index map set on PIC";
     }
   }
 }
 }
