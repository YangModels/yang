/*
 * Copyright (c) 2017 Juniper Networks, Inc.
 * All rights reserved.
 */
 module show-ilmi {
  namespace "http://yang.juniper.net/yang/1.1/jrpc/show-ilmi/junos/17.2R1.13";
  prefix show-ilmi;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ilmi-information {
     description "Show interim local management interface information";
     input {
       leaf level {
         default "all";
         type enumeration {
           enum "all" {
             description "Show ILMI information for all interfaces";
           }
         }
       }
     }
     output {
       container ilmi-information {
         uses ilmi-information-block;
       }
     }
   }
   rpc get-ilmi-statistics {
     description "Show ILMI statistics";
     output {
       container ilmi-statistics {
         uses ilmi-statistics-block;
       }
     }
   }
   rpc get-ilmi-interface-information {
     description "Show ILMI information for interface";
     input {
       leaf interface_name {
         description "Interface name";
         type string;
         mandatory true;
       }
     }
     output {
       container ilmi-interface-information {
         uses ilmi-interface-information-block;
       }
     }
   }
 grouping ilmi-information-block {
   container ilmi-interface-information {
     leaf interface-name {
       type string;
     }
     leaf atm-vpi {
       type int32;
     }
     leaf atm-vci {
       type int32;
     }
     leaf peer-ipaddr {
       type ipaddr;
     }
     leaf peer-interface-name {
       type string;
     }
   }
 }
 grouping ilmi-statistics-block {
   container ilmi-input-statistics {
     leaf packets {
       type int32;
     }
     leaf bad-versions {
       type int32;
     }
     leaf bad-community-names {
       type int32;
     }
     leaf bad-community-uses {
       type int32;
     }
     leaf asn-parse-errors {
       type int32;
     }
     leaf too-bigs {
       type int32;
     }
     leaf no-such-names {
       type int32;
     }
     leaf bad-values {
       type int32;
     }
     leaf read-onlys {
       type int32;
     }
     leaf general-errors {
       type int32;
     }
     leaf total-request-varbinds {
       type int32;
     }
     leaf total-set-varbinds {
       type int32;
     }
     leaf get-requests {
       type int32;
     }
     leaf get-nexts {
       type int32;
     }
     leaf set-requests {
       type int32;
     }
     leaf get-responses {
       type int32;
     }
     leaf traps {
       type int32;
     }
     leaf silent-drops {
       type int32;
     }
     leaf proxy-drops {
       type int32;
     }
   }
   container ilmi-output-statistics {
     leaf packets {
       type int32;
     }
     leaf too-bigs {
       type int32;
     }
     leaf no-such-names {
       type int32;
     }
     leaf bad-values {
       type int32;
     }
     leaf general-errors {
       type int32;
     }
     leaf get-requests {
       type int32;
     }
     leaf get-nexts {
       type int32;
     }
     leaf set-requests {
       type int32;
     }
     leaf get-responses {
       type int32;
     }
     leaf traps {
       type int32;
     }
   }
 }
 grouping ilmi-interface-information-block {
   leaf interface-name {
     type string;
   }
   leaf atm-vpi {
     type int32;
   }
   leaf atm-vci {
     type int32;
   }
   leaf peer-ipaddr {
     type ipaddr;
   }
   leaf peer-interface-name {
     type string;
   }
 }
 }
