/*
 * Copyright (c) 2017 Juniper Networks, Inc.
 * All rights reserved.
 */
 module request {
  namespace "http://yang.juniper.net/yang/1.1/jrpc/request/junos/17.2R1.13";
  prefix request;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc request-path-computation-client-main-pce {
     description "Request new active PCE";
     input {
       leaf pce-id {
         description "PCE ID from configuration";
         type string;
         mandatory true;
       }
     }
   }
   rpc request-path-computation-retry-delegation {
     description "Request new active PCE";
     input {
       leaf lsp-name {
         description "Name of static label-switched-path";
         type string;
         mandatory true;
       }
     }
   }
   rpc request-line-card-login {
     description "Connect to line card";
     input {
       leaf member {
         description "Member ID";
         type int32 {
           range "0 .. 63";
         }
         mandatory true;
       }
     }
   }
   rpc request-virtual-chassis-reactivate {
     description "Make active from inactive-split mode";
   }
   rpc request-virtual-chassis-renumber {
     description "Change member ID";
     input {
       leaf member-id {
         description "Current member ID";
         type int32 {
           range "0 .. 63";
         }
         mandatory true;
       }
       leaf new-member-id {
         description "New member ID";
         type int32 {
           range "0 .. 63";
         }
         mandatory true;
       }
     }
   }
   rpc request-virtual-chassis-recycle {
     description "Recycle member ID";
     input {
       leaf member-id {
         description "Member ID";
         type int32 {
           range "0 .. 63";
         }
         mandatory true;
       }
     }
   }
   rpc request-virtual-chassis-vc-port-set-interface {
     description "Member's virtual chassis interface";
     input {
       leaf interface-name {
         description "Name of dedicated virtual chassis interface";
         type string;
         mandatory true;
       }
       leaf disable {
         description "Disable virtual chassis interface";
         type empty;
       }
     }
   }
   rpc request-virtual-chassis-vc-port-set-pic-slot {
     description "Member's PIC slot";
     input {
       leaf pic-slot {
         description "PIC slot number";
         type uint32 {
           range "0 .. 3";
         }
         mandatory true;
       }
       leaf port {
         description "Port number";
         type uint32 {
           range "0 .. 45";
         }
         mandatory true;
       }
     }
   }
   rpc request-virtual-chassis-vc-port-set-fpc-slot {
     description "Member's FPC slot";
     input {
       leaf fpc-slot {
         description "FPC slot number";
         type uint32 {
           range "0 .. 63";
         }
         mandatory true;
       }
       leaf pic-slot {
         description "PIC slot number";
         type uint32 {
           range "0 .. 3";
         }
         mandatory true;
       }
       leaf port {
         description "Port number";
         type uint32 {
           range "0 .. 45";
         }
         mandatory true;
       }
     }
   }
   rpc request-virtual-chassis-vc-port-delete-pic-slot {
     description "Member's PIC slot";
     input {
       leaf pic-slot {
         description "PIC slot number";
         type uint32 {
           range "0 .. 3";
         }
         mandatory true;
       }
       leaf port {
         description "Port number";
         type uint32 {
           range "0 .. 45";
         }
         mandatory true;
       }
     }
   }
   rpc request-virtual-chassis-vc-port-delete-fpc-slot {
     description "Member's FPC slot";
     input {
       leaf fpc-slot {
         description "FPC slot number";
         type uint32 {
           range "0 .. 63";
         }
         mandatory true;
       }
       leaf pic-slot {
         description "PIC slot number";
         type uint32 {
           range "0 .. 3";
         }
         mandatory true;
       }
       leaf port {
         description "Port number";
         type uint32 {
           range "0 .. 45";
         }
         mandatory true;
       }
     }
   }
   rpc request-virtual-chassis-vc-port-diag-optics {
     description "Virtual chassis port diagnostics optics";
     input {
       leaf interface-name {
         description "Name of virtual chassis port";
         type string;
       }
     }
   }
   rpc req-virtual-chassis-mode {
     description "Set a member's mode (Warning: member's mode must be consistent)";
     input {
       leaf fabric {
         description "Set to virtual chassis fabric mode";
         type empty;
       }
       leaf mixed {
         description "Allow devices from different product families to become members";
         type empty;
       }
       leaf disable {
         description "Disable specified mode";
         type empty;
       }
       leaf reboot {
         description "Reboot system after changing mode";
         type empty;
       }
     }
   }
   rpc set-virtual-chassis-member-id {
     description "Set virtual-chassis information";
     input {
       leaf member {
         description "Virtual-Chassis member number";
         type int32 {
           range "0 .. 63";
         }
         mandatory true;
       }
       leaf slots-per-chassis {
         description "Virtual-Chassis FPC slots per chassis number";
         type enumeration {
           enum "12" {
             description "12 FPC slots per chassis";
           }
           enum "20" {
             description "20 FPC slots per chassis";
           }
         }
       }
     }
   }
   rpc delete-virtual-chassis-member-id {
     description "Delete virtual-chassis information";
   }
   rpc get-virtual-chassis-diagnostic-information {
     description "Device reachability diagnostics";
     input {
       leaf test-name {
         description "Name of the test";
         type string {
           length "1 .. 20";
         }
         mandatory true;
       }
       leaf destination-device {
         description "Probe destination (global) device ID";
         type uint32;
       }
       leaf destination-fpc {
         description "Probe destination FPC";
         type uint32;
       }
       leaf destination-ip-address {
         description "IP address of destination FPC";
         type ipaddr;
       }
       leaf source-fpc {
         description "Probe initiator FPC";
         type uint32;
       }
       leaf source-ip-address {
         description "IP address of source FPC";
         type ipaddr;
       }
       leaf probe-size {
         description "Size of one probe in bytes";
         default "56";
         type uint32 {
           range "56 .. 1500";
         }
       }
       leaf probe-count {
         description "Number of probes in a test";
         default "5";
         type uint32 {
           range "1 .. 10";
         }
       }
       leaf probe-pattern {
         description "Payload pattern byte in the probe (0x00-0xff)";
         default "0x00";
         type string {
           junos:posix-pattern "^0(x|X)([0-9|a-f|A-F])([0-9|a-f|A-F])$";
           junos:pattern-message "Must be hexadecimal bit pattern in (0x00..0xff)";
         }
       }
       leaf probe-interval {
         description "Duration between successive probes";
         default "1";
         units "seconds";
         type uint32 {
           range "1 .. 3";
         }
       }
       leaf test-interval {
         description "Time interval to perform this test again";
         default "1";
         units "seconds";
         type uint32 {
           range "1 .. 5";
         }
       }
       leaf test-count {
         description "Number of times this test to be performed";
         default "1";
         type uint32 {
           range "1 .. 3";
         }
       }
     }
     output {
       container virtual-chassis-diagnostic-information {
         uses virtual-chassis-diagnostic-information-block;
       }
     }
   }
   rpc switch-vc-routing-engine-protocol-master {
     description "Toggle mastership between VC members";
     input {
       leaf check {
         description "Check status of graceful switchover";
         type empty;
       }
     }
   }
 grouping virtual-chassis-diagnostic-information-block {
   container test-information {
     description "Details of the test";
     leaf test-name {
       type string;
       description "Name of the Device Reachability test";
     }
   }
   list current-test {
     description "Serial number of the test being performed";
     leaf test-number {
       type string;
       description "Serial Number of the test";
     }
   }
   list device-reachability-information {
     description "Device reachability statistics";
     leaf reachability-acknowledge {
       type string;
     }
     leaf connectivity-statistics-header {
       type string;
     }
     leaf session-information {
       type string;
     }
     leaf session-id {
       type uint32;
       description "Session ID";
     }
     leaf packet-response-information {
       type string;
     }
     leaf packet-count {
       type uint32;
       description "Total number of packets sent";
     }
     leaf packets-sent {
       type uint64;
     }
     leaf packets-received {
       type uint64;
     }
     leaf packets-sendfail {
       type uint32;
       description "Number of packets dropped";
     }
     leaf packet-breakup-information {
       type string;
     }
     leaf packets-unknown {
       type uint32;
       description "Number of unknown packets";
     }
     leaf packets-timedout {
       type uint32;
       description "Number of packets received after timeout";
     }
     leaf packets-duplicate-reply {
       type uint32;
       description "Number of duplicate reply packets";
     }
     leaf round-trip-information {
       type string;
     }
     leaf round-trip-time-minimum {
       type uint32;
       description "Minimum round trip time in seconds";
     }
     leaf round-trip-time-average {
       type uint32;
       description "Average round trip time in seconds";
     }
     leaf round-trip-time-maximum {
       type uint32;
       description "Minimum round trip time in seconds";
     }
     leaf test-interval {
       type string;
       description "Interval between successive tests";
     }
   }
   list virtual-chassis-diagnostic-error {
     leaf name {
       type string;
     }
   }
 }
 }
