/*
 * Copyright (c) 2017 Juniper Networks, Inc.
 * All rights reserved.
 */
 module show-isis {
  namespace "http://yang.juniper.net/yang/1.1/jrpc/show-isis/junos/17.2R1.13";
  prefix show-isis;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-isis-adjacency-information {
     description "Show IS-IS adjacency database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf system-id {
         description "System ID of intermediate system";
         type string;
       }
     }
     output {
       container isis-adjacency-information {
         uses isis-adjacency-information-block;
       }
     }
   }
   rpc get-isis-adjacency-holddown-information {
     description "Show IS-IS adjacency-holddown status";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf level {
         description "Number of IS-IS level";
         type uint32 {
           range "1 .. 2";
         }
       }
     }
     output {
       container isis-adjacency-holddown-information {
         uses isis-adjacency-holddown-information-block;
       }
     }
   }
   rpc get-isis-authentication-information {
     description "Show IS-IS authentication information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
     }
     output {
       container isis-authentication-information {
         uses isis-authentication-information-block;
       }
     }
   }
   rpc get-isis-bgporr-information {
     description "Show BGP optimal route reflection groups";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf destination {
         description "IP address and optional prefix length of destination";
         type ipprefix;
       }
       leaf instance {
         description "Name of IS-IS instance";
         type string;
       }
       leaf group {
         description "BGP optimal route-reflection peer group name";
         type string;
       }
     }
     output {
       container isis-bgporr-information {
         uses isis-bgporr-information-block;
       }
     }
   }
   rpc get-isis-backup-lsp-information {
     description "Show IS-IS MPLS backup LSP information";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container isis-backup-mplsp-information {
         uses isis-backup-mplsp-information-block;
       }
     }
   }
   rpc get-isis-backup-spf-results-information {
     description "Show results from backup SPF runs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf destination {
         description "Hostname or System-ID of remote destination";
         type string;
       }
       leaf instance {
         description "IS-IS instance";
         type string;
       }
       leaf level {
         description "Number of IS-IS level";
         type uint32 {
           range "1 .. 2";
         }
       }
       leaf no-coverage {
         description "Destinations with no backup coverage";
         type empty;
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-spf-information {
         uses isis-spf-information-block;
       }
     }
   }
   rpc get-isis-backup-coverage-information {
     description "Show IS-IS backup coverage";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
     }
     output {
       container isis-backup-coverage-information {
         uses isis-backup-coverage-information-block;
       }
     }
   }
   rpc get-isis-context-identifier-information {
     description "Show IS-IS context-identifier information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf instance {
         description "Name of IS-IS instance";
         type string;
       }
     }
     output {
       container isis-context-information {
         uses isis-context-information-block;
       }
     }
   }
   rpc get-isis-context-identifier-origin-information {
     description "Show IS-IS context-identifier information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf id_addr {
         description "Context identifier address of session";
         type ipprefix;
         mandatory true;
       }
       leaf instance {
         description "Name of IS-IS instance";
         type string;
       }
     }
     output {
       container isis-context-information {
         uses isis-context-information-block;
       }
     }
   }
   rpc get-isis-database-information {
     description "Show IS-IS link-state database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf level {
         description "Number of IS-IS level";
         type uint32 {
           range "1 .. 2";
         }
       }
       leaf system-id {
         description "System ID of IS";
         type string;
       }
     }
     output {
       container isis-database-information {
         uses isis-database-information-block;
       }
     }
   }
   rpc get-isis-hostname-information {
     description "Show IS-IS hostname database";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container isis-hostname-information {
         uses isis-hostname-information-block;
       }
     }
   }
   rpc get-isis-interface-information {
     description "Show IS-IS interface information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf interface-name {
         description "Name of interface";
         type string;
       }
     }
     output {
       container isis-interface-information {
         uses isis-interface-information-block;
       }
     }
   }
   rpc get-isis-interface-group-information {
     description "Show IS-IS interface-group information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
     }
     output {
       container isis-interface-group-information {
         uses isis-interface-group-information-block;
       }
     }
   }
   rpc get-isis-layer2-map-information {
     description "Show IS-IS ARP/ND mapping information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
       leaf destination {
         description "IP address of mapping entry";
         type ipaddr;
       }
     }
     output {
       container isis-layer2-map-information {
         uses isis-layer2-map-information-block;
       }
     }
   }
   rpc get-isis-overview-information {
     description "Show overview of IS-IS information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
     }
     output {
       container isis-overview-information {
         uses isis-overview-information-block;
       }
     }
   }
   rpc get-isis-route-information {
     description "Show IS-IS routing table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
       leaf destination {
         description "IP address and optional prefix length of destination";
         type ipprefix;
       }
       leaf floodgroup {
         description "Routes belonging to a specific floodgroup";
         type string {
           junos:posix-pattern "^[[:xdigit:]]{2}.(([[:xdigit:]]){2}){1,12}$";
           junos:pattern-message "Enter a valid area ID";
         }
       }
       leaf nexthop {
         description "Routes reachable through specific nexthop";
         type string;
       }
       leaf download-priority {
         description "Sorted by download priority";
         type empty;
       }
       leaf family {
         type enumeration {
           enum "inet" {
             description "Display IPv4 routes";
           }
           enum "inet6" {
             description "Display IPv6 routes";
           }
           enum "iso" {
             description "Display CLNS routes";
           }
         }
       }
       leaf topology {
         description "Name of topology from which routes were learned";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-route-information {
         uses isis-route-information-block;
       }
     }
   }
   rpc get-isis-purge-log-information {
     description "Show log of PURGE runs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
       leaf level {
         description "Number of IS-IS level";
         type uint32 {
           range "1 .. 2";
         }
       }
     }
     output {
       container isis-purge-information {
         uses isis-purge-information-block;
       }
     }
   }
   rpc get-isis-spf-log-information {
     description "Show log of SPF runs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
       leaf level {
         description "Number of IS-IS level";
         type uint32 {
           range "1 .. 2";
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-spf-information {
         uses isis-spf-information-block;
       }
     }
   }
   rpc get-isis-spf-results-information {
     description "Show results from SPF runs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "IS-IS instance";
         type string;
       }
       leaf level {
         description "Number of IS-IS level";
         type uint32 {
           range "1 .. 2";
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-spf-information {
         uses isis-spf-information-block;
       }
     }
   }
   rpc get-isis-spf-results-brief-information {
     description "Show brief summary of SPF results";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
       leaf level {
         description "Number of level";
         type uint32 {
           range "1 .. 2";
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-spf-information {
         uses isis-spf-information-block;
       }
     }
   }
   rpc get-isis-statistics-information {
     description "Show IS-IS performance statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of IS-IS instance";
         type string;
       }
     }
     output {
       container isis-statistics-information {
         uses isis-statistics-information-block;
       }
     }
   }
 grouping isis-adjacency-information-block {
   container brief {
     container isis-adjacency {
       leaf interface-name {
         type string;
         description "Name of interface";
       }
       leaf system-name {
         type string;
         description "Hostname for a system";
       }
       leaf not-remote-address {
         type empty;
       }
       leaf level {
         type int32;
         description "IS-IS Level";
       }
       leaf adjacency-state {
         type string;
         description "State of the adjacency";
       }
       leaf holdtime {
         type int32;
         description "Delay before timing out the adjacency (default is 180 seconds)";
       }
       leaf snpa {
         type string;
       }
     }
   }
   container detail {
     container isis-adjacency {
       leaf system-name {
         type string;
         description "Hostname for a system";
       }
       leaf interface-name {
         type string;
         description "Name of interface";
       }
       leaf level {
         type int32;
         description "IS-IS Level";
       }
       leaf adjacency-state {
         type string;
         description "State of the adjacency";
       }
       leaf holdtime {
         type int32;
         description "Delay before timing out the adjacency (default is 180 seconds)";
       }
       leaf interface-priority {
         type int32;
       }
       leaf transition-count {
         type int32;
       }
       leaf last-transition-time {
         type string;
       }
       leaf circuit-type {
         type int32;
       }
       leaf adjacency-flag {
         type string;
       }
       leaf mac-address {
         type mac-addr;
       }
       leaf adjacency-topologies {
         type string;
       }
       leaf adjacency-restart-capable {
         type string;
         description "Restart capability of the adjacency";
       }
       leaf adjacency-advertisement {
         type string;
         description "State of the adjacency advertisment";
       }
       leaf lan-id {
         type string;
       }
       leaf ip-address {
         type ipaddr;
       }
       leaf ipv6-address {
         type ipv6addr;
       }
       leaf adjacency-segment-level {
         type int32;
       }
       leaf ipv4-adjacency-segment-id {
         type int32;
       }
       leaf ipv6-adjacency-segment-id {
         type int32;
       }
       list snpa {
         list pfe-port-snpa {
           description "PFE Port SNPA";
           leaf pfe-id {
             type int32;
           }
           leaf port-id {
             type int32;
           }
         }
         list network-element-port-snpa {
           description "Network Element Port SNPA";
           leaf port-id {
             type int32;
           }
         }
         list mstp-root-snpa {
           description "Multiple Spanning Tree Protocol Root SNPA";
           leaf mstp-root-id {
             type int32;
           }
         }
         list gateway-snpa {
           description "Gateway SNPA";
           leaf gateway-addr {
             type ipaddr;
           }
         }
         list layer2-domain-port-snpa {
           description "Layer-2 Domain Port SNPA";
           leaf port-id {
             type int32;
           }
         }
         list replication-block-snpa {
           description "Replication Block SNPA";
           leaf replication-block-id {
             type int32;
           }
         }
         list replication-route-snpa {
           description "Replication Route SNPA";
           leaf network-element-id {
             type ipaddr;
           }
         }
         list layer2-multicast-port-snpa {
           description "Layer-2 Multicast Port SNPA";
           leaf layer2-multicast-port-id {
             type int32;
           }
         }
         list inh-snpa {
           description "Indirection SNPA";
           leaf inh-id {
             type int32;
           }
         }
       }
     }
   }
   container extensive {
     container isis-adjacency {
       leaf system-name {
         type string;
         description "Hostname for a system";
       }
       leaf interface-name {
         type string;
         description "Name of interface";
       }
       leaf level {
         type int32;
         description "IS-IS Level";
       }
       leaf adjacency-state {
         type string;
         description "State of the adjacency";
       }
       leaf holdtime {
         type int32;
         description "Delay before timing out the adjacency (default is 180 seconds)";
       }
       leaf interface-priority {
         type int32;
       }
       leaf transition-count {
         type int32;
       }
       leaf last-transition-time {
         type string;
       }
       leaf circuit-type {
         type int32;
       }
       leaf adjacency-flag {
         type string;
       }
       leaf mac-address {
         type mac-addr;
       }
       leaf adjacency-topologies {
         type string;
       }
       leaf adjacency-restart-capable {
         type string;
         description "Restart capability of the adjacency";
       }
       leaf adjacency-advertisement {
         type string;
         description "State of the adjacency advertisment";
       }
       leaf lan-id {
         type string;
       }
       leaf ip-address {
         type ipaddr;
       }
       leaf ipv6-address {
         type ipv6addr;
       }
       leaf adjacency-segment-level {
         type int32;
       }
       leaf ipv4-adjacency-segment-id {
         type int32;
       }
       leaf ipv6-adjacency-segment-id {
         type int32;
       }
       list snpa {
         list pfe-port-snpa {
           description "PFE Port SNPA";
           leaf pfe-id {
             type int32;
           }
           leaf port-id {
             type int32;
           }
         }
         list network-element-port-snpa {
           description "Network Element Port SNPA";
           leaf port-id {
             type int32;
           }
         }
         list mstp-root-snpa {
           description "Multiple Spanning Tree Protocol Root SNPA";
           leaf mstp-root-id {
             type int32;
           }
         }
         list gateway-snpa {
           description "Gateway SNPA";
           leaf gateway-addr {
             type ipaddr;
           }
         }
         list layer2-domain-port-snpa {
           description "Layer-2 Domain Port SNPA";
           leaf port-id {
             type int32;
           }
         }
         list replication-block-snpa {
           description "Replication Block SNPA";
           leaf replication-block-id {
             type int32;
           }
         }
         list replication-route-snpa {
           description "Replication Route SNPA";
           leaf network-element-id {
             type ipaddr;
           }
         }
         list layer2-multicast-port-snpa {
           description "Layer-2 Multicast Port SNPA";
           leaf layer2-multicast-port-id {
             type int32;
           }
         }
         list inh-snpa {
           description "Indirection SNPA";
           leaf inh-id {
             type int32;
           }
         }
       }
       list isis-adjacency-log {
         description "Entry describing adjacency transition";
         leaf adjacency-when {
           type string;
           description "Time at which the transition occurred";
         }
         leaf adjacency-state {
           type string;
           description "State of the adjacency";
         }
         leaf adjacency-event {
           type string;
           description "Event which triggered the transition";
         }
         leaf adjacency-down-reason {
           type string;
           description "Reason for the down transition event";
         }
       }
     }
   }
 }
 grouping isis-adjacency-holddown-information-block {
   container brief {
     list isis-adjacencyholddown {
       leaf level {
         type int32;
         description "IS-IS Level";
       }
       leaf active {
         type string;
       }
     }
   }
   container detail {
     list isis-adjacencyholddown {
       leaf level {
         type int32;
         description "IS-IS Level";
       }
       leaf active {
         type string;
       }
       leaf reset-complete {
         type string;
       }
       leaf last-holddown {
         type string;
       }
       leaf started {
         type string;
       }
       leaf network-stable {
         type string;
       }
       leaf time {
         type string;
         description "Time of the event";
       }
       leaf first-adj-up-time {
         type string;
       }
       leaf adj-up-count {
         type string;
       }
     }
   }
   container extensive {
     list isis-adjacencyholddown {
       leaf level {
         type int32;
         description "IS-IS Level";
       }
       leaf active {
         type string;
       }
       leaf reset-complete {
         type string;
       }
       leaf last-holddown {
         type string;
       }
       leaf started {
         type string;
       }
       leaf network-stable {
         type string;
       }
       leaf time {
         type string;
         description "Time of the event";
       }
       leaf first-adj-up-time {
         type string;
       }
       leaf adj-up-count {
         type string;
       }
       leaf adjacency-holddown-when {
         type string;
       }
       leaf adjacency-holddown-state {
         type string;
       }
       leaf adjacency-holddown-event {
         type string;
       }
       leaf adjacency-holddown-reason {
         type string;
       }
     }
   }
 }
 grouping isis-authentication-information-block {
   list isis-interface-authentication {
     leaf interface-name {
       type string;
       description "Name of interface";
     }
     list isis-interface-level-authentication {
       leaf level {
         type int32;
         description "IS-IS Level";
       }
       leaf isis-interface-level-iih-authentication {
         type string;
         description "Authentication type for IIH packets";
       }
       leaf isis-interface-level-csn-authentication {
         type string;
         description "Authentication type for CSN packets";
       }
       leaf isis-interface-level-psn-authentication {
         type string;
         description "Authentication type for PSN packets";
       }
     }
   }
   list isis-lsp-authentication {
     description "Authentication type for LSP packets";
     leaf level {
       type int32;
       description "IS-IS Level";
     }
     leaf isis-level-lsp-authentication {
       type string;
       description "Authentication type for LSP packets";
     }
   }
 }
 grouping isis-bgporr-information-block {
   container isis-bgporr {
     leaf isis-bgporr-name {
       type string;
     }
     leaf isis-bgporr-primary {
       type ipaddr;
     }
     leaf isis-bgporr-primary-active-tag {
       type string;
     }
     leaf isis-bgporr-backup {
       type ipaddr;
     }
     leaf isis-bgporr-backup-active-tag {
       type string;
     }
     container isis-route {
       container normal {
         leaf address-prefix {
           type ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         leaf isis-backup-score {
           type string;
         }
         leaf prefix-originator {
           type string;
         }
         leaf prefix-level {
           type int32;
         }
         leaf prefix-metric {
           type int32;
         }
         leaf prefix-preference {
           type int32;
         }
         leaf isis-route-priority {
           type string;
         }
         list snpa {
           list pfe-port-snpa {
             description "PFE Port SNPA";
             leaf pfe-id {
               type int32;
             }
             leaf port-id {
               type int32;
             }
           }
           list network-element-port-snpa {
             description "Network Element Port SNPA";
             leaf port-id {
               type int32;
             }
           }
           list mstp-root-snpa {
             description "Multiple Spanning Tree Protocol Root SNPA";
             leaf mstp-root-id {
               type int32;
             }
           }
           list gateway-snpa {
             description "Gateway SNPA";
             leaf gateway-addr {
               type ipaddr;
             }
           }
           list layer2-domain-port-snpa {
             description "Layer-2 Domain Port SNPA";
             leaf port-id {
               type int32;
             }
           }
           list replication-block-snpa {
             description "Replication Block SNPA";
             leaf replication-block-id {
               type int32;
             }
           }
           list replication-route-snpa {
             description "Replication Route SNPA";
             leaf network-element-id {
               type ipaddr;
             }
           }
           list layer2-multicast-port-snpa {
             description "Layer-2 Multicast Port SNPA";
             leaf layer2-multicast-port-id {
               type int32;
             }
           }
           list inh-snpa {
             description "Indirection SNPA";
             leaf inh-id {
               type int32;
             }
           }
         }
         list isis-rt-sessid {
           description "Session ID associated with the route";
           leaf isis-rt-sessid-val {
             type uint32;
           }
           leaf isis-rt-sessid-ver {
             type uint32;
           }
         }
       }
       container clns {
         leaf address-prefix {
           type ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         leaf snpa {
           type string;
         }
         leaf prefix-originator {
           type string;
         }
         leaf prefix-metric {
           type int32;
         }
         leaf prefix-preference {
           type int32;
         }
       }
       container orr {
         leaf address-prefix {
           type ipaddr;
         }
         leaf level {
           type int32;
           description "IS-IS Level";
         }
         leaf route-version {
           type int32;
         }
         leaf metric {
           type int32;
         }
         leaf metric-type {
           type string;
         }
         list snpa {
           list pfe-port-snpa {
             description "PFE Port SNPA";
             leaf pfe-id {
               type int32;
             }
             leaf port-id {
               type int32;
             }
           }
           list network-element-port-snpa {
             description "Network Element Port SNPA";
             leaf port-id {
               type int32;
             }
           }
           list mstp-root-snpa {
             description "Multiple Spanning Tree Protocol Root SNPA";
             leaf mstp-root-id {
               type int32;
             }
           }
           list gateway-snpa {
             description "Gateway SNPA";
             leaf gateway-addr {
               type ipaddr;
             }
           }
           list layer2-domain-port-snpa {
             description "Layer-2 Domain Port SNPA";
             leaf port-id {
               type int32;
             }
           }
           list replication-block-snpa {
             description "Replication Block SNPA";
             leaf replication-block-id {
               type int32;
             }
           }
           list replication-route-snpa {
             description "Replication Route SNPA";
             leaf network-element-id {
               type ipaddr;
             }
           }
           list layer2-multicast-port-snpa {
             description "Layer-2 Multicast Port SNPA";
             leaf layer2-multicast-port-id {
               type int32;
             }
           }
           list inh-snpa {
             description "Indirection SNPA";
             leaf inh-id {
               type int32;
             }
           }
         }
       }
       container mpls {
         leaf address-prefix {
           type ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         list snpa {
           list pfe-port-snpa {
             description "PFE Port SNPA";
             leaf pfe-id {
               type int32;
             }
             leaf port-id {
               type int32;
             }
           }
           list network-element-port-snpa {
             description "Network Element Port SNPA";
             leaf port-id {
               type int32;
             }
           }
           list mstp-root-snpa {
             description "Multiple Spanning Tree Protocol Root SNPA";
             leaf mstp-root-id {
               type int32;
             }
           }
           list gateway-snpa {
             description "Gateway SNPA";
             leaf gateway-addr {
               type ipaddr;
             }
           }
           list layer2-domain-port-snpa {
             description "Layer-2 Domain Port SNPA";
             leaf port-id {
               type int32;
             }
           }
           list replication-block-snpa {
             description "Replication Block SNPA";
             leaf replication-block-id {
               type int32;
             }
           }
           list replication-route-snpa {
             description "Replication Route SNPA";
             leaf network-element-id {
               type ipaddr;
             }
           }
           list layer2-multicast-port-snpa {
             description "Layer-2 Multicast Port SNPA";
             leaf layer2-multicast-port-id {
               type int32;
             }
           }
           list inh-snpa {
             description "Indirection SNPA";
             leaf inh-id {
               type int32;
             }
           }
         }
       }
       container inet-mpls {
         leaf address-prefix {
           type ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         leaf isis-backup-score {
           type string;
         }
         leaf prefix-originator {
           type string;
         }
         leaf prefix-level {
           type int32;
         }
         leaf prefix-metric {
           type int32;
         }
         leaf prefix-preference {
           type int32;
         }
         list snpa {
           list pfe-port-snpa {
             description "PFE Port SNPA";
             leaf pfe-id {
               type int32;
             }
             leaf port-id {
               type int32;
             }
           }
           list network-element-port-snpa {
             description "Network Element Port SNPA";
             leaf port-id {
               type int32;
             }
           }
           list mstp-root-snpa {
             description "Multiple Spanning Tree Protocol Root SNPA";
             leaf mstp-root-id {
               type int32;
             }
           }
           list gateway-snpa {
             description "Gateway SNPA";
             leaf gateway-addr {
               type ipaddr;
             }
           }
           list layer2-domain-port-snpa {
             description "Layer-2 Domain Port SNPA";
             leaf port-id {
               type int32;
             }
           }
           list replication-block-snpa {
             description "Replication Block SNPA";
             leaf replication-block-id {
               type int32;
             }
           }
           list replication-route-snpa {
             description "Replication Route SNPA";
             leaf network-element-id {
               type ipaddr;
             }
           }
           list layer2-multicast-port-snpa {
             description "Layer-2 Multicast Port SNPA";
             leaf layer2-multicast-port-id {
               type int32;
             }
           }
           list inh-snpa {
             description "Indirection SNPA";
             leaf inh-id {
               type int32;
             }
           }
         }
         list isis-rt-sessid {
           description "Session ID associated with the route";
           leaf isis-rt-sessid-val {
             type uint32;
           }
           leaf isis-rt-sessid-ver {
             type uint32;
           }
         }
       }
     }
   }
 }
 grouping isis-backup-mplsp-information-block {
   container isis-backup-mplsp {
     leaf lsp-name {
       type string;
       description "Tunneled into an RSVP LSP";
     }
     leaf lsp-addr {
       type ipaddr;
       description "LSP destination address";
     }
     leaf lsp-status {
       type string;
       description "LSP status";
     }
     leaf lsp-last-change {
       type string;
       description "Time of last LSP change";
     }
     leaf te-metric {
       type int32;
       description "LSP TE metric";
     }
     leaf metric {
       type int32;
     }
     leaf lsp-refcount {
       type int32;
     }
   }
 }
 grouping isis-spf-information-block {
   container isis-spf {
     leaf node-count {
       type int32;
     }
     container isis-spf-results-header {
       leaf isis-topology-id {
         type string;
       }
       leaf level {
         type int32;
         description "IS-IS Level";
       }
     }
     list isis-spf-result {
       leaf node-id {
         type string;
       }
       leaf metric {
         type int32;
       }
       leaf disconnected {
         type empty;
       }
       leaf no-first-fragment {
         type empty;
       }
       list next-hop-element {
         leaf interface-name {
           type string;
           description "Name of interface";
         }
         leaf isis-next-hop-type {
           type string;
         }
         leaf isis-next-hop {
           type string;
         }
         leaf snpa {
           type string;
         }
       }
       list prefix-element {
         leaf prefix-metric {
           type int32;
         }
         leaf external-prefix-metric {
           type int32;
         }
         leaf address-prefix {
           type ipaddr;
         }
       }
       list end-system-element {
         leaf end-system-metric {
           type int32;
         }
         leaf end-system-id {
           type string;
           description "Six-octet ISO system ID for a end-system";
         }
       }
     }
     container isis-spf-log-header {
       leaf isis-topology-id {
         type string;
       }
       leaf level {
         type int32;
         description "IS-IS Level";
       }
     }
     container isis-spf-log {
       leaf start-time {
         type string;
       }
       leaf elapsed-time {
         type string;
         description "Time this adjacency or session has been up or down";
       }
       leaf spf-trigger-count {
         type int32;
       }
       leaf logging-reason {
         type string;
       }
       leaf lsp-name {
         type string;
         description "Tunneled into an RSVP LSP";
       }
       leaf system-name {
         type string;
         description "Hostname for a system";
       }
       leaf interface-name {
         type string;
         description "Name of interface";
       }
     }
     container isis-backup-spf-result {
       leaf node-id {
         type string;
       }
       leaf no-first-fragment {
         type empty;
       }
       leaf backup-root {
         type string;
       }
       leaf backup-root-metric {
         type int32;
       }
       leaf metric {
         type int32;
       }
       leaf backup-root-preference {
         type int32;
       }
       leaf track-item {
         type string;
       }
       leaf track-item-isnbr {
         type string;
       }
       leaf rev-track-item {
         type string;
       }
       leaf rev-track-item-isnbr {
         type string;
       }
       list next-hop-element {
         leaf interface-name {
           type string;
           description "Name of interface";
         }
         leaf isis-next-hop-type {
           type string;
         }
         leaf isis-next-hop {
           type string;
         }
         leaf snpa {
           type string;
         }
       }
       list backup-next-hop-element {
         leaf interface-name {
           type string;
           description "Name of interface";
         }
         leaf isis-next-hop-type {
           type string;
         }
         leaf isis-next-hop {
           type string;
         }
         leaf snpa {
           type string;
         }
         leaf isis-backup-prefix-refcount {
           type uint32;
           description "Number of prefixes that uses this nexthop as backup";
         }
       }
       list no-coverage-reason-element {
         leaf isis-next-hop-type {
           type string;
         }
         leaf no-coverage-reason {
           type string;
         }
       }
     }
   }
 }
 grouping isis-backup-coverage-information-block {
   container isis-backup-coverage {
     leaf isis-topology-id {
       type string;
     }
     leaf level {
       type int32;
       description "IS-IS Level";
     }
     leaf isis-node-coverage {
       type string;
     }
     leaf isis-route-coverage-ipv4 {
       type string;
     }
     leaf isis-route-coverage-ipv4-mpls {
       type string;
     }
     leaf isis-route-coverage-ipv6 {
       type string;
     }
     leaf isis-route-coverage-ipv6-mpls {
       type string;
     }
     leaf isis-route-coverage-clns {
       type string;
     }
   }
 }
 grouping isis-context-information-block {
   container brief {
     description "Context information for an IS-IS instance";
     list isis-context {
       leaf isis-context-id {
         type ipaddr;
         description "Context identifier is an IP address identify protected context";
       }
       leaf isis-context-level {
         type int32;
         description "Advertise level";
       }
       leaf isis-context-owner-proto {
         type string;
         description "Routing protocols owns context identifier";
       }
       leaf isis-context-role {
         type string;
         description "Context role either primary or protector";
       }
       leaf isis-context-primary {
         type string;
         description "Context role is primary or protector";
       }
       leaf isis-context-metric {
         type uint32;
         description "Metric associate with context-id";
       }
     }
   }
   container detail {
     description "Context information for an IS-IS instance";
     list isis-context {
       leaf isis-context-id {
         type ipaddr;
         description "Context identifier is an IP address identify protected context";
       }
       leaf isis-context-level {
         type int32;
         description "Advertise level";
       }
       leaf isis-context-owner-proto {
         type string;
         description "Routing protocols owns context identifier";
       }
       leaf isis-context-role {
         type string;
         description "Context role either primary or protector";
       }
       leaf isis-context-primary {
         type string;
         description "Context role is primary or protector";
       }
       leaf isis-context-metric {
         type uint32;
         description "Metric associate with context-id";
       }
       leaf isis-context-advertiser {
         type string;
         description "Context-id advertiser name";
       }
       leaf isis-context-advertiser-router-id {
         type ipaddr;
         description "Router Ids of context-id advertiser";
       }
       leaf isis-context-advertiser-metric {
         type uint32;
         description "Context-id advertiser metric";
       }
       leaf isis-context-advertiser-level {
         type uint32;
         description "Context-id advertiser level";
       }
       leaf isis-not-compatible-mode {
         type empty;
       }
       leaf isis-context-advertiser-tlv {
         type string;
         description "Context-id advertiser tlv";
       }
     }
   }
 }
 grouping isis-database-information-block {
   container brief {
     container isis-database {
       leaf level {
         type int32;
         description "IS-IS Level";
       }
       leaf lsp-count {
         type int32;
       }
       container isis-database-entry {
         leaf lsp-id {
           type string;
         }
         leaf sequence-number {
           type int32;
           description "History event number";
         }
         leaf checksum {
           type int32;
         }
         leaf remaining-lifetime {
           type int32;
         }
         leaf lsp-attributes {
           type string;
         }
         container isis-neighbor {
         }
         container isis-prefix {
           container normal {
             leaf protocol-name {
               type string;
             }
             leaf isis-topology-id {
               type string;
             }
             leaf address-prefix {
               type ipaddr;
             }
             leaf metric {
               type int32;
             }
             leaf prefix-flag {
               type string;
             }
             leaf prefix-status {
               type string;
             }
           }
           container clns {
             leaf protocol-name {
               type string;
             }
             leaf isis-topology-id {
               type string;
             }
             leaf address-prefix {
               type ipaddr;
             }
             leaf metric {
               type int32;
             }
             leaf prefix-flag {
               type string;
             }
             leaf prefix-status {
               type string;
             }
           }
         }
         container isis-header {
         }
         container isis-packet {
         }
         container isis-tlv {
           container isis-tlv-overhead {
             leaf isis-tlv-type {
               type int32;
             }
             leaf tlv-length {
               type int32;
             }
             leaf bytes-left {
               type int32;
             }
           }
           container area-address-tlv {
             leaf address {
               type ipaddr;
             }
             leaf tlv-length {
               type int32;
             }
           }
           container lsp-buffer-size-tlv {
             leaf lsp-buffer-size {
               type int32;
             }
           }
           container protocols-tlv {
             leaf protocol {
               type string;
             }
           }
           container mt-tlv {
             leaf mtid {
               type string;
             }
           }
           container hostname-tlv {
             leaf hostname {
               type string;
             }
           }
           container purge-originator-tlv {
             leaf purge-originator {
               type string;
             }
             leaf purge-originator-from {
               type string;
             }
           }
           container ipaddress-tlv {
             leaf address {
               type ipaddr;
             }
           }
           container ipv6address-tlv {
             leaf address {
               type ipaddr;
             }
           }
           container router-id-tlv {
             leaf router-id {
               type ipaddr;
             }
           }
           container reachability-tlv {
             leaf isis-topology-id {
               type string;
             }
             leaf reachability-tlv.heading {
               type string;
             }
             leaf address-prefix {
               type ipaddr;
             }
             leaf metric-flag {
               type string;
             }
             leaf metric {
               type int32;
             }
             leaf reachability-delay {
               type empty;
             }
             leaf reachability-expense {
               type empty;
             }
             leaf reachability-error {
               type empty;
             }
             leaf prefix-status {
               type string;
             }
             leaf address {
               type ipaddr;
             }
             leaf neighbor-prefix {
               type ipaddr;
             }
             leaf tlv-length {
               type int32;
             }
             container isis-reachability-subtlv {
               container admin-groups {
                 leaf color {
                   type int32;
                 }
                 leaf no-group-flag {
                   type empty;
                 }
                 leaf admin-group-name {
                   type string;
                   description "Name of the admin group";
                 }
                 leaf admin-group-number {
                   type int32;
                   description "Number of the admin group";
                 }
               }
             }
           }
           container isis-iso-prefix-tlv {
             leaf isis-iso-prefix-tlv.heading {
               type string;
             }
             leaf metric-flag {
               type string;
             }
             leaf metric {
               type int32;
             }
             leaf reachability-delay {
               type empty;
             }
             leaf reachability-expense {
               type empty;
             }
             leaf reachability-error {
               type empty;
             }
             leaf prefix-status {
               type string;
             }
             leaf iso-prefix {
               type string;
             }
           }
           container isis-prefix-subtlv {
           }
           container ipv6-reachability-tlv {
             leaf isis-topology-id {
               type string;
             }
             leaf ipv6-reachability-tlv.heading {
               type string;
             }
             leaf ipv6-address {
               type ipv6addr;
             }
             leaf metric {
               type int32;
             }
             leaf prefix-extern {
               type empty;
             }
             leaf prefix-downflag {
               type empty;
             }
             leaf subtlv-size {
               type int32;
             }
             container isis-prefix-subtlv {
               container isis-prefix-tag {
               }
               container isis-prefix-sid {
               }
             }
           }
           container isis-reachability-subtlv {
             leaf local-ifindex {
               type uint32;
               description "Local interface index";
             }
             leaf remote-ifindex {
               type uint32;
               description "Remote interface index";
             }
             leaf max-bandwidth {
               type int32;
             }
             leaf max-reserve-bandwidth {
               type int32;
             }
             leaf current-bandwidth-header {
               type empty;
             }
             leaf bandwidth-priority {
               type int32;
             }
             leaf current-reserve-bandwidth {
               type int32;
             }
             leaf address {
               type ipaddr;
             }
             leaf neighbor-prefix {
               type ipaddr;
             }
             leaf te-metric {
               type int32;
               description "LSP TE metric";
             }
             leaf dste-bc-header {
               type empty;
             }
             leaf dste-bc-model {
               type string;
               description "DiffServ TE bandwidth constraint model";
             }
             leaf dste-bc-count {
               type int32;
               description "DiffServ TE bandwidth constraint count";
             }
             leaf dste-bc-bw {
               type int32;
               description "DiffServ TE bandwidth constraint BW";
             }
             leaf p2p-adj-sid-af {
               type string;
               description "Point-to-Point adjacency SID address family";
             }
             leaf p2p-adj-sid-flags {
               type string;
               description "Point-to-Point adjacency SID flags";
             }
             leaf p2p-adj-sid-weight {
               type int32;
               description "Point-to-Point adjacency SID weight";
             }
             leaf p2p-adj-sid-label {
               type string;
               description "Point-to-Point adjacency SID label";
             }
             leaf lan-adj-sid-af {
               type string;
               description "LAN adjacency SID address family";
             }
             leaf lan-adj-sid-flags {
               type string;
               description "LAN adjacency SID flags";
             }
             leaf lan-adj-sid-weight {
               type int32;
               description "LAN adjacency SID weight";
             }
             leaf lan-adj-sid-sysid {
               type string;
               description "LAN adjacency SID neighbor system id";
             }
             leaf lan-adj-sid-label {
               type string;
               description "LAN adjacency SID label";
             }
             leaf isis-subtlv-type {
               type int32;
             }
             leaf subtlv-length {
               type int32;
             }
             container admin-groups {
               leaf color {
                 type int32;
               }
               leaf no-group-flag {
                 type empty;
               }
               leaf admin-group-name {
                 type string;
                 description "Name of the admin group";
               }
               leaf admin-group-number {
                 type int32;
                 description "Number of the admin group";
               }
             }
           }
           container rtr-capability-tlv {
             leaf rtr-capability-tlv.heading {
               type string;
             }
             leaf router-id {
               type ipaddr;
             }
             leaf rtr-cap-flags {
               type string;
             }
             container spring-capability-sub-tlv {
               leaf spring-capability-flags {
                 type string;
               }
               leaf spring-capability-range {
                 type uint32;
               }
               leaf spring-capability-sid-label {
                 type uint32;
               }
             }
             container spring-algorithm-sub-tlv {
               leaf spring-algorithm-type {
                 type uint32;
               }
             }
           }
           container authentication-tlv {
             leaf tlv-length {
               type int32;
             }
           }
           container idrp-tlv {
             leaf tlv-length {
               type int32;
             }
           }
           container ip-prefix-tlv {
             leaf isis-topology-id {
               type string;
             }
             leaf ip-prefix-tlv.heading {
               type string;
             }
             leaf address-prefix {
               type ipaddr;
             }
             leaf metric {
               type int32;
             }
             leaf prefix-status {
               type string;
             }
             leaf subtlv-size {
               type int32;
             }
             container isis-prefix-subtlv {
               container isis-prefix-tag {
               }
               container isis-prefix-sid {
               }
             }
           }
           container isis-srlg-tlv {
             leaf isis-srlg-tlv.heading {
               type string;
             }
             leaf address-prefix {
               type ipaddr;
             }
             leaf srlg-flag {
               type string;
             }
             leaf srlg-address {
               type ipaddr;
             }
             leaf srlg-neighbor-prefix {
               type ipaddr;
             }
             leaf srlg-local-ifindex {
               type uint32;
               description "Local interface index";
             }
             leaf srlg-remote-ifindex {
               type uint32;
               description "Remote interface index";
             }
             container isis-srlg-value {
               leaf isis-srlg-value.heading {
                 type string;
               }
               leaf isis-srlg-name {
                 type string;
               }
             }
           }
           container unknown-sub-tlv {
             leaf isis-tlv-type {
               type int32;
             }
             leaf tlv-length {
               type int32;
             }
           }
           container label-binding-tlv {
             leaf protocol-name {
               type string;
             }
             leaf address-prefix {
               type ipaddr;
             }
             leaf label-binding-weight {
               type int32;
             }
             leaf label-binding-range {
               type int32;
             }
             leaf isis-label {
               type int32;
             }
           }
           container unknown-tlv {
             leaf isis-tlv-type {
               type int32;
             }
             leaf tlv-length {
               type int32;
             }
           }
           container tlv-stragglers {
             leaf bytes-left {
               type int32;
             }
           }
         }
         container isis-es-neighbor {
         }
         container isis-label-binding {
           container normal {
             leaf protocol-name {
               type string;
             }
             leaf address-prefix {
               type ipaddr;
             }
             leaf isis-label {
               type int32;
             }
             leaf binding-flags {
               type string;
             }
           }
         }
       }
     }
   }
   container detail {
     container isis-database {
       leaf level {
         type int32;
         description "IS-IS Level";
       }
       container isis-database-entry {
         leaf lsp-id {
           type string;
         }
         leaf sequence-number {
           type int32;
           description "History event number";
         }
         leaf checksum {
           type int32;
         }
         leaf remaining-lifetime {
           type int32;
         }
         leaf lsp-stub {
           type empty;
         }
         leaf isis-node-segment-ipv4-index {
           type int32;
           description "IPv4 Node Segment index for this device";
         }
         leaf isis-node-segment-ipv6-index {
           type int32;
           description "IPv6 Node Segment index for this device";
         }
         leaf isis-node-segment-block-header {
           type empty;
           description "Node Segment Blocks";
         }
         container isis-node-segment-block {
           description "Node Segment Blocks related information";
           leaf isis-node-segment-block-start-index {
             type int32;
             description "Starting Index for the specific Node Segment Block";
           }
           leaf isis-node-segment-block-size {
             type int32;
             description "Size of the specific Node Segment Block";
           }
           leaf isis-node-segment-block-first-label {
             type int32;
             description "First label allocated for the specific Node Segment Block";
           }
           leaf isis-node-segment-block-last-label {
             type int32;
             description "Last label allocated for the specific Node Segment Block";
           }
         }
         container isis-neighbor {
           leaf isis-topology-id {
             type string;
           }
           leaf is-neighbor-id {
             type string;
           }
           leaf metric {
             type int32;
           }
           leaf two-way-lsp-id {
             type string;
           }
           leaf firstfrag-lsp-id {
             type string;
           }
         }
         container isis-prefix {
           container normal {
             leaf protocol-name {
               type string;
             }
             leaf isis-topology-id {
               type string;
             }
             leaf address-prefix {
               type ipaddr;
             }
             leaf metric {
               type int32;
             }
             leaf prefix-flag {
               type string;
             }
             leaf prefix-status {
               type string;
             }
           }
           container clns {
             leaf protocol-name {
               type string;
             }
             leaf isis-topology-id {
               type string;
             }
             leaf address-prefix {
               type ipaddr;
             }
             leaf metric {
               type int32;
             }
             leaf prefix-flag {
               type string;
             }
             leaf prefix-status {
               type string;
             }
           }
         }
         container isis-header {
         }
         container isis-packet {
         }
         container isis-tlv {
           container isis-tlv-overhead {
             leaf isis-tlv-type {
               type int32;
             }
             leaf tlv-length {
               type int32;
             }
             leaf bytes-left {
               type int32;
             }
           }
           container area-address-tlv {
             leaf address {
               type ipaddr;
             }
             leaf tlv-length {
               type int32;
             }
           }
           container lsp-buffer-size-tlv {
             leaf lsp-buffer-size {
               type int32;
             }
           }
           container protocols-tlv {
             leaf protocol {
               type string;
             }
           }
           container mt-tlv {
             leaf mtid {
               type string;
             }
           }
           container hostname-tlv {
             leaf hostname {
               type string;
             }
           }
           container purge-originator-tlv {
             leaf purge-originator {
               type string;
             }
             leaf purge-originator-from {
               type string;
             }
           }
           container ipaddress-tlv {
             leaf address {
               type ipaddr;
             }
           }
           container ipv6address-tlv {
             leaf address {
               type ipaddr;
             }
           }
           container router-id-tlv {
             leaf router-id {
               type ipaddr;
             }
           }
           container reachability-tlv {
             leaf isis-topology-id {
               type string;
             }
             leaf reachability-tlv.heading {
               type string;
             }
             leaf address-prefix {
               type ipaddr;
             }
             leaf metric-flag {
               type string;
             }
             leaf metric {
               type int32;
             }
             leaf reachability-delay {
               type empty;
             }
             leaf reachability-expense {
               type empty;
             }
             leaf reachability-error {
               type empty;
             }
             leaf prefix-status {
               type string;
             }
             leaf address {
               type ipaddr;
             }
             leaf neighbor-prefix {
               type ipaddr;
             }
             leaf tlv-length {
               type int32;
             }
             container isis-reachability-subtlv {
               container admin-groups {
                 leaf color {
                   type int32;
                 }
                 leaf no-group-flag {
                   type empty;
                 }
                 leaf admin-group-name {
                   type string;
                   description "Name of the admin group";
                 }
                 leaf admin-group-number {
                   type int32;
                   description "Number of the admin group";
                 }
               }
             }
           }
           container isis-iso-prefix-tlv {
             leaf isis-iso-prefix-tlv.heading {
               type string;
             }
             leaf metric-flag {
               type string;
             }
             leaf metric {
               type int32;
             }
             leaf reachability-delay {
               type empty;
             }
             leaf reachability-expense {
               type empty;
             }
             leaf reachability-error {
               type empty;
             }
             leaf prefix-status {
               type string;
             }
             leaf iso-prefix {
               type string;
             }
           }
           container isis-prefix-subtlv {
           }
           container ipv6-reachability-tlv {
             leaf isis-topology-id {
               type string;
             }
             leaf ipv6-reachability-tlv.heading {
               type string;
             }
             leaf ipv6-address {
               type ipv6addr;
             }
             leaf metric {
               type int32;
             }
             leaf prefix-extern {
               type empty;
             }
             leaf prefix-downflag {
               type empty;
             }
             leaf subtlv-size {
               type int32;
             }
             container isis-prefix-subtlv {
               container isis-prefix-tag {
               }
               container isis-prefix-sid {
               }
             }
           }
           container isis-reachability-subtlv {
             leaf local-ifindex {
               type uint32;
               description "Local interface index";
             }
             leaf remote-ifindex {
               type uint32;
               description "Remote interface index";
             }
             leaf max-bandwidth {
               type int32;
             }
             leaf max-reserve-bandwidth {
               type int32;
             }
             leaf current-bandwidth-header {
               type empty;
             }
             leaf bandwidth-priority {
               type int32;
             }
             leaf current-reserve-bandwidth {
               type int32;
             }
             leaf address {
               type ipaddr;
             }
             leaf neighbor-prefix {
               type ipaddr;
             }
             leaf te-metric {
               type int32;
               description "LSP TE metric";
             }
             leaf dste-bc-header {
               type empty;
             }
             leaf dste-bc-model {
               type string;
               description "DiffServ TE bandwidth constraint model";
             }
             leaf dste-bc-count {
               type int32;
               description "DiffServ TE bandwidth constraint count";
             }
             leaf dste-bc-bw {
               type int32;
               description "DiffServ TE bandwidth constraint BW";
             }
             leaf p2p-adj-sid-af {
               type string;
               description "Point-to-Point adjacency SID address family";
             }
             leaf p2p-adj-sid-flags {
               type string;
               description "Point-to-Point adjacency SID flags";
             }
             leaf p2p-adj-sid-weight {
               type int32;
               description "Point-to-Point adjacency SID weight";
             }
             leaf p2p-adj-sid-label {
               type string;
               description "Point-to-Point adjacency SID label";
             }
             leaf lan-adj-sid-af {
               type string;
               description "LAN adjacency SID address family";
             }
             leaf lan-adj-sid-flags {
               type string;
               description "LAN adjacency SID flags";
             }
             leaf lan-adj-sid-weight {
               type int32;
               description "LAN adjacency SID weight";
             }
             leaf lan-adj-sid-sysid {
               type string;
               description "LAN adjacency SID neighbor system id";
             }
             leaf lan-adj-sid-label {
               type string;
               description "LAN adjacency SID label";
             }
             leaf isis-subtlv-type {
               type int32;
             }
             leaf subtlv-length {
               type int32;
             }
             container admin-groups {
               leaf color {
                 type int32;
               }
               leaf no-group-flag {
                 type empty;
               }
               leaf admin-group-name {
                 type string;
                 description "Name of the admin group";
               }
               leaf admin-group-number {
                 type int32;
                 description "Number of the admin group";
               }
             }
           }
           container rtr-capability-tlv {
             leaf rtr-capability-tlv.heading {
               type string;
             }
             leaf router-id {
               type ipaddr;
             }
             leaf rtr-cap-flags {
               type string;
             }
             container spring-capability-sub-tlv {
               leaf spring-capability-flags {
                 type string;
               }
               leaf spring-capability-range {
                 type uint32;
               }
               leaf spring-capability-sid-label {
                 type uint32;
               }
             }
             container spring-algorithm-sub-tlv {
               leaf spring-algorithm-type {
                 type uint32;
               }
             }
           }
           container authentication-tlv {
             leaf tlv-length {
               type int32;
             }
           }
           container idrp-tlv {
             leaf tlv-length {
               type int32;
             }
           }
           container ip-prefix-tlv {
             leaf isis-topology-id {
               type string;
             }
             leaf ip-prefix-tlv.heading {
               type string;
             }
             leaf address-prefix {
               type ipaddr;
             }
             leaf metric {
               type int32;
             }
             leaf prefix-status {
               type string;
             }
             leaf subtlv-size {
               type int32;
             }
             container isis-prefix-subtlv {
               container isis-prefix-tag {
               }
               container isis-prefix-sid {
               }
             }
           }
           container isis-srlg-tlv {
             leaf isis-srlg-tlv.heading {
               type string;
             }
             leaf address-prefix {
               type ipaddr;
             }
             leaf srlg-flag {
               type string;
             }
             leaf srlg-address {
               type ipaddr;
             }
             leaf srlg-neighbor-prefix {
               type ipaddr;
             }
             leaf srlg-local-ifindex {
               type uint32;
               description "Local interface index";
             }
             leaf srlg-remote-ifindex {
               type uint32;
               description "Remote interface index";
             }
             container isis-srlg-value {
               leaf isis-srlg-value.heading {
                 type string;
               }
               leaf isis-srlg-name {
                 type string;
               }
             }
           }
           container unknown-sub-tlv {
             leaf isis-tlv-type {
               type int32;
             }
             leaf tlv-length {
               type int32;
             }
           }
           container label-binding-tlv {
             leaf protocol-name {
               type string;
             }
             leaf address-prefix {
               type ipaddr;
             }
             leaf label-binding-weight {
               type int32;
             }
             leaf label-binding-range {
               type int32;
             }
             leaf isis-label {
               type int32;
             }
           }
           container unknown-tlv {
             leaf isis-tlv-type {
               type int32;
             }
             leaf tlv-length {
               type int32;
             }
           }
           container tlv-stragglers {
             leaf bytes-left {
               type int32;
             }
           }
         }
         container isis-es-neighbor {
           leaf es-neighbor-id {
             type string;
           }
           leaf metric {
             type int32;
           }
           leaf es-neighbor-status {
             type string;
           }
         }
         container isis-label-binding {
           container normal {
             leaf protocol-name {
               type string;
             }
             leaf address-prefix {
               type ipaddr;
             }
             leaf isis-label {
               type int32;
             }
             leaf binding-flags {
               type string;
             }
           }
         }
       }
     }
   }
   container extensive {
     container isis-database {
       leaf level {
         type int32;
         description "IS-IS Level";
       }
       container isis-database-entry {
         leaf lsp-id {
           type string;
         }
         leaf sequence-number {
           type int32;
           description "History event number";
         }
         leaf checksum {
           type int32;
         }
         leaf remaining-lifetime {
           type int32;
         }
         leaf lsp-stub {
           type empty;
         }
         leaf isis-node-segment-ipv4-index {
           type int32;
           description "IPv4 Node Segment index for this device";
         }
         leaf isis-node-segment-ipv6-index {
           type int32;
           description "IPv6 Node Segment index for this device";
         }
         leaf isis-node-segment-block-header {
           type empty;
           description "Node Segment Blocks";
         }
         container isis-node-segment-block {
           description "Node Segment Blocks related information";
           leaf isis-node-segment-block-start-index {
             type int32;
             description "Starting Index for the specific Node Segment Block";
           }
           leaf isis-node-segment-block-size {
             type int32;
             description "Size of the specific Node Segment Block";
           }
           leaf isis-node-segment-block-first-label {
             type int32;
             description "First label allocated for the specific Node Segment Block";
           }
           leaf isis-node-segment-block-last-label {
             type int32;
             description "Last label allocated for the specific Node Segment Block";
           }
         }
         container isis-neighbor {
           leaf isis-topology-id {
             type string;
           }
           leaf is-neighbor-id {
             type string;
           }
           leaf metric {
             type int32;
           }
           leaf two-way-lsp-id {
             type string;
           }
           leaf firstfrag-lsp-id {
             type string;
           }
         }
         container isis-prefix {
           container normal {
             leaf protocol-name {
               type string;
             }
             leaf isis-topology-id {
               type string;
             }
             leaf address-prefix {
               type ipaddr;
             }
             leaf metric {
               type int32;
             }
             leaf prefix-flag {
               type string;
             }
             leaf prefix-status {
               type string;
             }
           }
           container clns {
             leaf protocol-name {
               type string;
             }
             leaf isis-topology-id {
               type string;
             }
             leaf address-prefix {
               type ipaddr;
             }
             leaf metric {
               type int32;
             }
             leaf prefix-flag {
               type string;
             }
             leaf prefix-status {
               type string;
             }
           }
         }
         container isis-header {
           leaf lsp-id {
             type string;
           }
           leaf pdu-length {
             type int32;
           }
           leaf allocated-length {
             type int32;
           }
           leaf router-id {
             type ipaddr;
           }
           leaf remaining-lifetime {
             type int32;
           }
           leaf level {
             type int32;
             description "IS-IS Level";
           }
           leaf interface-index {
             type int32;
           }
           leaf estimated-free-bytes {
             type int32;
           }
           leaf actual-free-bytes {
             type int32;
           }
           leaf lsdb-timer-type {
             type string;
           }
           leaf lsdb-expiration-time {
             type int32;
           }
           leaf needs-rebuild {
             type empty;
           }
           leaf protocol {
             type string;
           }
         }
         container isis-packet {
           leaf lsp-id {
             type string;
           }
           leaf pdu-length {
             type int32;
           }
           leaf pdu-lifetime {
             type int32;
           }
           leaf checksum {
             type int32;
           }
           leaf sequence-number {
             type int32;
             description "History event number";
           }
           leaf lsp-attributes {
             type string;
           }
           leaf nlp-id {
             type int32;
           }
           leaf lsp-length {
             type int32;
           }
           leaf pdu-version {
             type int32;
           }
           leaf system-id-length {
             type int32;
           }
           leaf isis-packet-type {
             type int32;
           }
           leaf packet-version {
             type int32;
           }
           leaf maximum-area {
             type int32;
           }
         }
         container isis-tlv {
           leaf isis-tlv.heading {
             type string;
           }
           container isis-tlv-overhead {
             leaf isis-tlv-type {
               type int32;
             }
             leaf tlv-length {
               type int32;
             }
             leaf bytes-left {
               type int32;
             }
           }
           container area-address-tlv {
             leaf address {
               type ipaddr;
             }
             leaf tlv-length {
               type int32;
             }
           }
           container lsp-buffer-size-tlv {
             leaf lsp-buffer-size {
               type int32;
             }
           }
           container protocols-tlv {
             leaf protocol {
               type string;
             }
           }
           container mt-tlv {
             leaf mtid {
               type string;
             }
           }
           container hostname-tlv {
             leaf hostname {
               type string;
             }
           }
           container purge-originator-tlv {
             leaf purge-originator {
               type string;
             }
             leaf purge-originator-from {
               type string;
             }
           }
           container ipaddress-tlv {
             leaf address {
               type ipaddr;
             }
           }
           container ipv6address-tlv {
             leaf address {
               type ipaddr;
             }
           }
           container router-id-tlv {
             leaf router-id {
               type ipaddr;
             }
           }
           container reachability-tlv {
             leaf isis-topology-id {
               type string;
             }
             leaf reachability-tlv.heading {
               type string;
             }
             leaf address-prefix {
               type ipaddr;
             }
             leaf metric-flag {
               type string;
             }
             leaf metric {
               type int32;
             }
             leaf reachability-delay {
               type empty;
             }
             leaf reachability-expense {
               type empty;
             }
             leaf reachability-error {
               type empty;
             }
             leaf prefix-status {
               type string;
             }
             leaf address {
               type ipaddr;
             }
             leaf neighbor-prefix {
               type ipaddr;
             }
             leaf tlv-length {
               type int32;
             }
             container isis-reachability-subtlv {
               leaf local-ifindex {
                 type uint32;
                 description "Local interface index";
               }
               leaf remote-ifindex {
                 type uint32;
                 description "Remote interface index";
               }
               leaf max-bandwidth {
                 type int32;
               }
               leaf max-reserve-bandwidth {
                 type int32;
               }
               leaf current-bandwidth-header {
                 type empty;
               }
               leaf bandwidth-priority {
                 type int32;
               }
               leaf current-reserve-bandwidth {
                 type int32;
               }
               leaf te-metric {
                 type int32;
                 description "LSP TE metric";
               }
               leaf dste-bc-header {
                 type empty;
               }
               leaf dste-bc-model {
                 type string;
                 description "DiffServ TE bandwidth constraint model";
               }
               leaf dste-bc-count {
                 type int32;
                 description "DiffServ TE bandwidth constraint count";
               }
               leaf dste-bc-bw {
                 type int32;
                 description "DiffServ TE bandwidth constraint BW";
               }
               leaf p2p-adj-sid-af {
                 type string;
                 description "Point-to-Point adjacency SID address family";
               }
               leaf p2p-adj-sid-flags {
                 type string;
                 description "Point-to-Point adjacency SID flags";
               }
               leaf p2p-adj-sid-weight {
                 type int32;
                 description "Point-to-Point adjacency SID weight";
               }
               leaf p2p-adj-sid-label {
                 type string;
                 description "Point-to-Point adjacency SID label";
               }
               leaf lan-adj-sid-af {
                 type string;
                 description "LAN adjacency SID address family";
               }
               leaf lan-adj-sid-flags {
                 type string;
                 description "LAN adjacency SID flags";
               }
               leaf lan-adj-sid-weight {
                 type int32;
                 description "LAN adjacency SID weight";
               }
               leaf lan-adj-sid-sysid {
                 type string;
                 description "LAN adjacency SID neighbor system id";
               }
               leaf lan-adj-sid-label {
                 type string;
                 description "LAN adjacency SID label";
               }
               leaf isis-subtlv-type {
                 type int32;
               }
               leaf subtlv-length {
                 type int32;
               }
               container admin-groups {
                 leaf color {
                   type int32;
                 }
                 leaf no-group-flag {
                   type empty;
                 }
                 leaf admin-group-name {
                   type string;
                   description "Name of the admin group";
                 }
                 leaf admin-group-number {
                   type int32;
                   description "Number of the admin group";
                 }
               }
             }
           }
           container isis-iso-prefix-tlv {
             leaf isis-iso-prefix-tlv.heading {
               type string;
             }
             leaf metric-flag {
               type string;
             }
             leaf metric {
               type int32;
             }
             leaf reachability-delay {
               type empty;
             }
             leaf reachability-expense {
               type empty;
             }
             leaf reachability-error {
               type empty;
             }
             leaf prefix-status {
               type string;
             }
             leaf iso-prefix {
               type string;
             }
           }
           container isis-prefix-subtlv {
           }
           container ipv6-reachability-tlv {
             leaf isis-topology-id {
               type string;
             }
             leaf ipv6-reachability-tlv.heading {
               type string;
             }
             leaf ipv6-address {
               type ipv6addr;
             }
             leaf metric {
               type int32;
             }
             leaf prefix-extern {
               type empty;
             }
             leaf prefix-downflag {
               type empty;
             }
             leaf subtlv-size {
               type int32;
             }
             container isis-prefix-subtlv {
               container isis-prefix-tag {
               }
               container isis-prefix-sid {
               }
             }
           }
           container isis-reachability-subtlv {
             leaf local-ifindex {
               type uint32;
               description "Local interface index";
             }
             leaf remote-ifindex {
               type uint32;
               description "Remote interface index";
             }
             leaf max-bandwidth {
               type int32;
             }
             leaf max-reserve-bandwidth {
               type int32;
             }
             leaf current-bandwidth-header {
               type empty;
             }
             leaf bandwidth-priority {
               type int32;
             }
             leaf current-reserve-bandwidth {
               type int32;
             }
             leaf address {
               type ipaddr;
             }
             leaf neighbor-prefix {
               type ipaddr;
             }
             leaf te-metric {
               type int32;
               description "LSP TE metric";
             }
             leaf dste-bc-header {
               type empty;
             }
             leaf dste-bc-model {
               type string;
               description "DiffServ TE bandwidth constraint model";
             }
             leaf dste-bc-count {
               type int32;
               description "DiffServ TE bandwidth constraint count";
             }
             leaf dste-bc-bw {
               type int32;
               description "DiffServ TE bandwidth constraint BW";
             }
             leaf p2p-adj-sid-af {
               type string;
               description "Point-to-Point adjacency SID address family";
             }
             leaf p2p-adj-sid-flags {
               type string;
               description "Point-to-Point adjacency SID flags";
             }
             leaf p2p-adj-sid-weight {
               type int32;
               description "Point-to-Point adjacency SID weight";
             }
             leaf p2p-adj-sid-label {
               type string;
               description "Point-to-Point adjacency SID label";
             }
             leaf lan-adj-sid-af {
               type string;
               description "LAN adjacency SID address family";
             }
             leaf lan-adj-sid-flags {
               type string;
               description "LAN adjacency SID flags";
             }
             leaf lan-adj-sid-weight {
               type int32;
               description "LAN adjacency SID weight";
             }
             leaf lan-adj-sid-sysid {
               type string;
               description "LAN adjacency SID neighbor system id";
             }
             leaf lan-adj-sid-label {
               type string;
               description "LAN adjacency SID label";
             }
             leaf isis-subtlv-type {
               type int32;
             }
             leaf subtlv-length {
               type int32;
             }
             container admin-groups {
               leaf color {
                 type int32;
               }
               leaf no-group-flag {
                 type empty;
               }
               leaf admin-group-name {
                 type string;
                 description "Name of the admin group";
               }
               leaf admin-group-number {
                 type int32;
                 description "Number of the admin group";
               }
             }
           }
           container rtr-capability-tlv {
             leaf rtr-capability-tlv.heading {
               type string;
             }
             leaf router-id {
               type ipaddr;
             }
             leaf rtr-cap-flags {
               type string;
             }
             container spring-capability-sub-tlv {
               leaf spring-capability-flags {
                 type string;
               }
               leaf spring-capability-range {
                 type uint32;
               }
               leaf spring-capability-sid-label {
                 type uint32;
               }
             }
             container spring-algorithm-sub-tlv {
               leaf spring-algorithm-type {
                 type uint32;
               }
             }
           }
           container authentication-tlv {
             leaf tlv-length {
               type int32;
             }
           }
           container idrp-tlv {
             leaf tlv-length {
               type int32;
             }
           }
           container ip-prefix-tlv {
             leaf isis-topology-id {
               type string;
             }
             leaf ip-prefix-tlv.heading {
               type string;
             }
             leaf address-prefix {
               type ipaddr;
             }
             leaf metric {
               type int32;
             }
             leaf prefix-status {
               type string;
             }
             leaf subtlv-size {
               type int32;
             }
             container isis-prefix-subtlv {
               container isis-prefix-tag {
               }
               container isis-prefix-sid {
               }
             }
           }
           container isis-srlg-tlv {
             leaf isis-srlg-tlv.heading {
               type string;
             }
             leaf address-prefix {
               type ipaddr;
             }
             leaf srlg-flag {
               type string;
             }
             leaf srlg-address {
               type ipaddr;
             }
             leaf srlg-neighbor-prefix {
               type ipaddr;
             }
             leaf srlg-local-ifindex {
               type uint32;
               description "Local interface index";
             }
             leaf srlg-remote-ifindex {
               type uint32;
               description "Remote interface index";
             }
             container isis-srlg-value {
               leaf isis-srlg-value.heading {
                 type string;
               }
               leaf isis-srlg-name {
                 type string;
               }
             }
           }
           container unknown-sub-tlv {
             leaf isis-tlv-type {
               type int32;
             }
             leaf tlv-length {
               type int32;
             }
           }
           container label-binding-tlv {
             leaf protocol-name {
               type string;
             }
             leaf address-prefix {
               type ipaddr;
             }
             leaf label-binding-weight {
               type int32;
             }
             leaf label-binding-range {
               type int32;
             }
             leaf isis-label {
               type int32;
             }
           }
           container unknown-tlv {
             leaf isis-tlv-type {
               type int32;
             }
             leaf tlv-length {
               type int32;
             }
           }
           container tlv-stragglers {
             leaf bytes-left {
               type int32;
             }
           }
         }
         container transmission-status {
           leaf transmit-count {
             type int32;
           }
           leaf message {
             type string;
           }
           leaf interface-name {
             type string;
             description "Name of interface";
           }
           leaf transmit-time {
             type string;
             description "Time at which this message is queued for transmission";
           }
         }
         container isis-es-neighbor {
           leaf es-neighbor-id {
             type string;
           }
           leaf metric {
             type int32;
           }
           leaf es-neighbor-status {
             type string;
           }
         }
         container isis-label-binding {
           container normal {
             leaf protocol-name {
               type string;
             }
             leaf address-prefix {
               type ipaddr;
             }
             leaf isis-label {
               type int32;
             }
             leaf binding-flags {
               type string;
             }
           }
         }
       }
     }
   }
 }
 grouping isis-hostname-information-block {
   list isis-hostname {
     description "Entry in the system-ID-to-hostname mapping table";
     leaf system-id {
       type string;
       description "Six-octet ISO system ID for a system";
     }
     leaf system-name {
       type string;
       description "Hostname for a system";
     }
     leaf isis-hostname-type {
       type string;
       description "Type of system-ID-to-hostname mapping";
     }
   }
 }
 grouping isis-interface-information-block {
   container brief {
     container isis-interface {
       leaf interface-name {
         type string;
         description "Name of interface";
       }
       leaf circuit-type {
         type int32;
       }
       leaf circuit-id {
         type int32;
       }
       leaf isis-interface-state-one {
         type string;
       }
       leaf dr-id-one {
         type string;
       }
       leaf isis-interface-state-two {
         type string;
       }
       leaf dr-id-two {
         type string;
       }
       leaf metric-one {
         type int32;
       }
       leaf metric-two {
         type int32;
       }
       container interface-level-data {
       }
     }
   }
   container detail {
     container isis-interface {
       leaf isis-interface.heading {
         type string;
       }
       leaf interface-name {
         type string;
         description "Name of interface";
       }
       leaf interface-index {
         type int32;
       }
       leaf interface-state-value {
         type int32;
       }
       leaf circuit-id {
         type int32;
       }
       leaf circuit-type {
         type int32;
       }
       leaf interface-disabled-flag {
         type empty;
       }
       leaf lsp-interval {
         type int32;
       }
       leaf csnp-interval {
         type int32;
       }
       leaf system-name {
         type string;
         description "Hostname for a system";
       }
       leaf mesh-group {
         type string;
       }
       leaf adjacency-advertisement {
         type string;
         description "State of the adjacency advertisment";
       }
       leaf isis-layer2-map-enabled {
         type string;
         description "IS-IS controls kernel ARP/ND entries for its nexthops";
       }
       leaf interface-protection-type {
         type string;
       }
       leaf no-eligible-backup {
         type empty;
       }
       container interface-level-data {
         leaf level {
           type int32;
           description "IS-IS Level";
         }
         leaf adjacency-count {
           type int32;
         }
         leaf interface-priority {
           type int32;
         }
         leaf metric {
           type int32;
         }
         leaf passive {
           type string;
         }
         leaf hello-time {
           type int32;
         }
         leaf holdtime {
           type int32;
           description "Delay before timing out the adjacency (default is 180 seconds)";
         }
         leaf dr-id-one {
           type string;
         }
         leaf dr-id-two {
           type string;
         }
         leaf dr-flag {
           type string;
         }
       }
     }
   }
   container extensive {
     container isis-interface {
       leaf isis-interface.heading {
         type string;
       }
       leaf interface-name {
         type string;
         description "Name of interface";
       }
       leaf interface-index {
         type int32;
       }
       leaf interface-state-value {
         type int32;
       }
       leaf circuit-id {
         type int32;
       }
       leaf circuit-type {
         type int32;
       }
       leaf interface-disabled-flag {
         type empty;
       }
       leaf lsp-interval {
         type int32;
       }
       leaf csnp-interval {
         type int32;
       }
       leaf hello-padding {
         type string;
       }
       leaf max-hello-size {
         type int32;
       }
       leaf system-name {
         type string;
         description "Hostname for a system";
       }
       leaf mesh-group {
         type string;
       }
       leaf adjacency-advertisement {
         type string;
         description "State of the adjacency advertisment";
       }
       leaf isis-layer2-map-enabled {
         type string;
         description "IS-IS controls kernel ARP/ND entries for its nexthops";
       }
       leaf flood-group-iso-address {
         type string;
         description "ISO address of an interface LSP filter";
       }
       leaf igp-ldp-sync-state {
         type string;
         description "State of synchronization between Label Distribution Protocol (LDP) and the interior gateway protocol (IGP)";
       }
       leaf igp-ldp-sync-last-change {
         type string;
         description "Time since the state of synchronization between Label Distribution Protocol (LDP) and the interior gateway protocol (IGP) last changed";
       }
       leaf igp-ldp-sync-reason {
         type string;
         description "Reason for the change in the state of synchronization between Label Distribution Protocol (LDP) and the interior gateway protocol (IGP)";
       }
       leaf igp-ldp-sync-holdtime {
         type string;
         description "Length of time during which the maximum metric is advertised for an interface that is in the hold-down state because synchronization was lost between Label Distribution Protocol (LDP) and the interior gateway protocol (IGP)";
       }
       leaf igp-ldp-sync-timeleft {
         type int32;
         description "Remaining amount of time the interface will remain in the hold-down state because synchronization was lost between Label Distribution Protocol (LDP) and the interior gateway protocol (IGP)";
       }
       leaf interface-group-holddown-delay {
         type int32;
       }
       leaf interface-group-holddown-left {
         type int32;
       }
       container interface-level-data {
         leaf level {
           type int32;
           description "IS-IS Level";
         }
         leaf adjacency-count {
           type int32;
         }
         leaf interface-priority {
           type int32;
         }
         leaf metric {
           type int32;
         }
         leaf te-metric {
           type int32;
           description "LSP TE metric";
         }
         leaf passive {
           type string;
         }
         leaf hello-time {
           type int32;
         }
         leaf holdtime {
           type int32;
           description "Delay before timing out the adjacency (default is 180 seconds)";
         }
         leaf dr-id-one {
           type string;
         }
         leaf dr-id-two {
           type string;
         }
         leaf dr-flag {
           type string;
         }
         list isis-interface-level-topology {
           description "Topology-specific information for an interface level";
           leaf isis-topology-id {
             type string;
           }
           leaf isis-topology-metric {
             type int32;
             description "Metric for a topology";
           }
         }
       }
     }
   }
 }
 grouping isis-interface-group-information-block {
   container isis-interface-group {
     description "Interface-group information for an IS-IS instance";
     leaf isis-interface-group-name {
       type string;
     }
     leaf interface-name {
       type string;
       description "Name of interface";
     }
     leaf isis-interface-bandwidth {
       type string;
     }
     leaf isis-interface-state-updown {
       type string;
     }
     leaf isis-interface-state-ignore {
       type string;
     }
     leaf isis-interface-state-degrade {
       type string;
     }
     leaf isis-interface-group-bandwidth-nominal {
       type string;
     }
     leaf isis-interface-group-bandwidth-actual {
       type string;
     }
     container isis-level-information {
       description "IS-IS Level Information";
       leaf level {
         type int32;
         description "IS-IS Level";
       }
       container isis-bbm-information {
       }
     }
   }
 }
 grouping isis-layer2-map-information-block {
   container isis-layer2-map-database {
     leaf instance-name {
       type string;
     }
     leaf ip-entry-count {
       type uint32;
     }
     leaf ip6-entry-count {
       type uint32;
     }
     container isis-layer2-map-entry {
       leaf ip-address {
         type ipaddr;
       }
       leaf interface-name2 {
         type string;
       }
       leaf snpa {
         type string;
       }
       leaf isis-layer2-map-next-refresh {
         type uint32;
       }
       leaf isis-layer2-map-state {
         type string;
       }
     }
   }
 }
 grouping isis-overview-information-block {
   container isis-overview {
     description "Overview information for an IS-IS instance";
     leaf instance-name {
       type string;
     }
     leaf isis-router-id {
       type ipaddr;
       description "IS-IS router ID";
     }
     leaf isis-router-hostname {
       type string;
       description "IS-IS router hostname";
     }
     leaf isis-router-sysid {
       type string;
       description "IS-IS router sysid";
     }
     leaf isis-router-areaid {
       type string;
       description "IS-IS router areaid";
     }
     leaf isis-max-areas {
       type uint32;
       description "Maximum Number of Areas";
     }
     leaf isis-lsp-lifetime {
       type uint32;
       description "Maximum LSP lifetime";
     }
     leaf isis-lsp-lifetime-filter {
       type uint32;
       description "Low LSP life time filter";
     }
     leaf isis-reference-bandwidth {
       type uint64;
       description "Bandwidth for calculating metric defaults";
     }
     leaf isis-adjacency-holddown {
       type string;
       description "IS-IS Adjacency holddown status";
     }
     leaf isis-attached-bit-evaluation {
       type string;
       description "The IS-IS L1 attached bit evaluation";
     }
     leaf isis-layer2-map-enabled {
       type string;
       description "IS-IS controls kernel ARP/ND entries for its nexthops";
     }
     container isis-spf-information {
       description "SPF options";
       leaf isis-spf-delay {
         type string;
         description "Delay before performing SPF calculations";
       }
       leaf isis-spf-holddown {
         type string;
         description "Throttling delay between consecutive SPF calculations";
       }
       leaf isis-spf-rapid-runs {
         type uint32;
         description "Number of rapid SPF calculations before SPF holddown.";
       }
       leaf isis-uloop-avoidance {
         type string;
         description "Micro-loop avoidance status";
       }
       leaf isis-uloop-avoidance-method {
         type string;
         description "Micro-loop avoidance mechanism employed";
       }
       leaf isis-route-convergence-delay {
         type string;
         description "Delay before downloading routes to forwarding plane";
       }
       container isis-spf {
         leaf node-count {
           type int32;
         }
         container isis-spf-results-header {
           leaf isis-topology-id {
             type string;
           }
           leaf level {
             type int32;
             description "IS-IS Level";
           }
         }
         list isis-spf-result {
           leaf node-id {
             type string;
           }
           leaf metric {
             type int32;
           }
           leaf disconnected {
             type empty;
           }
           leaf no-first-fragment {
             type empty;
           }
           list next-hop-element {
             leaf interface-name {
               type string;
               description "Name of interface";
             }
             leaf isis-next-hop-type {
               type string;
             }
             leaf isis-next-hop {
               type string;
             }
             leaf snpa {
               type string;
             }
           }
           list prefix-element {
             leaf prefix-metric {
               type int32;
             }
             leaf external-prefix-metric {
               type int32;
             }
             leaf address-prefix {
               type ipaddr;
             }
           }
           list end-system-element {
             leaf end-system-metric {
               type int32;
             }
             leaf end-system-id {
               type string;
               description "Six-octet ISO system ID for a end-system";
             }
           }
         }
         container isis-spf-log-header {
           leaf isis-topology-id {
             type string;
           }
           leaf level {
             type int32;
             description "IS-IS Level";
           }
         }
         container isis-spf-log {
           leaf start-time {
             type string;
           }
           leaf elapsed-time {
             type string;
             description "Time this adjacency or session has been up or down";
           }
           leaf spf-trigger-count {
             type int32;
           }
           leaf logging-reason {
             type string;
           }
           leaf lsp-name {
             type string;
             description "Tunneled into an RSVP LSP";
           }
           leaf system-name {
             type string;
             description "Hostname for a system";
           }
           leaf interface-name {
             type string;
             description "Name of interface";
           }
         }
         container isis-backup-spf-result {
           leaf node-id {
             type string;
           }
           leaf no-first-fragment {
             type empty;
           }
           leaf backup-root {
             type string;
           }
           leaf backup-root-metric {
             type int32;
           }
           leaf metric {
             type int32;
           }
           leaf backup-root-preference {
             type int32;
           }
           leaf track-item {
             type string;
           }
           leaf track-item-isnbr {
             type string;
           }
           leaf rev-track-item {
             type string;
           }
           leaf rev-track-item-isnbr {
             type string;
           }
           list next-hop-element {
             leaf interface-name {
               type string;
               description "Name of interface";
             }
             leaf isis-next-hop-type {
               type string;
             }
             leaf isis-next-hop {
               type string;
             }
             leaf snpa {
               type string;
             }
           }
           list backup-next-hop-element {
             leaf interface-name {
               type string;
               description "Name of interface";
             }
             leaf isis-next-hop-type {
               type string;
             }
             leaf isis-next-hop {
               type string;
             }
             leaf snpa {
               type string;
             }
             leaf isis-backup-prefix-refcount {
               type uint32;
               description "Number of prefixes that uses this nexthop as backup";
             }
           }
           list no-coverage-reason-element {
             leaf isis-next-hop-type {
               type string;
             }
             leaf no-coverage-reason {
               type string;
             }
           }
         }
       }
     }
     container isis-overload-information {
       description "Overload bit behaviour at startup";
       leaf isis-overload-enabled {
         type empty;
         description "Overload bit upon startup is set";
       }
       leaf isis-overload-high-metrics {
         type string;
         description "High metrics are used for Overload signaling";
       }
       leaf isis-overload-allow-route-leaking {
         type string;
         description "Allow route leaking when configured to be in overload";
       }
       leaf isis-overload-timeout {
         type int32;
         description "Clearance of the Overload bit after startup";
       }
       leaf isis-overload-remaining-time {
         type string;
         description "Time remaining on configured overload timeout";
       }
     }
     container isis-routing {
       description "List of routed IS-IS address families";
       leaf isis-routing-ipv4 {
         type empty;
         description "Routing IPv4 prefixes is enabled";
       }
       leaf isis-routing-ipv6 {
         type empty;
         description "Routing IPv6 prefixes is enabled";
       }
       leaf isis-routing-clns {
         type empty;
         description "Routing CLNS prefixes is enabled";
       }
       leaf isis-routing-spring-mpls {
         type empty;
         description "Routing CLNS prefixes is enabled";
       }
     }
     container isis-traffic-engineering {
       description "Traffic engineering";
       leaf isis-te-status {
         type string;
         description "Traffic engineering status";
       }
       leaf isis-te-shortcuts-ipv4 {
         type empty;
         description "IPv4 Traffic engineering shortcuts are enabled";
       }
       leaf isis-te-shortcuts-ipv6 {
         type empty;
         description "IPv6 Traffic engineering shortcuts are enabled";
       }
       leaf isis-te-shortcuts-ipv4-mpls {
         type empty;
         description "IPv4-MPLS Traffic engineering shortcuts are enabled";
       }
       leaf isis-te-shortcuts-ipv6-mpls {
         type empty;
         description "IPv6-MPLS Traffic engineering shortcuts are enabled";
       }
       leaf isis-te-shortcuts-clns {
         type empty;
         description "CLNS Traffic engineering shortcuts are enabled";
       }
       leaf isis-ipv4-multicast-rpf-routes {
         type empty;
         description "IPv4 routes for multicast RPF checks are installed into inet.2";
       }
       leaf isis-ignore-lsp-metrics {
         type empty;
         description "Label-switched path metrics when doing shortcuts are ignored";
       }
     }
     container isis-restart {
       description "IS-IS restart parameters";
       leaf isis-restart-enabled {
         type string;
         description "IS-IS restart mode";
       }
       leaf isis-restart-duration {
         type uint32;
         description "Duration of IS-IS restart";
       }
       leaf isis-restart-helper-mode-enabled {
         type string;
         description "IS-IS helper mode";
       }
     }
     container isis-spring {
       description "IS-IS SPRING parameters";
       leaf isis-spring-enabled {
         type string;
         description "Source Packet Routing";
       }
       leaf isis-srgb-allocation {
         type string;
         description "SRGB Block Allocation";
       }
       leaf isis-node-segment-enabled {
         type string;
         description "Node Segments Enabled";
       }
       container isis-srgb-config {
         description "SRGB block configuration related information";
       }
       container isis-srgb-block {
         description "SRGB block related information";
       }
       container isis-node-segment {
         description "Node Segments related information";
         container isis-node-segment-block {
           description "Node Segment Blocks related information";
         }
       }
     }
     container isis-level-information {
       description "IS-IS Level Information";
       leaf isis-level {
         type int32;
         description "IS-IS Level";
       }
       leaf isis-preference {
         type uint32;
         description "IS-IS internal route preference";
       }
       leaf isis-external-preference {
         type uint32;
         description "IS-IS external route preference";
       }
       leaf isis-prefix-export-limit {
         type uint32;
         description "IS-IS limit for external route export";
       }
       leaf isis-prefix-export-count {
         type uint32;
         description "Actual number of exported prefixes";
       }
       leaf isis-wide-metrics {
         type empty;
         description "Generation of wide metric TLVs is enabled";
       }
       leaf isis-narrow-metrics {
         type empty;
         description "Generation of narrow metric TLVs is enabled";
       }
       leaf isis-level-spring-enabled {
         type empty;
         description "Source Packet Routing is enabled";
       }
       leaf isis-adjacency-holddown-state {
         type string;
       }
       leaf isis-purge-originator-info {
         type string;
         description "Type of POI that gets added to purged LSPs";
       }
     }
   }
 }
 grouping isis-route-information-block {
   container isis-routing-table {
     leaf isis-topology-id {
       type string;
     }
     leaf level-one-version {
       type int32;
     }
     leaf level-two-version {
       type int32;
     }
     container isis-route {
       container normal {
         leaf address-prefix {
           type ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         leaf isis-backup-score {
           type string;
         }
         leaf prefix-originator {
           type string;
         }
         leaf prefix-level {
           type int32;
         }
         leaf prefix-metric {
           type int32;
         }
         leaf prefix-preference {
           type int32;
         }
         leaf isis-route-priority {
           type string;
         }
         list snpa {
           list pfe-port-snpa {
             description "PFE Port SNPA";
             leaf pfe-id {
               type int32;
             }
             leaf port-id {
               type int32;
             }
           }
           list network-element-port-snpa {
             description "Network Element Port SNPA";
             leaf port-id {
               type int32;
             }
           }
           list mstp-root-snpa {
             description "Multiple Spanning Tree Protocol Root SNPA";
             leaf mstp-root-id {
               type int32;
             }
           }
           list gateway-snpa {
             description "Gateway SNPA";
             leaf gateway-addr {
               type ipaddr;
             }
           }
           list layer2-domain-port-snpa {
             description "Layer-2 Domain Port SNPA";
             leaf port-id {
               type int32;
             }
           }
           list replication-block-snpa {
             description "Replication Block SNPA";
             leaf replication-block-id {
               type int32;
             }
           }
           list replication-route-snpa {
             description "Replication Route SNPA";
             leaf network-element-id {
               type ipaddr;
             }
           }
           list layer2-multicast-port-snpa {
             description "Layer-2 Multicast Port SNPA";
             leaf layer2-multicast-port-id {
               type int32;
             }
           }
           list inh-snpa {
             description "Indirection SNPA";
             leaf inh-id {
               type int32;
             }
           }
         }
         list isis-rt-sessid {
           description "Session ID associated with the route";
           leaf isis-rt-sessid-val {
             type uint32;
           }
           leaf isis-rt-sessid-ver {
             type uint32;
           }
         }
       }
       container clns {
         leaf address-prefix {
           type ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         leaf snpa {
           type string;
         }
         leaf prefix-originator {
           type string;
         }
         leaf prefix-metric {
           type int32;
         }
         leaf prefix-preference {
           type int32;
         }
       }
       container orr {
         leaf address-prefix {
           type ipaddr;
         }
         leaf level {
           type int32;
           description "IS-IS Level";
         }
         leaf route-version {
           type int32;
         }
         leaf metric {
           type int32;
         }
         leaf metric-type {
           type string;
         }
         list snpa {
           list pfe-port-snpa {
             description "PFE Port SNPA";
             leaf pfe-id {
               type int32;
             }
             leaf port-id {
               type int32;
             }
           }
           list network-element-port-snpa {
             description "Network Element Port SNPA";
             leaf port-id {
               type int32;
             }
           }
           list mstp-root-snpa {
             description "Multiple Spanning Tree Protocol Root SNPA";
             leaf mstp-root-id {
               type int32;
             }
           }
           list gateway-snpa {
             description "Gateway SNPA";
             leaf gateway-addr {
               type ipaddr;
             }
           }
           list layer2-domain-port-snpa {
             description "Layer-2 Domain Port SNPA";
             leaf port-id {
               type int32;
             }
           }
           list replication-block-snpa {
             description "Replication Block SNPA";
             leaf replication-block-id {
               type int32;
             }
           }
           list replication-route-snpa {
             description "Replication Route SNPA";
             leaf network-element-id {
               type ipaddr;
             }
           }
           list layer2-multicast-port-snpa {
             description "Layer-2 Multicast Port SNPA";
             leaf layer2-multicast-port-id {
               type int32;
             }
           }
           list inh-snpa {
             description "Indirection SNPA";
             leaf inh-id {
               type int32;
             }
           }
         }
       }
       container mpls {
         leaf address-prefix {
           type ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         list snpa {
           list pfe-port-snpa {
             description "PFE Port SNPA";
             leaf pfe-id {
               type int32;
             }
             leaf port-id {
               type int32;
             }
           }
           list network-element-port-snpa {
             description "Network Element Port SNPA";
             leaf port-id {
               type int32;
             }
           }
           list mstp-root-snpa {
             description "Multiple Spanning Tree Protocol Root SNPA";
             leaf mstp-root-id {
               type int32;
             }
           }
           list gateway-snpa {
             description "Gateway SNPA";
             leaf gateway-addr {
               type ipaddr;
             }
           }
           list layer2-domain-port-snpa {
             description "Layer-2 Domain Port SNPA";
             leaf port-id {
               type int32;
             }
           }
           list replication-block-snpa {
             description "Replication Block SNPA";
             leaf replication-block-id {
               type int32;
             }
           }
           list replication-route-snpa {
             description "Replication Route SNPA";
             leaf network-element-id {
               type ipaddr;
             }
           }
           list layer2-multicast-port-snpa {
             description "Layer-2 Multicast Port SNPA";
             leaf layer2-multicast-port-id {
               type int32;
             }
           }
           list inh-snpa {
             description "Indirection SNPA";
             leaf inh-id {
               type int32;
             }
           }
         }
       }
       container inet-mpls {
         leaf address-prefix {
           type ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         leaf isis-backup-score {
           type string;
         }
         leaf prefix-originator {
           type string;
         }
         leaf prefix-level {
           type int32;
         }
         leaf prefix-metric {
           type int32;
         }
         leaf prefix-preference {
           type int32;
         }
         list snpa {
           list pfe-port-snpa {
             description "PFE Port SNPA";
             leaf pfe-id {
               type int32;
             }
             leaf port-id {
               type int32;
             }
           }
           list network-element-port-snpa {
             description "Network Element Port SNPA";
             leaf port-id {
               type int32;
             }
           }
           list mstp-root-snpa {
             description "Multiple Spanning Tree Protocol Root SNPA";
             leaf mstp-root-id {
               type int32;
             }
           }
           list gateway-snpa {
             description "Gateway SNPA";
             leaf gateway-addr {
               type ipaddr;
             }
           }
           list layer2-domain-port-snpa {
             description "Layer-2 Domain Port SNPA";
             leaf port-id {
               type int32;
             }
           }
           list replication-block-snpa {
             description "Replication Block SNPA";
             leaf replication-block-id {
               type int32;
             }
           }
           list replication-route-snpa {
             description "Replication Route SNPA";
             leaf network-element-id {
               type ipaddr;
             }
           }
           list layer2-multicast-port-snpa {
             description "Layer-2 Multicast Port SNPA";
             leaf layer2-multicast-port-id {
               type int32;
             }
           }
           list inh-snpa {
             description "Indirection SNPA";
             leaf inh-id {
               type int32;
             }
           }
         }
         list isis-rt-sessid {
           description "Session ID associated with the route";
           leaf isis-rt-sessid-val {
             type uint32;
           }
           leaf isis-rt-sessid-ver {
             type uint32;
           }
         }
       }
     }
   }
 }
 grouping isis-purge-information-block {
   container isis-purge {
     container isis-purge-log-header {
       leaf level {
         type int32;
         description "IS-IS Level";
       }
     }
     container isis-purge-log {
       leaf start-time {
         type string;
       }
       leaf lsp-name {
         type string;
         description "Tunneled into an RSVP LSP";
       }
       leaf osystem-name {
         type string;
         description "Hostname for a system";
       }
       leaf rsystem-name {
         type string;
         description "Hostname for a system";
       }
     }
   }
 }
 grouping isis-statistics-information-block {
   container isis-statistics {
     leaf system-name {
       type string;
       description "Hostname for a system";
     }
     leaf snp-queue-length {
       type int32;
     }
     leaf snp-queue-drops {
       type int32;
     }
     leaf lsp-queue-length {
       type int32;
     }
     leaf lsp-queue-drops {
       type int32;
     }
     leaf spf-runs {
       type int32;
     }
     leaf fragments-rebuilt {
       type int32;
     }
     leaf lsps-regenerated {
       type int32;
     }
     leaf purges-initiated {
       type int32;
     }
     leaf purges-received {
       type int32;
     }
     list isis-pdu-statistics {
       leaf isis-pdu-type {
         type string;
       }
       leaf packets-received {
         type uint64;
       }
       leaf packets-processed {
         type uint64;
       }
       leaf packets-dropped {
         type uint64;
       }
       leaf packets-sent {
         type uint64;
       }
       leaf packets-retransmitted {
         type uint64;
       }
     }
     container totals-information {
       leaf packets-received {
         type uint64;
       }
       leaf packets-sent {
         type uint64;
       }
     }
   }
 }
 }
