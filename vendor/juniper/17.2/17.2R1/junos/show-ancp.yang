/*
 * Copyright (c) 2017 Juniper Networks, Inc.
 * All rights reserved.
 */
 module show-ancp {
  namespace "http://yang.juniper.net/yang/1.1/jrpc/show-ancp/junos/17.2R1.13";
  prefix show-ancp;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ancp-cos-information {
     description "Show ANCP class-of-service information";
     input {
       leaf identifier {
         description "Access loop identifier";
         type string;
       }
     }
     output {
       container ancp-cos-information {
         uses ancp-cos-information-block;
       }
     }
   }
   rpc get-ancp-cos-pending-information {
     description "Show ANCP class-of-service pending update information";
     output {
       container ancp-cos-information {
         uses ancp-cos-information-block;
       }
     }
   }
   rpc get-ancp-cos-last-update-information {
     description "Show ANCP class-of-service last update information";
     output {
       container ancp-cos-information {
         uses ancp-cos-information-block;
       }
     }
   }
   rpc get-ancp-neighbor-information {
     description "Neighbor information";
     input {
       leaf verbosity_level {
         default "brief";
         type enumeration {
           enum "brief" {
             description "Display brief output (default)";
           }
           enum "detail" {
             description "Display detailed output";
           }
         }
       }
       container neighbor-opts {
         choice neighbor-opts_c {
           case ip-address {
             leaf ip-address {
               description "IP address of the neighbor";
               type ipaddr;
             }
           }
           case system-name {
             leaf system-name {
               description "MAC address of the neighbor";
               type string;
             }
           }
         }
       }
     }
     output {
       container ancp-neighbor-information {
         uses ancp-neighbor-information-block;
       }
     }
   }
   rpc get-ancp-subscriber-information {
     description "Subscriber information";
     input {
       leaf verbosity_level {
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-subscriber-identifier-information {
     description "Access circuit identifier";
     input {
       leaf identifier-name {
         description "Identifier";
         type string;
         mandatory true;
       }
       leaf verbosity_level {
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-subscriber-neighbor-information {
     description "IP address of the neighbor";
     input {
       leaf neighbor-ipaddress {
         description "IP address of the neighbor";
         type ipaddr;
         mandatory true;
       }
       leaf verbosity_level {
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-subscriber-mac-information {
     description "MAC address of the neighbor";
     input {
       leaf neighbor-macaddress {
         description "MAC address of the neighbor";
         type string;
         mandatory true;
       }
       leaf verbosity_level {
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-summary-information {
     description "ANCP summary";
     output {
       container ancp-summary-information {
         uses ancp-summary-information-block;
       }
     }
   }
   rpc get-ancp-subscriber-summary {
     description "ANCP subscribers summary";
   }
   rpc get-ancp-neighbor-summary {
     description "ANCP neighbors summary";
     input {
       container neighbor-opts {
         choice neighbor-opts_c {
           case ip-address {
             leaf ip-address {
               description "IP address of the neighbor";
               type ipaddr;
             }
           }
           case system-name {
             leaf system-name {
               description "MAC address of the neighbor";
               type string;
             }
           }
         }
       }
     }
   }
   rpc get-ancp-stats-information {
     description "Statistics";
     input {
       container neighbor-opts {
         choice neighbor-opts_c {
           case ip-address {
             leaf ip-address {
               description "IP address of the neighbor";
               type ipaddr;
             }
           }
           case system-name {
             leaf system-name {
               description "MAC address of the neighbor";
               type string;
             }
           }
         }
       }
     }
     output {
       container ancp-statistics-information {
         uses ancp-statistics-information-block;
       }
     }
   }
 grouping ancp-cos-information-block {
   container ancp-cos-heading {
     leaf keepalive-timer {
       type int32;
       description "Keepalive timer";
     }
     leaf connect-state {
       type string;
       description "State";
     }
     leaf connect-time {
       type string;
       description "Connect time";
     }
     leaf session-time {
       type string;
       description "Session sent time";
     }
     leaf rtcreate-time {
       type string;
       description "Routing instance create time";
     }
     leaf keepalive-time {
       type string;
       description "Keepalive sent time";
     }
     leaf update-time {
       type string;
       description "Update sent time";
     }
   }
   container ancp-cos-adjust-entry {
     leaf qos-adjust {
       type string;
     }
     leaf cos-adjust-adsl1-bytes {
       type int32;
     }
     leaf cos-adjust-adsl2-bytes {
       type int32;
     }
     leaf cos-adjust-adsl2-plus-bytes {
       type int32;
     }
     leaf cos-adjust-vdsl {
       type int32;
     }
     leaf cos-adjust-vdsl-bytes {
       type int32;
     }
     leaf cos-adjust-vdsl2 {
       type int32;
     }
     leaf cos-adjust-vdsl2-bytes {
       type int32;
     }
     leaf cos-adjust-sdsl {
       type int32;
     }
     leaf cos-adjust-sdsl-bytes {
       type int32;
     }
     leaf cos-adjust-other {
       type int32;
     }
     leaf cos-adjust-other-bytes {
       type int32;
     }
   }
   container ancp-qos-adjust-entry {
     leaf qos-adjust-adsl {
       type int32;
       description "QoS ADSL adjustment factor";
     }
     leaf qos-adjust-adsl2 {
       type int32;
       description "QoS ADSL2 adjustment factor";
     }
     leaf qos-adjust-adsl2-plus {
       type int32;
       description "QoS ADSL2+ adjustment factor";
     }
     leaf qos-adjust-vdsl {
       type int32;
       description "QoS VDSL adjustment factor";
     }
     leaf qos-adjust-vdsl2 {
       type int32;
       description "QoS VDSL2 adjustment factor";
     }
     leaf qos-adjust-sdsl {
       type int32;
       description "QoS SDSL adjustment factor";
     }
     leaf qos-adjust-other {
       type int32;
       description "QoS OTHER adjustment factor";
     }
   }
   container ancp-cos-entry {
     leaf interface-type {
       type string;
       description "Subscriber's interface type";
     }
     leaf interface-name {
       type string;
       description "Ifl/Iflset name";
     }
     leaf interface-index {
       type int32;
       description "Ifl/Iflset index";
     }
     leaf shaping-rate {
       type string;
       description "Shaping rate";
     }
     leaf last-update {
       type string;
       description "Last updated shaping rate";
     }
   }
 }
 grouping ancp-neighbor-information-block {
   container brief {
     list ancp-neighbor {
       description "Information about a single ANCP neighbor";
       leaf neighbor-stale-flag {
         type string;
         description "ANCP neighbor stale entry flag";
       }
       leaf protocol-version {
         type string;
         description "Neighbor protocol version";
       }
       leaf ip-address {
         type ipaddr;
         description "Neighbor IP address";
       }
       leaf partition-identifier {
         type int32;
         description "Neighbor partition identifier";
       }
       leaf state {
         type string;
         description "Neighbor adjacency state";
       }
       leaf up-time {
         type string;
         description "Up time";
       }
       leaf neighbor-subscriber-count {
         type int32;
         description "Neighbor subscriber count";
       }
       leaf capabilities {
         type string;
         description "Neighbor capabilities";
       }
     }
   }
   container detail {
     list ancp-neighbor {
       description "Information about a single ANCP neighbor";
       leaf protocol-version {
         type string;
         description "Neighbor protocol version";
       }
       leaf neighbor-stale-flag {
         type string;
         description "ANCP neighbor stale entry flag";
       }
       leaf ip-address {
         type ipaddr;
         description "Neighbor IP address";
       }
       leaf mac-address {
         type mac-addr;
         description "Neighbor MAC address";
       }
       leaf neighbor-autoconf-interface {
         type string;
         description "Auto-configure trigger interface";
       }
       leaf up-time {
         type string;
         description "Up time";
       }
       leaf tcp-port {
         type int32;
         description "TCP port used by connection";
       }
       leaf state {
         type string;
         description "Neighbor adjacency state";
       }
       leaf neighbor-subscriber-count {
         type int32;
         description "Neighbor subscriber count";
       }
       leaf system-instance {
         type int32;
         description "Neighbor system instance";
       }
       leaf peer-instance {
         type int32;
         description "Neighbor peer instance";
       }
       leaf capabilities {
         type string;
         description "Neighbor capabilities";
       }
       leaf adjacency-time {
         type int32;
         description "Adjacency time advertised in 100ms";
       }
       leaf peer-adjacency-time {
         type int32;
         description "Neighbor adjacency timer value in 100ms";
       }
       leaf adjacency-loss-hold-time {
         type int32;
         description "Audit duration upon adjacency loss in seconds";
       }
       leaf partition-type {
         type int32;
         description "Neighbor partition type";
       }
       leaf partition-flag {
         type int32;
         description "Neighbor partition flag";
       }
       leaf partition-identifier {
         type int32;
         description "Neighbor partition identifier";
       }
       leaf partition-adjacencies {
         type int32;
         description "Adjacencies established on partition";
       }
       leaf dead-time {
         type int32;
         description "Time left to receive an adjacency message";
       }
       leaf received-syn-count {
         type int32;
         description "Count of SYN messages received";
       }
       leaf received-synack-count {
         type int32;
         description "Count of SYNACK messages received";
       }
       leaf received-rstack-count {
         type int32;
         description "Count of RSTACK messages received";
       }
       leaf received-ack-count {
         type int32;
         description "Count of ACK messages received";
       }
       leaf received-port-up-count {
         type int32;
         description "Count of port up messages received";
       }
       leaf received-port-down-count {
         type int32;
         description "Count of port down messages received";
       }
       leaf received-generic-response-count {
         type int32;
         description "Count of generic response messages received";
       }
       leaf received-adjacency-update-count {
         type int32;
         description "Count of adjacency update messages received";
       }
       leaf received-oam-count {
         type int32;
         description "Count of OAM messages received";
       }
       leaf received-other-count {
         type int32;
         description "Count of other messages received";
       }
       leaf sent-syn-count {
         type int32;
         description "Count of SYN messages sent";
       }
       leaf sent-synack-count {
         type int32;
         description "Count of SYNACK messages sent";
       }
       leaf sent-rstack-count {
         type int32;
         description "Count of RSTACK messages sent";
       }
       leaf sent-ack-count {
         type int32;
         description "Count of ACK messages sent";
       }
       leaf sent-generic-response-count {
         type int32;
         description "Count of generic response messages sent";
       }
       leaf sent-oam-count {
         type int32;
         description "Count of OAM messages sent";
       }
       leaf max-discovery-limit-exceed-count {
         type int32;
         description "Count of discovery table entries not created due to limit";
       }
     }
   }
 }
 grouping ancp-subscriber-information-block {
   container brief {
     leaf access-loop-identifier {
       type string;
       description "Subscriber circuit identifier";
     }
     leaf dsl-line-state {
       type string;
       description "DSL line state";
     }
     leaf dsl-type {
       type string;
       description "DSL type";
     }
     leaf interface {
       type string;
       description "Subscriber's interface name";
     }
     leaf actual-net-data-downstream {
       type int32;
       description "Actual net data downstream";
     }
     leaf neighbor-ip-address {
       type ipaddr;
       description "IP address of the ANCP neighbor";
     }
     list ancp-subscriber {
       description "Information about a single ANCP subscriber";
       leaf subscriber-stale-flag {
         type string;
         description "ANCP neighbor stale entry flag";
       }
     }
     list ancp-neighbor {
       description "Information about a single ANCP neighbor";
     }
   }
   container detail {
     leaf ancp-subscriber-stale-flag {
       type string;
       description "ANCP neighbor stale entry flag";
     }
     leaf access-loop-identifier {
       type string;
       description "Subscriber circuit identifier";
     }
     leaf access-loop-remote-identifier {
       type string;
       description "Subscriber remote identifier";
     }
     leaf neighbor-ip-address {
       type ipaddr;
       description "IP address of the ANCP neighbor";
     }
     leaf access-aggregate-circuit-ascii-identifier {
       type string;
       description "Aggregate circuit ASCII identifier";
     }
     leaf access-aggregate-circuit-binary-identifier {
       type string;
       description "Aggregate circuit binary identifier";
     }
     leaf dsl-type {
       type string;
       description "DSL type";
     }
     leaf dsl-line-state {
       type string;
       description "DSL line state";
     }
     leaf dsl-line-data-link {
       type string;
       description "DSL data link type";
     }
     leaf dsl-line-encapsulation {
       type string;
       description "DSL line encapsulation";
     }
     leaf dsl-line-encapsulation-payload {
       type string;
       description "DSL line encapsulation payload";
     }
     leaf interface-type {
       type string;
       description "Subscriber's interface type";
     }
     leaf interface {
       type string;
       description "Subscriber's interface name";
     }
     leaf actual-net-data-upstream {
       type int32;
       description "Actual net data upstream";
     }
     leaf actual-net-data-downstream {
       type int32;
       description "Actual net data downstream";
     }
     leaf minimum-net-data-upstream {
       type int32;
       description "Minimum net data upstream";
     }
     leaf minimum-net-data-downstream {
       type int32;
       description "Minimum net data downstream";
     }
     leaf maximum-net-data-upstream {
       type int32;
       description "Maximum net data upstream";
     }
     leaf maximum-net-data-downstream {
       type int32;
       description "Maximum net data downstream";
     }
     leaf attainable-net-data-upstream {
       type int32;
       description "Attainable net data upstream";
     }
     leaf attainable-net-data-downstream {
       type int32;
       description "Attainable net data downstream";
     }
     leaf minimum-low-power-data-upstream {
       type int32;
       description "Minimum net low power upstream";
     }
     leaf minimum-low-power-data-downstream {
       type int32;
       description "Minimum net low power downstream";
     }
     leaf maximum-interleave-delay-upstream {
       type int32;
       description "Maximum interleaving delay upstream";
     }
     leaf maximum-interleave-delay-downstream {
       type int32;
       description "Maximum interleaving delay downstream";
     }
     leaf actual-interleave-delay-upstream {
       type int32;
       description "Actual interleaving delay upstream";
     }
     leaf actual-interleave-delay-downstream {
       type int32;
       description "Actual interleaving delay downstream";
     }
   }
 }
 grouping ancp-summary-information-block {
   container ancp-neighbor-summary {
     leaf ancp-neighbor-status-summary {
       type string;
       description "Neighbor summary";
     }
   }
   container ancp-neighbors-summary {
     leaf ancp-configured-status-nbr-summary {
       type uint32;
       description "Configured state summary";
     }
     leaf ancp-establishing-status-nbr-summary {
       type uint32;
       description "Establishing state summary";
     }
     leaf ancp-established-status-nbr-summary {
       type uint32;
       description "Established state summary";
     }
     leaf ancp-not-established-status-nbr-summary {
       type uint32;
       description "Not established state summary";
     }
     leaf ancp-total-status-nbr-summary {
       type uint32;
       description "Total state summary";
     }
   }
   container ancp-subscribers-summary {
     leaf ancp-show-time-status-subscr-summary {
       type uint32;
       description "SYN sent state summary";
     }
     leaf ancp-idle-status-subscr-summary {
       type uint32;
       description "SYN received state summary";
     }
     leaf ancp-silent-status-subscr-summary {
       type uint32;
       description "Established state summary";
     }
     leaf ancp-unknown-status-subscr-summary {
       type uint32;
       description "Unknown state summary";
     }
     leaf ancp-total-status-subscr-summary {
       type uint32;
       description "Total state summary";
     }
   }
 }
 grouping ancp-statistics-information-block {
   leaf neighbor-count {
     type int32;
     description "Count of ANCP neighbors in the system";
   }
   leaf subscriber-count {
     type int32;
     description "Count of ANCP subscribers in the system";
   }
   leaf accept-count {
     type int32;
     description "Count of session accepts";
   }
   leaf accept-fail-count {
     type int32;
     description "Count of session accept failures";
   }
   leaf accept-config-deny-count {
     type int32;
     description "Count of session accept denied because of no configuration";
   }
   leaf received-syn-count {
     type int32;
     description "Count of SYN messages received";
   }
   leaf received-synack-count {
     type int32;
     description "Count of SYNACK messages received";
   }
   leaf received-rstack-count {
     type int32;
     description "Count of RSTACK messages received";
   }
   leaf received-ack-count {
     type int32;
     description "Count of ACK messages received";
   }
   leaf received-port-up-count {
     type int32;
     description "Count of port up messages received";
   }
   leaf received-port-down-count {
     type int32;
     description "Count of port down messages received";
   }
   leaf received-generic-response-count {
     type int32;
     description "Count of generic response messages received";
   }
   leaf received-adjacency-update-count {
     type int32;
     description "Count of adjacency update messages received";
   }
   leaf received-oam-count {
     type int32;
     description "Count of OAM messages received";
   }
   leaf received-other-count {
     type int32;
     description "Count of other messages received";
   }
   leaf sent-syn-count {
     type int32;
     description "Count of SYN messages sent";
   }
   leaf sent-synack-count {
     type int32;
     description "Count of SYNACK messages sent";
   }
   leaf sent-rstack-count {
     type int32;
     description "Count of RSTACK messages sent";
   }
   leaf sent-ack-count {
     type int32;
     description "Count of ACK messages sent";
   }
   leaf sent-generic-response-count {
     type int32;
     description "Count of generic response messages sent";
   }
   leaf sent-oam-count {
     type int32;
     description "Count of OAM messages sent";
   }
 }
 }
