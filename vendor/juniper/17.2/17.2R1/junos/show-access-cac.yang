/*
 * Copyright (c) 2017 Juniper Networks, Inc.
 * All rights reserved.
 */
 module show-access-cac {
  namespace "http://yang.juniper.net/yang/1.1/jrpc/show-access-cac/junos/17.2R1.13";
  prefix show-access-cac;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-access-cac-pools-summary {
     description "Show access cac pool information summary";
     output {
       container access-cac-pools-summary {
         uses access-cac-pools-summary-block;
       }
     }
   }
   rpc get-access-cac-session {
     description "Show access cac session";
     output {
       container access-cac-session {
         uses access-cac-session-block;
       }
     }
   }
   rpc get-access-cac-iflset {
     description "Show access cac interface-set info";
     input {
       leaf interface-set-name {
         description "Name of interface-set";
         type string;
       }
       leaf display-style {
         description "Display style";
         type enumeration {
           enum "detail" {
             description "Display detailed output";
           }
         }
       }
     }
     output {
       container access-cac-iflset {
         uses access-cac-iflset-block;
       }
     }
   }
 grouping access-cac-pools-summary-block {
   leaf total-subscribers-with-pools {
     type uint32;
     description "Number of subscribers configured with bandwidth pools";
   }
   leaf total-mcast-video-pools {
     type uint32;
     description "Number of mcast video pools configured";
   }
   leaf total-video-pools {
     type uint32;
     description "Number of video pools configured";
   }
   leaf total-mcast-channels-subscribered {
     type uint32;
     description "Number of total mcast-channels subscribered";
   }
 }
 grouping access-cac-session-block {
   leaf session-not-available {
     type empty;
   }
   leaf access-cac-session-id {
     type uint64;
     description "Access cac session id";
   }
   leaf session-cfg-mcast-bandwidth {
     type uint64;
     description "Configured mcast video pool size";
   }
   leaf session-consumed-mcast-bandwidth {
     type uint64;
     description "Consumed mcast video bandwidth";
   }
   leaf session-cfg-video-bandwidth {
     type uint64;
     description "Configured shared video bandwidth";
   }
   leaf session-consumed-video-bandwidth {
     type uint64;
     description "Consumed shared video bandwidth";
   }
   list mcast-source-group {
     leaf mcast-source {
       type ipaddr;
       description "Source address";
     }
     leaf mcast-group {
       type ipaddr;
       description "Group address";
     }
     leaf channel-configured-rate {
       type uint64;
       description "Channel configured rate (bps)";
     }
     leaf channel-measured-rate {
       type uint64;
       description "Channel measured rate (bps)";
     }
     leaf measured-rate-not-available {
       type empty;
     }
   }
 }
 grouping access-cac-iflset-block {
   leaf access-cac-iflset-name {
     type string;
     description "Access cac tracked iflset name";
   }
   leaf access-cac-iflset-total-adjust {
     type uint64;
     description "Total current adjustment on iflset";
   }
   list mcast-source-group {
     leaf mcast-source {
       type ipaddr;
       description "Source address";
     }
     leaf mcast-group {
       type ipaddr;
       description "Group address";
     }
     leaf channel-configured-rate {
       type uint64;
       description "Channel configured rate (bps)";
     }
     leaf channel-measured-rate {
       type uint64;
       description "Channel measured rate (bps)";
     }
     leaf measured-rate-not-available {
       type empty;
     }
   }
 }
 }
