/*
 * Copyright (c) 2017 Juniper Networks, Inc.
 * All rights reserved.
 */
 module show-dhcp-security {
  namespace "http://yang.juniper.net/yang/1.1/jrpc/show-dhcp-security/junos/17.2R1.13";
  prefix show-dhcp-security;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-dhcp-security-arp-inspection-statistics {
     description "Show DHCP security ARP inspection statistics";
     output {
       container dhcp-dai-information {
         uses dhcp-dai-information-block;
       }
     }
   }
   rpc get-dhcp-security-binding {
     description "Show dhcp-security bindings";
     output {
       container dhcp-security-binding {
         uses dhcp-security-binding-block;
       }
     }
   }
   rpc get-dhcp-security-binding-interface {
     description "Name of interface on which to show bindings";
     input {
       leaf interface-name {
         description "Name of interface";
         type interface-name;
         mandatory true;
       }
     }
     output {
       container dhcp-security-binding {
         uses dhcp-security-binding-block;
       }
     }
   }
   rpc get-dhcp-security-binding-vlan {
     description "Name of vlan on which to show bindings";
     input {
       leaf vlan-name {
         description "Name of vlan";
         type string;
         mandatory true;
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-security-binding {
         uses dhcp-security-binding-block;
       }
     }
   }
   rpc get-dhcp-security-binding-ip-address {
     description "Ip-address to show bindings";
     input {
       leaf ip-address {
         description "Ip-address";
         type ipv4addr;
         mandatory true;
       }
     }
     output {
       container dhcp-security-binding {
         uses dhcp-security-binding-block;
       }
     }
   }
   rpc get-dhcp-security-binding-statistics {
     description "Show DHCP snooping statistics";
     output {
       container jdhcp-snooping-statistics {
         uses jdhcp-snooping-statistics-block;
       }
     }
   }
   rpc get-dhcp-security-ip-source-guard {
     description "Show IP Source Guard information";
     output {
       container dhcp-security-binding {
         uses dhcp-security-binding-block;
       }
     }
   }
   rpc get-dhcp-security-nd-inspection-statistics {
     description "Show neighbor discovery inspection statistics";
     output {
       container dhcp-ndi-information {
         uses dhcp-ndi-information-block;
       }
     }
   }
   rpc get-dhcp-security-ndi-interface {
     description "Name of interface for which to show statistics";
     input {
       leaf interface-name {
         description "Name of interface";
         type interface-name;
         mandatory true;
       }
     }
   }
   rpc get-dhcp-ipv6-statistics {
     description "Show DHCPv6 snooping statistics";
   }
   rpc get-dhcpv6-security-binding {
     description "Show DHCPv6 security bindings";
     output {
       container dhcpv6-security-binding {
         uses dhcpv6-security-binding-block;
       }
     }
   }
   rpc get-dhcpv6-security-binding-interface {
     description "Name of interface on which to show bindings";
     input {
       leaf interface-name {
         description "Name of interface";
         type interface-name;
         mandatory true;
       }
     }
     output {
       container dhcpv6-security-binding {
         uses dhcpv6-security-binding-block;
       }
     }
   }
   rpc get-dhcpv6-security-binding-vlan {
     description "Name of vlan on which to show bindings";
     input {
       leaf vlan-name {
         description "Name of vlan";
         type string;
         mandatory true;
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcpv6-security-binding {
         uses dhcpv6-security-binding-block;
       }
     }
   }
   rpc get-dhcpv6-security-binding-ip-address {
     description "IPv6 address to show bindings";
     input {
       leaf ipv6-address {
         description "IPv6 address";
         type ipv6addr;
         mandatory true;
       }
     }
     output {
       container dhcpv6-security-binding {
         uses dhcpv6-security-binding-block;
       }
     }
   }
   rpc get-dhcp-security-statistics {
     description "Show DHCP security statistics";
     output {
       container dhcp-security-statistics {
         uses dhcp-security-statistics-block;
       }
     }
   }
 grouping dhcp-dai-information-block {
   container dai-summary {
     list dai-entry {
     }
   }
 }
 grouping dhcp-security-binding-block {
   container dhcp-security-entries {
     list dhcp-security-entry {
     }
   }
 }
 grouping jdhcp-snooping-statistics-block {
   leaf successful-transfers {
     type int32;
     description "Successful transfers";
   }
   leaf failed-transfers {
     type int32;
     description "Failed transfers";
   }
   leaf successful-reads {
     type int32;
     description "Successful reads";
   }
   leaf failed-reads {
     type int32;
     description "Failed reads";
   }
   leaf successful-writes {
     type int32;
     description "Successful writes";
   }
   leaf failed-writes {
     type int32;
     description "Failed writes";
   }
 }
 grouping dhcp-ndi-information-block {
   container ndi-summary {
     list ndi-entry {
     }
   }
 }
 grouping dhcpv6-security-binding-block {
   container dhcpv6-security-entries {
     list dhcpv6-security-entry {
     }
   }
 }
 grouping dhcp-security-statistics-block {
   leaf total {
     type int32;
   }
   leaf discover {
     type int32;
   }
   leaf offer {
     type int32;
   }
   leaf request {
     type int32;
   }
   leaf decline {
     type int32;
   }
   leaf ack {
     type int32;
   }
   leaf nack {
     type int32;
   }
   leaf release {
     type int32;
   }
   leaf inform {
     type int32;
   }
   leaf force-renew {
     type int32;
   }
   leaf renew {
     type int32;
   }
   leaf rebind {
     type int32;
   }
   leaf total-ce-mac-mismatch {
     type int32;
   }
   leaf total-trans-stale-timer_expiry {
     type int32;
   }
   leaf succ-updated-snoop-binding {
     type int32;
   }
   leaf total-current-transient-ce {
     type int32;
   }
   leaf total-dropped {
     type int32;
   }
   leaf no-cfg {
     type int32;
   }
   leaf no-vlan {
     type int32;
   }
   leaf no-ifl {
     type int32;
   }
   leaf request-on-trusted-port {
     type int32;
   }
   leaf first-packet-time {
     type string;
   }
   leaf last-packet-time {
     type string;
   }
   leaf process-time-in-seconds {
     type int32;
   }
   leaf first-client-time {
     type string;
   }
   leaf last-client-time {
     type string;
   }
   leaf client-process-time-in-seconds {
     type int32;
   }
   leaf mclag_rcvd_request {
     type int32;
   }
   leaf mclag_rcvd_decline {
     type int32;
   }
   leaf mclag_rcvd_ack {
     type int32;
   }
   leaf mclag_rcvd_nack {
     type int32;
   }
   leaf mclag_rcvd_release {
     type int32;
   }
   leaf mclag_rcvd_snoop_binding {
     type int32;
   }
   leaf mclag_rcvd_req_snoop_binding {
     type int32;
   }
   leaf mclag_sent_request {
     type int32;
   }
   leaf mclag_sent_decline {
     type int32;
   }
   leaf mclag_sent_ack {
     type int32;
   }
   leaf mclag_sent_nack {
     type int32;
   }
   leaf mclag_sent_release {
     type int32;
   }
   leaf mclag_sent_snoop_binding {
     type int32;
   }
   leaf mclag_sent_req_snoop_binding {
     type int32;
   }
   container mclag_redundancy_groups {
     list mclag_redundancy_group_state {
     }
   }
 }
 }
