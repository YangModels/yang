/*
 * Copyright (c) 2017 Juniper Networks, Inc.
 * All rights reserved.
 */
 module show-backup-selection {
  namespace "http://yang.juniper.net/yang/1.1/jrpc/show-backup-selection/junos/17.2R1.13";
  prefix show-backup-selection;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-backup-selection {
     description "Show backup selection policies information";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf prefix {
         description "IP address and optional prefix length of destination";
         type ipprefix-optional;
       }
       leaf interface {
         description "Name of interface";
         type interface-wildcard;
       }
     }
   }
   rpc get-backup-selection-instance {
     description "Show routing instances information";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
       leaf instance-name {
         description "Instance name";
         type string;
       }
       leaf prefix {
         description "IP address and optional prefix length of destination";
         type ipprefix-optional;
       }
       leaf interface {
         description "Name of interface";
         type interface-wildcard;
       }
     }
     output {
       container instance-information {
         uses instance-information-block;
       }
     }
   }
 grouping instance-information-block {
   container terse {
     description "Operational and configuration information for routing instances";
     list instance-core {
       leaf instance-name {
         type string;
       }
       leaf instance-type {
         type string;
       }
       list instance-rib {
         leaf irib-name {
           type string;
         }
         leaf irib-active-count {
           type int32;
         }
         leaf irib-holddown-count {
           type int32;
         }
         leaf irib-hidden-count {
           type int32;
         }
       }
       container instance-localize {
       }
     }
   }
   container detail {
     description "Operational and configuration information for routing instances";
     list instance-core {
       leaf instance-name {
         type string;
       }
       leaf instance-description {
         type string;
       }
       leaf router-id {
         type ipaddr;
       }
       leaf instance-type {
         type string;
       }
       leaf instance-state {
         type string;
       }
       leaf instance-restart-state {
         type string;
       }
       leaf instance-pathsel-timeout {
         type int32;
       }
       list instance-rib {
         leaf irib-name {
           type string;
         }
         leaf irib-route-count {
           type int32;
         }
         leaf irib-active-count {
           type int32;
         }
         leaf irib-holddown-count {
           type int32;
         }
         leaf irib-hidden-count {
           type int32;
         }
         leaf irib-restart-state {
           type string;
         }
       }
       list instance-interface {
         leaf interface-name {
           type string;
           description "Name of interface";
         }
       }
       container instance-localize {
         list instance-localize-scope {
           leaf localize-scope {
             type string;
           }
         }
         list instance-localize-interface {
           leaf interface-name {
             type string;
             description "Name of interface";
           }
           leaf address-family {
             type string;
           }
           leaf nexthop-index {
             type int32;
           }
         }
       }
       list instance-vrf {
         leaf route-distinguisher {
           type string;
         }
         leaf vrf-import {
           type string;
         }
         leaf vrf-export {
           type string;
         }
         leaf vrf-import-target {
           type string;
         }
         leaf vrf-export-target {
           type string;
         }
         leaf vrf-label-allocation {
           type string;
         }
         leaf vrf-label-substitution {
           type string;
         }
         leaf fast-reroute-priority {
           type string;
         }
         leaf vrf-edge-protection-context-id {
           type ipaddr;
         }
       }
       list instance-vpls-meshgroup {
         leaf meshgroup-name {
           type string;
         }
         leaf route-distinguisher {
           type string;
         }
         leaf meshgroup-vrf-import {
           type string;
         }
         leaf meshgroup-vrf-export {
           type string;
         }
         leaf meshgroup-vrf-import-target {
           type string;
         }
         leaf meshgroup-vrf-export-target {
           type string;
         }
       }
     }
   }
 }
 }
