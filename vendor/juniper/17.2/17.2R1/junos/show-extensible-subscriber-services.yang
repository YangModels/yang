/*
 * Copyright (c) 2017 Juniper Networks, Inc.
 * All rights reserved.
 */
 module show-extensible-subscriber-services {
  namespace "http://yang.juniper.net/yang/1.1/jrpc/show-extensible-subscriber-services/junos/17.2R1.13";
  prefix show-extensible-subscriber-services;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-extensible-subscriber-services-sessions {
     description "Show sessions";
     input {
       leaf accounting-session-id {
         description "Accounting session ID";
         type string;
       }
     }
     output {
       container extensible-subscriber-services-information {
         uses extensible-subscriber-services-information-block;
       }
     }
   }
   rpc get-extensible-subscriber-services-services {
     description "Show services";
     output {
       container extensible-subscriber-services-information {
         uses extensible-subscriber-services-information-block;
       }
     }
   }
   rpc get-extensible-subscriber-services-dictionary {
     description "Show dictionary";
     input {
       leaf level {
         default "both";
         type enumeration {
           enum "both" {
             description "Display dictionary";
           }
           enum "attributes" {
             description "Display attributes";
           }
           enum "services" {
             description "Display services";
           }
         }
       }
     }
     output {
       container extensible-subscriber-services-information {
         uses extensible-subscriber-services-information-block;
       }
     }
   }
   rpc get-extensible-subscriber-services-counters {
     description "Show counters";
     output {
       container extensible-subscriber-services-information {
         uses extensible-subscriber-services-information-block;
       }
     }
   }
 grouping extensible-subscriber-services-information-block {
   leaf reload-dictionary {
     type string;
     description "Reload dictionary";
   }
   leaf session-id-error {
     type string;
     description "Session ID error";
   }
   leaf statistics {
     type string;
     description "Statistics";
   }
   leaf error-message {
     type string;
     description " Error Message";
   }
   container sessions {
     leaf session-id {
       type string;
       description "Session ID";
     }
     leaf session-timestamp {
       type string;
       description "Session Timestamp";
     }
     leaf service-name {
       type string;
       description "Service Name";
     }
     leaf total-sessions {
       type int32;
       description "Total Sessions count";
     }
   }
   container session-information {
     leaf service-id {
       type string;
       description "Service ID";
     }
     leaf service-timestamp {
       type string;
       description "Service Timestamp";
     }
     leaf service-name {
       type string;
       description "Service Name";
     }
     leaf commit-status {
       type string;
       description "Commit status of the service";
     }
     leaf total-services {
       type int32;
       description "Total Services count";
     }
   }
   container services {
     leaf service-name {
       type string;
       description "Service Name";
     }
     leaf action-header {
       type string;
       description "Action Header";
     }
     leaf provision-action {
       type string;
       description "Provision Action";
     }
     leaf deprovision-action {
       type string;
       description "Deprovision Action";
     }
     leaf services-per-action {
       type int32;
       description "Services count per action";
     }
     leaf total-services {
       type int32;
       description "Total Services count";
     }
   }
   container dictionary {
     leaf dictionary-type {
       type string;
       description "Dictionary Type";
     }
     container local-param-attributes {
       leaf attribute-name {
         type string;
         description "Attribute Name";
       }
       leaf attribute-code {
         type int32;
         description "Attribute Code";
       }
       leaf attribute-type {
         type string;
         description "Attribute Type";
       }
     }
     container param-attributes {
       leaf attribute-name {
         type string;
         description "Attribute Name";
       }
       leaf vendor-id {
         type int32;
       }
       leaf attribute-code {
         type int32;
         description "Attribute Code";
       }
       leaf attribute-type {
         type string;
         description "Attribute Type";
       }
       leaf has-tag {
         type string;
         description "Has Tag";
       }
       leaf config-type {
         type string;
         description "Config Type";
       }
     }
     container service-info {
       leaf service-name {
         type string;
         description "Service Name";
       }
       leaf service-attribute-name {
         type string;
         description "Service Attribute Name";
       }
       leaf action {
         type string;
         description "Action";
       }
       leaf action-type {
         type int32;
         description "Action Type";
       }
       leaf action-version {
         type string;
         description "Action Version";
       }
       leaf action-name {
         type string;
         description "Action Name";
       }
       leaf parameter-header {
         type string;
         description "Parameter Header";
       }
       leaf param-attribute-name {
         type string;
         description "Parameter Attribute Name";
       }
     }
   }
   container counters {
     leaf total-sessions {
       type int32;
       description "Total Sessions count";
     }
     leaf total-services {
       type int32;
       description "Total Services count";
     }
     leaf active-services {
       type int32;
       description "Active Services count";
     }
     leaf op-script-success {
       type uint32;
       description "Successful Op-script Execution count";
     }
     leaf op-script-failure {
       type uint32;
       description "Unsuccessful Op-script Execution count";
     }
     leaf commit-success {
       type uint32;
       description "Successful Commit Execution count";
     }
     leaf commit-failure {
       type uint32;
       description "Unsuccessful Commit Execution count";
     }
     leaf application-success {
       type uint32;
       description "Successful Application Execution count";
     }
     leaf application-failure {
       type uint32;
       description "Unsuccessful Application Execution count";
     }
     leaf service-requests-received {
       type uint32;
       description "Received Service Requests count";
     }
     leaf service-requests-acked {
       type uint32;
       description "Acknowledged Service Requests count";
     }
     leaf service-requests-nacked {
       type uint32;
       description "Negative Acknowledged Service Requests count";
     }
     leaf out-of-units {
       type uint32;
       description "Number of times there were no available IFL units";
     }
     leaf total-units {
       type uint32;
       description "Total number of IFL units";
     }
     leaf units-in-use {
       type uint32;
       description "Number of IFL units in use";
     }
     leaf units-usage {
       type uint32;
       description "Percentage of total IFL units in use";
     }
   }
   container debug {
     leaf dump-record {
       type string;
       description "File Name of Dump Record";
     }
     leaf dictionary-config-record {
       type string;
       description "File Name of Configured Dictionary";
     }
     leaf dictionary-active-record {
       type string;
       description "File Name of Active Dictionary";
     }
   }
   container profiling {
     leaf profile-dump-record {
       type string;
       description "File Name of Profile Dump Record";
     }
   }
 }
 }
