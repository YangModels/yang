/*
 * Copyright (c) 2017 Juniper Networks, Inc.
 * All rights reserved.
 */
 module monitor {
  namespace "http://yang.juniper.net/yang/1.1/jrpc/monitor/junos/17.2R1.13";
  prefix monitor;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc monitor-mpls-loss-measurement-rsvp-lsp {
     description "Trigger loss measurement for RSVP LSPs";
     input {
       leaf count {
         description "Number of queries to send";
         units "packets";
         type uint32 {
           range "1 .. 1000000";
         }
       }
       leaf detail {
         description "Display detailed output";
         type empty;
       }
       leaf interval {
         description "Delay between successive packets";
         units "seconds";
         type uint32 {
           range "1 .. 255";
         }
       }
       leaf traffic-class {
         description "Traffic class";
         type uint32 {
           range "0 .. 7";
         }
       }
       leaf bytes {
         description "Measure byte loss";
         type empty;
       }
       leaf lsp-name {
         description "Name of LSP";
         type string {
           length "1 .. 64";
         }
         mandatory true;
       }
     }
   }
   rpc monitor-mpls-delay-measurement-rsvp-lsp {
     description "Trigger delay measurement for RSVP LSPs";
     input {
       leaf count {
         description "Number of queries to send";
         units "packets";
         type uint32 {
           range "1 .. 1000000";
         }
       }
       leaf detail {
         description "Display detailed output";
         type empty;
       }
       leaf interval {
         description "Delay between successive packets";
         units "seconds";
         type uint32 {
           range "1 .. 255";
         }
       }
       leaf traffic-class {
         description "Traffic class";
         type uint32 {
           range "0 .. 7";
         }
       }
       leaf padding-size {
         description "Size of padding";
         type uint32 {
           range "0 .. 1500";
         }
       }
       leaf lsp-name {
         description "Name of LSP";
         type string {
           length "1 .. 64";
         }
         mandatory true;
       }
     }
   }
   rpc monitor-mpls-loss-delay-measurement-rsvp-lsp {
     description "Trigger combined loss delay measurement for RSVP LSPs";
     input {
       leaf count {
         description "Number of queries to send";
         units "packets";
         type uint32 {
           range "1 .. 1000000";
         }
       }
       leaf detail {
         description "Display detailed output";
         type empty;
       }
       leaf interval {
         description "Delay between successive packets";
         units "seconds";
         type uint32 {
           range "1 .. 255";
         }
       }
       leaf traffic-class {
         description "Traffic class";
         type uint32 {
           range "0 .. 7";
         }
       }
       leaf bytes {
         description "Measure byte loss";
         type empty;
       }
       leaf padding-size {
         description "Size of padding";
         type uint32 {
           range "0 .. 1500";
         }
       }
       leaf lsp-name {
         description "Name of LSP";
         type string {
           length "1 .. 64";
         }
         mandatory true;
       }
     }
   }
   rpc request-monitor-ethernet-delay-measurement {
     description "Trigger ethernet delay measurement from local to remote host";
     input {
       leaf ethdm-type {
         type enumeration {
           enum "one-way" {
             description "One-way delay measurement";
           }
           enum "two-way" {
             description "Two-way delay measurement";
           }
         }
         mandatory true;
       }
       leaf wait {
         description "Delay after sending last packet";
         units "seconds";
         type int32 {
           range "1 .. 255";
         }
       }
       leaf count {
         description "Number of delay measurement requests to send";
         type int32 {
           range "1 .. 65535";
         }
       }
       leaf maintenance-domain {
         description "Name of maintenance domain";
         type string {
           length "1 .. 45";
         }
         mandatory true;
       }
       leaf maintenance-association {
         description "Name of maintenance association";
         type string {
           length "1 .. 45";
         }
         mandatory true;
       }
       leaf remote-mac-address {
         description "MAC address of remote host in xx:xx:xx:xx:xx:xx format";
         type mac-unicast;
       }
       leaf mep {
         description "MEP identifier of remote host (default 1)";
         type int32 {
           range "1 .. 8191";
         }
       }
       leaf local-mep {
         description "MEP identifier of local host";
         type int32 {
           range "1 .. 8191";
         }
       }
       leaf priority {
         description "Priority (802.1p) value of delay measurement request frame";
         type int32 {
           range "0 .. 7";
         }
       }
       leaf size {
         description "Size of data in data TLV of request packets";
         units "bytes";
         type uint32 {
           range "1 .. 1400";
         }
       }
       leaf no-session-id-tlv {
         description "Supress insertion of session id tlv in request packet";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container ethdm-results {
         uses ethdm-results-block;
       }
     }
   }
   rpc request-monitor-ethernet-loss-measurement {
     description "Trigger ethernet loss measurement from local to remote host";
     input {
       leaf wait {
         description "Delay after sending last packet";
         units "seconds";
         type int32 {
           range "1 .. 255";
         }
       }
       leaf count {
         description "Number of loss measurement requests to send";
         type int32 {
           range "1 .. 65535";
         }
       }
       leaf maintenance-domain {
         description "Name of maintenance domain";
         type string {
           length "1 .. 45";
         }
         mandatory true;
       }
       leaf maintenance-association {
         description "Name of maintenance association";
         type string {
           length "1 .. 45";
         }
         mandatory true;
       }
       leaf remote-mac-address {
         description "MAC address of remote host in xx:xx:xx:xx:xx:xx format";
         type mac-unicast;
       }
       leaf mep {
         description "MEP identifier of remote host (default 1)";
         type int32 {
           range "1 .. 8191";
         }
       }
       leaf local-mep {
         description "MEP identifier of local host";
         type int32 {
           range "1 .. 8191";
         }
       }
       leaf priority {
         description "Frame priority (802.1p) value";
         type int32 {
           range "0 .. 7";
         }
       }
       leaf no-session-id-tlv {
         description "Supress insertion of session id tlv in request packet";
         type empty;
       }
     }
   }
   rpc request-monitor-ethernet-synthetic-loss-measurement {
     description "Trigger ethernet synthetic loss measurement (ETH_SLM) from local to remote host";
     input {
       leaf wait {
         description "Delay after sending last packet";
         units "milliseconds";
         type int32 {
           range "100 .. 5000";
         }
       }
       leaf count {
         description "Number of delay measurement requests to send";
         type int32 {
           range "1 .. 65535";
         }
       }
       leaf maintenance-domain {
         description "Name of maintenance domain";
         type string {
           length "1 .. 45";
         }
         mandatory true;
       }
       leaf maintenance-association {
         description "Name of maintenance association";
         type string {
           length "1 .. 45";
         }
         mandatory true;
       }
       leaf remote-mac-address {
         description "MAC address of remote host in xx:xx:xx:xx:xx:xx format";
         type mac-unicast;
       }
       leaf mep {
         description "MEP identifier of remote host (default 1)";
         type int32 {
           range "1 .. 8191";
         }
       }
       leaf local-mep {
         description "MEP identifier of local host";
         type int32 {
           range "1 .. 8191";
         }
       }
       leaf priority {
         description "Priority (802.1p) value of eth-slm request frame";
         type int32 {
           range "0 .. 7";
         }
       }
       leaf size {
         description "Size of data in data TLV of request packets";
         units "bytes";
         type int32 {
           range "1 .. 1400";
         }
       }
       leaf logical-system {
         description "Name of logical system";
         type string {
           junos:posix-pattern "^[a-zA-Z0-9_-]{1,63}$";
           junos:pattern-message "Logical-system name is a string consisting of up to 63 letters, numbers, dashes and underscores";
         }
       }
     }
     output {
       container ethslm-results {
         uses ethslm-results-block;
       }
     }
   }
 grouping ethdm-results-block {
   container cfm-ethdm-error-snapshot {
     leaf cfm-ethdm-error-reason {
       type string;
       description "Reason for failure of a ETH-DM request.";
     }
   }
   container cfm-ethdm-request-snapshot {
     leaf cfm-ethdm-type {
       type string;
       description "Type of ethernet delay measurement.";
     }
     leaf cfm-destination-mac-address {
       type string;
       description "MAC address of the target MEP or MIP.";
     }
     leaf cfm-interface-name {
       type string;
       description "Name of the interface.";
     }
   }
   list cfm-twoway-ethdm-reply-entry {
     leaf cfm-destination-mac-address {
       type string;
       description "MAC address of the target MEP or MIP.";
     }
     leaf cfm-twoway-ethdm-invalid-timestamp-response {
       type string;
       description "Invalid timestamp detected in the received DMR";
     }
     leaf cfm-twoway-ethdm-invalid-flags-response {
       type string;
       description "Invalid flags detected in the received DMR";
     }
     leaf cfm-twoway-ethdm-invalid-tlvoffset-response {
       type string;
       description "Invalid TLV offset detected in the received DMR";
     }
     leaf cfm-twoway-ethdm-no-endtlv-response {
       type string;
       description "End TLV was not found in the received DMR";
     }
     leaf cfm-twoway-ethdm-delay {
       type uint32;
       description "Two-way delay measured using ETH-DM.";
     }
     leaf cfm-twoway-ethdm-delay-variation {
       type uint32;
       description "Variation of two-way delay between two samples of measurement.";
     }
   }
   container cfm-oneway-ethdm-reply-summary {
     leaf cfm-oneway-ethdm-requests-packets {
       type uint32;
       description "Number of one-way ETH-DM requests transmitted.";
     }
   }
   container cfm-twoway-ethdm-reply-summary {
     leaf cfm-twoway-ethdm-requests-packets {
       type uint32;
       description "Number of two-way ETH-DM requests transmitted.";
     }
     leaf cfm-twoway-ethdm-responses-packets {
       type uint32;
       description "Number of two-way ETH-DM responses received.";
     }
     leaf cfm-twoway-ethdm-invalid-responses-packets {
       type uint32;
       description "Number of invalid two-way ETH-DM responses received.";
     }
     leaf cfm-twoway-ethdm-average-delay {
       type uint32;
       description "Average two-way delay measured using ETH-DM.";
     }
     leaf cfm-twoway-ethdm-average-delay-variation {
       type uint32;
       description "Average variation of delay between two samples of measurement.";
     }
     leaf cfm-twoway-ethdm-bestcase-delay {
       type uint32;
       description "Bestcase two-way delay measured using ETH-DM.";
     }
     leaf cfm-twoway-ethdm-worstcase-delay {
       type uint32;
       description "Worstcase two-way delay measured using ETH-DM.";
     }
   }
 }
 grouping ethslm-results-block {
   container cfm-ethslm-error-snapshot {
     leaf cfm-ethslm-error-reason {
       type string;
       description "Reason for failure of a ETH-SLM request.";
     }
   }
   container cfm-ethslm-request-snapshot {
     leaf cfm-destination-mac-address {
       type string;
       description "MAC address of the target MEP or MIP.";
     }
     leaf cfm-interface-name {
       type string;
       description "Name of the interface.";
     }
   }
   list cfm-ethslm-reply-entry {
     leaf cfm-destination-mac-address {
       type string;
       description "MAC address of the target MEP or MIP.";
     }
     leaf cfm-ethslm-invalid-flags-response {
       type string;
       description "Invalid flags detected in the received SLR";
     }
     leaf cfm-ethslm-invalid-tlvoffset-response {
       type string;
       description "Invalid TLV offset detected in the received SLR";
     }
     leaf cfm-ethslm-no-endtlv-response {
       type string;
       description "End TLV was not found in the received SLR";
     }
   }
   container cfm-ethslm-reply-summary {
     leaf cfm-ethslm-requests-packets {
       type uint32;
       description "Number of ETH-SLM requests transmitted.";
     }
     leaf cfm-ethslm-responses-packets {
       type uint32;
       description "Number of ETH-SLM responses received.";
     }
     leaf cfm-ethslm-invalid-responses-packets {
       type uint32;
       description "Number of invalid ETH-SLM requests received.";
     }
     leaf cfm-ethslm-packet-tx-packets {
       type uint32;
       description "Number of ETH-SLM requests transmitted (packet counter).";
     }
     leaf cfm-ethslm-packet-rx-packets {
       type uint32;
       description "Number of ETH-SLM responses received. (packet counter)";
     }
     leaf cfm-ethslm-near-end-frame-loss {
       type uint32;
       description "Near-end loss measured using ETH-SLM.";
     }
     leaf cfm-ethslm-near-end-loss-ratio {
       type string;
       description "Near-end loss ratio measured using ETH-SLM.";
     }
     leaf cfm-ethslm-far-end-frame-loss {
       type uint32;
       description "Far-end loss measured using ETH-SLM.";
     }
     leaf cfm-ethslm-far-end-loss-ratio {
       type string;
       description "Far-end loss ratio measured using ETH-SLM.";
     }
   }
 }
 }
