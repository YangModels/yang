/*
 * Copyright (c) 2017 Juniper Networks, Inc.
 * All rights reserved.
 */
 module show-ipv6 {
  namespace "http://yang.juniper.net/yang/1.1/jrpc/show-ipv6/junos/17.2R1.13";
  prefix show-ipv6;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ipv6-nd-information {
     description "Show IPv6 neighbor cache information";
     output {
       container ipv6-nd-information {
         uses ipv6-nd-information-block;
       }
     }
   }
   rpc get-ipv6-ra-information {
     description "Show IPv6 router advertisement information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface {
         description "Name of interface";
         type string;
       }
       leaf conflicts {
         description "Display conflicting information";
         type empty;
       }
       leaf prefix {
         description "Prefix and optional prefix length";
         type ipv6prefix;
       }
       leaf virtual-router {
         description "Display only virtual-interface information";
         type empty;
       }
     }
     output {
       container ipv6-ra-information {
         uses ipv6-ra-information-block;
       }
     }
   }
 grouping ipv6-nd-information-block {
   list ipv6-nd-entry {
     leaf ipv6-nd-neighbor-address {
       type ipv6addr;
       description "Address of the neighbor";
     }
     leaf ipv6-nd-neighbor-l2-address {
       type string;
       description "Layer 2 address of the neighbor";
     }
     leaf ipv6-nd-state {
       type string;
     }
     leaf ipv6-nd-expire {
       type int32;
     }
     leaf ipv6-nd-isrouter {
       type string;
     }
     leaf ipv6-nd-issecure {
       type string;
     }
     leaf ipv6-nd-interface-name {
       type string;
       description "Name of the interface";
     }
     leaf ipv6-nd-total {
       type int32;
       description "Total number of cache entries";
     }
   }
 }
 grouping ipv6-ra-information-block {
   list ipv6-ra-interface {
     leaf interface-name {
       type string;
       description "Name of interface";
     }
     leaf ipv6-ra-advertisements-sent {
       type int32;
       description "Number of router advertisements sent";
     }
     leaf ipv6-ra-advertisement-sent-time {
       type string;
       description "How long since the last router advertisement was sent";
     }
     leaf ipv6-ra-solicits-received {
       type int32;
       description "Number of router solicitations received";
     }
     leaf ipv6-ra-solicit-receive-time {
       type string;
       description "How long since the last router solicitation was sent";
     }
     leaf ipv6-ra-advertisements-received {
       type int32;
       description "Number of router advertisements received";
     }
     leaf ipv6-ra-solicit-router-advertisement-unicast {
       type int32;
       description "Enable forwarding IPv6 Solicited Router Advert as unicast";
     }
     leaf ipv6-ra-solicit-router-advertisement-preference {
       type string;
       description "Preference for Router Selection based on RA";
     }
     container vrrp-group {
       leaf vrrp-group-id {
         type int32;
         description "Group ID of the configured VRRP group";
       }
       leaf vrrp-advertisements-sent {
         type int32;
         description "Number of advertisements sent";
       }
       leaf vrrp-advertisement-sent-time {
         type string;
         description "How long since the last advertisement was sent";
       }
       leaf vrrp-solicits-received {
         type int32;
         description "Number of router solicitations received";
       }
       leaf vrrp-solicit-receive-time {
         type string;
         description "How long since the last solicitation was sent";
       }
       leaf vrrp-advertisements-received {
         type int32;
         description "Number of advertisements received";
       }
     }
     list ipv6-ra-advertisement {
       leaf ipv6-source-address {
         type ipv6addr;
         description "Sender of the advertisement";
       }
       leaf ipv6-ra-time-since {
         type string;
         description "How long since the advertisement was received";
       }
       leaf ipv6-ra-managed-flag {
         type int32;
         description "Advertised managed flag";
       }
       leaf ipv6-ra-managed-flag-conflict {
         type int32;
         description "Conflict with the advertised managed flag";
       }
       leaf ipv6-ra-other-config-flag {
         type int32;
         description "Advertised other configuration flag";
       }
       leaf ipv6-ra-other-config-flag-conflict {
         type int32;
         description "Conflict with the advertised other configuration flag";
       }
       leaf ipv6-ra-link-mtu {
         type int32;
         description "Advertised link MTU";
       }
       leaf ipv6-ra-link-mtu-conflict {
         type int32;
         description "Conflict with the advertised link MTU";
       }
       leaf ipv6-ra-reachable-time {
         type int32;
         description "Advertised reachable time";
       }
       leaf ipv6-ra-reachable-time-conflict {
         type int32;
         description "Conflict with the advertised reachable time";
       }
       leaf ipv6-ra-default-lifetime {
         type int32;
         description "Advertised default lifetime flag";
       }
       leaf ipv6-ra-default-lifetime-conflict {
         type int32;
         description "Conflict with the advertised default lifetime flag";
       }
       leaf ipv6-ra-retransmit-timer {
         type int32;
         description "Advertised retransmit timer flag";
       }
       leaf ipv6-ra-retransmit-timer-conflict {
         type int32;
         description "Conflict with the advertised retransmit timer flag";
       }
       leaf ipv6-ra-current-hop-limit {
         type int32;
         description "Advertised current hop limit flag";
       }
       leaf ipv6-ra-current-hop-limit-conflict {
         type int32;
         description "Conflict with the advertised current hop limit flag";
       }
       list ipv6-ra-rdnss {
         leaf ipv6-ra-rdnss-address {
           type ipv6addr;
           description "Advertised RDNSS address";
         }
         leaf ipv6-ra-rdnss-lifetime {
           type int32;
           description "Advertised lifetime of the RDNSS address";
         }
         leaf ipv6-ra-rdnss-lifetime-conflict {
           type int32;
           description "Conflict with the advertised lifetime of the RDNSS address";
         }
       }
       list ipv6-ra-prefix {
         leaf ipv6-ra-prefix-address {
           type ipv6prefix;
           description "Advertised prefix";
         }
         leaf ipv6-ra-prefix-valid-lifetime {
           type int32;
           description "Advertised valid lifetime of the prefix";
         }
         leaf ipv6-ra-prefix-valid-lifetime-conflict {
           type int32;
           description "Conflict with the advertised valid lifetime of the prefix";
         }
         leaf ipv6-ra-prefix-preferred-lifetime {
           type int32;
           description "Advertised preferred lifetime of the prefix";
         }
         leaf ipv6-ra-prefix-preferred-lifetime-conflict {
           type int32;
           description "Conflict with the advertised preferred lifetime of the prefix";
         }
         leaf ipv6-ra-prefix-on-link {
           type int32;
           description "Advertised on-link flag of the prefix";
         }
         leaf ipv6-ra-prefix-on-link-conflict {
           type int32;
           description "Conflict with the advertised on-link flag of the prefix";
         }
         leaf ipv6-ra-prefix-autonomous {
           type int32;
           description "Advertised autonomous flag of the prefix";
         }
         leaf ipv6-ra-prefix-autonomous-conflict {
           type int32;
           description "Conflict with the advertised autonomous flag of the prefix";
         }
       }
     }
   }
 }
 }
