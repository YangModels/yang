/*
 * Copyright (c) 2017 Juniper Networks, Inc.
 * All rights reserved.
 */
 module test {
  namespace "http://yang.juniper.net/yang/1.1/jrpc/test/junos/17.2R1.13";
  prefix test;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc test-routing-policy {
     description "Import and export policy evaluation";
     input {
       leaf policy {
         description "Policy name";
         type string;
       }
       leaf prefix {
         description "Destination prefix";
         type string;
       }
     }
     output {
       container route-information {
         uses route-information-block;
       }
     }
   }
   rpc jdhcpd-code-coverage {
     description "Execute functions for code coverage";
   }
   rpc test-rfc2544-benchmarking {
     description "Rfc2544 test configuration";
   }
   rpc test-rfc2544-benchmarking-test {
     description "Start/stop a rfc2544 test";
     input {
       leaf test-name {
         description "Test name";
         type string;
       }
       leaf test-start-stop-clear {
         type enumeration {
           enum "start" {
             description "Start test";
           }
           enum "stop" {
             description "Stop test";
           }
           enum "clear-counters" {
             description "Clear test counters";
           }
         }
         mandatory true;
       }
       leaf routing-instance {
         description "Name of routing instance for rfc2544 test ";
         type string {
           junos:posix-pattern "!^((__.*__)|(all)|(.*[ ].*)|(\"\")|(.{129,}))$";
           junos:pattern-message "Must be a non-reserved string of 128 characters or less with no spaces.";
         }
       }
     }
   }
   rpc test-rfc2544-benchmarking-test-id {
     description "Stop a rfc2544 test";
     input {
       leaf test-id {
         description "Test id";
         type uint32;
       }
       leaf test-stop {
         type enumeration {
           enum "stop" {
             description "Stop test";
           }
         }
       }
     }
   }
   rpc get-test-services-l2tp-tunnel-result {
     description "Check L2TP tunnel configuration for a subscriber";
     input {
       leaf user {
         description "Name of the subscriber";
         type string;
         mandatory true;
       }
       leaf password {
         description "Password for the subscriber";
         type string;
       }
       leaf tunnel-name {
         description "Name of the L2TP tunnel";
         type string;
       }
     }
     output {
       container test-services-l2tp-tunnel-result {
         uses test-services-l2tp-tunnel-result-block;
       }
     }
   }
   rpc test-services-traffic-load-balance-code-coverage {
     description "Execute Traffic load balance code-coverage";
     input {
       leaf database-id {
         description "Database identifier";
         type enumeration {
           enum "all" {
             description "All databases";
           }
           enum "probe" {
             description "Probe database";
           }
           enum "firewall" {
             description "Firewall";
           }
           enum "ip-db" {
             description "Ip database";
           }
           enum "clear-db" {
             description "Clear all databases";
           }
           enum "stats" {
             description "Stats";
           }
           enum "group-db" {
             description "Group database";
           }
           enum "heap" {
             description "Heap";
           }
           enum "virtual-svc-db" {
             description "Virtual srv database";
           }
           enum "instance-db" {
             description "Instance database";
           }
           enum "real-svc-db" {
             description "Real srv database";
           }
           enum "group-real-svc-db" {
             description "Group real srv database";
           }
           enum "validation-db" {
             description "Validation database";
           }
           enum "pconn-db" {
             description "Pconn database";
           }
           enum "gencfg-db" {
             description "Gencfg database";
           }
           enum "main" {
             description "Main functions";
           }
           enum "snmp" {
             description "SNMP functions";
           }
           enum "ui" {
             description "UI functions";
           }
           enum "config-parse" {
             description "Config parse functions";
           }
           enum "filter-config" {
             description "Filter database";
           }
           enum "ssd" {
             description "SSD functions";
           }
           enum "commit-checks" {
             description "Commit checks";
           }
         }
       }
     }
   }
   rpc test-services-traffic-load-balance-inject-error {
     description "Execute Traffic load balance error-injection";
     input {
       leaf error-id {
         description "Error identifier";
         type uint32;
         mandatory true;
       }
       leaf always-fail {
         description "Fail always";
         type enumeration {
           enum "enable" {
             description "Enable failure";
           }
           enum "disable" {
             description "Disable failure";
           }
         }
         mandatory true;
       }
     }
   }
   rpc test-services-url-filter-inject-error {
     description "Execute URL Filtering error-injection";
     input {
       leaf error-id {
         description "Error identifier";
         type uint32;
         mandatory true;
       }
       leaf always-fail {
         description "Fail always";
         type enumeration {
           enum "enable" {
             description "Enable failure";
           }
           enum "disable" {
             description "Disable failure";
           }
         }
         mandatory true;
       }
     }
   }
   rpc get-ppp-user-aaa-test-result {
     description "Test the aaa servers for a ppp user";
     input {
       leaf user {
         description "The username to test";
         type string;
         mandatory true;
       }
       leaf password {
         description "The password associated with username";
         type string;
       }
       leaf agent-remote-id {
         description "DSL forum agent remote id";
         type string {
           length "1 .. 63";
         }
       }
       leaf profile {
         description "Specify the access profile name which to use for user";
         type string;
       }
       leaf logical-system {
         description "Specify the logical-system in which to authenticate user";
         type string;
       }
       leaf routing-instance {
         description "Specify the routing-instance in which to authenticate user";
         type string;
       }
       leaf no-address-request {
         description "Request is for authentication without address-allocation";
         type empty;
       }
       leaf service-type {
         description "Service type ";
         type string;
       }
       container terminate-code-choice {
         choice terminate-code-choice_c {
           case terminate-code {
             leaf terminate-code {
               description "Specify PPP terminate-code";
               type enumeration {
                 enum "admin-logout" {
                   description "Terminated-id with default mapping to 10";
                 }
                 enum "admin-reconnect-request" {
                   description "Terminated-id with default mapping to 10";
                 }
                 enum "authenticate-authenticator-timeout" {
                   description "Terminated-id with default mapping to 10";
                 }
                 enum "authenticate-challenge-timeout" {
                   description "Terminated-id with default mapping to 17";
                 }
                 enum "authenticate-chap-no-resources" {
                   description "Terminated-id with default mapping to 10";
                 }
                 enum "authenticate-chap-peer-authenticator-timeout" {
                   description "Terminated-id with default mapping to 17";
                 }
                 enum "authenticate-chap-peer-challenge-timeout" {
                   description "Terminated-id with default mapping to 17";
                 }
                 enum "authenticate-deny-by-peer" {
                   description "Terminated-id with default mapping to 4";
                 }
                 enum "authenticate-eap-challenge-larger-than-mtu" {
                   description "Terminated-id with default mapping to 10";
                 }
                 enum "authenticate-eap-peer-authenticator-timeout" {
                   description "Terminated-id with default mapping to 10";
                 }
                 enum "authenticate-eap-request-timeout" {
                   description "Terminated-id with default mapping to 10";
                 }
                 enum "authenticate-inactivity-timeout" {
                   description "Terminated-id with default mapping to 8";
                 }
                 enum "authenticate-max-requests" {
                   description "Terminated-id with default mapping to 10";
                 }
                 enum "authenticate-no-authenticator" {
                   description "Terminated-id with default mapping to 10";
                 }
                 enum "authenticate-no-resources" {
                   description "Terminated-id with default mapping to 10";
                 }
                 enum "authenticate-pap-peer-authenticator-timeout" {
                   description "Terminated-id with default mapping to 10";
                 }
                 enum "authenticate-pap-request-timeout" {
                   description "Terminated-id with default mapping to 5";
                 }
                 enum "authenticate-session-timeout" {
                   description "Terminated-id with default mapping to 10";
                 }
                 enum "authenticate-too-many-requests" {
                   description "Terminated-id with default mapping to 17";
                 }
                 enum "authenticate-tunnel-fail-immediate" {
                   description "Terminated-id with default mapping to 10";
                 }
                 enum "authenticate-tunnel-unsupported-tunnel-type" {
                   description "Terminated-id with default mapping to 10";
                 }
                 enum "bridging-admin-disable" {
                   description "Terminated-id with default mapping to 10";
                 }
                 enum "bridging-failed-to-activate-family-bridging" {
                   description "Terminated-id with default mapping to 10";
                 }
                 enum "bridging-inhibited-by-authentication" {
                   description "Terminated-id with default mapping to 10";
                 }
                 enum "bridging-link-down" {
                   description "Terminated-id with default mapping to 10";
                 }
                 enum "bridging-max-configure-exceeded" {
                   description "Terminated-id with default mapping to 10";
                 }
                 enum "bridging-max-passive-retries-exceeded" {
                   description "Terminated-id with default mapping to 10";
                 }
                 enum "bridging-max-sevice-disable" {
                   description "Terminated-id with default mapping to 10";
                 }
                 enum "bridging-no-local-ieee802-tagged-frame-format" {
                   description "Terminated-id with default mapping to 10";
                 }
                 enum "bridging-no-local-mac-frame-format" {
                   description "Terminated-id with default mapping to 2";
                 }
                 enum "bridging-no-peer-ieee802-tagged-frame-format" {
                   description "Terminated-id with default mapping to 10";
                 }
                 enum "bridging-no-peer-mac-fram-fromat" {
                   description "Terminated-id with default mapping to 8";
                 }
                 enum "bridging-no-service" {
                   description "Terminated-id with default mapping to 10";
                 }
                 enum "bridging-renegotiate-rx-conf-ack" {
                   description "Terminated-id with default mapping to 10";
                 }
                 enum "bridging-renegotiate-rx-conf-nak" {
                   description "Terminated-id with default mapping to 10";
                 }
                 enum "bridging-renegotiate-rx-conf-rej" {
                   description "Terminated-id with default mapping to 10";
                 }
                 enum "bridging-renegotiate-rx-conf-req" {
                   description "Terminated-id with default mapping to 10";
                 }
                 enum "bridging-stale-stacking" {
                   description "Terminated-id with default mapping to 10";
                 }
                 enum "bridging-terminate-code-rej" {
                   description "Terminated-id with default mapping to 10";
                 }
                 enum "bridging-terminate-term-ack" {
                   description "Terminated-id with default mapping to 10";
                 }
                 enum "bridging-terminate-term-req" {
                   description "Terminated-id with default mapping to 10";
                 }
                 enum "bundle-fail-activation" {
                   description "Terminated-id with default mapping to 10";
                 }
                 enum "bundle-fail-create" {
                   description "Terminated-id with default mapping to 10";
                 }
                 enum "bundle-fail-engine-add" {
                   description "Terminated-id with default mapping to 10";
                 }
                 enum "bundle-fail-fragment-size-mismatch" {
                   description "Terminated-id with default mapping to 10";
                 }
                 enum "bundle-fail-fragmentation-location" {
                   description "Terminated-id with default mapping to 10";
                 }
                 enum "bundle-fail-fragmentation-mismatch" {
                   description "Terminated-id with default mapping to 10";
                 }
                 enum "bundle-fail-hash-link-selection-mismatch" {
                   description "Terminated-id with default mapping to 10";
                 }
                 enum "bundle-fail-join" {
                   description "Terminated-id with default mapping to 10";
                 }
                 enum "bundle-fail-local-mped-not-set-yet" {
                   description "Terminated-id with default mapping to 10";
                 }
                 enum "bundle-fail-local-mrru-mismatch" {
                   description "Terminated-id with default mapping to 10";
                 }
                 enum "bundle-fail-local-mru-mismatch" {
                   description "Terminated-id with default mapping to 10";
                 }
                 enum "bundle-fail-peer-endpoint-discriminator-mismatch" {
                   description "Terminated-id with default mapping to 10";
                 }
                 enum "bundle-fail-peer-mrru-mismatch" {
                   description "Terminated-id with default mapping to 6";
                 }
                 enum "bundle-fail-profile-nak" {
                   description "Terminated-id with default mapping to 10";
                 }
                 enum "bundle-fail-reassembly-location" {
                   description "Terminated-id with default mapping to 10";
                 }
                 enum "bundle-fail-reassembly-mismatch" {
                   description "Terminated-id with default mapping to 10";
                 }
                 enum "bundle-fail-record-network" {
                   description "Terminated-id with default mapping to 10";
                 }
                 enum "bundle-fail-server-location-mismatch" {
                   description "Terminated-id with default mapping to 10";
                 }
                 enum "bundle-fail-static-link" {
                   description "Terminated-id with default mapping to 10";
                 }
                 enum "bundle-fail-unrecoverable-ifl" {
                   description "Terminated-id with default mapping to 10";
                 }
                 enum "dynamic-profile-instantiation-failed" {
                   description "Terminated-id with default mapping to 9";
                 }
                 enum "failover-during-authentication" {
                   description "Terminated-id with default mapping to 17";
                 }
                 enum "interface-admin-disable" {
                   description "Terminated-id with default mapping to 6";
                 }
                 enum "interface-no-hardware" {
                   description "Terminated-id with default mapping to 8";
                 }
                 enum "ip-admin-disable" {
                   description "Terminated-id with default mapping to 10";
                 }
                 enum "ip-failed-to-activate-family-inet" {
                   description "Terminated-id with default mapping to 10";
                 }
                 enum "ip-failed-to-activate-services" {
                   description "Terminated-id with default mapping to 10";
                 }
                 enum "ip-failed-to-add-access-internal-route" {
                   description "Terminated-id with default mapping to 10";
                 }
                 enum "ip-inhibited-by-authentication" {
                   description "Terminated-id with default mapping to 10";
                 }
                 enum "ip-link-down" {
                   description "Terminated-id with default mapping to 10";
                 }
                 enum "ip-max-configure-exceeded" {
                   description "Terminated-id with default mapping to 10";
                 }
                 enum "ip-max-passive-retries-exceeded" {
                   description "Terminated-id with default mapping to 10";
                 }
                 enum "ip-no-local-ip-address" {
                   description "Terminated-id with default mapping to 10";
                 }
                 enum "ip-no-local-ip-address-mask" {
                   description "Terminated-id with default mapping to 10";
                 }
                 enum "ip-no-local-primary-dns-address" {
                   description "Terminated-id with default mapping to 10";
                 }
                 enum "ip-no-local-primary-nbns-address" {
                   description "Terminated-id with default mapping to 10";
                 }
                 enum "ip-no-local-secondary-dns-address" {
                   description "Terminated-id with default mapping to 10";
                 }
                 enum "ip-no-local-secondary-nbns-address" {
                   description "Terminated-id with default mapping to 10";
                 }
                 enum "ip-no-peer-ip-address" {
                   description "Terminated-id with default mapping to 10";
                 }
                 enum "ip-no-peer-ip-address-mask" {
                   description "Terminated-id with default mapping to 10";
                 }
                 enum "ip-no-peer-primary-dns-address" {
                   description "Terminated-id with default mapping to 10";
                 }
                 enum "ip-no-peer-primary-nbns-address" {
                   description "Terminated-id with default mapping to 10";
                 }
                 enum "ip-no-peer-secondary-dns-address" {
                   description "Terminated-id with default mapping to 10";
                 }
                 enum "ip-no-peer-secondary-nbns-address" {
                   description "Terminated-id with default mapping to 10";
                 }
                 enum "ip-no-service" {
                   description "Terminated-id with default mapping to 10";
                 }
                 enum "ip-peer-renegotiate-rx-conf-ack" {
                   description "Terminated-id with default mapping to 10";
                 }
                 enum "ip-peer-renegotiate-rx-conf-nak" {
                   description "Terminated-id with default mapping to 10";
                 }
                 enum "ip-peer-renegotiate-rx-conf-rej" {
                   description "Terminated-id with default mapping to 10";
                 }
                 enum "ip-peer-renegotiate-rx-conf-req" {
                   description "Terminated-id with default mapping to 10";
                 }
                 enum "ip-peer-terminate-code-rej" {
                   description "Terminated-id with default mapping to 10";
                 }
                 enum "ip-peer-terminate-term-ack" {
                   description "Terminated-id with default mapping to 10";
                 }
                 enum "ip-peer-terminate-term-req" {
                   description "Terminated-id with default mapping to 10";
                 }
                 enum "ip-service-disable" {
                   description "Terminated-id with default mapping to 10";
                 }
                 enum "ip-stale-stacking" {
                   description "Terminated-id with default mapping to 10";
                 }
                 enum "ipv6-admin-disable" {
                   description "Terminated-id with default mapping to 10";
                 }
                 enum "ipv6-failed-to-activate-family-inet6" {
                   description "Terminated-id with default mapping to 10";
                 }
                 enum "ipv6-failed-to-activate-services" {
                   description "Terminated-id with default mapping to 10";
                 }
                 enum "ipv6-inhibited-by-authentication" {
                   description "Terminated-id with default mapping to 10";
                 }
                 enum "ipv6-link-down" {
                   description "Terminated-id with default mapping to 10";
                 }
                 enum "ipv6-local-and-peer-interface-ids-identical" {
                   description "Terminated-id with default mapping to 10";
                 }
                 enum "ipv6-max-configure-exceeded" {
                   description "Terminated-id with default mapping to 10";
                 }
                 enum "ipv6-max-passive-retries-exceeded" {
                   description "Terminated-id with default mapping to 10";
                 }
                 enum "ipv6-no-local-ipv6-interface-id" {
                   description "Terminated-id with default mapping to 10";
                 }
                 enum "ipv6-no-peer-ipv6-interface-id" {
                   description "Terminated-id with default mapping to 10";
                 }
                 enum "ipv6-no-service" {
                   description "Terminated-id with default mapping to 10";
                 }
                 enum "ipv6-peer-renegotiate-rx-conf-ack" {
                   description "Terminated-id with default mapping to 10";
                 }
                 enum "ipv6-peer-renegotiate-rx-conf-nak" {
                   description "Terminated-id with default mapping to 10";
                 }
                 enum "ipv6-peer-renegotiate-rx-conf-rej" {
                   description "Terminated-id with default mapping to 10";
                 }
                 enum "ipv6-peer-renegotiate-rx-conf-req" {
                   description "Terminated-id with default mapping to 10";
                 }
                 enum "ipv6-peer-terminate-code-rej" {
                   description "Terminated-id with default mapping to 10";
                 }
                 enum "ipv6-peer-terminate-term-ack" {
                   description "Terminated-id with default mapping to 10";
                 }
                 enum "ipv6-peer-terminate-term-req" {
                   description "Terminated-id with default mapping to 10";
                 }
                 enum "ipv6-service-disable" {
                   description "Terminated-id with default mapping to 10";
                 }
                 enum "ipv6-stale-stacking" {
                   description "Terminated-id with default mapping to 10";
                 }
                 enum "l2tp-session-apply-link-attribute-failed" {
                   description "Terminated-id with default mapping to 10";
                 }
                 enum "lcp-authenticate-terminate-hold" {
                   description "Terminated-id with default mapping to 10";
                 }
                 enum "lcp-configured-mrru-too-small" {
                   description "Terminated-id with default mapping to 10";
                 }
                 enum "lcp-configured-mru-invalid" {
                   description "Terminated-id with default mapping to 10";
                 }
                 enum "lcp-configured-mru-too-small" {
                   description "Terminated-id with default mapping to 10";
                 }
                 enum "lcp-dynamic-interface-hold" {
                   description "Terminated-id with default mapping to 10";
                 }
                 enum "lcp-failed-to-activate-services" {
                   description "Terminated-id with default mapping to 10";
                 }
                 enum "lcp-keepalive-failure" {
                   description "Terminated-id with default mapping to 10";
                 }
                 enum "lcp-loopback-rx-conf-req" {
                   description "Terminated-id with default mapping to 10";
                 }
                 enum "lcp-loopback-rx-echo-reply" {
                   description "Terminated-id with default mapping to 10";
                 }
                 enum "lcp-loopback-rx-echo-req" {
                   description "Terminated-id with default mapping to 10";
                 }
                 enum "lcp-max-configure-exceeded" {
                   description "Terminated-id with default mapping to 10";
                 }
                 enum "lcp-max-passive-retries-exceeded" {
                   description "Terminated-id with default mapping to 10";
                 }
                 enum "lcp-mru-changed" {
                   description "Terminated-id with default mapping to 8";
                 }
                 enum "lcp-negotiation-timeout" {
                   description "Terminated-id with default mapping to 10";
                 }
                 enum "lcp-no-local-accm" {
                   description "Terminated-id with default mapping to 10";
                 }
                 enum "lcp-no-local-acfc" {
                   description "Terminated-id with default mapping to 10";
                 }
                 enum "lcp-no-local-authentication" {
                   description "Terminated-id with default mapping to 10";
                 }
                 enum "lcp-no-local-endpoint-discriminator" {
                   description "Terminated-id with default mapping to 10";
                 }
                 enum "lcp-no-local-magic-number" {
                   description "Terminated-id with default mapping to 10";
                 }
                 enum "lcp-no-local-mrru" {
                   description "Terminated-id with default mapping to 10";
                 }
                 enum "lcp-no-local-mru" {
                   description "Terminated-id with default mapping to 10";
                 }
                 enum "lcp-no-local-pfc" {
                   description "Terminated-id with default mapping to 10";
                 }
                 enum "lcp-no-peer-accm" {
                   description "Terminated-id with default mapping to 10";
                 }
                 enum "lcp-no-peer-acfc" {
                   description "Terminated-id with default mapping to 10";
                 }
                 enum "lcp-no-peer-authentication" {
                   description "Terminated-id with default mapping to 10";
                 }
                 enum "lcp-no-peer-endpoint-discriminator" {
                   description "Terminated-id with default mapping to 10";
                 }
                 enum "lcp-no-peer-magic-number" {
                   description "Terminated-id with default mapping to 10";
                 }
                 enum "lcp-no-peer-mrru" {
                   description "Terminated-id with default mapping to 10";
                 }
                 enum "lcp-no-peer-mru" {
                   description "Terminated-id with default mapping to 10";
                 }
                 enum "lcp-no-peer-pfc" {
                   description "Terminated-id with default mapping to 10";
                 }
                 enum "lcp-peer-renegotiate-rx-conf-ack" {
                   description "Terminated-id with default mapping to 1";
                 }
                 enum "lcp-peer-renegotiate-rx-conf-nak" {
                   description "Terminated-id with default mapping to 1";
                 }
                 enum "lcp-peer-renegotiate-rx-conf-rej" {
                   description "Terminated-id with default mapping to 1";
                 }
                 enum "lcp-peer-renegotiate-rx-conf-req" {
                   description "Terminated-id with default mapping to 1";
                 }
                 enum "lcp-peer-terminate-code-rej" {
                   description "Terminated-id with default mapping to 1";
                 }
                 enum "lcp-peer-terminate-protocol-reject" {
                   description "Terminated-id with default mapping to 1";
                 }
                 enum "lcp-peer-terminate-term-ack" {
                   description "Terminated-id with default mapping to 1";
                 }
                 enum "lcp-peer-terminate-term-req" {
                   description "Terminated-id with default mapping to 1";
                 }
                 enum "lcp-tunnel-disconnected" {
                   description "Terminated-id with default mapping to 10";
                 }
                 enum "lcp-tunnel-failed" {
                   description "Terminated-id with default mapping to 10";
                 }
                 enum "license-limit-exceeded" {
                   description "Terminated-id with default mapping to 10";
                 }
                 enum "link-interface-no-hardware" {
                   description "Terminated-id with default mapping to 10";
                 }
                 enum "lower-interface-attach-failed" {
                   description "Terminated-id with default mapping to 2";
                 }
                 enum "lower-interface-down" {
                   description "Terminated-id with default mapping to 2";
                 }
                 enum "lower-interface-teardown" {
                   description "Terminated-id with default mapping to 17";
                 }
                 enum "mpls-admin-disable" {
                   description "Terminated-id with default mapping to 10";
                 }
                 enum "mpls-failed-to-activate-family-mpls" {
                   description "Terminated-id with default mapping to 10";
                 }
                 enum "mpls-link-down" {
                   description "Terminated-id with default mapping to 10";
                 }
                 enum "mpls-max-configure-exceeded" {
                   description "Terminated-id with default mapping to 10";
                 }
                 enum "mpls-max-passive-retries-exceeded" {
                   description "Terminated-id with default mapping to 10";
                 }
                 enum "mpls-no-service" {
                   description "Terminated-id with default mapping to 10";
                 }
                 enum "mpls-peer-renegotiate-rx-conf-ack" {
                   description "Terminated-id with default mapping to 10";
                 }
                 enum "mpls-peer-renegotiate-rx-conf-nak" {
                   description "Terminated-id with default mapping to 10";
                 }
                 enum "mpls-peer-renegotiate-rx-conf-rej" {
                   description "Terminated-id with default mapping to 10";
                 }
                 enum "mpls-peer-renegotiate-rx-conf-req" {
                   description "Terminated-id with default mapping to 10";
                 }
                 enum "mpls-peer-terminate-code-rej" {
                   description "Terminated-id with default mapping to 10";
                 }
                 enum "mpls-peer-terminate-term-ack" {
                   description "Terminated-id with default mapping to 10";
                 }
                 enum "mpls-peer-terminate-term-req" {
                   description "Terminated-id with default mapping to 10";
                 }
                 enum "mpls-service-disable" {
                   description "Terminated-id with default mapping to 10";
                 }
                 enum "mpls-stale-stacking" {
                   description "Terminated-id with default mapping to 10";
                 }
                 enum "network-interface-admin-disable" {
                   description "Terminated-id with default mapping to 10";
                 }
                 enum "no-bundle" {
                   description "Terminated-id with default mapping to 8";
                 }
                 enum "no-interface" {
                   description "Terminated-id with default mapping to 10";
                 }
                 enum "no-link-interface" {
                   description "Terminated-id with default mapping to 10";
                 }
                 enum "no-ncps-available" {
                   description "Terminated-id with default mapping to 10";
                 }
                 enum "no-network-interface" {
                   description "Terminated-id with default mapping to 6";
                 }
                 enum "no-upper-interface" {
                   description "Terminated-id with default mapping to 9";
                 }
                 enum "osi-admin-disable" {
                   description "Terminated-id with default mapping to 10";
                 }
                 enum "osi-failed-to-activate-family-osi" {
                   description "Terminated-id with default mapping to 10";
                 }
                 enum "osi-link-down" {
                   description "Terminated-id with default mapping to 10";
                 }
                 enum "osi-max-configure-exceeded" {
                   description "Terminated-id with default mapping to 10";
                 }
                 enum "osi-max-passive-retries-exceeded" {
                   description "Terminated-id with default mapping to 10";
                 }
                 enum "osi-no-local-align-npdu" {
                   description "Terminated-id with default mapping to 10";
                 }
                 enum "osi-no-peer-align-npdu" {
                   description "Terminated-id with default mapping to 10";
                 }
                 enum "osi-no-service" {
                   description "Terminated-id with default mapping to 10";
                 }
                 enum "osi-peer-renegotiate-rx-conf-ack" {
                   description "Terminated-id with default mapping to 10";
                 }
                 enum "osi-peer-renegotiate-rx-conf-nak" {
                   description "Terminated-id with default mapping to 10";
                 }
                 enum "osi-peer-renegotiate-rx-conf-rej" {
                   description "Terminated-id with default mapping to 10";
                 }
                 enum "osi-peer-renegotiate-rx-conf-req" {
                   description "Terminated-id with default mapping to 10";
                 }
                 enum "osi-peer-terminate-code-rej" {
                   description "Terminated-id with default mapping to 10";
                 }
                 enum "osi-peer-terminate-term-ack" {
                   description "Terminated-id with default mapping to 10";
                 }
                 enum "osi-peer-terminate-term-req" {
                   description "Terminated-id with default mapping to 10";
                 }
                 enum "osi-service-disable" {
                   description "Terminated-id with default mapping to 10";
                 }
                 enum "osi-stale-stacking" {
                   description "Terminated-id with default mapping to 10";
                 }
                 enum "recovery-active-state-cleanup" {
                   description "Terminated-id with default mapping to 9";
                 }
                 enum "recovery-configured-state-cleanup" {
                   description "Terminated-id with default mapping to 9";
                 }
                 enum "recovery-init-state-cleanup" {
                   description "Terminated-id with default mapping to 9";
                 }
                 enum "recovery-terminated-state-cleanup" {
                   description "Terminated-id with default mapping to 9";
                 }
                 enum "recovery-terminating-state-cleanup" {
                   description "Terminated-id with default mapping to 9";
                 }
                 enum "session-init-failed" {
                   description "Terminated-id with default mapping to 9";
                 }
                 enum "subscriber-mgr-activation-failed" {
                   description "Terminated-id with default mapping to 9";
                 }
                 enum "subscriber-mgr-get-credentials-failed" {
                   description "Terminated-id with default mapping to 9";
                 }
                 enum "subscriber-mgr-link-interface-not-found" {
                   description "Terminated-id with default mapping to 9";
                 }
                 enum "subscriber-mgr-set-state-active-failed" {
                   description "Terminated-id with default mapping to 9";
                 }
               }
             }
           }
           case l2tp-terminate-code {
             leaf l2tp-terminate-code {
               description "Specify L2TP terminate-code";
               type enumeration {
                 enum "issu-in-progress" {
                   description "Terminated-id with default mapping to 10";
                 }
                 enum "session-access-interface-down" {
                   description "Terminated-id with default mapping to 8";
                 }
                 enum "session-administrative-close" {
                   description "Terminated-id with default mapping to 6";
                 }
                 enum "session-administrative-drain" {
                   description "Terminated-id with default mapping to 6";
                 }
                 enum "session-call-down" {
                   description "Terminated-id with default mapping to 10";
                 }
                 enum "session-call-failed" {
                   description "Terminated-id with default mapping to 15";
                 }
                 enum "session-create-failed-icrq-to-initiator-tunnel" {
                   description "Terminated-id with default mapping to 9";
                 }
                 enum "session-create-failed-invalid-config" {
                   description "Terminated-id with default mapping to 10";
                 }
                 enum "session-create-failed-limit-reached" {
                   description "Terminated-id with default mapping to 9";
                 }
                 enum "session-create-failed-no-resources" {
                   description "Terminated-id with default mapping to 9";
                 }
                 enum "session-create-failed-single-shot-tunnel-already-fired" {
                   description "Terminated-id with default mapping to 9";
                 }
                 enum "session-create-failed-too-busy" {
                   description "Terminated-id with default mapping to 9";
                 }
                 enum "session-failover-protocol-resync-disconnect" {
                   description "Terminated-id with default mapping to 6";
                 }
                 enum "session-hardware-unavailable" {
                   description "Terminated-id with default mapping to 8";
                 }
                 enum "session-no-resources-server-port" {
                   description "Terminated-id with default mapping to 9";
                 }
                 enum "session-not-ready" {
                   description "Terminated-id with default mapping to 9";
                 }
                 enum "session-receive-cdn" {
                   description "Terminated-id with default mapping to 10";
                 }
                 enum "session-receive-cdn-avp-bad-hidden" {
                   description "Terminated-id with default mapping to 10";
                 }
                 enum "session-receive-cdn-avp-bad-value-assigned-session-id" {
                   description "Terminated-id with default mapping to 10";
                 }
                 enum "session-receive-cdn-avp-duplicate-value-assigned-session-id" {
                   description "Terminated-id with default mapping to 10";
                 }
                 enum "session-receive-cdn-avp-malformed-bad-length" {
                   description "Terminated-id with default mapping to 10";
                 }
                 enum "session-receive-cdn-avp-malformed-truncated" {
                   description "Terminated-id with default mapping to 10";
                 }
                 enum "session-receive-cdn-avp-missing-mandatory-assigned-session-id" {
                   description "Terminated-id with default mapping to 10";
                 }
                 enum "session-receive-cdn-avp-missing-mandatory-result-code" {
                   description "Terminated-id with default mapping to 10";
                 }
                 enum "session-receive-cdn-avp-missing-random-vector" {
                   description "Terminated-id with default mapping to 10";
                 }
                 enum "session-receive-cdn-avp-missing-secret" {
                   description "Terminated-id with default mapping to 10";
                 }
                 enum "session-receive-cdn-avp-unknown" {
                   description "Terminated-id with default mapping to 10";
                 }
                 enum "session-receive-cdn-no-resources" {
                   description "Terminated-id with default mapping to 10";
                 }
                 enum "session-receive-iccn-avp-bad-hidden" {
                   description "Terminated-id with default mapping to 10";
                 }
                 enum "session-receive-iccn-avp-bad-value-framing-type" {
                   description "Terminated-id with default mapping to 10";
                 }
                 enum "session-receive-iccn-avp-bad-value-proxy-authen-type" {
                   description "Terminated-id with default mapping to 10";
                 }
                 enum "session-receive-iccn-avp-bad-value-unsupported-proxy-authen-type" {
                   description "Terminated-id with default mapping to 10";
                 }
                 enum "session-receive-iccn-avp-malformed-bad-length" {
                   description "Terminated-id with default mapping to 10";
                 }
                 enum "session-receive-iccn-avp-malformed-truncated" {
                   description "Terminated-id with default mapping to 10";
                 }
                 enum "session-receive-iccn-avp-missing-mandatory-connect-speed" {
                   description "Terminated-id with default mapping to 10";
                 }
                 enum "session-receive-iccn-avp-missing-mandatory-framing-type" {
                   description "Terminated-id with default mapping to 10";
                 }
                 enum "session-receive-iccn-avp-missing-mandatory-proxy-authen-challenge" {
                   description "Terminated-id with default mapping to 10";
                 }
                 enum "session-receive-iccn-avp-missing-mandatory-proxy-authen-id" {
                   description "Terminated-id with default mapping to 10";
                 }
                 enum "session-receive-iccn-avp-missing-mandatory-proxy-authen-name" {
                   description "Terminated-id with default mapping to 10";
                 }
                 enum "session-receive-iccn-avp-missing-mandatory-proxy-authen-response" {
                   description "Terminated-id with default mapping to 10";
                 }
                 enum "session-receive-iccn-avp-missing-random-vector" {
                   description "Terminated-id with default mapping to 10";
                 }
                 enum "session-receive-iccn-avp-missing-secret" {
                   description "Terminated-id with default mapping to 10";
                 }
                 enum "session-receive-iccn-avp-unknown" {
                   description "Terminated-id with default mapping to 10";
                 }
                 enum "session-receive-iccn-no-resources" {
                   description "Terminated-id with default mapping to 10";
                 }
                 enum "session-receive-iccn-unexpected" {
                   description "Terminated-id with default mapping to 10";
                 }
                 enum "session-receive-icrp-avp-bad-hidden" {
                   description "Terminated-id with default mapping to 10";
                 }
                 enum "session-receive-icrp-avp-bad-value-assigned-session-id" {
                   description "Terminated-id with default mapping to 10";
                 }
                 enum "session-receive-icrp-avp-duplicate-value-assigned-session-id" {
                   description "Terminated-id with default mapping to 10";
                 }
                 enum "session-receive-icrp-avp-malformed-bad-length" {
                   description "Terminated-id with default mapping to 10";
                 }
                 enum "session-receive-icrp-avp-malformed-truncated" {
                   description "Terminated-id with default mapping to 10";
                 }
                 enum "session-receive-icrp-avp-missing-mandatory-assigned-session-id" {
                   description "Terminated-id with default mapping to 10";
                 }
                 enum "session-receive-icrp-avp-missing-random-vector" {
                   description "Terminated-id with default mapping to 10";
                 }
                 enum "session-receive-icrp-avp-missing-secret" {
                   description "Terminated-id with default mapping to 10";
                 }
                 enum "session-receive-icrp-avp-unknown" {
                   description "Terminated-id with default mapping to 10";
                 }
                 enum "session-receive-icrp-no-resources" {
                   description "Terminated-id with default mapping to 10";
                 }
                 enum "session-receive-icrp-unexpected" {
                   description "Terminated-id with default mapping to 10";
                 }
                 enum "session-receive-icrq-administrative-close" {
                   description "Terminated-id with default mapping to 6";
                 }
                 enum "session-receive-icrq-authenticate-failed-host" {
                   description "Terminated-id with default mapping to 10";
                 }
                 enum "session-receive-icrq-avp-bad-hidden" {
                   description "Terminated-id with default mapping to 10";
                 }
                 enum "session-receive-icrq-avp-bad-value-assigned-session-id" {
                   description "Terminated-id with default mapping to 10";
                 }
                 enum "session-receive-icrq-avp-bad-value-bearer-type" {
                   description "Terminated-id with default mapping to 10";
                 }
                 enum "session-receive-icrq-avp-bad-value-cisco-nas-port" {
                   description "Terminated-id with default mapping to 10";
                 }
                 enum "session-receive-icrq-avp-duplicate-value-assigned-session-id" {
                   description "Terminated-id with default mapping to 10";
                 }
                 enum "session-receive-icrq-avp-malformed-bad-length" {
                   description "Terminated-id with default mapping to 10";
                 }
                 enum "session-receive-icrq-avp-malformed-truncated" {
                   description "Terminated-id with default mapping to 10";
                 }
                 enum "session-receive-icrq-avp-missing-mandatory-assigned-session-id" {
                   description "Terminated-id with default mapping to 10";
                 }
                 enum "session-receive-icrq-avp-missing-mandatory-call-serial-number" {
                   description "Terminated-id with default mapping to 10";
                 }
                 enum "session-receive-icrq-avp-missing-random-vector" {
                   description "Terminated-id with default mapping to 10";
                 }
                 enum "session-receive-icrq-avp-missing-secret" {
                   description "Terminated-id with default mapping to 10";
                 }
                 enum "session-receive-icrq-avp-unknown" {
                   description "Terminated-id with default mapping to 10";
                 }
                 enum "session-receive-icrq-no-resources" {
                   description "Terminated-id with default mapping to 10";
                 }
                 enum "session-receive-icrq-unexpected" {
                   description "Terminated-id with default mapping to 10";
                 }
                 enum "session-receive-occn-avp-bad-hidden" {
                   description "Terminated-id with default mapping to 10";
                 }
                 enum "session-receive-occn-avp-bad-value-framing-type" {
                   description "Terminated-id with default mapping to 10";
                 }
                 enum "session-receive-occn-avp-malformed-bad-length" {
                   description "Terminated-id with default mapping to 10";
                 }
                 enum "session-receive-occn-avp-malformed-truncated" {
                   description "Terminated-id with default mapping to 10";
                 }
                 enum "session-receive-occn-avp-missing-mandatory-connect-speed" {
                   description "Terminated-id with default mapping to 10";
                 }
                 enum "session-receive-occn-avp-missing-mandatory-framing-type" {
                   description "Terminated-id with default mapping to 10";
                 }
                 enum "session-receive-occn-avp-missing-random-vector" {
                   description "Terminated-id with default mapping to 10";
                 }
                 enum "session-receive-occn-avp-missing-secret" {
                   description "Terminated-id with default mapping to 10";
                 }
                 enum "session-receive-occn-avp-unknown" {
                   description "Terminated-id with default mapping to 10";
                 }
                 enum "session-receive-occn-no-resources" {
                   description "Terminated-id with default mapping to 10";
                 }
                 enum "session-receive-occn-unexpected" {
                   description "Terminated-id with default mapping to 10";
                 }
                 enum "session-receive-ocrp-avp-bad-hidden" {
                   description "Terminated-id with default mapping to 10";
                 }
                 enum "session-receive-ocrp-avp-bad-value-assigned-session-id" {
                   description "Terminated-id with default mapping to 10";
                 }
                 enum "session-receive-ocrp-avp-duplicate-value-assigned-session-id" {
                   description "Terminated-id with default mapping to 10";
                 }
                 enum "session-receive-ocrp-avp-malformed-bad-length" {
                   description "Terminated-id with default mapping to 10";
                 }
                 enum "session-receive-ocrp-avp-malformed-truncated" {
                   description "Terminated-id with default mapping to 10";
                 }
                 enum "session-receive-ocrp-avp-missing-mandatory-assigned-session-id" {
                   description "Terminated-id with default mapping to 10";
                 }
                 enum "session-receive-ocrp-avp-missing-random-vector" {
                   description "Terminated-id with default mapping to 10";
                 }
                 enum "session-receive-ocrp-avp-missing-secret" {
                   description "Terminated-id with default mapping to 10";
                 }
                 enum "session-receive-ocrp-avp-unknown" {
                   description "Terminated-id with default mapping to 10";
                 }
                 enum "session-receive-ocrp-no-resources" {
                   description "Terminated-id with default mapping to 10";
                 }
                 enum "session-receive-ocrp-unexpected" {
                   description "Terminated-id with default mapping to 10";
                 }
                 enum "session-receive-ocrq-administrative-close" {
                   description "Terminated-id with default mapping to 6";
                 }
                 enum "session-receive-ocrq-authenticate-failed-host" {
                   description "Terminated-id with default mapping to 10";
                 }
                 enum "session-receive-ocrq-avp-bad-hidden" {
                   description "Terminated-id with default mapping to 10";
                 }
                 enum "session-receive-ocrq-avp-bad-value-assigned-session-id" {
                   description "Terminated-id with default mapping to 10";
                 }
                 enum "session-receive-ocrq-avp-bad-value-bearer-type" {
                   description "Terminated-id with default mapping to 10";
                 }
                 enum "session-receive-ocrq-avp-bad-value-framing-type" {
                   description "Terminated-id with default mapping to 10";
                 }
                 enum "session-receive-ocrq-avp-duplicate-value-assigned-session-id" {
                   description "Terminated-id with default mapping to 10";
                 }
                 enum "session-receive-ocrq-avp-malformed-bad-length" {
                   description "Terminated-id with default mapping to 10";
                 }
                 enum "session-receive-ocrq-avp-malformed-truncated" {
                   description "Terminated-id with default mapping to 10";
                 }
                 enum "session-receive-ocrq-avp-missing-mandatory-assigned-session-id" {
                   description "Terminated-id with default mapping to 10";
                 }
                 enum "session-receive-ocrq-avp-missing-mandatory-bearer-type" {
                   description "Terminated-id with default mapping to 10";
                 }
                 enum "session-receive-ocrq-avp-missing-mandatory-call-serial-number" {
                   description "Terminated-id with default mapping to 10";
                 }
                 enum "session-receive-ocrq-avp-missing-mandatory-called-number" {
                   description "Terminated-id with default mapping to 10";
                 }
                 enum "session-receive-ocrq-avp-missing-mandatory-framing-type" {
                   description "Terminated-id with default mapping to 10";
                 }
                 enum "session-receive-ocrq-avp-missing-mandatory-maximum-bps" {
                   description "Terminated-id with default mapping to 10";
                 }
                 enum "session-receive-ocrq-avp-missing-mandatory-minimum-bps" {
                   description "Terminated-id with default mapping to 10";
                 }
                 enum "session-receive-ocrq-avp-missing-random-vector" {
                   description "Terminated-id with default mapping to 10";
                 }
                 enum "session-receive-ocrq-avp-missing-secret" {
                   description "Terminated-id with default mapping to 10";
                 }
                 enum "session-receive-ocrq-avp-unknown" {
                   description "Terminated-id with default mapping to 10";
                 }
                 enum "session-receive-ocrq-no-resources" {
                   description "Terminated-id with default mapping to 10";
                 }
                 enum "session-receive-ocrq-unexpected" {
                   description "Terminated-id with default mapping to 10";
                 }
                 enum "session-receive-ocrq-unsupported" {
                   description "Terminated-id with default mapping to 9";
                 }
                 enum "session-receive-sli-avp-bad-hidden" {
                   description "Terminated-id with default mapping to 10";
                 }
                 enum "session-receive-sli-avp-bad-value-accm" {
                   description "Terminated-id with default mapping to 10";
                 }
                 enum "session-receive-sli-avp-malformed-bad-length" {
                   description "Terminated-id with default mapping to 10";
                 }
                 enum "session-receive-sli-avp-malformed-truncated" {
                   description "Terminated-id with default mapping to 10";
                 }
                 enum "session-receive-sli-avp-missing-mandatory-accm" {
                   description "Terminated-id with default mapping to 10";
                 }
                 enum "session-receive-sli-avp-missing-random-vector" {
                   description "Terminated-id with default mapping to 10";
                 }
                 enum "session-receive-sli-avp-missing-secret" {
                   description "Terminated-id with default mapping to 10";
                 }
                 enum "session-receive-sli-avp-unknown" {
                   description "Terminated-id with default mapping to 10";
                 }
                 enum "session-receive-sli-no-resources" {
                   description "Terminated-id with default mapping to 10";
                 }
                 enum "session-receive-unexpected-packet-lac-incoming" {
                   description "Terminated-id with default mapping to 10";
                 }
                 enum "session-receive-unexpected-packet-lac-outgoing" {
                   description "Terminated-id with default mapping to 10";
                 }
                 enum "session-receive-unexpected-packet-lns-incoming" {
                   description "Terminated-id with default mapping to 10";
                 }
                 enum "session-receive-unexpected-packet-lns-outgoing" {
                   description "Terminated-id with default mapping to 10";
                 }
                 enum "session-receive-unknown-session-id" {
                   description "Terminated-id with default mapping to 10";
                 }
                 enum "session-receive-wen-avp-bad-hidden" {
                   description "Terminated-id with default mapping to 10";
                 }
                 enum "session-receive-wen-avp-malformed-bad-length" {
                   description "Terminated-id with default mapping to 10";
                 }
                 enum "session-receive-wen-avp-malformed-truncated" {
                   description "Terminated-id with default mapping to 10";
                 }
                 enum "session-receive-wen-avp-missing-mandatory-call-errors" {
                   description "Terminated-id with default mapping to 10";
                 }
                 enum "session-receive-wen-avp-missing-random-vector" {
                   description "Terminated-id with default mapping to 10";
                 }
                 enum "session-receive-wen-avp-missing-secret" {
                   description "Terminated-id with default mapping to 10";
                 }
                 enum "session-receive-wen-avp-unknown" {
                   description "Terminated-id with default mapping to 10";
                 }
                 enum "session-receive-wen-no-resources" {
                   description "Terminated-id with default mapping to 10";
                 }
                 enum "session-timeout-connection" {
                   description "Terminated-id with default mapping to 10";
                 }
                 enum "session-timeout-inactivity" {
                   description "Terminated-id with default mapping to 4";
                 }
                 enum "session-timeout-session" {
                   description "Terminated-id with default mapping to 5";
                 }
                 enum "session-timeout-upper-create" {
                   description "Terminated-id with default mapping to 9";
                 }
                 enum "session-transmit-speed-unavailable" {
                   description "Terminated-id with default mapping to 9";
                 }
                 enum "session-tunnel-down" {
                   description "Terminated-id with default mapping to 15";
                 }
                 enum "session-tunnel-failed" {
                   description "Terminated-id with default mapping to 15";
                 }
                 enum "session-tunnel-switch-profile-deleted" {
                   description "Terminated-id with default mapping to 6";
                 }
                 enum "session-tunneled-interface-down" {
                   description "Terminated-id with default mapping to 8";
                 }
                 enum "session-unknown-cause" {
                   description "Terminated-id with default mapping to 9";
                 }
                 enum "session-upper-create-failed" {
                   description "Terminated-id with default mapping to 9";
                 }
                 enum "session-upper-removed" {
                   description "Terminated-id with default mapping to 15";
                 }
                 enum "session-warmstart-not-operational" {
                   description "Terminated-id with default mapping to 15";
                 }
                 enum "session-warmstart-recovery-error" {
                   description "Terminated-id with default mapping to 15";
                 }
                 enum "session-warmstart-uppper-not-restacked" {
                   description "Terminated-id with default mapping to 10";
                 }
                 enum "session-rx-icrq-issu-in-progress" {
                   description "Terminated-id with default mapping to 10";
                 }
                 enum "session-rx-ocrq-issu-in-progress" {
                   description "Terminated-id with default mapping to 10";
                 }
                 enum "tunnel-administrative-close" {
                   description "Terminated-id with default mapping to 6";
                 }
                 enum "tunnel-administrative-drain" {
                   description "Terminated-id with default mapping to 6";
                 }
                 enum "tunnel-control-channel-failed" {
                   description "Terminated-id with default mapping to 15";
                 }
                 enum "tunnel-created-no-sessions" {
                   description "Terminated-id with default mapping to 1";
                 }
                 enum "tunnel-destination-address-changed" {
                   description "Terminated-id with default mapping to 6";
                 }
                 enum "tunnel-destination-down" {
                   description "Terminated-id with default mapping to 10";
                 }
                 enum "tunnel-failover-protocol-no-resources-for-recovery-tunnel" {
                   description "Terminated-id with default mapping to 15";
                 }
                 enum "tunnel-failover-protocol-no-resources-for-session-resync" {
                   description "Terminated-id with default mapping to 15";
                 }
                 enum "tunnel-failover-protocol-not-supported" {
                   description "Terminated-id with default mapping to 15";
                 }
                 enum "tunnel-failover-protocol-not-supported-by-peer" {
                   description "Terminated-id with default mapping to 15";
                 }
                 enum "tunnel-failover-protocol-recovery-control-channel-failed" {
                   description "Terminated-id with default mapping to 15";
                 }
                 enum "tunnel-failover-protocol-recovery-tunnel-failed" {
                   description "Terminated-id with default mapping to 15";
                 }
                 enum "tunnel-failover-protocol-recovery-tunnel-finished" {
                   description "Terminated-id with default mapping to 1";
                 }
                 enum "tunnel-failover-protocol-recovery-tunnel-primary-down" {
                   description "Terminated-id with default mapping to 1";
                 }
                 enum "tunnel-failover-protocol-session-resync-failed" {
                   description "Terminated-id with default mapping to 15";
                 }
                 enum "tunnel-host-profile-changed" {
                   description "Terminated-id with default mapping to 6";
                 }
                 enum "tunnel-host-profile-deleted" {
                   description "Terminated-id with default mapping to 6";
                 }
                 enum "tunnel-receive-fsq-avp-bad-hidden" {
                   description "Terminated-id with default mapping to 15";
                 }
                 enum "tunnel-receive-fsq-avp-malformed-bad-length" {
                   description "Terminated-id with default mapping to 15";
                 }
                 enum "tunnel-receive-fsq-avp-malformed-truncated" {
                   description "Terminated-id with default mapping to 15";
                 }
                 enum "tunnel-receive-fsq-avp-missing-mandatory-failover-session-state" {
                   description "Terminated-id with default mapping to 15";
                 }
                 enum "tunnel-receive-fsq-avp-missing-random-vector" {
                   description "Terminated-id with default mapping to 15";
                 }
                 enum "tunnel-receive-fsq-avp-missing-secret" {
                   description "Terminated-id with default mapping to 15";
                 }
                 enum "tunnel-receive-fsq-avp-unknown" {
                   description "Terminated-id with default mapping to 15";
                 }
                 enum "tunnel-receive-fsq-no-resources" {
                   description "Terminated-id with default mapping to 15";
                 }
                 enum "tunnel-receive-fsq-session-id-not-null" {
                   description "Terminated-id with default mapping to 15";
                 }
                 enum "tunnel-receive-fsr-avp-bad-hidden" {
                   description "Terminated-id with default mapping to 15";
                 }
                 enum "tunnel-receive-fsr-avp-malformed-bad-length" {
                   description "Terminated-id with default mapping to 15";
                 }
                 enum "tunnel-receive-fsr-avp-malformed-truncated" {
                   description "Terminated-id with default mapping to 15";
                 }
                 enum "tunnel-receive-fsr-avp-missing-mandatory-failover-session-state" {
                   description "Terminated-id with default mapping to 15";
                 }
                 enum "tunnel-receive-fsr-avp-missing-random-vector" {
                   description "Terminated-id with default mapping to 15";
                 }
                 enum "tunnel-receive-fsr-avp-missing-secret" {
                   description "Terminated-id with default mapping to 15";
                 }
                 enum "tunnel-receive-fsr-avp-unknown" {
                   description "Terminated-id with default mapping to 15";
                 }
                 enum "tunnel-receive-fsr-no-resources" {
                   description "Terminated-id with default mapping to 15";
                 }
                 enum "tunnel-receive-fsr-session-id-not-null" {
                   description "Terminated-id with default mapping to 15";
                 }
                 enum "tunnel-receive-recovery-scccn-authenticate-failed-challenge" {
                   description "Terminated-id with default mapping to 17";
                 }
                 enum "tunnel-receive-recovery-scccn-avp-bad-hidden" {
                   description "Terminated-id with default mapping to 15";
                 }
                 enum "tunnel-receive-recovery-scccn-avp-bad-value-challenge-response" {
                   description "Terminated-id with default mapping to 15";
                 }
                 enum "tunnel-receive-recovery-scccn-avp-malformed-bad-length" {
                   description "Terminated-id with default mapping to 15";
                 }
                 enum "tunnel-receive-recovery-scccn-avp-malformed-truncated" {
                   description "Terminated-id with default mapping to 15";
                 }
                 enum "tunnel-receive-recovery-scccn-avp-missing-challenge-response" {
                   description "Terminated-id with default mapping to 17";
                 }
                 enum "tunnel-receive-recovery-scccn-avp-missing-random-vector" {
                   description "Terminated-id with default mapping to 15";
                 }
                 enum "tunnel-receive-recovery-scccn-avp-missing-secret" {
                   description "Terminated-id with default mapping to 15";
                 }
                 enum "tunnel-receive-recovery-scccn-avp-unexpected-challenge-response" {
                   description "Terminated-id with default mapping to 15";
                 }
                 enum "tunnel-receive-recovery-scccn-avp-unknown" {
                   description "Terminated-id with default mapping to 15";
                 }
                 enum "tunnel-receive-recovery-scccn-no-resources" {
                   description "Terminated-id with default mapping to 15";
                 }
                 enum "tunnel-receive-recovery-scccn-session-id-not-null" {
                   description "Terminated-id with default mapping to 15";
                 }
                 enum "tunnel-receive-recovery-scccp-avp-unexpected-challenge-response" {
                   description "Terminated-id with default mapping to 15";
                 }
                 enum "tunnel-receive-recovery-scccp-avp-bad-value-challenge-response" {
                   description "Terminated-id with default mapping to 15";
                 }
                 enum "tunnel-receive-recovery-scccp-avp-missing-challenge-response" {
                   description "Terminated-id with default mapping to 17";
                 }
                 enum "tunnel-receive-recovery-sccrp-authenticate-failed-challenge" {
                   description "Terminated-id with default mapping to 17";
                 }
                 enum "tunnel-receive-recovery-sccrp-avp-bad-hidden" {
                   description "Terminated-id with default mapping to 15";
                 }
                 enum "tunnel-receive-recovery-sccrp-avp-bad-value-assigned-tunnel-id" {
                   description "Terminated-id with default mapping to 15";
                 }
                 enum "tunnel-receive-recovery-sccrp-avp-bad-value-bearer-capabilities" {
                   description "Terminated-id with default mapping to 15";
                 }
                 enum "tunnel-receive-recovery-sccrp-avp-bad-value-challenge" {
                   description "Terminated-id with default mapping to 15";
                 }
                 enum "tunnel-receive-recovery-sccrp-avp-bad-value-framing-capabilities" {
                   description "Terminated-id with default mapping to 15";
                 }
                 enum "tunnel-receive-recovery-sccrp-avp-bad-value-protocol-version" {
                   description "Terminated-id with default mapping to 15";
                 }
                 enum "tunnel-receive-recovery-sccrp-avp-bad-value-receive-window-size" {
                   description "Terminated-id with default mapping to 15";
                 }
                 enum "tunnel-receive-recovery-sccrp-avp-bad-value-suggested-control-sequence" {
                   description "Terminated-id with default mapping to 15";
                 }
                 enum "tunnel-receive-recovery-sccrp-avp-duplicate-value-assigned-tunnel-id" {
                   description "Terminated-id with default mapping to 15";
                 }
                 enum "tunnel-receive-recovery-sccrp-avp-malformed-bad-length" {
                   description "Terminated-id with default mapping to 15";
                 }
                 enum "tunnel-receive-recovery-sccrp-avp-malformed-truncated" {
                   description "Terminated-id with default mapping to 15";
                 }
                 enum "tunnel-receive-recovery-sccrp-avp-mismatched-host-name" {
                   description "Terminated-id with default mapping to 15";
                 }
                 enum "tunnel-receive-recovery-sccrp-avp-mismatched-vendor-name" {
                   description "Terminated-id with default mapping to 15";
                 }
                 enum "tunnel-receive-recovery-sccrp-avp-missing-mandatory-assigned-tunnel-id" {
                   description "Terminated-id with default mapping to 15";
                 }
                 enum "tunnel-receive-recovery-sccrp-avp-missing-mandatory-framing-capabilities" {
                   description "Terminated-id with default mapping to 15";
                 }
                 enum "tunnel-receive-recovery-sccrp-avp-missing-mandatory-host-name" {
                   description "Terminated-id with default mapping to 15";
                 }
                 enum "tunnel-receive-recovery-sccrp-avp-missing-mandatory-protocol-version" {
                   description "Terminated-id with default mapping to 15";
                 }
                 enum "tunnel-receive-recovery-sccrp-avp-missing-random-vector" {
                   description "Terminated-id with default mapping to 15";
                 }
                 enum "tunnel-receive-recovery-sccrp-avp-missing-secret" {
                   description "Terminated-id with default mapping to 15";
                 }
                 enum "tunnel-receive-recovery-sccrp-avp-unexpected-challenge-without-secret" {
                   description "Terminated-id with default mapping to 15";
                 }
                 enum "tunnel-receive-recovery-sccrp-avp-unknown" {
                   description "Terminated-id with default mapping to 15";
                 }
                 enum "tunnel-receive-recovery-sccrp-no-resources" {
                   description "Terminated-id with default mapping to 15";
                 }
                 enum "tunnel-receive-recovery-sccrp-session-id-not-null" {
                   description "Terminated-id with default mapping to 15";
                 }
                 enum "tunnel-receive-recovery-sccrq-administrative-close" {
                   description "Terminated-id with default mapping to 6";
                 }
                 enum "tunnel-receive-recovery-sccrq-avp-bad-hidden" {
                   description "Terminated-id with default mapping to 15";
                 }
                 enum "tunnel-receive-recovery-sccrq-avp-bad-value-assigned-tunnel-id" {
                   description "Terminated-id with default mapping to 15";
                 }
                 enum "tunnel-receive-recovery-sccrq-avp-bad-value-bearer-capabilities" {
                   description "Terminated-id with default mapping to 15";
                 }
                 enum "tunnel-receive-recovery-sccrq-avp-bad-value-challenge" {
                   description "Terminated-id with default mapping to 15";
                 }
                 enum "tunnel-receive-recovery-sccrq-avp-bad-value-framing-capabilities" {
                   description "Terminated-id with default mapping to 15";
                 }
                 enum "tunnel-receive-recovery-sccrq-avp-bad-value-protocol-version" {
                   description "Terminated-id with default mapping to 15";
                 }
                 enum "tunnel-receive-recovery-sccrq-avp-bad-value-receive-window-size" {
                   description "Terminated-id with default mapping to 15";
                 }
                 enum "tunnel-receive-recovery-sccrq-avp-bad-value-tunnel-recovery" {
                   description "Terminated-id with default mapping to 15";
                 }
                 enum "tunnel-receive-recovery-sccrq-avp-duplicate-value-assigned-tunnel-id" {
                   description "Terminated-id with default mapping to 15";
                 }
                 enum "tunnel-receive-recovery-sccrq-avp-duplicate-value-tie-breaker" {
                   description "Terminated-id with default mapping to 15";
                 }
                 enum "tunnel-receive-recovery-sccrq-avp-malformed-bad-length" {
                   description "Terminated-id with default mapping to 15";
                 }
                 enum "tunnel-receive-recovery-sccrq-avp-malformed-truncated" {
                   description "Terminated-id with default mapping to 15";
                 }
                 enum "tunnel-receive-recovery-sccrq-avp-mismatched-host-name" {
                   description "Terminated-id with default mapping to 15";
                 }
                 enum "tunnel-receive-recovery-sccrq-avp-mismatched-vendor-name" {
                   description "Terminated-id with default mapping to 15";
                 }
                 enum "tunnel-receive-recovery-sccrq-avp-missing-mandatory-assigned-tunnel-id" {
                   description "Terminated-id with default mapping to 15";
                 }
                 enum "tunnel-receive-recovery-sccrq-avp-missing-mandatory-framing-capabilities" {
                   description "Terminated-id with default mapping to 15";
                 }
                 enum "tunnel-receive-recovery-sccrq-avp-missing-mandatory-host-name" {
                   description "Terminated-id with default mapping to 15";
                 }
                 enum "tunnel-receive-recovery-sccrq-avp-missing-mandatory-protocol-version" {
                   description "Terminated-id with default mapping to 15";
                 }
                 enum "tunnel-receive-recovery-sccrq-avp-missing-mandatory-tunnel-recovery" {
                   description "Terminated-id with default mapping to 15";
                 }
                 enum "tunnel-receive-recovery-sccrq-avp-missing-random-vector" {
                   description "Terminated-id with default mapping to 15";
                 }
                 enum "tunnel-receive-recovery-sccrq-avp-missing-secret" {
                   description "Terminated-id with default mapping to 15";
                 }
                 enum "tunnel-receive-recovery-sccrq-avp-missing-tie-breaker" {
                   description "Terminated-id with default mapping to 15";
                 }
                 enum "tunnel-receive-recovery-sccrq-avp-unexpected-challenge-without-secret" {
                   description "Terminated-id with default mapping to 15";
                 }
                 enum "tunnel-receive-recovery-sccrq-avp-unknown" {
                   description "Terminated-id with default mapping to 15";
                 }
                 enum "tunnel-receive-recovery-sccrq-no-resources-max-tunnels" {
                   description "Terminated-id with default mapping to 15";
                 }
                 enum "tunnel-receive-recovery-sccrq-session-id-not-null" {
                   description "Terminated-id with default mapping to 15";
                 }
                 enum "tunnel-receive-recovery-sccrq-tunnel-id-not-null" {
                   description "Terminated-id with default mapping to 15";
                 }
                 enum "tunnel-receive-recovery-stopccn-avp-bad-hidden" {
                   description "Terminated-id with default mapping to 15";
                 }
                 enum "tunnel-receive-recovery-stopccn-avp-bad-value-assigned-tunnel-id" {
                   description "Terminated-id with default mapping to 15";
                 }
                 enum "tunnel-receive-recovery-stopccn-avp-duplicate-value-assigned-tunnel-id" {
                   description "Terminated-id with default mapping to 15";
                 }
                 enum "tunnel-receive-recovery-stopccn-avp-malformed-bad-length" {
                   description "Terminated-id with default mapping to 15";
                 }
                 enum "tunnel-receive-recovery-stopccn-avp-malformed-truncated" {
                   description "Terminated-id with default mapping to 15";
                 }
                 enum "tunnel-receive-recovery-stopccn-avp-missing-mandatory-assigned-tunnel-id" {
                   description "Terminated-id with default mapping to 15";
                 }
                 enum "tunnel-receive-recovery-stopccn-avp-missing-mandatory-result-code" {
                   description "Terminated-id with default mapping to 15";
                 }
                 enum "tunnel-receive-recovery-stopccn-avp-missing-random-vector" {
                   description "Terminated-id with default mapping to 15";
                 }
                 enum "tunnel-receive-recovery-stopccn-avp-missing-secret" {
                   description "Terminated-id with default mapping to 15";
                 }
                 enum "tunnel-receive-recovery-stopccn-avp-unknown" {
                   description "Terminated-id with default mapping to 15";
                 }
                 enum "tunnel-receive-recovery-stopccn-no-resources" {
                   description "Terminated-id with default mapping to 15";
                 }
                 enum "tunnel-receive-recovery-stopccn-session-id-not-null" {
                   description "Terminated-id with default mapping to 15";
                 }
                 enum "tunnel-receive-recovery-unexpected-packet" {
                   description "Terminated-id with default mapping to 15";
                 }
                 enum "tunnel-receive-recovery-unknown-packet-message-type-indecipherable" {
                   description "Terminated-id with default mapping to 15";
                 }
                 enum "tunnel-receive-recovery-unknown-packet-message-type-unrecognized" {
                   description "Terminated-id with default mapping to 15";
                 }
                 enum "tunnel-receive-scccn-authenticate-failed-challenge" {
                   description "Terminated-id with default mapping to 17";
                 }
                 enum "tunnel-receive-scccn-avp-bad-hidden" {
                   description "Terminated-id with default mapping to 15";
                 }
                 enum "tunnel-receive-scccn-avp-bad-value-challenge-response" {
                   description "Terminated-id with default mapping to 15";
                 }
                 enum "tunnel-receive-scccn-avp-malformed-bad-length" {
                   description "Terminated-id with default mapping to 15";
                 }
                 enum "tunnel-receive-scccn-avp-malformed-truncated" {
                   description "Terminated-id with default mapping to 15";
                 }
                 enum "tunnel-receive-scccn-avp-missing-challenge-response" {
                   description "Terminated-id with default mapping to 17";
                 }
                 enum "tunnel-receive-scccn-avp-missing-random-vector" {
                   description "Terminated-id with default mapping to 15";
                 }
                 enum "tunnel-receive-scccn-avp-missing-secret" {
                   description "Terminated-id with default mapping to 15";
                 }
                 enum "tunnel-receive-scccn-avp-unexpected-challenge-response" {
                   description "Terminated-id with default mapping to 15";
                 }
                 enum "tunnel-receive-scccn-avp-unknown" {
                   description "Terminated-id with default mapping to 15";
                 }
                 enum "tunnel-receive-scccn-no-resources" {
                   description "Terminated-id with default mapping to 15";
                 }
                 enum "tunnel-receive-scccn-session-id-not-null" {
                   description "Terminated-id with default mapping to 15";
                 }
                 enum "tunnel-receive-scccn-unexpected" {
                   description "Terminated-id with default mapping to 15";
                 }
                 enum "tunnel-receive-sccrp-authenticate-failed-challenge" {
                   description "Terminated-id with default mapping to 17";
                 }
                 enum "tunnel-receive-sccrp-authenticate-failed-host" {
                   description "Terminated-id with default mapping to 17";
                 }
                 enum "tunnel-receive-sccrp-avp-bad-hidden" {
                   description "Terminated-id with default mapping to 15";
                 }
                 enum "tunnel-receive-sccrp-avp-bad-value-assigned-tunnel-id" {
                   description "Terminated-id with default mapping to 15";
                 }
                 enum "tunnel-receive-sccrp-avp-bad-value-bearer-capabilities" {
                   description "Terminated-id with default mapping to 15";
                 }
                 enum "tunnel-receive-sccrp-avp-bad-value-challenge" {
                   description "Terminated-id with default mapping to 15";
                 }
                 enum "tunnel-receive-sccrp-avp-bad-value-challenge-response" {
                   description "Terminated-id with default mapping to 15";
                 }
                 enum "tunnel-receive-sccrp-avp-bad-value-failover-capability" {
                   description "Terminated-id with default mapping to 15";
                 }
                 enum "tunnel-receive-sccrp-avp-bad-value-framing-capabilities" {
                   description "Terminated-id with default mapping to 15";
                 }
                 enum "tunnel-receive-sccrp-avp-bad-value-protocol-version" {
                   description "Terminated-id with default mapping to 15";
                 }
                 enum "tunnel-receive-sccrp-avp-bad-value-receive-window-size" {
                   description "Terminated-id with default mapping to 15";
                 }
                 enum "tunnel-receive-sccrp-avp-duplicate-value-assigned-tunnel-id" {
                   description "Terminated-id with default mapping to 15";
                 }
                 enum "tunnel-receive-sccrp-avp-malformed-bad-length" {
                   description "Terminated-id with default mapping to 15";
                 }
                 enum "tunnel-receive-sccrp-avp-malformed-truncated" {
                   description "Terminated-id with default mapping to 15";
                 }
                 enum "tunnel-receive-sccrp-avp-missing-challenge-response" {
                   description "Terminated-id with default mapping to 17";
                 }
                 enum "tunnel-receive-sccrp-avp-missing-mandatory-assigned-tunnel-id" {
                   description "Terminated-id with default mapping to 15";
                 }
                 enum "tunnel-receive-sccrp-avp-missing-mandatory-framing-capabilities" {
                   description "Terminated-id with default mapping to 15";
                 }
                 enum "tunnel-receive-sccrp-avp-missing-mandatory-host-name" {
                   description "Terminated-id with default mapping to 15";
                 }
                 enum "tunnel-receive-sccrp-avp-missing-mandatory-protocol-version" {
                   description "Terminated-id with default mapping to 15";
                 }
                 enum "tunnel-receive-sccrp-avp-missing-random-vector" {
                   description "Terminated-id with default mapping to 15";
                 }
                 enum "tunnel-receive-sccrp-avp-missing-secret" {
                   description "Terminated-id with default mapping to 15";
                 }
                 enum "tunnel-receive-sccrp-avp-unexpected-challenge-response" {
                   description "Terminated-id with default mapping to 15";
                 }
                 enum "tunnel-receive-sccrp-avp-unexpected-challenge-without-secret" {
                   description "Terminated-id with default mapping to 15";
                 }
                 enum "tunnel-receive-sccrp-avp-unknown" {
                   description "Terminated-id with default mapping to 15";
                 }
                 enum "tunnel-receive-sccrp-no-resources" {
                   description "Terminated-id with default mapping to 15";
                 }
                 enum "tunnel-receive-sccrp-session-id-not-null" {
                   description "Terminated-id with default mapping to 15";
                 }
                 enum "tunnel-receive-sccrp-unexpected" {
                   description "Terminated-id with default mapping to 15";
                 }
                 enum "tunnel-receive-sccrq-administrative-close" {
                   description "Terminated-id with default mapping to 6";
                 }
                 enum "tunnel-receive-sccrq-authenticate-failed-host" {
                   description "Terminated-id with default mapping to 17";
                 }
                 enum "tunnel-receive-sccrq-avp-bad-hidden" {
                   description "Terminated-id with default mapping to 15";
                 }
                 enum "tunnel-receive-sccrq-avp-bad-value-assigned-tunnel-id" {
                   description "Terminated-id with default mapping to 15";
                 }
                 enum "tunnel-receive-sccrq-avp-bad-value-bearer-capabilities" {
                   description "Terminated-id with default mapping to 15";
                 }
                 enum "tunnel-receive-sccrq-avp-bad-value-challenge" {
                   description "Terminated-id with default mapping to 15";
                 }
                 enum "tunnel-receive-sccrq-avp-bad-value-failover-capability" {
                   description "Terminated-id with default mapping to 15";
                 }
                 enum "tunnel-receive-sccrq-avp-bad-value-framing-capabilities" {
                   description "Terminated-id with default mapping to 15";
                 }
                 enum "tunnel-receive-sccrq-avp-bad-value-protocol-version" {
                   description "Terminated-id with default mapping to 15";
                 }
                 enum "tunnel-receive-sccrq-avp-bad-value-receive-window-size" {
                   description "Terminated-id with default mapping to 15";
                 }
                 enum "tunnel-receive-sccrq-avp-duplicate-value-assigned-tunnel-id" {
                   description "Terminated-id with default mapping to 15";
                 }
                 enum "tunnel-receive-sccrq-avp-malformed-bad-length" {
                   description "Terminated-id with default mapping to 15";
                 }
                 enum "tunnel-receive-sccrq-avp-malformed-truncated" {
                   description "Terminated-id with default mapping to 15";
                 }
                 enum "tunnel-receive-sccrq-avp-missing-mandatory-assigned-tunnel-id" {
                   description "Terminated-id with default mapping to 15";
                 }
                 enum "tunnel-receive-sccrq-avp-missing-mandatory-framing-capabilities" {
                   description "Terminated-id with default mapping to 15";
                 }
                 enum "tunnel-receive-sccrq-avp-missing-mandatory-host-name" {
                   description "Terminated-id with default mapping to 15";
                 }
                 enum "tunnel-receive-sccrq-avp-missing-mandatory-protocol-version" {
                   description "Terminated-id with default mapping to 15";
                 }
                 enum "tunnel-receive-sccrq-avp-missing-random-vector" {
                   description "Terminated-id with default mapping to 15";
                 }
                 enum "tunnel-receive-sccrq-avp-missing-secret" {
                   description "Terminated-id with default mapping to 15";
                 }
                 enum "tunnel-receive-sccrq-avp-unexpected-challenge-without-secret" {
                   description "Terminated-id with default mapping to 15";
                 }
                 enum "tunnel-receive-sccrq-avp-unknown" {
                   description "Terminated-id with default mapping to 15";
                 }
                 enum "tunnel-receive-sccrq-bad-address" {
                   description "Terminated-id with default mapping to 15";
                 }
                 enum "tunnel-receive-sccrq-invalid-ns" {
                   description "Terminated-id with default mapping to 10";
                 }
                 enum "tunnel-receive-sccrq-no-resources" {
                   description "Terminated-id with default mapping to 15";
                 }
                 enum "tunnel-receive-sccrq-no-resources-max-tunnels" {
                   description "Terminated-id with default mapping to 15";
                 }
                 enum "tunnel-receive-sccrq-session-id-not-null" {
                   description "Terminated-id with default mapping to 15";
                 }
                 enum "tunnel-receive-sccrq-unexpected" {
                   description "Terminated-id with default mapping to 15";
                 }
                 enum "tunnel-receive-session-packet-null-session-id-invalid" {
                   description "Terminated-id with default mapping to 15";
                 }
                 enum "tunnel-receive-session-packet-null-session-id-without-assigned-session-id" {
                   description "Terminated-id with default mapping to 15";
                 }
                 enum "tunnel-receive-stopccn" {
                   description "Terminated-id with default mapping to 1";
                 }
                 enum "tunnel-receive-stopccn-avp-bad-hidden" {
                   description "Terminated-id with default mapping to 15";
                 }
                 enum "tunnel-receive-stopccn-avp-bad-value-assigned-tunnel-id" {
                   description "Terminated-id with default mapping to 15";
                 }
                 enum "tunnel-receive-stopccn-avp-duplicate-value-assigned-tunnel-id" {
                   description "Terminated-id with default mapping to 15";
                 }
                 enum "tunnel-receive-stopccn-avp-malformed-bad-length" {
                   description "Terminated-id with default mapping to 15";
                 }
                 enum "tunnel-receive-stopccn-avp-malformed-truncated" {
                   description "Terminated-id with default mapping to 15";
                 }
                 enum "tunnel-receive-stopccn-avp-missing-mandatory-assigned-tunnel-id" {
                   description "Terminated-id with default mapping to 15";
                 }
                 enum "tunnel-receive-stopccn-avp-missing-mandatory-result-code" {
                   description "Terminated-id with default mapping to 15";
                 }
                 enum "tunnel-receive-stopccn-avp-missing-random-vector" {
                   description "Terminated-id with default mapping to 15";
                 }
                 enum "tunnel-receive-stopccn-avp-missing-secret" {
                   description "Terminated-id with default mapping to 15";
                 }
                 enum "tunnel-receive-stopccn-avp-unknown" {
                   description "Terminated-id with default mapping to 15";
                 }
                 enum "tunnel-receive-stopccn-no-resources" {
                   description "Terminated-id with default mapping to 15";
                 }
                 enum "tunnel-receive-stopccn-session-id-not-null" {
                   description "Terminated-id with default mapping to 15";
                 }
                 enum "tunnel-receive-unexpected-packet" {
                   description "Terminated-id with default mapping to 15";
                 }
                 enum "tunnel-receive-unexpected-packet-for-session" {
                   description "Terminated-id with default mapping to 15";
                 }
                 enum "tunnel-receive-unknown-packet-message-type-indecipherable" {
                   description "Terminated-id with default mapping to 15";
                 }
                 enum "tunnel-receive-unknown-packet-message-type-unrecognized" {
                   description "Terminated-id with default mapping to 15";
                 }
                 enum "tunnel-timeout-connection" {
                   description "Terminated-id with default mapping to 15";
                 }
                 enum "tunnel-timeout-connection-recovery-tunnel" {
                   description "Terminated-id with default mapping to 15";
                 }
                 enum "tunnel-timeout-idle" {
                   description "Terminated-id with default mapping to 1";
                 }
                 enum "tunnel-unknown-cause" {
                   description "Terminated-id with default mapping to 9";
                 }
                 enum "tunnel-warmstart-not-operational" {
                   description "Terminated-id with default mapping to 15";
                 }
                 enum "tunnel-warmstart-recovery-error" {
                   description "Terminated-id with default mapping to 15";
                 }
               }
             }
           }
         }
       }
     }
     output {
       container aaa-test-result {
         uses aaa-test-result-block;
       }
     }
   }
   rpc get-dhcp-user-aaa-test-result {
     description "Test the aaa servers for a dhcp user";
     input {
       leaf user {
         description "The username to test";
         type string;
         mandatory true;
       }
       leaf password {
         description "The password associated with username";
         type string;
       }
       leaf profile {
         description "Specify the access profile name which to use for user";
         type string;
       }
       leaf logical-system {
         description "Specify the logical-system in which to authenticate user";
         type string;
       }
       leaf routing-instance {
         description "Specify the routing-instance in which to authenticate user";
         type string;
       }
       leaf service-type {
         description "Service type ";
         type string;
       }
       leaf mac-address {
         description "Specify the Mac address of the DHCP client";
         type mac-addr;
       }
       leaf option-82 {
         description "Specify the DHCP option 82";
         type string;
       }
       leaf agent-remote-id {
         description "DSL forum agent remote id ";
         type string {
           length "1 .. 63";
         }
       }
       leaf source-address {
         description "Use specified address as source address";
         type ipv4addr;
       }
       leaf no-address-request {
         description "Request is for authentication without address-allocation";
         type empty;
       }
       leaf terminate-code {
         description "Specify DHCP terminate-code";
         type enumeration {
           enum "client-request" {
             description "Terminated-id with default mapping to 1";
           }
           enum "lost-carrier" {
             description "Terminated-id with default mapping to 2";
           }
           enum "nak" {
             description "Terminated-id with default mapping to 15";
           }
           enum "nas-logout" {
             description "Terminated-id with default mapping to 10";
           }
           enum "no-offers" {
             description "Terminated-id with default mapping to 4";
           }
         }
       }
     }
     output {
       container aaa-test-result {
         uses aaa-test-result-block;
       }
     }
   }
   rpc get-authdlite-user-aaa-test-result {
     description "Test the aaa servers for a authdlite user";
     input {
       leaf user {
         description "The username to test";
         type string;
         mandatory true;
       }
       leaf password {
         description "The password associated with username";
         type string;
       }
       leaf profile {
         description "Specify the access profile name which to use for user";
         type string;
       }
       leaf port {
         description "Specify NAS-port to be used for test";
         type string;
       }
       leaf zero-stats {
         description "Specify that acct stats should be set to zero";
         type empty;
       }
     }
     output {
       container aaa-test-result {
         uses aaa-test-result-block;
       }
     }
   }
   rpc test-dot1x-sync-req {
     description "Send sync request to peer AD";
     input {
       leaf rg-id {
         description "Specify redundancy-group";
         type uint32;
       }
     }
   }
   rpc test-dot1x-sync-all {
     description "Send sync message containing all the authenticated entries";
     input {
       leaf rg-id {
         description "Specify redundancy-group";
         type uint32;
       }
     }
   }
   rpc test-dot1x-sync-mac {
     description "Simulate receiving sync message for particular session";
     input {
       leaf session {
         description "Session param ae-id, ifl-nm, mac, ch-id, user, filter-id, vlan, voip";
         type string;
       }
     }
   }
   rpc test-dot1x-del-sync-mac {
     input {
       leaf session {
         description "Session param ae-id, ifl-nm, mac";
         type string;
       }
     }
   }
   rpc test-zone-server-online {
     description "Online";
     input {
       leaf location {
         description "Location: local or remote";
         type enumeration {
           enum "local" {
             description "Local device";
           }
           enum "remote" {
             description "Remote device";
           }
         }
         mandatory true;
       }
       leaf n-port-wwn {
         description "N-Port WWN";
         type wwn;
         mandatory true;
       }
       leaf f-port-wwn {
         description "F-Port WWN";
         type wwn;
         mandatory true;
       }
       leaf fcid {
         description "FCID";
         type string {
           junos:posix-pattern "^0x[abcdefABCDEF0123456789]{6}$";
           junos:pattern-message "Must be hexadecimal bit pattern of form 0xDDAAPP";
         }
         mandatory true;
       }
       leaf fabric {
         description "Name of fabric";
         type string;
         mandatory true;
       }
     }
   }
   rpc test-zone-server-offline {
     description "Offline";
     input {
       leaf fcid {
         description "FCID";
         type string {
           junos:posix-pattern "^0x[abcdefABCDEF0123456789]{6}$";
           junos:pattern-message "Must be hexadecimal bit pattern of form 0xDDAAPP";
         }
         mandatory true;
       }
       leaf fabric {
         description "Name of fabric";
         type string;
         mandatory true;
       }
     }
   }
   rpc none {
     description "Layer 2 forwarding commands";
     input {
       leaf in-memory-debug {
         description "Enable or disable in-memory tracing";
         type enumeration {
           enum "disable" {
             description "Disable in-memory tracing";
           }
           enum "enable" {
             description "Enable in-memory tracing";
           }
         }
       }
     }
   }
   rpc test-aaa-asm-ccr {
     description "Test commands to send CCR from diameter-asm";
     input {
       leaf msg-type {
         description "Specify CCR Message type";
         type enumeration {
           enum "ccri" {
             description "Trigger CCR-I message";
           }
           enum "ccru" {
             description "Trigger CCR-U message";
           }
           enum "ccrt" {
             description "Trigger CCR-T message";
           }
         }
         mandatory true;
       }
       leaf app-type {
         description "Specify Application type";
         type enumeration {
           enum "app-gx" {
             description "Trigger Gx message";
           }
           enum "app-gy" {
             description "Trigger Gy message";
           }
         }
         mandatory true;
       }
       leaf message-length {
         description "Specify message length";
         type enumeration {
           enum "short" {
             description "Short Gx message";
           }
           enum "long" {
             description "Long Gy message";
           }
         }
       }
       leaf te-id {
         description "TEID to be used in CCR";
         type uint32;
         mandatory true;
       }
       leaf bearer-id {
         description "Bearer-id to be used in CCR";
         type uint32;
         mandatory true;
       }
       leaf profile {
         description "Diameter application profile name";
         type string {
           length "1 .. 64";
         }
       }
       leaf count {
         description "Number of ccr messages, default is 1";
         type uint32;
       }
       leaf rate {
         description "Number of ccr messages per 100msec, default is 100";
         type uint32;
       }
     }
   }
   rpc get-radius-server-access-test-result {
     description "Test user access to a radius server";
     input {
       leaf address {
         description "RADIUS server address";
         type ipv4addr;
         mandatory true;
       }
       leaf authentication-port {
         description "RADIUS server authentication port number";
         default "1812";
         type uint16 {
           range "1 .. 65535";
         }
       }
       leaf secret {
         description "Shared secret with the RADIUS server";
         type string;
         mandatory true;
       }
       leaf user {
         description "User name to be authenticated to the RADIUS server";
         type string;
         mandatory true;
       }
       leaf password {
         description "Password for the user";
         type string;
         mandatory true;
       }
       leaf timeout {
         description "Request timeout period";
         default "3";
         units "seconds";
         type uint32 {
           range "1 .. 90";
         }
       }
       leaf retry {
         description "Retry attempts";
         default "3";
         type uint32 {
           range "1 .. 10";
         }
       }
       leaf source-address {
         description "Use specified address as source address";
         type ipv4addr;
       }
     }
   }
   rpc get-radius-profile-access-test-result {
     description "Test user access to an access profile";
     input {
       leaf profile-name {
         description "Access profile name";
         type string;
         mandatory true;
       }
       leaf user {
         description "User name to be authenticated to the RADIUS server";
         type string;
         mandatory true;
       }
       leaf password {
         description "Password for the user";
         type string;
         mandatory true;
       }
       leaf get-radius-profile-access-test-detail-result {
         description "Show radius attributes returned by the server";
         type empty;
       }
     }
     output {
       container radius-profile-access-test-result {
         uses radius-profile-access-test-result-block;
       }
     }
   }
 grouping route-information-block {
   leaf as-number {
     type int32;
   }
   leaf router-id {
     type ipaddr;
   }
   leaf maximum-ecmp {
     type int32;
   }
   leaf note-network-services-mode {
     type string;
   }
   list route-table {
     leaf table-name {
       type string;
       description "Unicast routing table";
     }
     leaf destination-count {
       type int32;
       description "Number of destinations in this rib";
     }
     leaf total-route-count {
       type int32;
     }
     leaf active-route-count {
       type int32;
       description "Active routes";
     }
     leaf holddown-route-count {
       type int32;
     }
     leaf hidden-route-count {
       type int32;
     }
     leaf restart-state {
       type string;
     }
     leaf prefix-max {
       type int32;
     }
     leaf prefix-threshold {
       type int32;
     }
     leaf prefix-label {
       type string;
     }
     leaf route-max {
       type int32;
     }
     leaf route-threshold {
       type int32;
     }
     leaf route-limit-label {
       type string;
     }
     list protocols {
       leaf protocol-name {
         type string;
       }
       leaf protocol-route-count {
         type int32;
         description "Total protocol routes";
       }
     }
     list rt {
       list terse {
         leaf rt-destination {
           type string;
         }
         leaf rt-prefix-length {
           type int32;
         }
         list rt-entry {
           leaf active-tag {
             type string;
             description "Visual indication of active state of this route entry";
           }
           leaf validation-state {
             type string;
           }
           leaf protocol-name {
             type string;
           }
           leaf preference {
             type int32;
             description "Preference for the route";
           }
           leaf metric {
             type int32;
           }
           leaf metric2 {
             type int32;
           }
           leaf nh-type {
             type string;
             description "Special next hop: Reject, Blackhole, Receive, Multicast, Local, or Unused";
           }
           leaf as-path {
             type string;
           }
           list route-data-dcf {
             list snpa {
               list pfe-port-snpa {
                 description "PFE Port SNPA";
                 leaf pfe-id {
                   type int32;
                 }
                 leaf port-id {
                   type int32;
                 }
               }
               list network-element-port-snpa {
                 description "Network Element Port SNPA";
                 leaf port-id {
                   type int32;
                 }
               }
               list mstp-root-snpa {
                 description "Multiple Spanning Tree Protocol Root SNPA";
                 leaf mstp-root-id {
                   type int32;
                 }
               }
               list gateway-snpa {
                 description "Gateway SNPA";
                 leaf gateway-addr {
                   type ipaddr;
                 }
               }
               list layer2-domain-port-snpa {
                 description "Layer-2 Domain Port SNPA";
                 leaf port-id {
                   type int32;
                 }
               }
               list replication-block-snpa {
                 description "Replication Block SNPA";
                 leaf replication-block-id {
                   type int32;
                 }
               }
               list replication-route-snpa {
                 description "Replication Route SNPA";
                 leaf network-element-id {
                   type ipaddr;
                 }
               }
               list layer2-multicast-port-snpa {
                 description "Layer-2 Multicast Port SNPA";
                 leaf layer2-multicast-port-id {
                   type int32;
                 }
               }
               list inh-snpa {
                 description "Indirection SNPA";
                 leaf inh-id {
                   type int32;
                 }
               }
             }
           }
           container rtd-flow-dep {
           }
           container communities {
             leaf community {
               type string;
               description "Basic community";
             }
             leaf extended-community {
               type string;
               description "Extended community";
             }
           }
           container attrset {
           }
           container link-state-information {
             container link-state-link {
               leaf color {
                 type int32;
               }
               leaf metric {
                 type int32;
               }
               leaf te-metric {
                 type int32;
                 description "LSP TE metric";
               }
               leaf ldp-support {
                 type string;
               }
               leaf rsvpte-support {
                 type string;
               }
               leaf maximum-bw {
                 type uint64;
               }
               leaf reservable-bw {
                 type uint64;
               }
               container protections {
                 leaf protection-type {
                   type string;
                   description "LSP protection desired";
                 }
               }
               container link-srlgs {
                 leaf link-srlg {
                   type string;
                 }
               }
               container unreserved-bws {
                 list unreserved-bw {
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf node-area {
                   type string;
                 }
               }
               container node-ipv4-router-ids {
                 leaf node-ipv4-router-id {
                   type ipaddr;
                 }
               }
               container node-topologies {
                 list node-topology {
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   leaf node-spring-srgb-block-start {
                     type uint32;
                   }
                   leaf node-spring-srgb-block-range {
                     type uint32;
                   }
                   leaf node-spring-srgb-block-flags {
                     type string;
                   }
                 }
               }
               container node-spring-algorithms {
                 list node-spring-algorithm {
                   leaf node-spring-algorithm-type {
                     type uint32;
                   }
                 }
               }
             }
             container link-state-prefix {
               container link-state-prefix-sid {
                 leaf link-state-prefix-sid-index {
                   type uint32;
                 }
                 leaf link-state-prefix-sid-flags {
                   type string;
                 }
                 leaf link-state-prefix-sid-algo {
                   type string;
                 }
               }
             }
             container link-state-unknown-tlvs {
               list link-state-unknown-tlv {
                 leaf unknown-type {
                   type uint32;
                 }
                 leaf unknown-length {
                   type uint32;
                 }
                 leaf unknown-bytes {
                   type string;
                 }
               }
             }
           }
           container aggregate {
           }
           list nh {
             description "Next-hop gateway information";
           }
           container protocol-nh {
             description "Protocol next hop";
             list nh {
               description "Next-hop gateway information";
               leaf nh-string {
                 type string;
               }
               leaf elnh-address {
                 type int32;
                 description "Address of Element Next-hop";
               }
               leaf to {
                 type string;
                 description "Neighbor address to which to send (next-hop address)";
               }
               leaf via {
                 type string;
                 description "Reachable via a local interface";
               }
               leaf localized-table {
                 type string;
                 description "Name of localized table";
               }
               leaf weight {
                 type int32;
                 description "Next-hop weight";
               }
               leaf balance {
                 type int32;
                 description "Next-hop balance";
               }
               leaf uflags {
                 type int32;
                 description "Next-hop uflags";
               }
               leaf filter {
                 type string;
                 description "Next-hop firewall filter";
               }
               leaf selected-next-hop {
                 type empty;
                 description "Present if this next hop is selected";
               }
               leaf session {
                 type int32;
                 description "Session ID Associated with this NH";
               }
               leaf statistics-id-group-terse {
                 type string;
                 description "Statistics ID Group Associated with this NH";
               }
               leaf ext-int-type {
                 type string;
                 description "Next-hop type of equal-external-internal multipath";
               }
               leaf fc {
                 type int32;
                 description "Forwarding-class";
               }
               leaf lsp-name {
                 type string;
                 description "Tunneled into an RSVP LSP";
               }
               leaf mpls-label {
                 type string;
                 description "Label of MPLS packet";
               }
               leaf label-ttl-action {
                 type string;
                 description "TTL action associated with labels";
               }
               leaf load-balance-label {
                 type string;
                 description "Load balance action associated with labels";
               }
               leaf label-element {
                 type string;
                 description "Pointer to the tag label element";
               }
               leaf label-element-parent {
                 type string;
                 description "Pointer to the tag label element parent";
               }
               leaf label-element-refcount {
                 type string;
                 description "Number of references to the tag label element";
               }
               leaf label-element-childcount {
                 type string;
                 description "Number of child references to the tag label element";
               }
               leaf label-element-lspid {
                 type string;
                 description "LSP ID of the tag label element";
               }
               leaf nh-table-receive {
                 type string;
                 description "Destination is a local address";
               }
               leaf nh-table {
                 type string;
                 description "Indirect pointing to another table";
               }
               leaf nh-localized-ifl {
                 type string;
                 description "Indirect pointing to a localized ifl";
               }
               leaf nh-local-interface {
                 type string;
                 description "Destination is a local interface";
               }
               leaf nh-service {
                 type string;
                 description "Next-hop service";
               }
               leaf nh-service-pkt-dist {
                 type string;
                 description "Multi services packet distribution type";
               }
               leaf nh-service-app-data {
                 type string;
                 description "Multi services application specific data";
               }
               leaf nh-private-comp {
                 type string;
                 description "Private Composite Next-hop";
               }
               leaf nh-index {
                 type uint32;
                 description "Next-hop index";
               }
               leaf nh-address {
                 type int32;
                 description "Address of next hop";
               }
               leaf tunnel-composite-attr-type {
                 type string;
                 description "Tunnel-Type for tunnel-composite-nexthop";
               }
               leaf tunnel-composite-attr-reference-count {
                 type int32;
                 description "Tunnel-reference-count for tunnel-composite-nexthop";
               }
               leaf tunnel-composite-attr-nh-id {
                 type int32;
                 description "Tunnel-NextHop-Id for tunnel-composite-nexthop";
               }
               leaf tunnel-composite-attr-dest {
                 type ipaddr;
                 description "Tunnel-Destination for tunnel-composite-nexthop";
               }
               leaf tunnel-composite-attr-src {
                 type ipaddr;
                 description "Tunnel-Source for tunnel-composite-nexthop";
               }
               leaf tunnel-composite-attr-tid {
                 type int32;
                 description "Tunnel-Id for tunnel-composite-nexthop";
               }
               leaf tunnel-composite-attr-label {
                 type string;
                 description "Tunnel-VPN-Label for tunnel-composite-nexthop";
               }
               leaf tunnel-composite-attr-label-ttl {
                 type string;
                 description "Tunnel-VPN-Label-TTL for tunnel-composite-nexthop";
               }
               leaf tunnel-composite-attr-segment-addr {
                 type ipaddr;
                 description "IPv6 segment-address";
               }
               leaf tunnel-composite-attr-vni {
                 type int32;
                 description "Tunnel-VNI for tunnel-composite-nexthop in VxLAN";
               }
               leaf tunnel-composite-attr-dest-mac {
                 type string;
                 description "Tunnel-Dest-Mac for tunnel-composite-nexthop in VxLAN";
               }
             }
           }
         }
       }
       list terse-mpls-fwd {
         leaf rt-destination {
           type string;
         }
         leaf rt-prefix-length {
           type int32;
         }
         list rt-entry {
           leaf active-tag {
             type string;
             description "Visual indication of active state of this route entry";
           }
           leaf validation-state {
             type string;
           }
           leaf protocol-name {
             type string;
           }
           leaf preference {
             type int32;
             description "Preference for the route";
           }
           leaf metric {
             type int32;
           }
           leaf metric2 {
             type int32;
           }
           leaf nh-type {
             type string;
             description "Special next hop: Reject, Blackhole, Receive, Multicast, Local, or Unused";
           }
           leaf as-path {
             type string;
           }
           list route-data-dcf {
             list snpa {
               list pfe-port-snpa {
                 description "PFE Port SNPA";
                 leaf pfe-id {
                   type int32;
                 }
                 leaf port-id {
                   type int32;
                 }
               }
               list network-element-port-snpa {
                 description "Network Element Port SNPA";
                 leaf port-id {
                   type int32;
                 }
               }
               list mstp-root-snpa {
                 description "Multiple Spanning Tree Protocol Root SNPA";
                 leaf mstp-root-id {
                   type int32;
                 }
               }
               list gateway-snpa {
                 description "Gateway SNPA";
                 leaf gateway-addr {
                   type ipaddr;
                 }
               }
               list layer2-domain-port-snpa {
                 description "Layer-2 Domain Port SNPA";
                 leaf port-id {
                   type int32;
                 }
               }
               list replication-block-snpa {
                 description "Replication Block SNPA";
                 leaf replication-block-id {
                   type int32;
                 }
               }
               list replication-route-snpa {
                 description "Replication Route SNPA";
                 leaf network-element-id {
                   type ipaddr;
                 }
               }
               list layer2-multicast-port-snpa {
                 description "Layer-2 Multicast Port SNPA";
                 leaf layer2-multicast-port-id {
                   type int32;
                 }
               }
               list inh-snpa {
                 description "Indirection SNPA";
                 leaf inh-id {
                   type int32;
                 }
               }
             }
           }
           container rtd-flow-dep {
           }
           container communities {
             leaf community {
               type string;
               description "Basic community";
             }
             leaf extended-community {
               type string;
               description "Extended community";
             }
           }
           container attrset {
           }
           container link-state-information {
             container link-state-link {
               leaf color {
                 type int32;
               }
               leaf metric {
                 type int32;
               }
               leaf te-metric {
                 type int32;
                 description "LSP TE metric";
               }
               leaf ldp-support {
                 type string;
               }
               leaf rsvpte-support {
                 type string;
               }
               leaf maximum-bw {
                 type uint64;
               }
               leaf reservable-bw {
                 type uint64;
               }
               container protections {
                 leaf protection-type {
                   type string;
                   description "LSP protection desired";
                 }
               }
               container link-srlgs {
                 leaf link-srlg {
                   type string;
                 }
               }
               container unreserved-bws {
                 list unreserved-bw {
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf node-area {
                   type string;
                 }
               }
               container node-ipv4-router-ids {
                 leaf node-ipv4-router-id {
                   type ipaddr;
                 }
               }
               container node-topologies {
                 list node-topology {
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   leaf node-spring-srgb-block-start {
                     type uint32;
                   }
                   leaf node-spring-srgb-block-range {
                     type uint32;
                   }
                   leaf node-spring-srgb-block-flags {
                     type string;
                   }
                 }
               }
               container node-spring-algorithms {
                 list node-spring-algorithm {
                   leaf node-spring-algorithm-type {
                     type uint32;
                   }
                 }
               }
             }
             container link-state-prefix {
               container link-state-prefix-sid {
                 leaf link-state-prefix-sid-index {
                   type uint32;
                 }
                 leaf link-state-prefix-sid-flags {
                   type string;
                 }
                 leaf link-state-prefix-sid-algo {
                   type string;
                 }
               }
             }
             container link-state-unknown-tlvs {
               list link-state-unknown-tlv {
                 leaf unknown-type {
                   type uint32;
                 }
                 leaf unknown-length {
                   type uint32;
                 }
                 leaf unknown-bytes {
                   type string;
                 }
               }
             }
           }
           container aggregate {
           }
           list nh {
             description "Next-hop gateway information";
           }
           container protocol-nh {
             description "Protocol next hop";
             list nh {
               description "Next-hop gateway information";
               leaf nh-string {
                 type string;
               }
               leaf elnh-address {
                 type int32;
                 description "Address of Element Next-hop";
               }
               leaf to {
                 type string;
                 description "Neighbor address to which to send (next-hop address)";
               }
               leaf via {
                 type string;
                 description "Reachable via a local interface";
               }
               leaf localized-table {
                 type string;
                 description "Name of localized table";
               }
               leaf weight {
                 type int32;
                 description "Next-hop weight";
               }
               leaf balance {
                 type int32;
                 description "Next-hop balance";
               }
               leaf uflags {
                 type int32;
                 description "Next-hop uflags";
               }
               leaf filter {
                 type string;
                 description "Next-hop firewall filter";
               }
               leaf selected-next-hop {
                 type empty;
                 description "Present if this next hop is selected";
               }
               leaf session {
                 type int32;
                 description "Session ID Associated with this NH";
               }
               leaf statistics-id-group-terse {
                 type string;
                 description "Statistics ID Group Associated with this NH";
               }
               leaf ext-int-type {
                 type string;
                 description "Next-hop type of equal-external-internal multipath";
               }
               leaf fc {
                 type int32;
                 description "Forwarding-class";
               }
               leaf lsp-name {
                 type string;
                 description "Tunneled into an RSVP LSP";
               }
               leaf mpls-label {
                 type string;
                 description "Label of MPLS packet";
               }
               leaf label-ttl-action {
                 type string;
                 description "TTL action associated with labels";
               }
               leaf load-balance-label {
                 type string;
                 description "Load balance action associated with labels";
               }
               leaf label-element {
                 type string;
                 description "Pointer to the tag label element";
               }
               leaf label-element-parent {
                 type string;
                 description "Pointer to the tag label element parent";
               }
               leaf label-element-refcount {
                 type string;
                 description "Number of references to the tag label element";
               }
               leaf label-element-childcount {
                 type string;
                 description "Number of child references to the tag label element";
               }
               leaf label-element-lspid {
                 type string;
                 description "LSP ID of the tag label element";
               }
               leaf nh-table-receive {
                 type string;
                 description "Destination is a local address";
               }
               leaf nh-table {
                 type string;
                 description "Indirect pointing to another table";
               }
               leaf nh-localized-ifl {
                 type string;
                 description "Indirect pointing to a localized ifl";
               }
               leaf nh-local-interface {
                 type string;
                 description "Destination is a local interface";
               }
               leaf nh-service {
                 type string;
                 description "Next-hop service";
               }
               leaf nh-service-pkt-dist {
                 type string;
                 description "Multi services packet distribution type";
               }
               leaf nh-service-app-data {
                 type string;
                 description "Multi services application specific data";
               }
               leaf nh-private-comp {
                 type string;
                 description "Private Composite Next-hop";
               }
               leaf nh-index {
                 type uint32;
                 description "Next-hop index";
               }
               leaf nh-address {
                 type int32;
                 description "Address of next hop";
               }
               leaf tunnel-composite-attr-type {
                 type string;
                 description "Tunnel-Type for tunnel-composite-nexthop";
               }
               leaf tunnel-composite-attr-reference-count {
                 type int32;
                 description "Tunnel-reference-count for tunnel-composite-nexthop";
               }
               leaf tunnel-composite-attr-nh-id {
                 type int32;
                 description "Tunnel-NextHop-Id for tunnel-composite-nexthop";
               }
               leaf tunnel-composite-attr-dest {
                 type ipaddr;
                 description "Tunnel-Destination for tunnel-composite-nexthop";
               }
               leaf tunnel-composite-attr-src {
                 type ipaddr;
                 description "Tunnel-Source for tunnel-composite-nexthop";
               }
               leaf tunnel-composite-attr-tid {
                 type int32;
                 description "Tunnel-Id for tunnel-composite-nexthop";
               }
               leaf tunnel-composite-attr-label {
                 type string;
                 description "Tunnel-VPN-Label for tunnel-composite-nexthop";
               }
               leaf tunnel-composite-attr-label-ttl {
                 type string;
                 description "Tunnel-VPN-Label-TTL for tunnel-composite-nexthop";
               }
               leaf tunnel-composite-attr-segment-addr {
                 type ipaddr;
                 description "IPv6 segment-address";
               }
               leaf tunnel-composite-attr-vni {
                 type int32;
                 description "Tunnel-VNI for tunnel-composite-nexthop in VxLAN";
               }
               leaf tunnel-composite-attr-dest-mac {
                 type string;
                 description "Tunnel-Dest-Mac for tunnel-composite-nexthop in VxLAN";
               }
             }
           }
         }
       }
       list brief {
         leaf rt-destination {
           type string;
         }
         leaf rt-prefix-length {
           type int32;
         }
         list rt-entry {
           leaf active-tag {
             type string;
             description "Visual indication of active state of this route entry";
           }
           leaf protocol-name {
             type string;
           }
           leaf preference {
             type int32;
             description "Preference for the route";
           }
           leaf preference2 {
             type int32;
           }
           leaf age {
             type string;
           }
           leaf metric {
             type int32;
           }
           leaf med {
             type int32;
             description "Multiple exit discriminator";
           }
           leaf local-preference {
             type int32;
           }
           leaf metric2 {
             type int32;
           }
           leaf rt-tag {
             type int32;
           }
           leaf rt-tag2 {
             type int32;
           }
           leaf learned-from {
             type ipaddr;
             description "Peer address from which this route was learned";
           }
           leaf peer-as {
             type int32;
             description "Peer AS number";
           }
           leaf evpn-remote-mes {
             type ipaddr;
             description "Remote PE";
           }
           leaf evpn-routing-instance-name {
             type string;
             description "Routing Instance";
           }
           leaf evpn-tag-rt-type {
             type string;
             description "Route Type";
           }
           leaf evpn-vlan-id {
             type int32;
             description "VLAN-ID";
           }
           leaf rt-evpn-esi {
             type string;
             description "ESI";
           }
           leaf evpn-isid {
             type int32;
             description "ISID";
           }
           leaf rt-evpn-bmac {
             type string;
             description "BMAC";
           }
           leaf as-path {
             type string;
           }
           leaf validation-state {
             type string;
           }
           leaf nh-type {
             type string;
             description "Special next hop: Reject, Blackhole, Receive, Multicast, Local, or Unused";
           }
           leaf bgp-rtarget-type {
             type string;
             description "BGP RT-Constrain route type";
           }
           leaf bgp-rtarget-generation {
             type uint32;
             description "BGP RT-Constrain generation";
           }
           leaf bgp-rtarget-for {
             type string;
             description "BGP RT-Constrain member";
           }
           list route-data-dcf {
             list snpa {
               list pfe-port-snpa {
                 description "PFE Port SNPA";
                 leaf pfe-id {
                   type int32;
                 }
                 leaf port-id {
                   type int32;
                 }
               }
               list network-element-port-snpa {
                 description "Network Element Port SNPA";
                 leaf port-id {
                   type int32;
                 }
               }
               list mstp-root-snpa {
                 description "Multiple Spanning Tree Protocol Root SNPA";
                 leaf mstp-root-id {
                   type int32;
                 }
               }
               list gateway-snpa {
                 description "Gateway SNPA";
                 leaf gateway-addr {
                   type ipaddr;
                 }
               }
               list layer2-domain-port-snpa {
                 description "Layer-2 Domain Port SNPA";
                 leaf port-id {
                   type int32;
                 }
               }
               list replication-block-snpa {
                 description "Replication Block SNPA";
                 leaf replication-block-id {
                   type int32;
                 }
               }
               list replication-route-snpa {
                 description "Replication Route SNPA";
                 leaf network-element-id {
                   type ipaddr;
                 }
               }
               list layer2-multicast-port-snpa {
                 description "Layer-2 Multicast Port SNPA";
                 leaf layer2-multicast-port-id {
                   type int32;
                 }
               }
               list inh-snpa {
                 description "Indirection SNPA";
                 leaf inh-id {
                   type int32;
                 }
               }
             }
           }
           container rtd-flow-dep {
           }
           container communities {
             leaf community {
               type string;
               description "Basic community";
             }
             leaf extended-community {
               type string;
               description "Extended community";
             }
           }
           container attrset {
           }
           container link-state-information {
             container link-state-link {
               leaf color {
                 type int32;
               }
               leaf metric {
                 type int32;
               }
               leaf te-metric {
                 type int32;
                 description "LSP TE metric";
               }
               leaf ldp-support {
                 type string;
               }
               leaf rsvpte-support {
                 type string;
               }
               leaf maximum-bw {
                 type uint64;
               }
               leaf reservable-bw {
                 type uint64;
               }
               container protections {
                 leaf protection-type {
                   type string;
                   description "LSP protection desired";
                 }
               }
               container link-srlgs {
                 leaf link-srlg {
                   type string;
                 }
               }
               container unreserved-bws {
                 list unreserved-bw {
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf node-area {
                   type string;
                 }
               }
               container node-ipv4-router-ids {
                 leaf node-ipv4-router-id {
                   type ipaddr;
                 }
               }
               container node-topologies {
                 list node-topology {
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   leaf node-spring-srgb-block-start {
                     type uint32;
                   }
                   leaf node-spring-srgb-block-range {
                     type uint32;
                   }
                   leaf node-spring-srgb-block-flags {
                     type string;
                   }
                 }
               }
               container node-spring-algorithms {
                 list node-spring-algorithm {
                   leaf node-spring-algorithm-type {
                     type uint32;
                   }
                 }
               }
             }
             container link-state-prefix {
               container link-state-prefix-sid {
                 leaf link-state-prefix-sid-index {
                   type uint32;
                 }
                 leaf link-state-prefix-sid-flags {
                   type string;
                 }
                 leaf link-state-prefix-sid-algo {
                   type string;
                 }
               }
             }
             container link-state-unknown-tlvs {
               list link-state-unknown-tlv {
                 leaf unknown-type {
                   type uint32;
                 }
                 leaf unknown-length {
                   type uint32;
                 }
                 leaf unknown-bytes {
                   type string;
                 }
               }
             }
           }
           container aggregate {
           }
           list nh {
             description "Next-hop gateway information";
           }
           container protocol-nh {
             description "Protocol next hop";
             list nh {
               description "Next-hop gateway information";
               leaf nh-string {
                 type string;
               }
               leaf elnh-address {
                 type int32;
                 description "Address of Element Next-hop";
               }
               leaf to {
                 type string;
                 description "Neighbor address to which to send (next-hop address)";
               }
               leaf via {
                 type string;
                 description "Reachable via a local interface";
               }
               leaf localized-table {
                 type string;
                 description "Name of localized table";
               }
               leaf weight {
                 type int32;
                 description "Next-hop weight";
               }
               leaf balance {
                 type int32;
                 description "Next-hop balance";
               }
               leaf uflags {
                 type int32;
                 description "Next-hop uflags";
               }
               leaf filter {
                 type string;
                 description "Next-hop firewall filter";
               }
               leaf selected-next-hop {
                 type empty;
                 description "Present if this next hop is selected";
               }
               leaf session {
                 type int32;
                 description "Session ID Associated with this NH";
               }
               leaf statistics-id-group-terse {
                 type string;
                 description "Statistics ID Group Associated with this NH";
               }
               leaf ext-int-type {
                 type string;
                 description "Next-hop type of equal-external-internal multipath";
               }
               leaf fc {
                 type int32;
                 description "Forwarding-class";
               }
               leaf lsp-name {
                 type string;
                 description "Tunneled into an RSVP LSP";
               }
               leaf mpls-label {
                 type string;
                 description "Label of MPLS packet";
               }
               leaf label-ttl-action {
                 type string;
                 description "TTL action associated with labels";
               }
               leaf load-balance-label {
                 type string;
                 description "Load balance action associated with labels";
               }
               leaf label-element {
                 type string;
                 description "Pointer to the tag label element";
               }
               leaf label-element-parent {
                 type string;
                 description "Pointer to the tag label element parent";
               }
               leaf label-element-refcount {
                 type string;
                 description "Number of references to the tag label element";
               }
               leaf label-element-childcount {
                 type string;
                 description "Number of child references to the tag label element";
               }
               leaf label-element-lspid {
                 type string;
                 description "LSP ID of the tag label element";
               }
               leaf nh-table-receive {
                 type string;
                 description "Destination is a local address";
               }
               leaf nh-table {
                 type string;
                 description "Indirect pointing to another table";
               }
               leaf nh-localized-ifl {
                 type string;
                 description "Indirect pointing to a localized ifl";
               }
               leaf nh-local-interface {
                 type string;
                 description "Destination is a local interface";
               }
               leaf nh-service {
                 type string;
                 description "Next-hop service";
               }
               leaf nh-service-pkt-dist {
                 type string;
                 description "Multi services packet distribution type";
               }
               leaf nh-service-app-data {
                 type string;
                 description "Multi services application specific data";
               }
               leaf nh-private-comp {
                 type string;
                 description "Private Composite Next-hop";
               }
               leaf nh-index {
                 type uint32;
                 description "Next-hop index";
               }
               leaf nh-address {
                 type int32;
                 description "Address of next hop";
               }
               leaf tunnel-composite-attr-type {
                 type string;
                 description "Tunnel-Type for tunnel-composite-nexthop";
               }
               leaf tunnel-composite-attr-reference-count {
                 type int32;
                 description "Tunnel-reference-count for tunnel-composite-nexthop";
               }
               leaf tunnel-composite-attr-nh-id {
                 type int32;
                 description "Tunnel-NextHop-Id for tunnel-composite-nexthop";
               }
               leaf tunnel-composite-attr-dest {
                 type ipaddr;
                 description "Tunnel-Destination for tunnel-composite-nexthop";
               }
               leaf tunnel-composite-attr-src {
                 type ipaddr;
                 description "Tunnel-Source for tunnel-composite-nexthop";
               }
               leaf tunnel-composite-attr-tid {
                 type int32;
                 description "Tunnel-Id for tunnel-composite-nexthop";
               }
               leaf tunnel-composite-attr-label {
                 type string;
                 description "Tunnel-VPN-Label for tunnel-composite-nexthop";
               }
               leaf tunnel-composite-attr-label-ttl {
                 type string;
                 description "Tunnel-VPN-Label-TTL for tunnel-composite-nexthop";
               }
               leaf tunnel-composite-attr-segment-addr {
                 type ipaddr;
                 description "IPv6 segment-address";
               }
               leaf tunnel-composite-attr-vni {
                 type int32;
                 description "Tunnel-VNI for tunnel-composite-nexthop in VxLAN";
               }
               leaf tunnel-composite-attr-dest-mac {
                 type string;
                 description "Tunnel-Dest-Mac for tunnel-composite-nexthop in VxLAN";
               }
             }
           }
         }
       }
       list brief-mpls-fwd {
         leaf rt-destination {
           type string;
         }
         leaf rt-prefix-length {
           type int32;
         }
         list rt-entry {
           leaf active-tag {
             type string;
             description "Visual indication of active state of this route entry";
           }
           leaf protocol-name {
             type string;
           }
           leaf preference {
             type int32;
             description "Preference for the route";
           }
           leaf preference2 {
             type int32;
           }
           leaf age {
             type string;
           }
           leaf metric {
             type int32;
           }
           leaf med {
             type int32;
             description "Multiple exit discriminator";
           }
           leaf local-preference {
             type int32;
           }
           leaf metric2 {
             type int32;
           }
           leaf rt-tag {
             type int32;
           }
           leaf rt-tag2 {
             type int32;
           }
           leaf learned-from {
             type ipaddr;
             description "Peer address from which this route was learned";
           }
           leaf peer-as {
             type int32;
             description "Peer AS number";
           }
           leaf evpn-remote-mes {
             type ipaddr;
             description "Remote PE";
           }
           leaf evpn-routing-instance-name {
             type string;
             description "Routing Instance";
           }
           leaf evpn-tag-rt-type {
             type string;
             description "Route Type";
           }
           leaf evpn-vlan-id {
             type int32;
             description "VLAN-ID";
           }
           leaf rt-evpn-esi {
             type string;
             description "ESI";
           }
           leaf evpn-isid {
             type int32;
             description "ISID";
           }
           leaf rt-evpn-bmac {
             type string;
             description "BMAC";
           }
           leaf as-path {
             type string;
           }
           leaf validation-state {
             type string;
           }
           leaf nh-type {
             type string;
             description "Special next hop: Reject, Blackhole, Receive, Multicast, Local, or Unused";
           }
           list route-data-dcf {
             list snpa {
               list pfe-port-snpa {
                 description "PFE Port SNPA";
                 leaf pfe-id {
                   type int32;
                 }
                 leaf port-id {
                   type int32;
                 }
               }
               list network-element-port-snpa {
                 description "Network Element Port SNPA";
                 leaf port-id {
                   type int32;
                 }
               }
               list mstp-root-snpa {
                 description "Multiple Spanning Tree Protocol Root SNPA";
                 leaf mstp-root-id {
                   type int32;
                 }
               }
               list gateway-snpa {
                 description "Gateway SNPA";
                 leaf gateway-addr {
                   type ipaddr;
                 }
               }
               list layer2-domain-port-snpa {
                 description "Layer-2 Domain Port SNPA";
                 leaf port-id {
                   type int32;
                 }
               }
               list replication-block-snpa {
                 description "Replication Block SNPA";
                 leaf replication-block-id {
                   type int32;
                 }
               }
               list replication-route-snpa {
                 description "Replication Route SNPA";
                 leaf network-element-id {
                   type ipaddr;
                 }
               }
               list layer2-multicast-port-snpa {
                 description "Layer-2 Multicast Port SNPA";
                 leaf layer2-multicast-port-id {
                   type int32;
                 }
               }
               list inh-snpa {
                 description "Indirection SNPA";
                 leaf inh-id {
                   type int32;
                 }
               }
             }
           }
           container rtd-flow-dep {
           }
           container communities {
             leaf community {
               type string;
               description "Basic community";
             }
             leaf extended-community {
               type string;
               description "Extended community";
             }
           }
           container attrset {
           }
           container link-state-information {
             container link-state-link {
               leaf color {
                 type int32;
               }
               leaf metric {
                 type int32;
               }
               leaf te-metric {
                 type int32;
                 description "LSP TE metric";
               }
               leaf ldp-support {
                 type string;
               }
               leaf rsvpte-support {
                 type string;
               }
               leaf maximum-bw {
                 type uint64;
               }
               leaf reservable-bw {
                 type uint64;
               }
               container protections {
                 leaf protection-type {
                   type string;
                   description "LSP protection desired";
                 }
               }
               container link-srlgs {
                 leaf link-srlg {
                   type string;
                 }
               }
               container unreserved-bws {
                 list unreserved-bw {
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf node-area {
                   type string;
                 }
               }
               container node-ipv4-router-ids {
                 leaf node-ipv4-router-id {
                   type ipaddr;
                 }
               }
               container node-topologies {
                 list node-topology {
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   leaf node-spring-srgb-block-start {
                     type uint32;
                   }
                   leaf node-spring-srgb-block-range {
                     type uint32;
                   }
                   leaf node-spring-srgb-block-flags {
                     type string;
                   }
                 }
               }
               container node-spring-algorithms {
                 list node-spring-algorithm {
                   leaf node-spring-algorithm-type {
                     type uint32;
                   }
                 }
               }
             }
             container link-state-prefix {
               container link-state-prefix-sid {
                 leaf link-state-prefix-sid-index {
                   type uint32;
                 }
                 leaf link-state-prefix-sid-flags {
                   type string;
                 }
                 leaf link-state-prefix-sid-algo {
                   type string;
                 }
               }
             }
             container link-state-unknown-tlvs {
               list link-state-unknown-tlv {
                 leaf unknown-type {
                   type uint32;
                 }
                 leaf unknown-length {
                   type uint32;
                 }
                 leaf unknown-bytes {
                   type string;
                 }
               }
             }
           }
           container aggregate {
           }
           list nh {
             description "Next-hop gateway information";
           }
           container protocol-nh {
             description "Protocol next hop";
             list nh {
               description "Next-hop gateway information";
               leaf nh-string {
                 type string;
               }
               leaf elnh-address {
                 type int32;
                 description "Address of Element Next-hop";
               }
               leaf to {
                 type string;
                 description "Neighbor address to which to send (next-hop address)";
               }
               leaf via {
                 type string;
                 description "Reachable via a local interface";
               }
               leaf localized-table {
                 type string;
                 description "Name of localized table";
               }
               leaf weight {
                 type int32;
                 description "Next-hop weight";
               }
               leaf balance {
                 type int32;
                 description "Next-hop balance";
               }
               leaf uflags {
                 type int32;
                 description "Next-hop uflags";
               }
               leaf filter {
                 type string;
                 description "Next-hop firewall filter";
               }
               leaf selected-next-hop {
                 type empty;
                 description "Present if this next hop is selected";
               }
               leaf session {
                 type int32;
                 description "Session ID Associated with this NH";
               }
               leaf statistics-id-group-terse {
                 type string;
                 description "Statistics ID Group Associated with this NH";
               }
               leaf ext-int-type {
                 type string;
                 description "Next-hop type of equal-external-internal multipath";
               }
               leaf fc {
                 type int32;
                 description "Forwarding-class";
               }
               leaf lsp-name {
                 type string;
                 description "Tunneled into an RSVP LSP";
               }
               leaf mpls-label {
                 type string;
                 description "Label of MPLS packet";
               }
               leaf label-ttl-action {
                 type string;
                 description "TTL action associated with labels";
               }
               leaf load-balance-label {
                 type string;
                 description "Load balance action associated with labels";
               }
               leaf label-element {
                 type string;
                 description "Pointer to the tag label element";
               }
               leaf label-element-parent {
                 type string;
                 description "Pointer to the tag label element parent";
               }
               leaf label-element-refcount {
                 type string;
                 description "Number of references to the tag label element";
               }
               leaf label-element-childcount {
                 type string;
                 description "Number of child references to the tag label element";
               }
               leaf label-element-lspid {
                 type string;
                 description "LSP ID of the tag label element";
               }
               leaf nh-table-receive {
                 type string;
                 description "Destination is a local address";
               }
               leaf nh-table {
                 type string;
                 description "Indirect pointing to another table";
               }
               leaf nh-localized-ifl {
                 type string;
                 description "Indirect pointing to a localized ifl";
               }
               leaf nh-local-interface {
                 type string;
                 description "Destination is a local interface";
               }
               leaf nh-service {
                 type string;
                 description "Next-hop service";
               }
               leaf nh-service-pkt-dist {
                 type string;
                 description "Multi services packet distribution type";
               }
               leaf nh-service-app-data {
                 type string;
                 description "Multi services application specific data";
               }
               leaf nh-private-comp {
                 type string;
                 description "Private Composite Next-hop";
               }
               leaf nh-index {
                 type uint32;
                 description "Next-hop index";
               }
               leaf nh-address {
                 type int32;
                 description "Address of next hop";
               }
               leaf tunnel-composite-attr-type {
                 type string;
                 description "Tunnel-Type for tunnel-composite-nexthop";
               }
               leaf tunnel-composite-attr-reference-count {
                 type int32;
                 description "Tunnel-reference-count for tunnel-composite-nexthop";
               }
               leaf tunnel-composite-attr-nh-id {
                 type int32;
                 description "Tunnel-NextHop-Id for tunnel-composite-nexthop";
               }
               leaf tunnel-composite-attr-dest {
                 type ipaddr;
                 description "Tunnel-Destination for tunnel-composite-nexthop";
               }
               leaf tunnel-composite-attr-src {
                 type ipaddr;
                 description "Tunnel-Source for tunnel-composite-nexthop";
               }
               leaf tunnel-composite-attr-tid {
                 type int32;
                 description "Tunnel-Id for tunnel-composite-nexthop";
               }
               leaf tunnel-composite-attr-label {
                 type string;
                 description "Tunnel-VPN-Label for tunnel-composite-nexthop";
               }
               leaf tunnel-composite-attr-label-ttl {
                 type string;
                 description "Tunnel-VPN-Label-TTL for tunnel-composite-nexthop";
               }
               leaf tunnel-composite-attr-segment-addr {
                 type ipaddr;
                 description "IPv6 segment-address";
               }
               leaf tunnel-composite-attr-vni {
                 type int32;
                 description "Tunnel-VNI for tunnel-composite-nexthop in VxLAN";
               }
               leaf tunnel-composite-attr-dest-mac {
                 type string;
                 description "Tunnel-Dest-Mac for tunnel-composite-nexthop in VxLAN";
               }
             }
           }
         }
       }
       list bgp-brief {
         leaf rt-destination {
           type string;
         }
         leaf rt-prefix-length {
           type int32;
         }
         list rt-entry {
           leaf active-tag {
             type string;
             description "Visual indication of active state of this route entry";
           }
           leaf med {
             type int32;
             description "Multiple exit discriminator";
           }
           leaf local-preference {
             type int32;
           }
           leaf as-path {
             type string;
           }
           list route-data-dcf {
             list snpa {
               list pfe-port-snpa {
                 description "PFE Port SNPA";
                 leaf pfe-id {
                   type int32;
                 }
                 leaf port-id {
                   type int32;
                 }
               }
               list network-element-port-snpa {
                 description "Network Element Port SNPA";
                 leaf port-id {
                   type int32;
                 }
               }
               list mstp-root-snpa {
                 description "Multiple Spanning Tree Protocol Root SNPA";
                 leaf mstp-root-id {
                   type int32;
                 }
               }
               list gateway-snpa {
                 description "Gateway SNPA";
                 leaf gateway-addr {
                   type ipaddr;
                 }
               }
               list layer2-domain-port-snpa {
                 description "Layer-2 Domain Port SNPA";
                 leaf port-id {
                   type int32;
                 }
               }
               list replication-block-snpa {
                 description "Replication Block SNPA";
                 leaf replication-block-id {
                   type int32;
                 }
               }
               list replication-route-snpa {
                 description "Replication Route SNPA";
                 leaf network-element-id {
                   type ipaddr;
                 }
               }
               list layer2-multicast-port-snpa {
                 description "Layer-2 Multicast Port SNPA";
                 leaf layer2-multicast-port-id {
                   type int32;
                 }
               }
               list inh-snpa {
                 description "Indirection SNPA";
                 leaf inh-id {
                   type int32;
                 }
               }
             }
           }
           container rtd-flow-dep {
           }
           container communities {
             leaf community {
               type string;
               description "Basic community";
             }
             leaf extended-community {
               type string;
               description "Extended community";
             }
           }
           container attrset {
           }
           container link-state-information {
             container link-state-link {
               leaf color {
                 type int32;
               }
               leaf metric {
                 type int32;
               }
               leaf te-metric {
                 type int32;
                 description "LSP TE metric";
               }
               leaf ldp-support {
                 type string;
               }
               leaf rsvpte-support {
                 type string;
               }
               leaf maximum-bw {
                 type uint64;
               }
               leaf reservable-bw {
                 type uint64;
               }
               container protections {
                 leaf protection-type {
                   type string;
                   description "LSP protection desired";
                 }
               }
               container link-srlgs {
                 leaf link-srlg {
                   type string;
                 }
               }
               container unreserved-bws {
                 list unreserved-bw {
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf node-area {
                   type string;
                 }
               }
               container node-ipv4-router-ids {
                 leaf node-ipv4-router-id {
                   type ipaddr;
                 }
               }
               container node-topologies {
                 list node-topology {
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   leaf node-spring-srgb-block-start {
                     type uint32;
                   }
                   leaf node-spring-srgb-block-range {
                     type uint32;
                   }
                   leaf node-spring-srgb-block-flags {
                     type string;
                   }
                 }
               }
               container node-spring-algorithms {
                 list node-spring-algorithm {
                   leaf node-spring-algorithm-type {
                     type uint32;
                   }
                 }
               }
             }
             container link-state-prefix {
               container link-state-prefix-sid {
                 leaf link-state-prefix-sid-index {
                   type uint32;
                 }
                 leaf link-state-prefix-sid-flags {
                   type string;
                 }
                 leaf link-state-prefix-sid-algo {
                   type string;
                 }
               }
             }
             container link-state-unknown-tlvs {
               list link-state-unknown-tlv {
                 leaf unknown-type {
                   type uint32;
                 }
                 leaf unknown-length {
                   type uint32;
                 }
                 leaf unknown-bytes {
                   type string;
                 }
               }
             }
           }
           container aggregate {
           }
           list nh {
             description "Next-hop gateway information";
           }
           container protocol-nh {
             description "Protocol next hop";
             list nh {
               description "Next-hop gateway information";
               leaf nh-string {
                 type string;
               }
               leaf elnh-address {
                 type int32;
                 description "Address of Element Next-hop";
               }
               leaf to {
                 type string;
                 description "Neighbor address to which to send (next-hop address)";
               }
               leaf via {
                 type string;
                 description "Reachable via a local interface";
               }
               leaf localized-table {
                 type string;
                 description "Name of localized table";
               }
               leaf weight {
                 type int32;
                 description "Next-hop weight";
               }
               leaf balance {
                 type int32;
                 description "Next-hop balance";
               }
               leaf uflags {
                 type int32;
                 description "Next-hop uflags";
               }
               leaf filter {
                 type string;
                 description "Next-hop firewall filter";
               }
               leaf selected-next-hop {
                 type empty;
                 description "Present if this next hop is selected";
               }
               leaf session {
                 type int32;
                 description "Session ID Associated with this NH";
               }
               leaf statistics-id-group-terse {
                 type string;
                 description "Statistics ID Group Associated with this NH";
               }
               leaf ext-int-type {
                 type string;
                 description "Next-hop type of equal-external-internal multipath";
               }
               leaf fc {
                 type int32;
                 description "Forwarding-class";
               }
               leaf lsp-name {
                 type string;
                 description "Tunneled into an RSVP LSP";
               }
               leaf mpls-label {
                 type string;
                 description "Label of MPLS packet";
               }
               leaf label-ttl-action {
                 type string;
                 description "TTL action associated with labels";
               }
               leaf load-balance-label {
                 type string;
                 description "Load balance action associated with labels";
               }
               leaf label-element {
                 type string;
                 description "Pointer to the tag label element";
               }
               leaf label-element-parent {
                 type string;
                 description "Pointer to the tag label element parent";
               }
               leaf label-element-refcount {
                 type string;
                 description "Number of references to the tag label element";
               }
               leaf label-element-childcount {
                 type string;
                 description "Number of child references to the tag label element";
               }
               leaf label-element-lspid {
                 type string;
                 description "LSP ID of the tag label element";
               }
               leaf nh-table-receive {
                 type string;
                 description "Destination is a local address";
               }
               leaf nh-table {
                 type string;
                 description "Indirect pointing to another table";
               }
               leaf nh-localized-ifl {
                 type string;
                 description "Indirect pointing to a localized ifl";
               }
               leaf nh-local-interface {
                 type string;
                 description "Destination is a local interface";
               }
               leaf nh-service {
                 type string;
                 description "Next-hop service";
               }
               leaf nh-service-pkt-dist {
                 type string;
                 description "Multi services packet distribution type";
               }
               leaf nh-service-app-data {
                 type string;
                 description "Multi services application specific data";
               }
               leaf nh-private-comp {
                 type string;
                 description "Private Composite Next-hop";
               }
               leaf nh-index {
                 type uint32;
                 description "Next-hop index";
               }
               leaf nh-address {
                 type int32;
                 description "Address of next hop";
               }
               leaf tunnel-composite-attr-type {
                 type string;
                 description "Tunnel-Type for tunnel-composite-nexthop";
               }
               leaf tunnel-composite-attr-reference-count {
                 type int32;
                 description "Tunnel-reference-count for tunnel-composite-nexthop";
               }
               leaf tunnel-composite-attr-nh-id {
                 type int32;
                 description "Tunnel-NextHop-Id for tunnel-composite-nexthop";
               }
               leaf tunnel-composite-attr-dest {
                 type ipaddr;
                 description "Tunnel-Destination for tunnel-composite-nexthop";
               }
               leaf tunnel-composite-attr-src {
                 type ipaddr;
                 description "Tunnel-Source for tunnel-composite-nexthop";
               }
               leaf tunnel-composite-attr-tid {
                 type int32;
                 description "Tunnel-Id for tunnel-composite-nexthop";
               }
               leaf tunnel-composite-attr-label {
                 type string;
                 description "Tunnel-VPN-Label for tunnel-composite-nexthop";
               }
               leaf tunnel-composite-attr-label-ttl {
                 type string;
                 description "Tunnel-VPN-Label-TTL for tunnel-composite-nexthop";
               }
               leaf tunnel-composite-attr-segment-addr {
                 type ipaddr;
                 description "IPv6 segment-address";
               }
               leaf tunnel-composite-attr-vni {
                 type int32;
                 description "Tunnel-VNI for tunnel-composite-nexthop in VxLAN";
               }
               leaf tunnel-composite-attr-dest-mac {
                 type string;
                 description "Tunnel-Dest-Mac for tunnel-composite-nexthop in VxLAN";
               }
             }
           }
         }
       }
       list detail {
         leaf rt-destination {
           type string;
         }
         leaf rt-prefix-length {
           type int32;
         }
         leaf rt-entry-count {
           type int32;
           description "Number of route entries in this route";
         }
         leaf rt-announced-count {
           type int32;
           description "Number of announced route entries";
         }
         leaf rt-state {
           type string;
           description "State of this route";
         }
         leaf tsi {
           type string;
           description "Task-specific information";
         }
         list rt-entry {
           leaf nh-type {
             type string;
             description "Special next hop: Reject, Blackhole, Receive, Multicast, Local, or Unused";
           }
           leaf nh-index {
             type uint32;
             description "Next-hop index";
           }
           leaf nh-address {
             type int32;
             description "Address of next hop";
           }
           leaf nh-reference-count {
             type int32;
             description "Number of references to this next hop";
           }
           leaf ext-int-intf-index {
             type int32;
             description "Interface index of equal-external-internal multipath";
           }
           leaf nh-flood-overflow {
             type empty;
             description "Flood nexthop exceeds maximum branches";
           }
           leaf client-data {
             type string;
             description "Route server client details";
           }
           leaf route-distinguisher {
             type string;
           }
           leaf validation-state {
             type string;
           }
           leaf pmsi {
             type string;
             description "P-multicast service interface";
           }
           leaf connector {
             type string;
           }
           leaf color {
             type int32;
           }
           leaf color2 {
             type int32;
           }
           leaf prefix-segment-index {
             type int32;
           }
           leaf rt-isis-level {
             type int32;
           }
           leaf rt-isis-downbit {
             type int32;
           }
           leaf rt-entry-state {
             type string;
             description "State of this route entry";
           }
           leaf rt-entry-pim-state {
             type string;
             description "PIM state of this route entry";
           }
           leaf inactive-reason {
             type string;
             description "HFRR profile Inactive reason (if any)";
           }
           leaf local-as {
             type int32;
             description "Local AS number";
           }
           leaf peer-as {
             type int32;
             description "Peer AS number";
           }
           leaf learned-from {
             type ipaddr;
             description "Peer address from which this route was learned";
           }
           leaf age {
             type string;
           }
           leaf metric {
             type int32;
           }
           leaf metric2 {
             type int32;
           }
           leaf med-plus-igp {
             type int32;
           }
           leaf rt-tag {
             type int32;
           }
           leaf rt-tag2 {
             type int32;
           }
           leaf rt-aigp {
             type uint64;
           }
           leaf rt-resolving-aigp {
             type uint64;
           }
           leaf rt-orr {
             type uint32;
           }
           leaf rt-ospf-area {
             type string;
           }
           leaf task-name {
             type string;
             description "Name of this task";
           }
           leaf announce-bits {
             type int32;
           }
           leaf announce-tasks {
             type string;
           }
           leaf as-path {
             type string;
           }
           leaf bgp-rt-flag {
             type string;
             description "BGP route flag";
           }
           leaf bgp-rtarget-type {
             type string;
             description "BGP RT-Constrain route type";
           }
           leaf bgp-rtarget-generation {
             type uint32;
             description "BGP RT-Constrain generation";
           }
           leaf bgp-rtarget-for {
             type string;
             description "BGP RT-Constrain member";
           }
           leaf label-base {
             type int32;
             description "Label base for l2vpn";
           }
           leaf label-range {
             type int32;
             description "Label range for l2vpn";
           }
           leaf l2vpn-status-vector {
             type string;
           }
           leaf label-offset {
             type int32;
             description "Label offset for l2vpn";
           }
           leaf remote-site {
             type int32;
             description "Remote site id";
           }
           leaf l2vpn-mesh-group {
             type string;
           }
           leaf vc-label {
             type int32;
             description "VC label";
           }
           leaf context-id {
             type ipaddr;
             description "Context Identifier";
           }
           leaf route-control-word {
             type string;
             description "Control Word";
           }
           leaf mtu {
             type int32;
             description "MTU along an interface";
           }
           leaf cell-bundle-size {
             type int32;
             description "Cell bundle size";
           }
           leaf vlan-id {
             type int32;
           }
           leaf flow-label-transmit {
             type int32;
           }
           leaf flow-label-receive {
             type int32;
           }
           leaf tdm-payload-size {
             type int32;
           }
           leaf tdm-bitrate {
             type int32;
           }
           leaf pw-status-code {
             type int32;
           }
           leaf cac-bandwidth-failure {
             type empty;
             description "Call admission control failure due to insufficient bandwidth";
           }
           leaf vpn-label {
             type int32;
             description "VPN label";
           }
           leaf route-label {
             type int32;
             description "Route label";
           }
           leaf route-labels {
             type string;
             description "Route label";
           }
           leaf mac-route-esi {
             type string;
             description "ESI";
           }
           leaf evpn-igmp-flags {
             type int32;
             description "IGMP flags";
           }
           leaf overlay-gateway-address {
             type ipaddr;
             description "Overlay gateway address";
           }
           leaf local-preference {
             type int32;
           }
           leaf peer-id {
             type ipaddr;
           }
           leaf path-id {
             type string;
           }
           leaf gateway {
             type string;
             description "Sourcing gateway";
           }
           leaf rtrib-primary {
             type string;
             description "Primary routing table";
           }
           leaf rtrib-secondary {
             type string;
             description "Secondary routing table";
           }
           leaf indirect-nh-count {
             type int32;
             description "Number of indirect next hops";
           }
           leaf composite-nh-count {
             type int32;
             description "Number of composite next hops";
           }
           leaf helper-nhid {
             type uint32;
             description "Helper nexthop index";
           }
           leaf helper-refcount {
             type int32;
             description "Reference count of those needing helper route";
           }
           leaf backup-pe-group-name {
             type string;
             description "Name of the backup PE group";
           }
           leaf designated-forwarder {
             type string;
             description "Indicates if we are the designated forwarder for this route";
           }
           leaf rt-entry-opaque-data {
             type string;
             description "Opaque data associated with the route entry";
           }
           leaf rt-stats-id-grp-single-line {
             type string;
             description "Stats-id-group associated with the route entry";
           }
           leaf hidden-reason {
             type string;
             description "Protocol's reason for hiding the route";
           }
           leaf bgp-bmp-send-flag-start {
             type string;
           }
           leaf bgp-bmp-send-flag-pre {
             type string;
           }
           leaf bgp-bmp-send-flag-post {
             type string;
           }
           leaf bgp-bmp-send-flag-station {
             type string;
           }
           leaf evpn-routing-instance-name {
             type string;
             description "Routing Instance";
           }
           leaf evpn-tag-rt-type {
             type string;
             description "Route Type";
           }
           leaf evpn-vlan-id {
             type int32;
             description "VLAN-ID";
           }
           leaf evpn-isid {
             type int32;
             description "ISID";
           }
           leaf rt-evpn-esi {
             type string;
             description "ESI";
           }
           leaf rt-evpn-bmac {
             type string;
             description "BMAC";
           }
           leaf active-tag {
             type string;
             description "Visual indication of active state of this route entry";
           }
           leaf protocol-name {
             type string;
           }
           leaf preference {
             type int32;
             description "Preference for the route";
           }
           leaf preference2 {
             type int32;
           }
           list route-data-dcf {
             leaf snpa-count {
               type int32;
               description "Number of SNPAs in this route";
             }
             leaf snpa-length {
               type int32;
               description "Total length of the SNPAs, in bytes";
             }
             list snpa {
               list pfe-port-snpa {
                 description "PFE Port SNPA";
                 leaf pfe-id {
                   type int32;
                 }
                 leaf port-id {
                   type int32;
                 }
               }
               list network-element-port-snpa {
                 description "Network Element Port SNPA";
                 leaf port-id {
                   type int32;
                 }
               }
               list mstp-root-snpa {
                 description "Multiple Spanning Tree Protocol Root SNPA";
                 leaf mstp-root-id {
                   type int32;
                 }
               }
               list gateway-snpa {
                 description "Gateway SNPA";
                 leaf gateway-addr {
                   type ipaddr;
                 }
               }
               list layer2-domain-port-snpa {
                 description "Layer-2 Domain Port SNPA";
                 leaf port-id {
                   type int32;
                 }
               }
               list replication-block-snpa {
                 description "Replication Block SNPA";
                 leaf replication-block-id {
                   type int32;
                 }
               }
               list replication-route-snpa {
                 description "Replication Route SNPA";
                 leaf network-element-id {
                   type ipaddr;
                 }
               }
               list layer2-multicast-port-snpa {
                 description "Layer-2 Multicast Port SNPA";
                 leaf layer2-multicast-port-id {
                   type int32;
                 }
               }
               list inh-snpa {
                 description "Indirection SNPA";
                 leaf inh-id {
                   type int32;
                 }
               }
             }
             container multicast-member-map-data {
               description "Multicast member map";
               leaf multicast-root-hash {
                 type int32;
               }
               leaf multicast-core-hash {
                 type int32;
               }
               leaf multicast-edge-hash {
                 type int32;
               }
               leaf multicast-member-map {
                 type string;
               }
             }
             container layer3-multicast-data {
               description "Layer3 multicast core key";
               leaf layer3-multicast-corekey {
                 type int32;
               }
             }
             container multicast-vsg-corekey-data {
               description "Vsg multicast core key";
               leaf multicast-vsg-corekey-key {
                 type int32;
               }
               leaf multicast-vsg-corekey-len {
                 type int32;
               }
             }
           }
           container connection-bandwidth {
             description "Bandwidth of a layer 2 connection";
             leaf connection-bandwidth.heading {
               type string;
               description "Bandwidth of a layer 2 connection";
             }
             leaf bandwidth {
               type int32;
             }
             leaf class-type {
               type int32;
             }
             leaf class-bandwidth {
               type int32;
             }
           }
           container rtd-flow-dep {
             leaf flow-dep-state {
               type string;
             }
             leaf flow-origin {
               type ipaddr;
               description "Originator of the flow information";
             }
             leaf flow-next-as {
               type uint32;
               description "Neighbor AS of the flow information";
             }
             container flow-ucast-rt {
               description "Unicast route used for resolution";
             }
           }
           container communities {
             leaf community {
               type string;
               description "Basic community";
             }
             leaf extended-community {
               type string;
               description "Extended community";
             }
           }
           container attrset {
           }
           container route-flap-damping {
             leaf last-merit {
               type int32;
               description "Last merit value";
             }
             leaf merit {
               type int32;
               description "Current merit value";
             }
             leaf damping-parameters {
               type string;
             }
             leaf default-damping-parameters {
               type empty;
               description "Default damping parameters used";
             }
             leaf last-update {
               type string;
             }
             leaf first-update {
               type string;
             }
             leaf route-flap-count {
               type int32;
               description "Number of times this route has flapped";
             }
             leaf suppressed {
               type empty;
               description "This route is suppressed";
             }
             leaf reuse-time {
               type string;
               description "Time until this route is reusable";
             }
             leaf reuse-preference {
               type int32;
               description "Preference to use when this route is reused";
             }
             leaf expire-time {
               type string;
               description "Time when this damping entry expires";
             }
           }
           container link-state-information {
             container link-state-link {
               leaf color {
                 type int32;
               }
               leaf metric {
                 type int32;
               }
               leaf te-metric {
                 type int32;
                 description "LSP TE metric";
               }
               leaf ldp-support {
                 type string;
               }
               leaf rsvpte-support {
                 type string;
               }
               leaf maximum-bw {
                 type uint64;
               }
               leaf reservable-bw {
                 type uint64;
               }
               container protections {
                 leaf protection-type {
                   type string;
                   description "LSP protection desired";
                 }
               }
               container link-srlgs {
                 leaf link-srlg {
                   type string;
                 }
               }
               container unreserved-bws {
                 list unreserved-bw {
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf node-area {
                   type string;
                 }
               }
               container node-ipv4-router-ids {
                 leaf node-ipv4-router-id {
                   type ipaddr;
                 }
               }
               container node-topologies {
                 list node-topology {
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   leaf node-spring-srgb-block-start {
                     type uint32;
                   }
                   leaf node-spring-srgb-block-range {
                     type uint32;
                   }
                   leaf node-spring-srgb-block-flags {
                     type string;
                   }
                 }
               }
               container node-spring-algorithms {
                 list node-spring-algorithm {
                   leaf node-spring-algorithm-type {
                     type uint32;
                   }
                 }
               }
             }
             container link-state-prefix {
               container link-state-prefix-sid {
                 leaf link-state-prefix-sid-index {
                   type uint32;
                 }
                 leaf link-state-prefix-sid-flags {
                   type string;
                 }
                 leaf link-state-prefix-sid-algo {
                   type string;
                 }
               }
             }
             container link-state-unknown-tlvs {
               list link-state-unknown-tlv {
                 leaf unknown-type {
                   type uint32;
                 }
                 leaf unknown-length {
                   type uint32;
                 }
                 leaf unknown-bytes {
                   type string;
                 }
               }
             }
           }
           container aggregate {
             leaf aggregate-flags {
               type string;
               description "Flags on this aggregate route entry";
             }
             leaf aggregate-depth {
               type int32;
               description "Depth of this aggregate";
             }
             leaf aggregate-active {
               type empty;
               description "Present if this aggregate is active";
             }
             leaf contributing-route-count {
               type int32;
               description "Number of contributing routes in this aggregate";
             }
             container aggregate-as-path {
               leaf as-path {
                 type string;
               }
               leaf reference-count {
                 type int32;
               }
             }
             list aggregated-route {
               leaf destination-prefix {
                 type string;
                 description "Destination prefix and mask";
               }
               leaf protocol-name {
                 type string;
               }
             }
           }
           container nhh {
             leaf nh-type {
               type string;
               description "Special next hop: Reject, Blackhole, Receive, Multicast, Local, or Unused";
             }
             leaf nh-index {
               type uint32;
               description "Next-hop index";
             }
             leaf nh-address {
               type int32;
               description "Address of next hop";
             }
             leaf nh-reference-count {
               type int32;
               description "Number of references to this next hop";
             }
             leaf ext-int-intf-index {
               type int32;
               description "Interface index of equal-external-internal multipath";
             }
             leaf nh-flood-overflow {
               type empty;
               description "Flood nexthop exceeds maximum branches";
             }
           }
           list nh {
             description "Next-hop gateway information";
             leaf nh-string {
               type string;
             }
             leaf elnh-address {
               type int32;
               description "Address of Element Next-hop";
             }
             leaf to {
               type string;
               description "Neighbor address to which to send (next-hop address)";
             }
             leaf via {
               type string;
               description "Reachable via a local interface";
             }
             leaf localized-table {
               type string;
               description "Name of localized table";
             }
             leaf weight {
               type int32;
               description "Next-hop weight";
             }
             leaf balance {
               type int32;
               description "Next-hop balance";
             }
             leaf uflags {
               type int32;
               description "Next-hop uflags";
             }
             leaf filter {
               type string;
               description "Next-hop firewall filter";
             }
             leaf selected-next-hop {
               type empty;
               description "Present if this next hop is selected";
             }
             leaf session {
               type int32;
               description "Session ID Associated with this NH";
             }
             leaf statistics-id-group-terse {
               type string;
               description "Statistics ID Group Associated with this NH";
             }
             leaf ext-int-type {
               type string;
               description "Next-hop type of equal-external-internal multipath";
             }
             leaf fc {
               type int32;
               description "Forwarding-class";
             }
             leaf lsp-name {
               type string;
               description "Tunneled into an RSVP LSP";
             }
             leaf mpls-label {
               type string;
               description "Label of MPLS packet";
             }
             leaf label-ttl-action {
               type string;
               description "TTL action associated with labels";
             }
             leaf load-balance-label {
               type string;
               description "Load balance action associated with labels";
             }
             leaf label-element {
               type string;
               description "Pointer to the tag label element";
             }
             leaf label-element-parent {
               type string;
               description "Pointer to the tag label element parent";
             }
             leaf label-element-refcount {
               type string;
               description "Number of references to the tag label element";
             }
             leaf label-element-childcount {
               type string;
               description "Number of child references to the tag label element";
             }
             leaf label-element-lspid {
               type string;
               description "LSP ID of the tag label element";
             }
             leaf nh-table-receive {
               type string;
               description "Destination is a local address";
             }
             leaf nh-table {
               type string;
               description "Indirect pointing to another table";
             }
             leaf nh-localized-ifl {
               type string;
               description "Indirect pointing to a localized ifl";
             }
             leaf nh-local-interface {
               type string;
               description "Destination is a local interface";
             }
             leaf nh-service {
               type string;
               description "Next-hop service";
             }
             leaf nh-service-pkt-dist {
               type string;
               description "Multi services packet distribution type";
             }
             leaf nh-service-app-data {
               type string;
               description "Multi services application specific data";
             }
             leaf nh-private-comp {
               type string;
               description "Private Composite Next-hop";
             }
             leaf nh-index {
               type uint32;
               description "Next-hop index";
             }
             leaf nh-address {
               type int32;
               description "Address of next hop";
             }
             leaf tunnel-composite-attr-type {
               type string;
               description "Tunnel-Type for tunnel-composite-nexthop";
             }
             leaf tunnel-composite-attr-reference-count {
               type int32;
               description "Tunnel-reference-count for tunnel-composite-nexthop";
             }
             leaf tunnel-composite-attr-nh-id {
               type int32;
               description "Tunnel-NextHop-Id for tunnel-composite-nexthop";
             }
             leaf tunnel-composite-attr-dest {
               type ipaddr;
               description "Tunnel-Destination for tunnel-composite-nexthop";
             }
             leaf tunnel-composite-attr-src {
               type ipaddr;
               description "Tunnel-Source for tunnel-composite-nexthop";
             }
             leaf tunnel-composite-attr-tid {
               type int32;
               description "Tunnel-Id for tunnel-composite-nexthop";
             }
             leaf tunnel-composite-attr-label {
               type string;
               description "Tunnel-VPN-Label for tunnel-composite-nexthop";
             }
             leaf tunnel-composite-attr-label-ttl {
               type string;
               description "Tunnel-VPN-Label-TTL for tunnel-composite-nexthop";
             }
             leaf tunnel-composite-attr-segment-addr {
               type ipaddr;
               description "IPv6 segment-address";
             }
             leaf tunnel-composite-attr-vni {
               type int32;
               description "Tunnel-VNI for tunnel-composite-nexthop in VxLAN";
             }
             leaf tunnel-composite-attr-dest-mac {
               type string;
               description "Tunnel-Dest-Mac for tunnel-composite-nexthop in VxLAN";
             }
           }
           container protocol-nh {
             description "Protocol next hop";
             leaf to {
               type string;
               description "Neighbor address to which to send (next-hop address)";
             }
             leaf metric {
               type int32;
             }
             leaf aigp {
               type string;
               description "AIGP";
             }
             leaf balance {
               type int32;
               description "Next-hop balance";
             }
             leaf flags {
               type string;
               description "Enabled trace flags";
             }
             leaf res-path-inode-flags {
               type string;
             }
             leaf res-path-flags {
               type string;
             }
             leaf res-path-fnh-link {
               type string;
             }
             leaf res-path-inh-link {
               type string;
             }
             leaf mpls-label {
               type string;
               description "Label of MPLS packet";
             }
             leaf label-ttl-action {
               type string;
               description "TTL action associated with labels";
             }
             leaf load-balance-label {
               type string;
               description "Load balance action associated with labels";
             }
             leaf composite-nh {
               type string;
             }
             leaf vpnlabel-nh {
               type string;
             }
             leaf indirect-nh {
               type string;
             }
             leaf ext-int-type {
               type string;
               description "Next-hop type of equal-external-internal multipath";
             }
             leaf forwarding-nh-count {
               type int32;
               description "Number of indirect path forwarding next hops";
             }
             leaf nh-type {
               type string;
               description "Special next hop: Reject, Blackhole, Receive, Multicast, Local, or Unused";
             }
             container eth-header-rewrite {
               description "Ethernet header rewrite information";
               leaf eth-header-rewrite-smac {
                 type string;
                 description "Source MAC address";
               }
               leaf eth-header-rewrite-dmac {
                 type string;
                 description "Destination MAC address";
               }
               leaf eth-header-rewrite-tpid {
                 type int32;
                 description "Ethernet header TPID";
               }
               leaf eth-header-rewrite-tci {
                 type int32;
                 description "Ethernet header TCI";
               }
               leaf eth-header-rewrite-vlan-id {
                 type int32;
                 description "Ethernet header VLAN ID";
               }
               leaf eth-header-rewrite-ethertype {
                 type int32;
                 description "Ethernet header ethertype";
               }
             }
             container vxlan-header-rewrite {
               description "VXLAN tunnel rewrite information";
               leaf vxlan-header-rewrite-mtu {
                 type int32;
                 description "VXLAN tunnel MTU";
               }
               leaf vxlan-header-rewrite-flags {
                 type int32;
                 description "VXLAN tunnel flags";
               }
               leaf vxlan-header-rewrite-encap-rtb-id {
                 type int32;
                 description "VXLAN tunnel encapsulation table ID";
               }
               leaf vxlan-header-rewrite-decap-rtb-id {
                 type int32;
                 description "VXLAN tunnel decapsulation table ID";
               }
               leaf vxlan-header-rewrite-encap-vnid {
                 type int32;
                 description "VXLAN tunnel encapsulation VNI";
               }
               leaf vxlan-header-rewrite-decap-vnid {
                 type int32;
                 description "VXLAN tunnel decapsulation VNI";
               }
               leaf vxlan-header-rewrite-svtep {
                 type ipaddr;
                 description "Source VTEP address";
               }
               leaf vxlan-header-rewrite-dvtep {
                 type ipaddr;
                 description "Destination VTEP address";
               }
               leaf vxlan-header-rewrite-smac {
                 type string;
                 description "Source MAC address";
               }
               leaf vxlan-header-rewrite-dmac {
                 type string;
                 description "Destination MAC address";
               }
             }
             list nh {
               description "Next-hop gateway information";
               leaf nh-string {
                 type string;
               }
               leaf elnh-address {
                 type int32;
                 description "Address of Element Next-hop";
               }
               leaf to {
                 type string;
                 description "Neighbor address to which to send (next-hop address)";
               }
               leaf via {
                 type string;
                 description "Reachable via a local interface";
               }
               leaf localized-table {
                 type string;
                 description "Name of localized table";
               }
               leaf weight {
                 type int32;
                 description "Next-hop weight";
               }
               leaf balance {
                 type int32;
                 description "Next-hop balance";
               }
               leaf uflags {
                 type int32;
                 description "Next-hop uflags";
               }
               leaf filter {
                 type string;
                 description "Next-hop firewall filter";
               }
               leaf selected-next-hop {
                 type empty;
                 description "Present if this next hop is selected";
               }
               leaf session {
                 type int32;
                 description "Session ID Associated with this NH";
               }
               leaf statistics-id-group-terse {
                 type string;
                 description "Statistics ID Group Associated with this NH";
               }
               leaf ext-int-type {
                 type string;
                 description "Next-hop type of equal-external-internal multipath";
               }
               leaf fc {
                 type int32;
                 description "Forwarding-class";
               }
               leaf lsp-name {
                 type string;
                 description "Tunneled into an RSVP LSP";
               }
               leaf mpls-label {
                 type string;
                 description "Label of MPLS packet";
               }
               leaf label-ttl-action {
                 type string;
                 description "TTL action associated with labels";
               }
               leaf load-balance-label {
                 type string;
                 description "Load balance action associated with labels";
               }
               leaf label-element {
                 type string;
                 description "Pointer to the tag label element";
               }
               leaf label-element-parent {
                 type string;
                 description "Pointer to the tag label element parent";
               }
               leaf label-element-refcount {
                 type string;
                 description "Number of references to the tag label element";
               }
               leaf label-element-childcount {
                 type string;
                 description "Number of child references to the tag label element";
               }
               leaf label-element-lspid {
                 type string;
                 description "LSP ID of the tag label element";
               }
               leaf nh-table-receive {
                 type string;
                 description "Destination is a local address";
               }
               leaf nh-table {
                 type string;
                 description "Indirect pointing to another table";
               }
               leaf nh-localized-ifl {
                 type string;
                 description "Indirect pointing to a localized ifl";
               }
               leaf nh-local-interface {
                 type string;
                 description "Destination is a local interface";
               }
               leaf nh-service {
                 type string;
                 description "Next-hop service";
               }
               leaf nh-service-pkt-dist {
                 type string;
                 description "Multi services packet distribution type";
               }
               leaf nh-service-app-data {
                 type string;
                 description "Multi services application specific data";
               }
               leaf nh-private-comp {
                 type string;
                 description "Private Composite Next-hop";
               }
               leaf nh-index {
                 type uint32;
                 description "Next-hop index";
               }
               leaf nh-address {
                 type int32;
                 description "Address of next hop";
               }
               leaf tunnel-composite-attr-type {
                 type string;
                 description "Tunnel-Type for tunnel-composite-nexthop";
               }
               leaf tunnel-composite-attr-reference-count {
                 type int32;
                 description "Tunnel-reference-count for tunnel-composite-nexthop";
               }
               leaf tunnel-composite-attr-nh-id {
                 type int32;
                 description "Tunnel-NextHop-Id for tunnel-composite-nexthop";
               }
               leaf tunnel-composite-attr-dest {
                 type ipaddr;
                 description "Tunnel-Destination for tunnel-composite-nexthop";
               }
               leaf tunnel-composite-attr-src {
                 type ipaddr;
                 description "Tunnel-Source for tunnel-composite-nexthop";
               }
               leaf tunnel-composite-attr-tid {
                 type int32;
                 description "Tunnel-Id for tunnel-composite-nexthop";
               }
               leaf tunnel-composite-attr-label {
                 type string;
                 description "Tunnel-VPN-Label for tunnel-composite-nexthop";
               }
               leaf tunnel-composite-attr-label-ttl {
                 type string;
                 description "Tunnel-VPN-Label-TTL for tunnel-composite-nexthop";
               }
               leaf tunnel-composite-attr-segment-addr {
                 type ipaddr;
                 description "IPv6 segment-address";
               }
               leaf tunnel-composite-attr-vni {
                 type int32;
                 description "Tunnel-VNI for tunnel-composite-nexthop in VxLAN";
               }
               leaf tunnel-composite-attr-dest-mac {
                 type string;
                 description "Tunnel-Dest-Mac for tunnel-composite-nexthop in VxLAN";
               }
             }
           }
         }
       }
       list bgp-detail {
         leaf rt-destination {
           type string;
         }
         leaf rt-prefix-length {
           type int32;
         }
         leaf rt-entry-count {
           type int32;
           description "Number of route entries in this route";
         }
         leaf rt-announced-count {
           type int32;
           description "Number of announced route entries";
         }
         list rt-entry {
           leaf bgp-group-name {
             type string;
           }
           leaf bgp-rt-flag {
             type string;
             description "BGP route flag";
           }
           leaf label-base {
             type int32;
             description "Label base for l2vpn";
           }
           leaf label-range {
             type int32;
             description "Label range for l2vpn";
           }
           leaf l2vpn-status-vector {
             type string;
           }
           leaf label-offset {
             type int32;
             description "Label offset for l2vpn";
           }
           leaf l2vpn-mesh-group {
             type string;
           }
           leaf route-distinguisher {
             type string;
           }
           leaf vpn-label {
             type int32;
             description "VPN label";
           }
           leaf route-label {
             type int32;
             description "Route label";
           }
           leaf route-labels {
             type string;
             description "Route label";
           }
           leaf mac-route-esi {
             type string;
             description "ESI";
           }
           leaf evpn-igmp-flags {
             type int32;
             description "IGMP flags";
           }
           leaf overlay-gateway-address {
             type ipaddr;
             description "Overlay gateway address";
           }
           leaf bgp-no-label-reason {
             type string;
           }
           leaf bgp-metric-flags {
             type string;
             description "BGP metrics flags";
           }
           leaf med {
             type int32;
             description "Multiple exit discriminator";
           }
           leaf local-preference {
             type int32;
           }
           leaf bgp-output-queue-class {
             type string;
             description "BGP output queue class";
           }
           leaf as-path {
             type string;
           }
           leaf pmsi {
             type string;
             description "P-multicast service interface";
           }
           leaf cluster-id {
             type string;
           }
           leaf originator {
             type string;
           }
           leaf connector {
             type string;
           }
           leaf path-id {
             type string;
           }
           leaf bgp-aigp {
             type string;
             description "Accumulated IGP Metric";
           }
           leaf bgp-elc {
             type empty;
             description "Entropy label capable";
           }
           leaf bgp-elc-nh-valid {
             type string;
             description "Whether next hop field matches route next hop";
           }
           leaf hidden-reason {
             type string;
             description "Protocol's reason for hiding the route";
           }
           leaf bgp-bmp-send-flag-start {
             type string;
           }
           leaf bgp-bmp-send-flag-pre {
             type string;
           }
           leaf bgp-bmp-send-flag-post {
             type string;
           }
           leaf bgp-bmp-send-flag-station {
             type string;
           }
           leaf active-tag {
             type string;
             description "Visual indication of active state of this route entry";
           }
           list route-data-dcf {
             list snpa {
               list pfe-port-snpa {
                 description "PFE Port SNPA";
                 leaf pfe-id {
                   type int32;
                 }
                 leaf port-id {
                   type int32;
                 }
               }
               list network-element-port-snpa {
                 description "Network Element Port SNPA";
                 leaf port-id {
                   type int32;
                 }
               }
               list mstp-root-snpa {
                 description "Multiple Spanning Tree Protocol Root SNPA";
                 leaf mstp-root-id {
                   type int32;
                 }
               }
               list gateway-snpa {
                 description "Gateway SNPA";
                 leaf gateway-addr {
                   type ipaddr;
                 }
               }
               list layer2-domain-port-snpa {
                 description "Layer-2 Domain Port SNPA";
                 leaf port-id {
                   type int32;
                 }
               }
               list replication-block-snpa {
                 description "Replication Block SNPA";
                 leaf replication-block-id {
                   type int32;
                 }
               }
               list replication-route-snpa {
                 description "Replication Route SNPA";
                 leaf network-element-id {
                   type ipaddr;
                 }
               }
               list layer2-multicast-port-snpa {
                 description "Layer-2 Multicast Port SNPA";
                 leaf layer2-multicast-port-id {
                   type int32;
                 }
               }
               list inh-snpa {
                 description "Indirection SNPA";
                 leaf inh-id {
                   type int32;
                 }
               }
             }
           }
           container rtd-flow-dep {
           }
           container communities {
             leaf community {
               type string;
               description "Basic community";
             }
             leaf extended-community {
               type string;
               description "Extended community";
             }
           }
           container attrset {
             leaf attrset-as {
               type int32;
               description "Originator AS";
             }
             leaf med {
               type int32;
               description "Multiple exit discriminator";
             }
             leaf local-preference {
               type int32;
             }
             leaf as-path {
               type string;
             }
             leaf pmsi {
               type string;
               description "P-multicast service interface";
             }
             leaf cluster-id {
               type string;
             }
             leaf originator {
               type string;
             }
             leaf connector {
               type string;
             }
             container communities {
               leaf community {
                 type string;
                 description "Basic community";
               }
               leaf extended-community {
                 type string;
                 description "Extended community";
               }
             }
           }
           container link-state-information {
             container link-state-link {
               leaf color {
                 type int32;
               }
               leaf metric {
                 type int32;
               }
               leaf te-metric {
                 type int32;
                 description "LSP TE metric";
               }
               leaf ldp-support {
                 type string;
               }
               leaf rsvpte-support {
                 type string;
               }
               leaf maximum-bw {
                 type uint64;
               }
               leaf reservable-bw {
                 type uint64;
               }
               container protections {
                 leaf protection-type {
                   type string;
                   description "LSP protection desired";
                 }
               }
               container link-srlgs {
                 leaf link-srlg {
                   type string;
                 }
               }
               container unreserved-bws {
                 list unreserved-bw {
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf node-area {
                   type string;
                 }
               }
               container node-ipv4-router-ids {
                 leaf node-ipv4-router-id {
                   type ipaddr;
                 }
               }
               container node-topologies {
                 list node-topology {
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   leaf node-spring-srgb-block-start {
                     type uint32;
                   }
                   leaf node-spring-srgb-block-range {
                     type uint32;
                   }
                   leaf node-spring-srgb-block-flags {
                     type string;
                   }
                 }
               }
               container node-spring-algorithms {
                 list node-spring-algorithm {
                   leaf node-spring-algorithm-type {
                     type uint32;
                   }
                 }
               }
             }
             container link-state-prefix {
               container link-state-prefix-sid {
                 leaf link-state-prefix-sid-index {
                   type uint32;
                 }
                 leaf link-state-prefix-sid-flags {
                   type string;
                 }
                 leaf link-state-prefix-sid-algo {
                   type string;
                 }
               }
             }
             container link-state-unknown-tlvs {
               list link-state-unknown-tlv {
                 leaf unknown-type {
                   type uint32;
                 }
                 leaf unknown-length {
                   type uint32;
                 }
                 leaf unknown-bytes {
                   type string;
                 }
               }
             }
           }
           container aggregate {
           }
           list nh {
             description "Next-hop gateway information";
             leaf to {
               type string;
               description "Neighbor address to which to send (next-hop address)";
             }
           }
           container protocol-nh {
             description "Protocol next hop";
             list nh {
               description "Next-hop gateway information";
               leaf nh-string {
                 type string;
               }
               leaf elnh-address {
                 type int32;
                 description "Address of Element Next-hop";
               }
               leaf to {
                 type string;
                 description "Neighbor address to which to send (next-hop address)";
               }
               leaf via {
                 type string;
                 description "Reachable via a local interface";
               }
               leaf localized-table {
                 type string;
                 description "Name of localized table";
               }
               leaf weight {
                 type int32;
                 description "Next-hop weight";
               }
               leaf balance {
                 type int32;
                 description "Next-hop balance";
               }
               leaf uflags {
                 type int32;
                 description "Next-hop uflags";
               }
               leaf filter {
                 type string;
                 description "Next-hop firewall filter";
               }
               leaf selected-next-hop {
                 type empty;
                 description "Present if this next hop is selected";
               }
               leaf session {
                 type int32;
                 description "Session ID Associated with this NH";
               }
               leaf statistics-id-group-terse {
                 type string;
                 description "Statistics ID Group Associated with this NH";
               }
               leaf ext-int-type {
                 type string;
                 description "Next-hop type of equal-external-internal multipath";
               }
               leaf fc {
                 type int32;
                 description "Forwarding-class";
               }
               leaf lsp-name {
                 type string;
                 description "Tunneled into an RSVP LSP";
               }
               leaf mpls-label {
                 type string;
                 description "Label of MPLS packet";
               }
               leaf label-ttl-action {
                 type string;
                 description "TTL action associated with labels";
               }
               leaf load-balance-label {
                 type string;
                 description "Load balance action associated with labels";
               }
               leaf label-element {
                 type string;
                 description "Pointer to the tag label element";
               }
               leaf label-element-parent {
                 type string;
                 description "Pointer to the tag label element parent";
               }
               leaf label-element-refcount {
                 type string;
                 description "Number of references to the tag label element";
               }
               leaf label-element-childcount {
                 type string;
                 description "Number of child references to the tag label element";
               }
               leaf label-element-lspid {
                 type string;
                 description "LSP ID of the tag label element";
               }
               leaf nh-table-receive {
                 type string;
                 description "Destination is a local address";
               }
               leaf nh-table {
                 type string;
                 description "Indirect pointing to another table";
               }
               leaf nh-localized-ifl {
                 type string;
                 description "Indirect pointing to a localized ifl";
               }
               leaf nh-local-interface {
                 type string;
                 description "Destination is a local interface";
               }
               leaf nh-service {
                 type string;
                 description "Next-hop service";
               }
               leaf nh-service-pkt-dist {
                 type string;
                 description "Multi services packet distribution type";
               }
               leaf nh-service-app-data {
                 type string;
                 description "Multi services application specific data";
               }
               leaf nh-private-comp {
                 type string;
                 description "Private Composite Next-hop";
               }
               leaf nh-index {
                 type uint32;
                 description "Next-hop index";
               }
               leaf nh-address {
                 type int32;
                 description "Address of next hop";
               }
               leaf tunnel-composite-attr-type {
                 type string;
                 description "Tunnel-Type for tunnel-composite-nexthop";
               }
               leaf tunnel-composite-attr-reference-count {
                 type int32;
                 description "Tunnel-reference-count for tunnel-composite-nexthop";
               }
               leaf tunnel-composite-attr-nh-id {
                 type int32;
                 description "Tunnel-NextHop-Id for tunnel-composite-nexthop";
               }
               leaf tunnel-composite-attr-dest {
                 type ipaddr;
                 description "Tunnel-Destination for tunnel-composite-nexthop";
               }
               leaf tunnel-composite-attr-src {
                 type ipaddr;
                 description "Tunnel-Source for tunnel-composite-nexthop";
               }
               leaf tunnel-composite-attr-tid {
                 type int32;
                 description "Tunnel-Id for tunnel-composite-nexthop";
               }
               leaf tunnel-composite-attr-label {
                 type string;
                 description "Tunnel-VPN-Label for tunnel-composite-nexthop";
               }
               leaf tunnel-composite-attr-label-ttl {
                 type string;
                 description "Tunnel-VPN-Label-TTL for tunnel-composite-nexthop";
               }
               leaf tunnel-composite-attr-segment-addr {
                 type ipaddr;
                 description "IPv6 segment-address";
               }
               leaf tunnel-composite-attr-vni {
                 type int32;
                 description "Tunnel-VNI for tunnel-composite-nexthop in VxLAN";
               }
               leaf tunnel-composite-attr-dest-mac {
                 type string;
                 description "Tunnel-Dest-Mac for tunnel-composite-nexthop in VxLAN";
               }
             }
           }
         }
         container communities {
           leaf community {
             type string;
             description "Basic community";
           }
           leaf extended-community {
             type string;
             description "Extended community";
           }
         }
       }
     }
   }
   container rt-martians {
     list route-filter {
       description "Entries in martian table";
       leaf address {
         type ipaddr;
       }
       leaf flags {
         type string;
         description "Enabled trace flags";
       }
       leaf extended-information {
         type string;
       }
     }
   }
   container rt-ribgroup {
     leaf rt-ribgroup-name {
       type string;
       description "Rib-group name";
     }
     leaf rt-ribgroup-address {
       type string;
       description "Rib-group address";
     }
     leaf rt-ribgroup-address-family {
       type string;
       description "Rib-group address family";
     }
     leaf rt-ribgroup-flags {
       type string;
       description "Rib-group flags";
     }
     leaf rt-ribgroup-refcount {
       type uint32;
       description "Rib-group refcount";
     }
     leaf rt-ribgroup-export-name {
       type string;
       description "Export RIB name";
     }
     leaf rt-ribgroup-import-name {
       type string;
       description "Import RIB name";
     }
     leaf rt-ribgroup-import-policy-name {
       type string;
       description "Import policy name";
     }
     leaf rt-ribgroup-import-secondary-name {
       type string;
       description "Import secondary RIB name";
     }
     leaf rt-ribgroup-union-head-name {
       type string;
       description "Rib-group union head name";
     }
     leaf rt-ribgroup-union-child-name {
       type string;
       description "Rib-group union child name";
     }
   }
   container rt-test-policy-prefix {
     leaf rt-policy-name {
       type string;
     }
     leaf rt-destination {
       type string;
     }
     leaf rt-prefix-length {
       type int32;
     }
     container rt-test-policy-term {
       leaf rt-policy-term-name {
         type string;
       }
       leaf rt-policy-term-result {
         type string;
       }
       leaf rt-policy-term-action {
         type string;
       }
     }
   }
   container rt-test-policy {
     leaf rt-policy-name {
       type string;
     }
     leaf rt-route-accepted {
       type int32;
     }
     leaf rt-route-rejected {
       type int32;
     }
   }
   list route-entry {
     leaf destination-address {
       type string;
     }
     leaf route-flags {
       type string;
     }
     leaf route-state {
       type string;
     }
     list nh-entry {
       list event-history {
       }
     }
   }
 }
 grouping test-services-l2tp-tunnel-result-block {
   container l2tp-tunnel-test-subscriber-information {
     description "Subscriber information obtained from tunnel verification";
     leaf subscriber-name {
       type string;
       description "Name of the subscriber";
     }
     leaf subscriber-authentication-status {
       type string;
       description "Status of the subscriber authentication";
     }
     leaf subscriber-tunneling-status {
       type string;
       description "Status of the subscriber tunneling";
     }
   }
   container l2tp-tunnel-test-result-table {
     description "Table of tunnel verification result";
     list l2tp-tunnel-test-result-entry {
       description "Result information for one tunnel's verification";
       leaf tunnel-name {
         type string;
         description "Name of the tunnel";
       }
       leaf tunnel-peer {
         type ipaddr;
         description "IP address of the tunnel peer";
       }
       leaf tunnel-logical-system {
         type string;
         description "Logical system of the tunnel";
       }
       leaf tunnel-routing-instance {
         type string;
         description "Routing instance of the tunnel";
       }
       leaf tunnel-status {
         type string;
         description "Status of tunnel establishment";
       }
     }
   }
 }
 grouping aaa-test-result-block {
   leaf aaa-test-status {
     type string;
     description "Server status";
   }
   leaf radius-server-attribute-name {
     type string;
     description "Access radius attribute name";
   }
   leaf radius-server-attribute-value {
     type string;
     description "Access radius attribute value";
   }
   leaf terminate-attribute-name {
     type string;
     description "Client termination attribute name";
   }
   leaf terminate-attribute-value {
     type string;
     description "Client termination attribute value";
   }
 }
 grouping radius-profile-access-test-result-block {
   leaf radius-profile-name {
     type string;
     description "Access profile name";
   }
   leaf radius-client-user-name {
     type string;
     description "Session user name";
   }
   leaf radius-client-password {
     type string;
     description "Session password";
   }
   leaf radius-profile-num-servers {
     type int32;
     description "Access profile num servers";
   }
   leaf radius-server-ip-address {
     type ipaddr;
     description "Server IP address";
   }
   leaf radius-server-udp-port {
     type uint32;
     description "Server UDP port";
   }
   leaf radius-server-source-address {
     type ipaddr;
     description "Source IP address";
   }
   leaf radius-server-timeout {
     type uint32;
     description "Server timeout value in seconds";
   }
   leaf radius-server-retry-count {
     type uint32;
     description "Server retry count";
   }
   leaf radius-server-secret {
     type string;
     description "Radius shared secret";
   }
   leaf radius-server-status {
     type string;
     description "Server status";
   }
   leaf radius-server-attempts {
     type int32;
     description "Access profile connection attemps";
   }
 }
 }
