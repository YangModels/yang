/*
 * Copyright (c) 2017 Juniper Networks, Inc.
 * All rights reserved.
 */
 module show-connections {
  namespace "http://yang.juniper.net/yang/1.1/jrpc/show-connections/junos/17.2R1.13";
  prefix show-connections;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ccc-information {
     description "Show circuit cross-connect connections";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf conn-type {
         default "all";
         type enumeration {
           enum "all" {
             description "All connections (default)";
           }
           enum "interface-switch" {
             description "Interface switch connections";
           }
           enum "lsp-switch" {
             description "LSP switch connections";
           }
           enum "p2mp-receive-switch" {
             description "Point-to-multipoint LSP to local interfaces switch";
           }
           enum "remote-interface-switch" {
             description "Remote interface switch connections";
           }
           enum "p2mp-transmit-switch" {
             description "Local interface to point-to-multipoint LSP switch";
           }
         }
       }
       leaf state {
         default "up-down";
         type enumeration {
           enum "down" {
             description "Connections that are not operational";
           }
           enum "up" {
             description "Connections that are operational";
           }
           enum "up-down" {
             description "Both operational and nonoperational connections (default)";
           }
         }
       }
       leaf detail {
         default "status";
         type enumeration {
           enum "brief" {
             description "Connection status (one line)";
           }
           enum "extensive" {
             description "Connection status and history";
           }
           enum "history" {
             description "Connection history";
           }
           enum "labels" {
             description "Labels used for transmit and receive LSPs";
           }
           enum "statistics" {
             description "Connection statistics";
           }
           enum "status" {
             description "Connection and circuit status (default)";
           }
         }
       }
       leaf connection-name {
         description "Name of connection";
         type string;
       }
     }
     output {
       container ccc-information {
         uses ccc-information-block;
       }
     }
   }
 grouping ccc-information-block {
   leaf ccc-no-connections {
     type empty;
   }
   leaf ccc-link-monitoring-status {
     type string;
     description "CCC link monitoring status";
   }
   leaf ccc-restarting {
     type empty;
   }
   list ccc-connection {
     leaf ccc-connection-name {
       type string;
       description "Connection name";
     }
     leaf ccc-connection-type {
       type string;
       description "Type of CCC connection";
     }
     leaf ccc-connection-status {
       type string;
       description "Status of the CCC connection";
     }
     leaf ccc-connection-last-uptime {
       type string;
       description "Time the connection was last up";
     }
     leaf ccc-connection-up-transitions {
       type int32;
       description "Number of transitions to up state";
     }
     list ccc-connection-circuit {
       leaf ccc-circuit-name {
         type string;
       }
       leaf ccc-circuit-type {
         type string;
       }
       leaf ccc-circuit-status {
         type string;
       }
     }
     container ccc-connection-in-labels {
       description "Incoming labels for this CCC connection";
       leaf ccc-connection-in-labels.heading {
         type string;
         description "Incoming labels for this CCC connection";
       }
       leaf mpls-label {
         type string;
         description "Label of MPLS packet";
       }
       leaf no-label {
         type empty;
       }
     }
     container ccc-connection-out-labels {
       description "Outgoing labels for this CCC connection";
       leaf ccc-connection-out-labels.heading {
         type string;
         description "Outgoing labels for this CCC connection";
       }
       leaf mpls-label {
         type string;
         description "Label of MPLS packet";
       }
       leaf no-label {
         type empty;
       }
     }
     container ccc-connection-history {
       list ccc-connection-history-log {
         leaf event-time {
           type string;
         }
         leaf event-name {
           type string;
         }
         leaf interface-label-info {
           type string;
         }
         leaf receive-lsp-count {
           type int32;
         }
         leaf transmit-lsp-count {
           type int32;
         }
       }
     }
   }
 }
 }
