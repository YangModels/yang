/*
 * Copyright (c) 2017 Juniper Networks, Inc.
 * All rights reserved.
 */
 module show-fibre-channel {
  namespace "http://yang.juniper.net/yang/1.1/jrpc/show-fibre-channel/junos/17.2R1.13";
  prefix show-fibre-channel;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-event-server-registrations {
     description "Display event server registration entries";
     input {
       leaf fabric {
         description "Fabric name";
         type string;
       }
     }
   }
   rpc get-event-server-statistics {
     description "Display event server statistics";
     input {
       leaf fabric {
         description "Fabric name";
         type string;
       }
     }
   }
   rpc get-fibre-channel-interface-information {
     description "Display FC-switching interface information";
     input {
       leaf verbosity_level {
         default "brief";
         type enumeration {
           enum "brief" {
             description "Display brief output (default)";
           }
           enum "detail" {
             description "Display detailed output";
           }
         }
       }
       leaf interface-name {
         description "Name of interface";
         type interface-name;
       }
       leaf fabric {
         description "Name of fabric";
         type string;
       }
     }
   }
   rpc get-fibre-channel-fabric-information {
     description "Display FC-switching fabric information";
     input {
       leaf verbosity_level {
         default "summary";
         type enumeration {
           enum "extensive" {
             description "Display extensive output";
           }
           enum "summary" {
             description "Display summary output (default)";
           }
         }
       }
       leaf sort-by {
         description "Specify display order";
         default "name";
         type enumeration {
           enum "name" {
             description "Sort display by name";
           }
           enum "tag" {
             description "Sort display by tag";
           }
         }
       }
       leaf fabric-name {
         description "Name of fabric for which to display the table";
         type string;
       }
     }
   }
   rpc get-fc-fcid-server-information {
     description "Fcid server database";
   }
   rpc get-fc-fcid-server-statistics-information {
     description "Fcid server Statistics";
   }
   rpc get-fc-fcid-client-information {
     description "Fcid client database";
   }
   rpc get-fc-fcid-client-statistics-information {
     description "Fcid client Statistics";
   }
   rpc get-fc-zoning-database-information {
     description "Zoning database";
     input {
       leaf fabric {
         description "Name of fabric";
         type string;
       }
       leaf zone-set {
         description "Zone-set name";
         type string;
       }
       leaf zone {
         description "Zone name";
         type string;
       }
       leaf member-alias {
         description "Alias name";
         type string;
       }
     }
   }
   rpc get-fc-zone-query {
     description "Perform a query operation on currently active zone set";
     input {
       leaf fabric {
         description "Name of fabric";
         type string;
         mandatory true;
       }
       leaf n-port-wwn {
         description "N-Port WWN";
         type wwn;
         mandatory true;
       }
     }
   }
   rpc get-fc-active-zone-set-information {
     description "Active zone set";
     input {
       leaf fabric {
         description "Name of fabric";
         type string;
       }
     }
   }
   rpc get-fibre-channel-filter-information {
     description "Filter";
   }
   rpc get-fc-filter-information {
     description "Filter terms information";
     input {
       leaf fabric {
         description "Name of fabric";
         type string;
       }
       leaf term-name {
         description "Term name";
         type string;
       }
     }
   }
   rpc get-fc-nport-filter-information {
     description "Nport operational filter state";
     input {
       leaf fabric {
         description "Name of fabric";
         type string;
       }
       leaf n-port-wwn {
         description "N-Port WWN";
         type wwn;
       }
       leaf fcid {
         description "F-Port WWN";
         type string {
           junos:posix-pattern "^0x[abcdefABCDEF0123456789]{6}$";
           junos:pattern-message "Must be hexadecimal bit pattern of form 0xDDAAPP";
         }
       }
     }
   }
   rpc get-zs-filter-statistics-information {
     description "Statistics";
     input {
       leaf fabric {
         description "Name of fabric";
         type string;
       }
     }
   }
   rpc get-fc-enforcement-database-information {
     description "Enforcement-database";
     input {
       leaf fabric {
         description "Name of fabric";
         type string;
       }
       leaf n-port-wwn {
         description "N-Port WWN";
         type wwn;
       }
       leaf f-port-wwn {
         description "F-Port WWN";
         type wwn;
       }
       leaf fcid {
         description "F-Port WWN";
         type string {
           junos:posix-pattern "^0x[abcdefABCDEF0123456789]{6}$";
           junos:pattern-message "Must be hexadecimal bit pattern of form 0xDDAAPP";
         }
       }
     }
   }
   rpc get-fibre-channel-flogi-information {
     description "Nport Information";
     input {
       leaf verbosity_level {
         default "brief";
         type enumeration {
           enum "brief" {
             description "Display brief output (default)";
           }
           enum "detail" {
             description "Display detailed output";
           }
         }
       }
       leaf fabric {
         description "Name of fabric";
         type string;
       }
     }
   }
   rpc get-fibre-channel-flogi-fport-information {
     description "Fport Information";
     input {
       leaf fabric {
         description "Name of fabric";
         type string;
       }
     }
   }
   rpc get-flogi-statistics-information {
     description "FLOGI Server Statistics";
     input {
       leaf fabric {
         description "Name of fabric";
         type string;
       }
     }
   }
   rpc get-ie-information {
     description "Display interconnect element information";
     input {
       leaf verbosity_level {
         default "summary";
         type enumeration {
           enum "detail" {
             description "Display detailed output";
           }
           enum "summary" {
             description "Display summarised output (default)";
           }
         }
       }
       leaf ie-name {
         description "Interconnect element logical name";
         type string;
       }
       leaf fabric-name {
         description "Fabric name";
         type string;
       }
     }
   }
   rpc get-plat-obj-information {
     description "Display platform object information";
     input {
       leaf verbosity_level {
         default "summary";
         type enumeration {
           enum "detail" {
             description "Display detailed output";
           }
           enum "summary" {
             description "Display summarised output (default)";
           }
         }
       }
       leaf platform-object-name {
         description "Platform object name";
         type string;
       }
       leaf fabric-name {
         description "Fabric name";
         type string;
       }
     }
   }
   rpc get-fcs-statistics-information {
     description "Display server command statistics";
     input {
       leaf fabric {
         description "Name of fabric";
         type string;
       }
     }
   }
   rpc get-fibre-channel-routes-information {
     description "Display route database";
     input {
       leaf fabric {
         description "Name of fabric";
         type string;
       }
     }
   }
   rpc get-fibre-channel-next-hops-information {
     description "Display next-hop database";
     input {
       leaf fabric {
         description "Name of fabric";
         type string;
       }
     }
   }
   rpc get-fibre-channel-virtual-switch-information {
     description "Display FC-switching virtual switch information";
     input {
       leaf verbosity_level {
         default "summary";
         type enumeration {
           enum "extensive" {
             description "Display extensive output";
           }
           enum "summary" {
             description "Display summary output (default)";
           }
         }
       }
       leaf fabric {
         description "Display virtual switches for specified fabric";
         type string;
       }
       leaf virtual-switch {
         description "Display specified virtual switch in a given or all fabrics";
         type string;
       }
     }
   }
   rpc get-fibre-channel-fc2-session-information {
     description "Display FC2 sessions";
     input {
       leaf verbosity_level {
         default "brief";
         type enumeration {
           enum "brief" {
             description "Display brief output (default)";
           }
           enum "detail" {
             description "Display detailed output";
           }
         }
       }
       leaf fabric {
         description "Name of fabric";
         type string;
       }
     }
   }
   rpc get-fibre-channel-fc2-statistics-information {
     description "Display FC2 statistics";
     input {
       leaf fabric {
         description "Name of fabric";
         type string;
       }
     }
   }
   rpc get-fibre-channel-name-server-information {
     description "Display Fibre Channel name server information";
     input {
       leaf verbosity_level {
         default "brief";
         type enumeration {
           enum "brief" {
             description "Display brief output (default)";
           }
           enum "detail" {
             description "Display detailed output";
           }
         }
       }
       leaf fabric {
         description "Display name server entries for specified fabric";
         type string;
       }
     }
   }
   rpc get-fibre-channel-name-server-domain-information {
     description "Display name server entries for specified domain-id";
     input {
       leaf verbosity_level {
         default "brief";
         type enumeration {
           enum "brief" {
             description "Display brief output (default)";
           }
           enum "detail" {
             description "Display detailed output";
           }
         }
       }
       leaf domain-id {
         description "Domain Identifier";
         type uint32 {
           range "1 .. 239";
         }
         mandatory true;
       }
       leaf fabric {
         description "Fabric Name";
         type string;
       }
     }
   }
   rpc get-fibre-channel-name-server-port-information {
     description "Display entries for specified port";
     input {
       leaf verbosity_level {
         default "brief";
         type enumeration {
           enum "brief" {
             description "Display brief output (default)";
           }
           enum "detail" {
             description "Display detailed output";
           }
         }
       }
       leaf fcid {
         description "FCID";
         type string {
           junos:posix-pattern "^0x[abcdefABCDEF0123456789]{6}$";
           junos:pattern-message "Must be hexadecimal bit pattern of form 0xNNNNNN";
         }
         mandatory true;
       }
       leaf fabric {
         description "Fabric Name";
         type string;
       }
     }
   }
   rpc get-fc-fip-information {
     description "Display FCoE Initialization Protocol information";
     input {
       leaf verbosity_level {
         default "brief";
         type enumeration {
           enum "brief" {
             description "Display brief output (default)";
           }
           enum "detail" {
             description "Display detailed output";
           }
         }
       }
     }
   }
   rpc get-fc-fip-fabric-information {
     description "Name of fabric";
     input {
       leaf verbosity_level {
         default "brief";
         type enumeration {
           enum "brief" {
             description "Display brief output (default)";
           }
           enum "detail" {
             description "Display detailed output";
           }
         }
       }
       leaf fabric-name {
         description "Fabric name";
         type string;
         mandatory true;
       }
     }
   }
   rpc get-fc-fip-fcf-information {
     description "MAC of FCF";
     input {
       leaf verbosity_level {
         default "brief";
         type enumeration {
           enum "brief" {
             description "Display brief output (default)";
           }
           enum "detail" {
             description "Display detailed output";
           }
         }
       }
       leaf fcf-mac {
         description "MAC address of FCF";
         type mac-addr;
         mandatory true;
       }
       leaf fabric {
         description "Name of fabric";
         type string;
       }
     }
   }
   rpc get-fc-fip-interface-information {
     description "Interface";
     input {
       leaf verbosity_level {
         default "brief";
         type enumeration {
           enum "brief" {
             description "Display brief output (default)";
           }
           enum "detail" {
             description "Display detailed output";
           }
         }
       }
       leaf interface-name {
         description "Name of interface";
         type interface-name;
       }
       leaf fabric {
         description "Name of fabric";
         type string;
       }
       leaf enode {
         description "Enode MAC";
         type mac-addr;
       }
       leaf vn-port {
         description "VN_Port MAC";
         type mac-addr;
       }
     }
   }
   rpc get-fc-fip-enode-information {
     description "ENode";
     input {
       leaf verbosity_level {
         default "brief";
         type enumeration {
           enum "brief" {
             description "Display brief output (default)";
           }
           enum "detail" {
             description "Display detailed output";
           }
         }
       }
       leaf enode-mac {
         description "Enode MAC";
         type mac-addr;
         mandatory true;
       }
       leaf vn-port {
         description "VN_Port MAC";
         type mac-addr;
       }
       leaf fabric {
         description "Name of fabric";
         type string;
       }
     }
   }
   rpc get-fc-fip-statistics-information {
     description "FIP statistics";
     input {
       leaf fabric {
         description "Name of fabric";
         type string;
       }
     }
   }
   rpc get-fspf-overview-information {
     description "Show overview of FSPF information";
     input {
       leaf verbosity_level {
         default "brief";
         type enumeration {
           enum "brief" {
             description "Display brief output (default)";
           }
           enum "extensive" {
             description "Display extensive output";
           }
         }
       }
       leaf fabric {
         description "Name of Fabric";
         type string;
         mandatory true;
       }
     }
   }
   rpc get-fibre-channel-fspf-interface-information {
     description "Show Fibre Channel FSPF interface information";
     input {
       leaf verbosity_level {
         default "brief";
         type enumeration {
           enum "brief" {
             description "Display brief output (default)";
           }
           enum "detail" {
             description "Display detailed output";
           }
           enum "extensive" {
             description "Display extensive output";
           }
         }
       }
       leaf fabric {
         description "Name of Fabric";
         type string;
         mandatory true;
       }
       leaf interface-name {
         description "Name of logical interface";
         type string;
       }
     }
   }
   rpc get-fibre-channel-fspf-neighbor-information {
     description "Show Fibre Channel FSPF neighbor information";
     input {
       leaf verbosity_level {
         default "brief";
         type enumeration {
           enum "brief" {
             description "Display brief output (default)";
           }
           enum "detail" {
             description "Display detailed output";
           }
           enum "extensive" {
             description "Display extensive output";
           }
         }
       }
       leaf fabric {
         description "Name of Fabric";
         type string;
         mandatory true;
       }
       leaf interface {
         description "Name of logical interface";
         type string;
       }
     }
   }
   rpc get-fspf-database-information {
     description "Show FSPF link-state database";
     input {
       leaf level {
         default "brief";
         type enumeration {
           enum "brief" {
             description "Display brief output (default)";
           }
           enum "detail" {
             description "Display detailed output";
           }
           enum "extensive" {
             description "Display extensive output";
           }
           enum "summary" {
             description "Display summary output";
           }
         }
       }
       leaf lsr-type {
         type enumeration {
           enum "switch" {
             description "Switch link-state records";
           }
         }
       }
       leaf lsr-id {
         description "Link-state ID";
         default "all";
         type string;
       }
       leaf advertising-switch {
         description "Domain ID of advertising switch";
         type string;
       }
       leaf fabric {
         description "Name of Fabric";
         type string;
         mandatory true;
       }
     }
   }
   rpc get-fspf-route-information {
     description "Show FSPF routing table";
     input {
       leaf level {
         type enumeration {
           enum "detail" {
             description "Display detailed output";
           }
         }
       }
       leaf fabric {
         description "Name of Fabric";
         type string;
         mandatory true;
       }
     }
   }
   rpc get-fspf-fabric-statistics-information {
     description "Show FSPF fabric statistics";
     input {
       leaf fabric {
         description "Name of Fabric";
         type string;
         mandatory true;
       }
     }
   }
   rpc get-fspf-statistics-information {
     description "Show FSPF statistics";
   }
   rpc get-fibre-channel-proxy-information {
     description "Show proxy login sessions";
     input {
       leaf verbosity_level {
         default "brief";
         type enumeration {
           enum "brief" {
             description "Display brief output (default)";
           }
           enum "detail" {
             description "Display detailed output";
           }
         }
       }
       leaf fabric {
         description "Name of fabric";
         type string;
       }
       leaf interface {
         description "Name of interface";
         type interface-name;
       }
     }
   }
   rpc get-proxy-fabric-state-information {
     description "Show proxy fabric-state information";
     input {
       leaf fabric {
         description "Name of fabric";
         type string;
       }
     }
   }
   rpc get-fibre-channel-proxy-np-port {
     description "Show proxy np-port information";
     input {
       leaf verbosity_level {
         default "brief";
         type enumeration {
           enum "brief" {
             description "Display brief output (default)";
           }
           enum "detail" {
             description "Display detailed output";
           }
         }
       }
       leaf fabric {
         description "Name of fabric";
         type string;
       }
       leaf interface {
         description "Name of interface";
         type interface-name;
       }
     }
   }
   rpc get-proxy-statistics-information {
     description "Show proxy statistics";
     input {
       leaf fabric {
         description "Name of fabric";
         type string;
       }
       leaf interface {
         description "Name of interface";
         type interface-name;
       }
     }
   }
   rpc get-rscn-server-registrations {
     description "Display State Change Registration entries";
     input {
       leaf fabric {
         description "Fabric name";
         type string;
       }
     }
   }
   rpc get-rscn-server-statistics {
     description "Display RSCN Server Statistics";
     input {
       leaf fabric {
         description "Fabric name";
         type string;
       }
     }
   }
 }
