/*
 * Copyright (c) 2017 Juniper Networks, Inc.
 * All rights reserved.
 */
 module show-security {
  namespace "http://yang.juniper.net/yang/1.1/jrpc/show-security/junos-es/17.2R1.13";
  prefix show-security;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-security-alarm-information {
     description "Show active security alarm information";
     input {
       leaf alarm-id {
         description "Alarm ID filter";
         type uint32;
       }
       leaf-list alarm-type {
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type time;
       }
       leaf older-than {
         description "Alarms older than filter (YYYY-MM-DD.HH:MM:SS)";
         type time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf style {
         type enumeration {
           enum "detail" {
             description "Show detail alarm information";
           }
         }
       }
     }
     output {
       container security-alarm-information {
         uses security-alarm-information-block;
       }
     }
   }
   rpc get-security-log-information {
     description "Show auditable security log information";
     input {
       leaf destination-address {
         description "Destination address and optional prefix length";
         type ipprefix-optional;
       }
       leaf destination-port {
         description "Destination port";
         type uint32;
       }
       leaf event-id {
         description "Event ID filter";
         type string;
       }
       leaf interface-name {
         description "Name of interface";
         type string;
       }
       leaf older-than {
         description "Events older than filter (YYYY-MM-DD.HH:MM:SS)";
         type time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type time;
       }
       leaf result {
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type ipprefix-optional;
       }
       leaf source-port {
         description "Source port";
         type uint32;
       }
       leaf username {
         description "Username filter";
         type string;
       }
       leaf sort-by {
         description "Sort by selected field";
         default "time";
         type enumeration {
           enum "destination-address" {
             description "Sort by destination address";
           }
           enum "destination-port" {
             description "Sort by destination port";
           }
           enum "interface-name" {
             description "Sort by interface name";
           }
           enum "policy-name" {
             description "Sort by policy name";
           }
           enum "protocol" {
             description "Sort by protocol";
           }
           enum "source-address" {
             description "Sort by source address";
           }
           enum "source-port" {
             description "Sort by source port";
           }
           enum "time" {
             description "Sort by time of event arrival";
           }
           enum "username" {
             description "Sort by event user name ";
           }
         }
       }
       leaf direction {
         default "ascending";
         type enumeration {
           enum "ascending" {
             description "Sort in ascending order";
           }
           enum "descending" {
             description "Sort in descending order";
           }
         }
       }
       leaf style {
         type enumeration {
           enum "detail" {
             description "Show detail alarm information";
           }
         }
       }
     }
     output {
       container security-log-information {
         uses security-log-information-block;
       }
     }
   }
   rpc show-security-hpl-infile {
     description "Show security logs in binary format";
     input {
       leaf file_name {
         description "Name of the binary log file to be displayed ";
         type string {
           length "1 .. 256";
         }
       }
     }
   }
   rpc show-security-hpl-infile-last {
     description "Show recent security logs in binary format";
     input {
       leaf seconds {
         description "Number of seconds of binary logs to display";
         type uint32;
       }
     }
   }
   rpc show-security-hpl-infile {
     description "Show security logs stream file";
     input {
       leaf file-name {
         description "Name of the stream log file to be displayed ";
         type string {
           length "1 .. 256";
         }
         mandatory true;
       }
     }
   }
   rpc show-security-log-query {
     description "Query logs from database";
     input {
       leaf category {
         description "Category name";
         type enumeration {
           enum "all" {
             description "Category all";
           }
           enum "utm" {
             description "Utm";
           }
           enum "fw-auth" {
             description "Fw-auth";
           }
           enum "screen" {
             description "Screen";
           }
           enum "alg" {
             description "Alg";
           }
           enum "nat" {
             description "Nat";
           }
           enum "flow" {
             description "Flow";
           }
           enum "sctp" {
             description "Sctp";
           }
           enum "gtp" {
             description "Gtp";
           }
           enum "ipsec" {
             description "Ipsec";
           }
           enum "idp" {
             description "Idp";
           }
           enum "rtlog" {
             description "Rtlog";
           }
           enum "pst-ds-lite" {
             description "Pst-ds-lite";
           }
           enum "appqos" {
             description "Appqos";
           }
           enum "secintel" {
             description "Secintel";
           }
         }
         mandatory true;
       }
       leaf count {
         description "Number of logs to be queried";
         type uint32;
       }
       leaf src-ip {
         description "Filter source ip";
         type ipaddr;
       }
       leaf dst-ip {
         description "Filter destination ip";
         type ipaddr;
       }
       leaf src-port {
         description "Filter source port";
         type uint16 {
           range "1 .. 65535";
         }
       }
       leaf dst-port {
         description "Filter destination port";
         type uint16 {
           range "1 .. 65535";
         }
       }
       leaf application {
         description "Filter application";
         type string {
           length "1 .. 256";
         }
       }
       leaf user {
         description "Filter user";
         type string {
           length "1 .. 256";
         }
       }
       leaf service {
         description "Filter service";
         type string {
           length "1 .. 256";
         }
       }
       leaf event-type {
         description "Filter event-type";
         type string {
           length "1 .. 256";
         }
       }
       leaf start-time {
         description "Earliest timestamp to include in output (YYYY-MM-DDTHH:MM:SS)";
         type time;
       }
       leaf stop-time {
         description "Latest timestamp to include in output (YYYY-MM-DDTHH:MM:SS)";
         type time;
       }
     }
   }
   rpc get-hakr-keychain-information {
     description "Show all protocols keychain";
     input {
       leaf verbosity {
         default "brief";
         type enumeration {
           enum "brief" {
             description "Display brief output (default)";
           }
           enum "detail" {
             description "Display detailed output";
           }
         }
       }
     }
     output {
       container hakr-keychain-information {
         uses hakr-keychain-information-block;
       }
     }
   }
   rpc get-pki-certificate-request {
     description "Show PKCS-10 certificate request information";
     input {
       leaf certificate-id {
         description "Certificate identifier";
         type string {
           junos:posix-pattern "^.{1,32}$";
           junos:pattern-message "Must be string of 32 characters or less";
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-ca-certificate {
     description "Show certificate-authority certificate information";
     input {
       container ca-cert-choice {
         choice ca-cert-choice_c {
           case ca-profile {
             leaf ca-profile {
               description "Certificate authority profile";
               type string {
                 junos:posix-pattern "^.{1,32}$";
                 junos:pattern-message "Must be string of 32 characters or less";
               }
             }
           }
           case ca-profile-group {
             leaf ca-profile-group {
               description "Show CA profile group";
               type string {
                 junos:posix-pattern "^.{1,32}$";
                 junos:pattern-message "Must be string of 32 characters or less";
               }
             }
           }
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-local-certificate {
     description "Show router certificate information";
     input {
       container certificate-choice {
         choice certificate-choice_c {
           case certificate-id {
             leaf certificate-id {
               description "Certificate identifier";
               type string {
                 junos:posix-pattern "^.{1,32}$";
                 junos:pattern-message "Must be string of 32 characters or less";
               }
             }
           }
           case system-generated {
             leaf system-generated {
               description "Autogenerated self-signed certificate";
               type empty;
             }
           }
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-crl {
     description "Show certificate revocation list information";
     input {
       leaf ca-profile {
         description "Certificate authority profile";
         type string {
           junos:posix-pattern "^.{1,32}$";
           junos:pattern-message "Must be string of 32 characters or less";
         }
       }
       leaf level {
         default "brief";
         type enumeration {
           enum "brief" {
             description "Display brief output";
           }
           enum "detail" {
             description "Display detailed output";
           }
         }
       }
     }
     output {
       container x509-pkid-crl-information-list {
         uses x509-pkid-crl-information-list-block;
       }
     }
   }
   rpc get-security-associations-information {
     description "Show IPSec security association information";
     input {
       leaf level {
         default "brief";
         type enumeration {
           enum "brief" {
             description "Display brief output";
           }
           enum "detail" {
             description "Display detailed output";
           }
         }
       }
       leaf family {
         description "Show IPSec security association information by family";
         default "inet";
         type enumeration {
           enum "inet" {
             description "Show IPv4";
           }
           enum "inet6" {
             description "Show IPv6";
           }
         }
       }
       leaf sa-type {
         description "Show IPSec security association by type";
         type enumeration {
           enum "shortcut" {
             description "Show Shortcut SAs";
           }
         }
       }
       leaf show-index-ipsec-security-association {
         description "Index of security association";
         type uint32 {
           range "1 .. 4294967295";
         }
       }
       leaf show-vpnname-ipsec-security-association {
         description "VPN name";
         default "all";
         type string;
       }
       leaf show-trafficselectorname-ipsec-security-association {
         description "Traffic-selector name";
         default "all";
         type string;
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   		63 letters, numbers, dashes and underscores";
         }
       }
     }
     output {
       container security-associations-information {
         uses security-associations-information-block;
       }
     }
   }
   rpc get-control-plane-security-associations-information {
     description "Show IPSec control plane security association information";
     input {
       leaf level {
         default "brief";
         type enumeration {
           enum "brief" {
             description "Display brief output";
           }
           enum "detail" {
             description "Display detailed output";
           }
         }
       }
       leaf show-saname-ipsec-control-plane-security-association {
         description "SA name";
         default "all";
         type string;
       }
     }
   }
   rpc get-ipsec-statistics-information {
     description "Show IPSec statistics";
     input {
       leaf fpc {
         description "FPC slot number";
         type uint32 {
           range "0 .. 63";
         }
       }
       leaf pic {
         description "PIC slot number";
         type uint32 {
           range "0 .. 3";
         }
       }
       leaf show-index-ipsec-statistics {
         description "Index of Security Association";
         default "0";
         type uint32;
       }
     }
     output {
       container usp-ipsec-total-statistics-information {
         uses usp-ipsec-total-statistics-information-block;
       }
     }
   }
   rpc get-inactive-tunnels {
     description "Inactive-tunnels";
     input {
       leaf level {
         default "brief";
         type enumeration {
           enum "brief" {
             description "Display brief output";
           }
           enum "detail" {
             description "Display detailed output";
           }
         }
       }
       leaf family {
         description "Show IPSec security association information by family";
         default "inet";
         type enumeration {
           enum "inet" {
             description "Show IPv4";
           }
           enum "inet6" {
             description "Show IPv6";
           }
         }
       }
       leaf show-index-ipsec-security-association {
         description "Index of security association";
         default "0";
         type uint32;
       }
       leaf show-vpnname-ipsec-security-association {
         description "VPN name";
         default "all";
         type string;
       }
       leaf sa-type {
         description "Show inactive IPSec SAs by type";
         type enumeration {
           enum "shortcut" {
             description "Show Shortcut SAs";
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   		63 letters, numbers, dashes and underscores";
         }
       }
     }
     output {
       container ipsec-unestablished-tunnel-information {
         uses ipsec-unestablished-tunnel-information-block;
       }
     }
   }
   rpc get-ipsec-next-hop-tunnel-information {
     description "Show manual and auto next-hop-tunnel entries";
     input {
       leaf interface-name {
         description "Name of secure tunnel logical interface";
         default "all";
         type string;
       }
     }
   }
   rpc get-ipsec-traffic-selector-information {
     description "Show traffic-selector information for a st0 interface";
     input {
       leaf interface-name {
         description "Name of secure tunnel logical interface";
         type string;
         mandatory true;
       }
       leaf source-address {
         description "Source IP address";
         type ipprefix-mandatory;
       }
       leaf destination-address {
         description "Destination IP address";
         type ipprefix-mandatory;
       }
       leaf level {
         default "brief";
         type enumeration {
           enum "brief" {
             description "Display brief output";
           }
           enum "detail" {
             description "Display detailed output";
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   		63 letters, numbers, dashes and underscores";
         }
       }
     }
   }
   rpc get-ipsec-tunnel-event-statistics {
     description "Show tunnel event statstics";
   }
   rpc get-pre-shared-key {
     description "Show IKE pre-shared key information for a particular group-ike-id user";
     input {
       leaf user-id {
         description "IKE user-id value";
         type string;
       }
       leaf master-key {
         description "Master pre-shared key";
         type string;
         mandatory true;
       }
     }
     output {
       container ike-show-pre-shared-key-information {
         uses ike-show-pre-shared-key-information-block;
       }
     }
   }
   rpc get-ike-security-associations-information {
     description "Show IKE security association information";
     input {
       leaf peer-address {
         description "IP address of the peer";
         type ipaddr;
       }
       leaf level {
         default "brief";
         type enumeration {
           enum "brief" {
             description "Show brief output (default)";
           }
           enum "detail" {
             description "Show detailed output";
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   		63 letters, numbers, dashes and underscores";
         }
       }
       leaf family {
         description "Show IKE security association by family";
         default "inet";
         type enumeration {
           enum "inet" {
             description "Show IPv4";
           }
           enum "inet6" {
             description "Show IPv6";
           }
         }
       }
       leaf show-index-ike-security-association {
         description "Index of security association";
         type uint32 {
           range "1 .. 4294967295";
         }
       }
       leaf sa-type {
         description "Show IKE security association by type";
         type enumeration {
           enum "shortcut" {
             description "Show Shortcut SAs";
           }
         }
       }
     }
     output {
       container ike-security-associations-information {
         uses ike-security-associations-information-block;
       }
     }
   }
   rpc get-ike-active-peers-information {
     description "Show IKE active peers ";
     input {
       leaf level {
         default "brief";
         type enumeration {
           enum "brief" {
             description "Display brief output";
           }
           enum "detail" {
             description "Display detailed output";
           }
         }
       }
       leaf peer-address {
         description "IP of peer";
         type ipaddr;
       }
       leaf port {
         description "Port number of peer";
         type uint32 {
           range "1 .. 65535";
         }
       }
       leaf ike-id {
         description "IKE ID";
         default "all";
         type string;
       }
       leaf xauth-username {
         description "XAUTH username";
         default "all";
         type string;
       }
       leaf debug {
         description "Show additional peer-entry debug information";
         type empty;
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   		63 letters, numbers, dashes and underscores";
         }
       }
     }
     output {
       container ike-active-peers-information {
         uses ike-active-peers-information-block;
       }
     }
   }
   rpc get-config-ike-debug {
     description "Show current enabled IKE debug information";
     output {
       container security-ike-debug-info {
         uses security-ike-debug-info-block;
       }
     }
   }
   rpc get-iked-tunnel-mapping-information {
     description "Display tunnel mapping info for site-to-site tunnels";
     input {
       leaf level {
         default "brief";
         type enumeration {
           enum "brief" {
             description "Display brief tunnel-mapping (default)";
           }
           enum "summary" {
             description "Display tunnel-mapping summary info";
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
     output {
       container iked-tunnel-mapping-information {
         uses iked-tunnel-mapping-information-block;
       }
     }
   }
   rpc get-gvpn-security-associations-information {
     description "Show IPSec security association information";
     input {
       leaf level {
         default "brief";
         type enumeration {
           enum "brief" {
             description "Display brief output";
           }
           enum "detail" {
             description "Display detailed output";
           }
         }
       }
       leaf show-gvpn-index-ipsec-security-association {
         description "Index of security association";
         default "0";
         type uint32;
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
       leaf group-id {
         description "Group VPN identification number";
         type uint32 {
           range "1 .. 4294967295";
         }
       }
     }
     output {
       container ipsec-security-associations-information {
         uses ipsec-security-associations-information-block;
       }
     }
   }
   rpc get-gvpn-ipsec-statistics-information {
     description "Show IPSec statistics";
     input {
       leaf fpc {
         description "FPC slot number";
         type uint32 {
           range "0 .. 63";
         }
       }
       leaf pic {
         description "PIC slot number";
         type uint32 {
           range "0 .. 3";
         }
       }
       leaf show-gvpn-index-ipsec-statistics {
         description "Index of Security Association";
         default "0";
         type uint32;
       }
     }
     output {
       container usp-ipsec-total-statistics-information {
         uses usp-ipsec-total-statistics-information-block;
       }
     }
   }
   rpc get-gvpn-inactive-tunnels {
     description "Inactive-tunnels";
     input {
       leaf level {
         default "brief";
         type enumeration {
           enum "brief" {
             description "Display brief output";
           }
           enum "detail" {
             description "Display detailed output";
           }
         }
       }
       leaf group-id {
         description "Group VPN identification number";
         type uint32 {
           range "1 .. 4294967295";
         }
       }
     }
     output {
       container ipsec-unestablished-tunnel-information {
         uses ipsec-unestablished-tunnel-information-block;
       }
     }
   }
   rpc get-gvpn-ike-security-associations-information {
     description "Show IKE security association information";
     input {
       leaf level {
         default "brief";
         type enumeration {
           enum "brief" {
             description "Show brief output (default)";
           }
           enum "detail" {
             description "Show detailed output";
           }
         }
       }
       leaf peer-address {
         description "IP address of the peer";
         type ipaddr;
       }
       leaf index {
         description "Index of security association";
         default "0";
         type uint32;
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
     output {
       container ike-security-associations-information {
         uses ike-security-associations-information-block;
       }
     }
   }
   rpc get-gvpn-kek-security-associations-information {
     description "Show KEK security association information";
     input {
       leaf level {
         default "brief";
         type enumeration {
           enum "brief" {
             description "Show brief output (default)";
           }
           enum "detail" {
             description "Show detailed output";
           }
         }
       }
       leaf peer-address {
         description "IP address of the peer";
         type ipaddr;
       }
       leaf index {
         description "Index of security association";
         default "0";
         type uint32;
       }
       container groupchoice {
         description "Specify a group by name or ID";
         choice groupchoice_c {
           case group-id {
             leaf group-id {
               description "Group VPN identification number";
               type uint32 {
                 range "1 .. 4294967295";
               }
             }
           }
           case vpn {
             leaf vpn {
               description "Group VPN Name";
               type string {
                 length "1 .. 32";
               }
             }
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
     output {
       container ike-security-associations-information {
         uses ike-security-associations-information-block;
       }
     }
   }
   rpc get-gvpn-policy-information {
     description "Show group vpn policies";
     input {
       container groupchoice {
         description "Specify a group by name or ID";
         choice groupchoice_c {
           case group-id {
             leaf group-id {
               description "Group VPN identification number";
               type uint32 {
                 range "1 .. 4294967295";
               }
             }
           }
           case vpn {
             leaf vpn {
               description "Group VPN Name";
               type string {
                 length "1 .. 32";
               }
             }
           }
         }
       }
     }
   }
   rpc get-security-group-vpn-server-registered-members {
     description "Show group VPN registered members for group VPN server";
     input {
       container group_choice {
         description "Specify a group by name or id";
         choice group_choice_c {
           case group {
             leaf group {
               description "Show specified group";
               type string {
                 length "1 .. 32";
               }
             }
           }
           case group-id {
             leaf group-id {
               description "Show specified group id";
               type uint32 {
                 range "1 .. 65535";
               }
             }
           }
           case peer-address {
             leaf peer-address {
               description "Peer IP address";
               type ipaddr;
             }
           }
         }
       }
       leaf level {
         default "brief";
         type enumeration {
           enum "brief" {
             description "Show brief output (default)";
           }
           enum "detail" {
             description "Show detailed output";
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
   }
   rpc get-security-group-vpn-server-kek-sa {
     description "Show KEK security association information";
     input {
       leaf level {
         default "brief";
         type enumeration {
           enum "brief" {
             description "Show brief output (default)";
           }
           enum "detail" {
             description "Show detailed output";
           }
         }
       }
       container group_index_choice {
         description "Specify peer-address, group, group-id or index filter";
         choice group_index_choice_c {
           case group {
             leaf group {
               description "Show specified group";
               type string {
                 length "1 .. 32";
               }
             }
           }
           case group-id {
             leaf group-id {
               description "Show specified group id";
               type uint32 {
                 range "1 .. 65535";
               }
             }
           }
           case index {
             leaf index {
               description "Index of security association";
               type uint32;
             }
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
   }
   rpc get-security-group-vpn-server-security-information {
     description "Show IPSec security association information for group VPN server";
     input {
       leaf level {
         default "brief";
         type enumeration {
           enum "brief" {
             description "Show brief output (default)";
           }
           enum "detail" {
             description "Show detailed output";
           }
         }
       }
       container group_choice {
         description "Specify group or group-id filter";
         choice group_choice_c {
           case group {
             leaf group {
               description "Show specified group";
               type string {
                 length "1 .. 32";
               }
             }
           }
           case group-id {
             leaf group-id {
               description "Show specified group id";
               type uint32 {
                 range "1 .. 65535";
               }
             }
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
   }
   rpc get-security-group-vpn-server-ike-security-associations-information {
     description "Show IKE security association information";
     input {
       leaf level {
         default "brief";
         type enumeration {
           enum "brief" {
             description "Show brief output (default)";
           }
           enum "detail" {
             description "Show detailed output";
           }
         }
       }
       container group_index_choice {
         description "Specify peer-address, group, group-id or index filter";
         choice group_index_choice_c {
           case peer-address {
             leaf peer-address {
               description "Peer IP address";
               type ipaddr;
             }
           }
           case group {
             leaf group {
               description "Show specified group";
               type string {
                 length "1 .. 32";
               }
             }
           }
           case group-id {
             leaf group-id {
               description "Show specified group id";
               type uint32 {
                 range "1 .. 65535";
               }
             }
           }
           case index {
             leaf index {
               description "Index of security association";
               type uint32;
             }
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
   }
   rpc get-security-group-vpn-svr-svr-cluster-info {
     description "Show group vpn server cluster information";
     input {
       leaf level {
         default "brief";
         type enumeration {
           enum "brief" {
             description "Show brief output (default)";
           }
           enum "detail" {
             description "Show detailed output";
           }
         }
       }
       container group_cluster_index_choice {
         description "Specify group, group-id or peer gateway filter";
         choice group_cluster_index_choice_c {
           case group {
             leaf group {
               description "Show specified group";
               type string {
                 length "1 .. 32";
               }
             }
           }
           case group-id {
             leaf group-id {
               description "Show specified group id";
               type uint32 {
                 range "1 .. 65535";
               }
             }
           }
           case peer-gateway {
             leaf peer-gateway {
               description "Show specified peer server gateway name";
               type string {
                 length "1 .. 32";
               }
             }
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
   }
   rpc get-security-group-vpn-server-stats {
     description "Show group server statistics";
     input {
       container group_choice {
         description "Specify a group by name or id";
         choice group_choice_c {
           case group {
             leaf group {
               description "Show specified group";
               type string {
                 length "1 .. 32";
               }
             }
           }
           case group-id {
             leaf group-id {
               description "Show specified group id";
               type uint32 {
                 range "1 .. 65535";
               }
             }
           }
         }
       }
       leaf fpc {
         description "FPC slot number";
         type uint32 {
           range "0 .. 63";
         }
       }
       leaf pic {
         description "PIC slot number";
         type uint32 {
           range "0 .. 3";
         }
       }
       leaf kmd-instance {
         description "Name of KMD instance or 'all'";
         default "all";
         type string {
           junos:posix-pattern "^[a-zA-Z0-9_-]{1,63}$";
           junos:pattern-message "KMD instance name is a string consisting of up to   63 letters, numbers, dashes and underscores";
         }
       }
     }
   }
   rpc get-internal-security-association {
     description "Show internal security association";
   }
   rpc get-idp-application-system-cache {
     description "Show IDP application system cache";
     output {
       container idp-application-system-cache-information {
         uses idp-application-system-cache-information-block;
       }
     }
   }
   rpc get-idp-active-policy {
     description "Show active IDP policy";
     status deprecated;
     output {
       container idp-version-information {
         uses idp-version-information-block;
       }
     }
   }
   rpc get-idp-policy-commit-status {
     description "Show the status of ongoing policy compilation and load";
     input {
       leaf clear {
         description "Clears the policy commit status";
         type empty;
       }
     }
     output {
       container idp-policy-commit-status {
         uses idp-policy-commit-status-block;
       }
     }
   }
   rpc get-idp-security-package-information {
     description "Show the version of currently installed security-package";
     output {
       container idp-security-package-information {
         uses idp-security-package-information-block;
       }
     }
   }
   rpc get-idp-recent-security-package-information {
     description "List ten most recent security package versions";
     output {
       container idp-recent-security-package-information {
         uses idp-recent-security-package-information-block;
       }
     }
   }
   rpc get-idp-memory-information {
     description "Show IDP data plane memory statistics";
     output {
       container idp-memory-information {
         uses idp-memory-information-block;
       }
     }
   }
   rpc get-idp-subscriber-policy-list {
     description "Show the list of currently installed policies";
     output {
       container idp-subscriber-policy-list {
         uses idp-subscriber-policy-list-block;
       }
     }
   }
   rpc get-idp-policy-template-information {
     description "Show available policy templates";
     output {
       leaf idp-policy-template-information {
         type string;
         description "List available IDP policy templates";
       }
     }
   }
   rpc get-idp-status-information {
     description "Show IDP status";
     output {
       container idp-status-information {
         uses idp-status-information-block;
       }
     }
   }
   rpc get-idp-detail-status-information {
     description "Show IDP detail status";
     output {
       container idp-detail-status-information {
         uses idp-detail-status-information-block;
       }
     }
   }
   rpc get-idp-predefined-attack-groups {
     description "Show predefined attack groups";
     output {
       container idp-predefined-attack-groups {
         uses idp-predefined-attack-groups-block;
       }
     }
   }
   rpc get-idp-predefined-attack-group-filters {
     description "Configure filters";
     input {
       leaf category {
         description "Category of attack group";
         type string;
       }
     }
   }
   rpc get-idp-predefined-attacks {
     description "Show predefined attacks";
     output {
       container idp-predefined-attacks {
         uses idp-predefined-attacks-block;
       }
     }
   }
   rpc get-idp-predefined-attack-filters {
     description "Configure filters";
     input {
       leaf category {
         description "Category of attack";
         type string;
       }
       leaf severity {
         description "Severity of attack";
         type enumeration {
           enum "info" {
             description "Provide information of attack when it matches";
           }
           enum "warning" {
             description "The attack is a minor one";
           }
           enum "minor" {
             description "The attack is a minor one";
           }
           enum "major" {
             description "The attack is a major one";
           }
           enum "critical" {
             description "The attack is a critical one";
           }
         }
       }
       leaf direction {
         description "Direction of attack";
         type enumeration {
           enum "client-to-server" {
             description "Select attacks from client to server";
           }
           enum "server-to-client" {
             description "Select attacks from server to client";
           }
           enum "any" {
             description "Select attacks which are in any direction";
           }
           enum "exclude-client-to-server" {
             description "Filter out attacks from client to server";
           }
           enum "exclude-server-to-client" {
             description "Filter out attacks from server to client";
           }
           enum "exclude-any" {
             description "Filter out attacks which are in any direction";
           }
         }
       }
     }
   }
   rpc get-idp-counter-information {
     description "Show IDP counters";
     output {
       container idp-counter-information {
         uses idp-counter-information-block;
       }
     }
   }
   rpc get-idp-counters-packet {
     description "Show IDP Packet counters";
   }
   rpc get-idp-counters-tcp-reass {
     description "Show IDP Reassembler counters";
   }
   rpc get-idp-counters-ips {
     description "Show IPS counters";
   }
   rpc get-idp-counters-flow {
     description "Show IDP Flow counters";
   }
   rpc get-idp-counters-dfa {
     description "Show IDP DFA counters";
   }
   rpc get-idp-counters-log {
     description "Show IDP Log counters";
   }
   rpc get-idp-counters-pol-mngr {
     description "Show IDP Policy counters";
   }
   rpc get-idp-counters-packet-log {
     description "Show IDP Packet capture counters";
   }
   rpc get-idp-counters-appid {
     description "Show Application Identification counters";
   }
   rpc get-idp-counters-ssl-inspection {
     description "Show SSL Inspection counters";
   }
   rpc get-idp-counters-memory {
     description "Show IDP memory counters";
   }
   rpc get-idp-counters-action {
     description "Show IDP policy action counters";
   }
   rpc get-idp-counters-pdf-decoder {
     description "Show the PDF decoder counters";
   }
   rpc get-idp-counters-http-decoder {
     description "Show the HTTP decoder counters";
   }
   rpc get-idp-applications-information {
     description "Show IDP application statistics";
   }
   rpc get-idp-attack-table-information {
     description "Show IDP attack table";
   }
   rpc get-idp-attack-description-information {
     description "Show description of specified attack";
     input {
       leaf attack-name {
         description "Attack name";
         type string;
         mandatory true;
       }
     }
     output {
       container idp-attack-description-information {
         uses idp-attack-description-information-block;
       }
     }
   }
   rpc get-idp-attack-detail-information {
     description "Show details of specified attack";
     input {
       leaf attack-name {
         description "Attack name";
         type string;
         mandatory true;
       }
     }
     output {
       container idp-attack-detail-information {
         uses idp-attack-detail-information-block;
       }
     }
   }
   rpc get-idp-ssl-session-cache-information {
     description "Session ID cache";
     output {
       container get-idp-ssl-session-cache-information {
         uses get-idp-ssl-session-cache-information-block;
       }
     }
   }
   rpc get-idp-ssl-key-information {
     description "Show SSL keys";
     input {
       leaf key-name {
         description "Key name";
         type string {
           length "1 .. 31";
         }
       }
     }
     output {
       container idp-ssl-key-information {
         uses idp-ssl-key-information-block;
       }
     }
   }
   rpc get-idp-lsys-policy-association {
     description "Show IDP policy association";
     output {
       container idp-lsys-policy-association {
         uses idp-lsys-policy-association-block;
       }
     }
   }
   rpc get-eedebug-action-profile {
     description "Show current datapath-debug action profile";
   }
   rpc get-eedebug-events {
     description "Show current registered data path events";
   }
   rpc get-eedebug-counters {
     description "Show datapath counters";
   }
   rpc show-eedebug-capture {
     description "Show datapath debug capture file";
   }
   rpc get-alg-status {
     description "Show ALG status";
   }
   rpc get-alg-h323-counters {
     description "Show H323 counters";
   }
   rpc get-alg-mgcp-call-information {
     description "Show MGCP calls";
     input {
       leaf endpoint {
         description "Show MGCP call endpoint";
         type string {
           length "1 .. 63";
         }
       }
     }
   }
   rpc get-alg-mgcp-counter-information {
     description "Show MGCP counters";
   }
   rpc get-alg-mgcp-endpoint-information {
     description "Show MGCP endpoints";
     input {
       leaf endpoint-name {
         description "Show MGCP endpoint with identifier";
         type string {
           length "1 .. 63";
         }
       }
     }
   }
   rpc get-alg-msrpc-uuid2oid-table {
     description "Show MSRPC UUID to OID table";
   }
   rpc get-alg-sccp-calls {
     description "Show SCCP calls";
     input {
       leaf level {
         default "brief";
         type enumeration {
           enum "detail" {
             description "Display detailed call information";
           }
           enum "brief" {
             description "Display brief call information (default)";
           }
         }
       }
     }
   }
   rpc get-alg-sccp-counters {
     description "Show SCCP counters";
   }
   rpc get-alg-sip-call-information {
     description "Show SIP calls";
     input {
       leaf level {
         default "brief";
         type enumeration {
           enum "detail" {
             description "Display detailed call information";
           }
           enum "brief" {
             description "Display brief call information (default)";
           }
         }
       }
     }
   }
   rpc get-alg-sip-counter-information {
     description "Show SIP counters";
   }
   rpc get-alg-sip-rate-information {
     description "Show SIP rate";
   }
   rpc show-alg-ike-esp-state {
     description "Show all IKE-ESP ALG state information";
   }
   rpc show-alg-ike-esp-summary {
     description "Show IKE-ESP ALG summary";
   }
   rpc get-appfw-rule-set {
     description "Show security application firewall rule-set";
     input {
       container rule-set-choice {
         choice rule-set-choice_c {
           case rule-set-name {
             leaf rule-set-name {
               description "Show the rule-set information matching the given rule-set name";
               type string {
                 length "1 .. 64";
               }
               mandatory true;
             }
           }
           case all {
             leaf all {
               description "Show all rule-sets information";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-application-firewall-shadow-rules {
     description "Show security application firewall shadow-rules in one rule-set";
     input {
       leaf rule-set-name {
         description "Rule-set name";
         type string {
           length "1 .. 64";
         }
         mandatory true;
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-application-firewall-match-rule {
     description "Show matching rules in one rule-set";
     input {
       leaf rule-set-name {
         description "Rule-set name";
         type string {
           length "1 .. 64";
         }
         mandatory true;
       }
       leaf dynamic-application {
         description "Dynamic application name";
         type string;
         mandatory true;
       }
       leaf encrypted {
         description "Specify encrypted or plain-text rules";
         default "any";
         type enumeration {
           enum "yes" {
             description "Encrypted rule";
           }
           enum "no" {
             description "Non-encrypted rule";
           }
           enum "any" {
             description "Encrypted and non-encrypted rule";
           }
         }
       }
       leaf result-count {
         description "Number of rules to show";
         default "1";
         type uint32 {
           range "1 .. 128000";
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-avt-counters {
     description "Show Application tracking counters";
   }
   rpc show-utmd-status {
     description "Show security utm status";
   }
   rpc show-utmd-session {
     description "Show security utm session";
   }
   rpc show-utmd-session-fpc {
     description "Show security utm session fpc";
     input {
       leaf fpc-slot {
         description "FPC slot number";
         type uint32 {
           range "0 .. 63";
         }
       }
       leaf pic-slot {
         description "PIC slot number";
         type uint32 {
           range "0 .. 3";
         }
       }
     }
   }
   rpc show-anti-virus {
     description "Show anti-virus information";
   }
   rpc show-anti-virus-statistics {
     description "Show anti-virus statistics";
   }
   rpc show-anti-virus-statistics-fpc {
     description "Show anti-virus statistics fpc";
     input {
       leaf fpc-slot {
         description "FPC slot number";
         type uint32 {
           range "0 .. 63";
         }
       }
       leaf pic-slot {
         description "PIC slot number";
         type uint32 {
           range "0 .. 3";
         }
       }
     }
   }
   rpc show-anti-virus-status {
     description "Show anti-virus status";
   }
   rpc show-anti-virus-status-detail {
     description "Show anti-virus detailed status";
   }
   rpc anti-virus-status-fpc {
     description "Show anti-virus status fpc";
     input {
       leaf fpc-slot {
         description "FPC slot number";
         type uint32 {
           range "0 .. 63";
         }
       }
       leaf pic-slot {
         description "PIC slot number";
         type uint32 {
           range "0 .. 3";
         }
       }
     }
   }
   rpc show-web-filtering {
     description "Show web-filtering information";
   }
   rpc show-web-filtering-statistics {
     description "Show web-filtering statistics";
   }
   rpc show-web-filtering-statistics-fpc {
     description "Show web-filtering statistics fpc";
     input {
       leaf fpc-slot {
         description "FPC slot number";
         type uint32 {
           range "0 .. 63";
         }
       }
       leaf pic-slot {
         description "PIC slot number";
         type uint32 {
           range "0 .. 3";
         }
       }
     }
   }
   rpc show-web-filtering-status {
     description "Show web-filtering status";
   }
   rpc show-web-filtering-status-fpc {
     description "Show web-filtering status fpc";
     input {
       leaf fpc-slot {
         description "FPC slot number";
         type uint32 {
           range "0 .. 63";
         }
       }
       leaf pic-slot {
         description "PIC slot number";
         type uint32 {
           range "0 .. 3";
         }
       }
     }
   }
   rpc show-content-filtering {
     description "Show content-filtering information";
   }
   rpc show-content-filtering-statistics {
     description "Show content-filtering statistics";
   }
   rpc show-content-filtering-statistics-fpc {
     description "Show content-filtering statistics fpc";
     input {
       leaf fpc-slot {
         description "FPC slot number";
         type uint32 {
           range "0 .. 63";
         }
       }
       leaf pic-slot {
         description "PIC slot number";
         type uint32 {
           range "0 .. 3";
         }
       }
     }
   }
   rpc show-anti-spam {
     description "Show anti-spam information";
   }
   rpc show-anti-spam-statistics {
     description "Show anti-spam statistics";
   }
   rpc show-anti-spam-statistics-fpc {
     description "Show anti-spam statistics fpc";
     input {
       leaf fpc-slot {
         description "FPC slot number";
         type uint32 {
           range "0 .. 63";
         }
       }
       leaf pic-slot {
         description "PIC slot number";
         type uint32 {
           range "0 .. 3";
         }
       }
     }
   }
   rpc show-anti-spam-status {
     description "Show anti-spam status";
   }
   rpc get-security-dynamic-address {
     description "Security dynamic address name";
     input {
       leaf category-name {
         description "Source category";
         type enumeration {
           enum "IPFilter" {
             description "IPFilter";
           }
           enum "GeoIP" {
             description "GeoIP";
           }
           enum "CC" {
             description "Command and control";
           }
           enum "JWAS" {
             description "JWAS";
           }
           enum "Blacklist" {
             description "Blacklist";
           }
           enum "Whitelist" {
             description "Whitelist";
           }
           enum "Infected-Hosts" {
             description "Infected-Hosts";
           }
         }
       }
       leaf feed-name {
         description "Source feed name";
         type string {
           length "1 .. 63";
         }
       }
       leaf address-name {
         description "Dynamic address name";
         type string {
           length "1 .. 63";
         }
       }
       leaf ip-start {
         description "Numerically minimal IP address within the range";
         type ipaddr;
       }
       leaf ip-end {
         description "Numerically maximal IP address within the range";
         type ipaddr;
       }
       leaf instance {
         description "Dynamic address instance";
         type enumeration {
           enum "default" {
             description "Default instance";
           }
           enum "geoip" {
             description "GeoIP instance";
           }
           enum "advanced-anti-malware" {
             description "Instance for anti-malware solution";
           }
         }
       }
     }
   }
   rpc get-security-dynamic-address-summary {
     description "Summary about dynamic address";
     input {
       leaf instance {
         description "Dynamic address instance";
         type enumeration {
           enum "default" {
             description "Default instance";
           }
           enum "geoip" {
             description "GeoIP instance";
           }
           enum "advanced-anti-malware" {
             description "Instance for anti-malware solution";
           }
         }
       }
     }
   }
   rpc get-ssh-key-information {
     description "Show SSH identity brief information";
     input {
       leaf identity-name {
         description "Show brief information of specified identity";
         type string {
           junos:posix-pattern "^[[:alnum:]_-]+$";
           junos:pattern-message "Must be a string of letters, numbers, dashes or underscores";
         }
       }
     }
   }
   rpc get-ssh-key-public-information {
     description "Show SSH identity public key";
     input {
       leaf identity-name {
         description "Show public key of specified identity";
         type string {
           junos:posix-pattern "^[[:alnum:]_-]+$";
           junos:pattern-message "Must be a string of letters, numbers, dashes or underscores";
         }
         mandatory true;
       }
     }
   }
   rpc show-ds-lite-softwire-sc-infomation {
     description "Show softwire information";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc show-ds-lite-softwire-one-sc-information {
     description "Show Softwire Concentrator object";
     input {
       leaf softwire-name-str {
         description "Softwire Name";
         type string;
         mandatory true;
       }
       leaf start-id {
         description "Show softwire initiator info from start identifier";
         type uint32 {
           range "1 .. 100000";
         }
       }
       leaf count {
         description "Number of softwire initiator entries";
         type uint32 {
           range "1 .. 100000";
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-user-connection {
     description "Show Dynamic VPN user connection information";
     input {
       leaf level {
         default "detail";
         type enumeration {
           enum "terse" {
             description "Display terse output";
           }
           enum "detail" {
             description "Display detailed user connection information (default)";
           }
         }
       }
     }
   }
   rpc get-firewall-dynamic-policies {
     description "Show security firewall dynamic policies";
     input {
       leaf from-zone {
         description "Show the policy information matching the given source zone";
         type string;
       }
       leaf to-zone {
         description "Show the policy information matching the given destination zone";
         type string;
       }
       leaf detail {
         description "Show the detailed dynamic policy information";
         type empty;
       }
       leaf scope-id {
         description "Show the policy information matching the given scope policy id [4...MAX_POLICIES]";
         type uint32 {
           range "4 .. 4294967295";
         }
       }
     }
   }
   rpc get-flow-statistics-all {
     description "Show flow statistics";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc get-flow-status-all {
     description "Show flow status";
   }
   rpc get-flow-gate-information {
     description "Show gate information";
     input {
       leaf source-prefix {
         description "Source IP prefix or address";
         type ipprefix;
       }
       leaf destination-prefix {
         description "Destination IP prefix or address";
         type ipprefix;
       }
       leaf source-port {
         description "Source port";
         type uint32 {
           range "1 .. 65535";
         }
       }
       leaf destination-port {
         description "Destination port";
         type uint32 {
           range "1 .. 65535";
         }
       }
       leaf protocol {
         description "IP protocol number";
         type string;
       }
       leaf family {
         description "Protocol family";
         type enumeration {
           enum "inet" {
             description "Show IPv4";
           }
           enum "inet6" {
             description "Show IPv6/IPv6-NATPT";
           }
         }
       }
       leaf level {
         default "brief";
         type enumeration {
           enum "summary" {
             description "Show output summary";
           }
           enum "brief" {
             description "Show brief output (default)";
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-flow-cp-session {
     description "Show CP sessions";
     input {
       leaf source-prefix {
         description "Source IP prefix or address";
         type ipprefix;
       }
       leaf destination-prefix {
         description "Destination IP prefix or address";
         type ipprefix;
       }
       leaf source-port {
         description "Source port";
         type uint32 {
           range "1 .. 65535";
         }
       }
       leaf destination-port {
         description "Destination port";
         type uint32 {
           range "1 .. 65535";
         }
       }
       leaf protocol {
         description "IP protocol number";
         type string;
       }
       leaf family {
         description "Protocol family";
         type enumeration {
           enum "inet" {
             description "Show IPv4";
           }
           enum "inet6" {
             description "Show IPv6/IPv6-NATPT";
           }
         }
       }
       leaf level {
         default "terse";
         type enumeration {
           enum "summary" {
             description "Show output summary";
           }
           enum "terse" {
             description "Show terse output (default)";
           }
         }
       }
       container lsys {
         choice lsys_c {
           case logical-system {
             leaf logical-system {
               description "Logical-system name";
               type string;
             }
           }
           case root-logical-system {
             leaf root-logical-system {
               description "Root logical-system (default)";
               type empty;
             }
           }
         }
       }
       leaf conn-tag {
         description "Session connection tag";
         type uint32 {
           range "0 .. 4294967295";
         }
       }
     }
   }
   rpc get-flow-session-information {
     description "Show session table";
     input {
       leaf source-prefix {
         description "Source IP prefix or address";
         type ipprefix;
       }
       leaf destination-prefix {
         description "Destination IP prefix or address";
         type ipprefix;
       }
       leaf source-port {
         description "Source port";
         type uint32 {
           range "1 .. 65535";
         }
       }
       leaf destination-port {
         description "Destination port";
         type uint32 {
           range "1 .. 65535";
         }
       }
       leaf protocol {
         description "IP protocol number";
         type string;
       }
       leaf level {
         default "brief";
         type enumeration {
           enum "summary" {
             description "Show output summary";
           }
           enum "brief" {
             description "Show brief output (default)";
           }
           enum "extensive" {
             description "Show detailed output";
           }
         }
       }
       leaf enc {
         type enumeration {
           enum "encrypted" {
             description "Show encrypted traffic";
           }
         }
       }
       leaf add-on {
         type enumeration {
           enum "idp" {
             description "IDP sessions";
           }
           enum "tunnel" {
             description "Tunnel sessions";
           }
           enum "nat" {
             description "Sessions with network address translation";
           }
           enum "services-offload" {
             description "Services-offload sessions";
           }
           enum "resource-manager" {
             description "Sessions with resource manager";
           }
           enum "application-firewall" {
             description "Show application-firewall sessions";
           }
           enum "application-traffic-control" {
             description "Show application-traffic-control sessions";
           }
           enum "security-intelligence" {
             description "Show security-intelligence sessions";
           }
           enum "advanced-anti-malware" {
             description "Show advanced-anti-malware sessions";
           }
         }
       }
       leaf application {
         description "Application protocol name";
         type enumeration {
           enum "dns" {
             description "Domain Name Service";
           }
           enum "ftp" {
             description "File Transfer Protocol";
           }
           enum "ignore" {
             description "Ignore application type";
           }
           enum "mgcp-ca" {
             description "MGCP-CA";
           }
           enum "mgcp-ua" {
             description "MGCP-UA";
           }
           enum "ms-rpc" {
             description "Microsoft RPC";
           }
           enum "pptp" {
             description "Point-to-Point Tunneling Protocol";
           }
           enum "sun-rpc" {
             description "Sun Microsystems RPC";
           }
           enum "q931" {
             description "Q.931";
           }
           enum "ras" {
             description "RAS";
           }
           enum "realaudio" {
             description "RealAudio";
           }
           enum "rsh" {
             description "Remote Shell";
           }
           enum "rtsp" {
             description "Real Time Streaming Protocol";
           }
           enum "sccp" {
             description "Skinny Client Control Protocol";
           }
           enum "sip" {
             description "Session Initiation Protocol";
           }
           enum "sqlnet-v2" {
             description "Oracle SQL*Net Version 2";
           }
           enum "talk" {
             description "Talk program";
           }
           enum "tftp" {
             description "Trivial File Transfer Protocol";
           }
           enum "http" {
             description "Hyper Text transfer protocol";
           }
           enum "https" {
             description "Secure HyperText Transfer Protocol";
           }
           enum "smtp" {
             description "Simple Mail Transfer Protocol";
           }
           enum "imap" {
             description "Internet Message Access Protocol";
           }
           enum "ssh" {
             description "Secure Shell";
           }
           enum "telnet" {
             description "Telnet Terminal Emulation Protocol";
           }
         }
       }
       leaf family {
         description "Protocol family";
         type enumeration {
           enum "inet" {
             description "Show IPv4";
           }
           enum "inet6" {
             description "Show IPv6/IPv6-NATPT";
           }
         }
       }
       leaf policy-id {
         description "Policy id value";
         type uint32 {
           range "1 .. 4294967295";
         }
       }
       leaf interface {
         description "Name of incoming or outgoing interface";
         type string;
       }
       leaf application-firewall-rule-set {
         description "Show application-firewall session by rule-set";
         type string;
       }
       leaf application-traffic-control-rule-set {
         description "Show application-traffic-control session by rule-set";
         type string;
       }
       leaf dynamic-application {
         description "Dynamic application name";
         type string;
       }
       leaf dynamic-application-group {
         description "Dynamic application group name";
         type string;
       }
       leaf start-identifier {
         description "Show sessions from this start identifier";
         type uint32 {
           range "1 .. 4294967295";
         }
       }
       leaf count {
         description "Number of entries to show";
         type uint32 {
           range "1 .. 4294967295";
         }
       }
       container lsys {
         choice lsys_c {
           case logical-system {
             leaf logical-system {
               description "Logical-system name";
               type string;
             }
           }
           case root-logical-system {
             leaf root-logical-system {
               description "Root logical-system (default)";
               type empty;
             }
           }
         }
       }
       leaf conn-tag {
         description "Session connection tag";
         type uint32 {
           range "0 .. 4294967295";
         }
       }
     }
   }
   rpc get-flow-session-by-identifier {
     description "Show session with specified session identifier";
     input {
       leaf session-identifier {
         description "Session identifier";
         type uint32 {
           range "1 .. 4294967295";
         }
         mandatory true;
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-flow-session-summary-idp {
     description "Show IDP session summary";
     status deprecated;
     output {
       container idp-session-summary-information {
         uses idp-session-summary-information-block;
       }
     }
   }
   rpc get-flow-ipaction-information {
     description "Show ip-action table";
     input {
       leaf source-prefix {
         description "Source IP prefix or address";
         type ipprefix;
       }
       leaf destination-prefix {
         description "Destination IP prefix or address";
         type ipprefix;
       }
       leaf source-port {
         description "Source port";
         type uint32 {
           range "1 .. 65535";
         }
       }
       leaf destination-port {
         description "Destination port";
         type uint32 {
           range "1 .. 65535";
         }
       }
       leaf protocol {
         description "IP protocol number";
         type string;
       }
       leaf family {
         description "Protocol family";
         type enumeration {
           enum "inet" {
             description "Show IPv4";
           }
           enum "inet6" {
             description "Show IPv6/IPv6-NATPT";
           }
         }
       }
       container lsys {
         choice lsys_c {
           case logical-system {
             leaf logical-system {
               description "Logical-system name";
               type string;
             }
           }
           case root-logical-system {
             leaf root-logical-system {
               description "Root logical-system (default)";
               type empty;
             }
           }
         }
       }
       leaf level {
         default "brief";
         type enumeration {
           enum "summary" {
             description "Show output summary";
           }
           enum "brief" {
             description "Show brief output (default)";
           }
         }
       }
     }
   }
   rpc get-flow-ipaction-information-all {
     description "Show all ip-action entries";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc get-forward-options-information {
     description "Show forward-options status";
   }
   rpc get-secure-wire-information {
     description "Show secure wire information";
     input {
       leaf secure-wire-name {
         description "Display specified secure wire";
         type string;
       }
     }
   }
   rpc get-mirror-filter {
     description "Show  mirror-filter with specified filter-name";
     input {
       container filter {
         choice filter_c {
           case name {
             leaf get-mirror-filter-by-name {
               description "Mirror filter name";
               type string;
               mandatory true;
             }
           }
           case all {
             leaf get-mirror-filter-all {
               description "List all mirror filters Counter";
               type empty;
             }
           }
         }
       }
     }
   }
   rpc get-firewall-authentication-users {
     description "Show current firewall authentication users";
     input {
       container lsys {
         choice lsys_c {
           case logical-system {
             leaf logical-system {
               description "Logical-system name";
               type string;
             }
           }
           case root-logical-system {
             leaf root-logical-system {
               description "Root logical-system (default)";
               type empty;
             }
           }
         }
       }
       container filter {
         choice filter_c {
           case identifier {
             leaf get-firewall-authentication-users-specific {
               description "Locate authentication entry by id";
               type uint32;
             }
           }
           case auth-type {
             leaf get-firewall-authentication-users {
               description "Show authentication entry matching the given auth-type";
               type enumeration {
                 enum "user-firewall" {
                   description "User firewall authentication";
                 }
                 enum "pass-through" {
                   description "Pass-through authentication";
                 }
                 enum "web-authentication" {
                   description "Web firewall authentication";
                 }
               }
             }
           }
           case address {
             leaf get-firewall-authentication-users-specific {
               description "Locate authentication entry by ip address";
               type ipprefix;
             }
           }
           case from-zone {
             leaf from-zone {
               description "Show authentication entry matching the given source zone, null for web-auth and userfw-auth";
               type string;
             }
           }
           case to-zone {
             leaf to-zone {
               description "Show authentication entry matching the given destination zone, null for web-auth and userfw-auth";
               type string;
             }
           }
         }
       }
     }
   }
   rpc get-firewall-authentication-history {
     description "Show firewall authentication history";
     input {
       container lsys {
         choice lsys_c {
           case logical-system {
             leaf logical-system {
               description "Logical-system name";
               type string;
             }
           }
           case root-logical-system {
             leaf root-logical-system {
               description "Root logical-system (default)";
               type empty;
             }
           }
         }
       }
       container filter {
         choice filter_c {
           case identifier {
             leaf get-firewall-authentication-history-specific {
               description "Locate authentication history by id";
               type uint32;
             }
           }
           case address {
             leaf get-firewall-authentication-history-specific {
               description "Locate authentication history by ip address";
               type ipprefix;
             }
           }
           case from-zone {
             leaf from-zone {
               description "Show authentication history matching the given source zone, null for web-auth and userfw-auth";
               type string;
             }
           }
           case to-zone {
             leaf to-zone {
               description "Show authentication history matching the given destination zone, null for web-auth and userfw-auth";
               type string;
             }
           }
         }
       }
     }
   }
   rpc get-security-screen-ids-data {
     description "Show screen data";
   }
   rpc get-security-screen-ids-status {
     description "Show status of screen object";
     input {
       leaf screen-name {
         description "Screen name";
         type string;
         mandatory true;
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-ids-statistics {
     description "Show screen attack statistics information";
     input {
       container filter {
         choice filter_c {
           case zone {
             leaf zone {
               description "IDS statistics zone";
               type string;
             }
           }
           case interface {
             leaf interface {
               description "IDS statistics interface";
               type string;
             }
           }
         }
       }
       leaf ip {
         description "IDS statistics ip";
         type enumeration {
           enum "tunnel" {
             description "IDS statistics ip tunnel";
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-destination-nat-pool-information {
     description "Show destination NAT address-pool information";
     input {
       container pool-choice {
         choice pool-choice_c {
           case pool-name {
             leaf pool-name {
               description "Destination address pool name";
               type string {
                 length "1 .. 32";
               }
               mandatory true;
             }
           }
           case all {
             leaf all {
               description "Display all destination NAT address-pool information";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-destination-nat-rule-sets-information {
     description "Show destination NAT rule-set information";
     input {
       container rule-choice {
         choice rule-choice_c {
           case rule-name {
             leaf rule-name {
               description "Destination NAT rule name";
               type string {
                 length "1 .. 32";
               }
               mandatory true;
             }
           }
           case all {
             leaf all {
               description "Display all destination NAT rule-sets information";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-destination-nat-rule-application-information {
     description "Show destination NAT rule application information";
     input {
       container rule-choice {
         choice rule-choice_c {
           case rule-name {
             leaf rule-name {
               description "Destination NAT rule name";
               type string {
                 length "1 .. 32";
               }
               mandatory true;
             }
           }
           case all {
             leaf all {
               description "Display all destination NAT rule with application configured information";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc retrieve-destination-nat-summary-information {
     description "Show destination NAT summary information";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc retrieve-source-nat-pool-information {
     description "Show source NAT information of this pool";
     input {
       container pool-choice {
         choice pool-choice_c {
           case pool-name {
             leaf pool-name {
               description "Source address pool name";
               type string;
               mandatory true;
             }
           }
           case all {
             leaf all {
               description "Display all source NAT pool information";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-persist-nat-all {
     description "Show all persistent NAT information";
     input {
       container lsys {
         choice lsys_c {
           case logical-system {
             leaf logical-system {
               description "Logical-system name";
               type string;
             }
           }
           case root-logical-system {
             leaf root-logical-system {
               description "Root logical-system (default)";
               type empty;
             }
           }
         }
       }
       leaf family {
         description "Protocol family";
         type enumeration {
           enum "inet" {
             description "Show IPv4";
           }
           enum "inet6" {
             description "Show IPv6/IPv6-NATV6V4";
           }
         }
       }
     }
   }
   rpc get-persist-nat-sum {
     description "Show persistent NAT summary information";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc retrieve-persist-nat-pool-information {
     description "Show persistent NAT information of this pool";
     input {
       leaf pool-name {
         description "Source NAT pool name";
         type string;
         mandatory true;
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-persist-nat-interface-information {
     description "Show persistent NAT information of this interface";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc retrieve-persist-nat-ip-port-information {
     description "Show persistent NAT information of internal IP and port";
     input {
       leaf ip {
         description "Internal IP address";
         type ipaddr;
         mandatory true;
       }
       leaf internal-port {
         description "Internal port";
         type uint16;
       }
       leaf internal-protocol {
         description "Internal protocol";
         type string;
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc retrieve-source-nat-paired-address-information {
     description "Show paired address information";
     input {
       leaf pool-name {
         description "Address pool name";
         type string;
       }
       container ip-choice {
         choice ip-choice_c {
           case internal-ip {
             leaf internal-ip {
               description "Internal IP address";
               type ipaddr;
             }
           }
           case xlated-ip {
             leaf xlated-ip {
               description "Xlated IP address";
               type ipaddr;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-source-nat-rule-sets-information {
     description "Show source NAT rule-set information";
     input {
       container rule-choice {
         choice rule-choice_c {
           case rule-name {
             leaf rule-name {
               description "Source NAT rule name";
               type string {
                 length "1 .. 32";
               }
               mandatory true;
             }
           }
           case all {
             leaf all {
               description "Display all source NAT rule-sets information";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-source-nat-rule-application-information {
     description "Show source NAT rule application information";
     input {
       container rule-choice {
         choice rule-choice_c {
           case rule-name {
             leaf rule-name {
               description "Source NAT rule name";
               type string {
                 length "1 .. 32";
               }
               mandatory true;
             }
           }
           case all {
             leaf all {
               description "Display all source NAT rule with application configured information";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc retrieve-source-nat-summary {
     description "Show source NAT summary information";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc get-static-nat-rule-information {
     description "Show static NAT rule information";
     input {
       container rule-choice {
         choice rule-choice_c {
           case rule-name {
             leaf rule-name {
               description "Static NAT rule name";
               type string {
                 length "1 .. 32";
               }
               mandatory true;
             }
           }
           case all {
             leaf all {
               description "Display all static NAT rule information";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-interface-nat-ports-information {
     description "Show interface nat ports information";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc get-incoming-table-information {
     description "Show incoming table information";
     status deprecated;
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc retrieve-source-nat-pool-resource-usage {
     description "Show source pool resource usage information";
     input {
       container pool-choice {
         choice pool-choice_c {
           case pool-name {
             leaf pool-name {
               description "Source address pool name";
               type string;
               mandatory true;
             }
           }
           case all {
             leaf all {
               description "Display all source NAT pool resource usage";
               type empty;
             }
           }
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-firewall-policies {
     description "Show security firewall policies";
     input {
       leaf from-zone {
         description "Show the policy information matching the given source zone";
         type string;
       }
       leaf to-zone {
         description "Show the policy information matching the given destination zone";
         type string;
       }
       leaf policy-name {
         description "Show the policy information matching the given policy name";
         type string;
       }
       leaf detail {
         description "Show the detailed information";
         type empty;
       }
       leaf zone-context {
         description "Show the count of policies in each context (from-zone and to-zone)";
         type empty;
       }
       leaf start {
         description "Show the policies from a given position";
         type uint32 {
           range "1 .. 65535";
         }
       }
       leaf count {
         description "Number of policies to show";
         type uint32 {
           range "1 .. 65535";
         }
       }
       leaf application-firewall {
         description "Show the information of application-firewall";
         type empty;
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-security-policies-hit-count {
     description "Show the hit count of policies";
     input {
       leaf from-zone {
         description "Show the policy hit-count matching the given source zone";
         type string;
       }
       leaf to-zone {
         description "Show the policy hit-count matching the given destination zone";
         type string;
       }
       leaf order {
         description "Policy order";
         type enumeration {
           enum "ascending" {
             description "Ascending order";
           }
           enum "descending" {
             description "Descending order";
           }
         }
       }
       leaf less-than {
         description "Maximum hit-count ";
         type uint32 {
           range "0 .. 4294967295";
         }
       }
       leaf greater-than {
         description "Minimum hit-count ";
         type uint32 {
           range "0 .. 4294967295";
         }
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc get-global-firewall-policies {
     description "Show the policy information of global policies";
     input {
       leaf policy-name {
         description "Show the policy information matching the given policy name";
         type string;
       }
       leaf detail {
         description "Show the detailed information";
         type empty;
       }
       leaf zone-context {
         description "Show the count of policies in each context (from-zone and to-zone)";
         type empty;
       }
       leaf start {
         description "Show the policies from a given position";
         type uint32 {
           range "1 .. 65535";
         }
       }
       leaf count {
         description "Number of policies to show";
         type uint32 {
           range "1 .. 65535";
         }
       }
       leaf application-firewall {
         description "Show the information of application-firewall";
         type empty;
       }
       container lsys {
         choice lsys_c {
           case logical-system {
             leaf logical-system {
               description "Logical-system name";
               type string;
             }
           }
           case root-logical-system {
             leaf root-logical-system {
               description "Root logical-system (default)";
               type empty;
             }
           }
         }
       }
     }
   }
   rpc unknown-source-identity-of-policies {
     description "Show the unknown-source-identity of policy";
   }
   rpc match-firewall-policies {
     description "Show security match policies";
     input {
       container lsys {
         choice lsys_c {
           case logical-system {
             leaf logical-system {
               description "Logical-system name";
               type string;
             }
           }
           case root-logical-system {
             leaf root-logical-system {
               description "Root logical-system (default)";
               type empty;
             }
           }
         }
       }
       leaf from-zone {
         description "Match policy for the given source zone";
         type string;
         mandatory true;
       }
       leaf to-zone {
         description "Match policy for the given destination zone";
         type string;
         mandatory true;
       }
       leaf source-ip {
         description "Match policy for the given source IP";
         type string;
         mandatory true;
       }
       leaf destination-ip {
         description "Match policy for the given destination IP";
         type string;
         mandatory true;
       }
       leaf source-port {
         description "Match policy for the given source port";
         type uint32 {
           range "1 .. 65535";
         }
         mandatory true;
       }
       leaf destination-port {
         description "Match policy for the given destination port";
         type uint32 {
           range "1 .. 65535";
         }
         mandatory true;
       }
       leaf protocol {
         description "Match policy for the given protocol";
         type string;
         mandatory true;
       }
       leaf result-count {
         description "Expected results count (optional)";
         type uint32 {
           range "1 .. 16";
         }
       }
       leaf source-identity {
         description "Match policy for the given roles (optional)";
         type string {
           junos:posix-pattern "!^any$";
           junos:pattern-message "source identity must not be any";
         }
       }
     }
   }
   rpc match-global-policies {
     description "Match global policy";
     input {
       container lsys {
         choice lsys_c {
           case logical-system {
             leaf logical-system {
               description "Logical-system name";
               type string;
             }
           }
           case root-logical-system {
             leaf root-logical-system {
               description "Root logical-system (default)";
               type empty;
             }
           }
         }
       }
       leaf source-ip {
         description "Match policy for the given source IP";
         type string;
         mandatory true;
       }
       leaf destination-ip {
         description "Match policy for the given destination IP";
         type string;
         mandatory true;
       }
       leaf source-port {
         description "Match policy for the given source port";
         type uint32 {
           range "1 .. 65535";
         }
         mandatory true;
       }
       leaf destination-port {
         description "Match policy for the given destination port";
         type uint32 {
           range "1 .. 65535";
         }
         mandatory true;
       }
       leaf protocol {
         description "Match policy for the given protocol";
         type string;
         mandatory true;
       }
       leaf result-count {
         description "Expected results count (optional)";
         type uint32 {
           range "1 .. 16";
         }
       }
       leaf source-identity {
         description "Match policy for the given roles (optional)";
         type string {
           junos:posix-pattern "!^any$";
           junos:pattern-message "source identity must not be any";
         }
       }
       leaf from-zone {
         description "Match policy for the given source zone (optional)";
         type string;
       }
       leaf to-zone {
         description "Match policy for the given destination zone (optional)";
         type string;
       }
     }
   }
   rpc get-firewall-policy-dns-cache {
     description "Show DNS cache of firewall policy";
     input {
       leaf dns-name {
         description "Show DNS cache matching the given DNS name";
         type string;
       }
     }
   }
   rpc shadow-firewall-policies {
     description "Show security shadow policies";
     input {
       container lsys {
         choice lsys_c {
           case logical-system {
             leaf logical-system {
               description "Logical-system name";
               type string;
             }
           }
           case root-logical-system {
             leaf root-logical-system {
               description "Root logical-system (default)";
               type empty;
             }
           }
         }
       }
       leaf from-zone {
         description "Show shadow policy information for the given source zone";
         type string;
         mandatory true;
       }
       leaf to-zone {
         description "Show shadow policy information for the given destination zone";
         type string;
         mandatory true;
       }
       leaf policy {
         description "Show shadow policy information for the given policy";
         type string;
       }
       leaf reverse {
         description "Show the policies which shadows the given policy";
         type empty;
       }
     }
   }
   rpc shadow-global-policies {
     description "Shadow policy information for global policy";
     input {
       container lsys {
         choice lsys_c {
           case logical-system {
             leaf logical-system {
               description "Logical-system name";
               type string;
             }
           }
           case root-logical-system {
             leaf root-logical-system {
               description "Root logical-system (default)";
               type empty;
             }
           }
         }
       }
       leaf policy {
         description "Show shadow policy information for the given policy";
         type string;
       }
       leaf reverse {
         description "Show the policies which shadows the given policy";
         type empty;
       }
     }
   }
   rpc get-resmgr-group-active {
     description "Show active resource manager group service information";
     input {
       leaf group-number {
         description "Show active resource manager group";
         type uint32;
       }
     }
   }
   rpc get-resmgr-resource-active {
     description "Show active resource manager resource service information";
     input {
       leaf resource-number {
         description "Show active resource manager resource";
         type uint32;
       }
     }
   }
   rpc get-resmgr-settings {
     description "Show resource manager settings information";
   }
   rpc get-resource-manager-summary {
     description "Show resource manager summary information";
   }
   rpc get-security-report-threats-summary {
     description "Show threat indicator summary";
   }
   rpc get-security-report-threats-statistics {
     description "Show the threat statistics";
   }
   rpc get-security-report-threats-recent-activity {
     description "Show the most recent threat activities";
   }
   rpc get-security-report-traffic-statistics {
     description "Show the traffic statistics";
   }
   rpc get-performance-summary-information {
     description "Show security SPU monitoring information";
   }
   rpc get-spu-monitoring-information {
     description "Show the FPC slot security monitoring information";
     input {
       leaf fpc-slot {
         description "FPC slot number";
         type uint32 {
           range "0 .. 63";
         }
         mandatory true;
       }
     }
   }
   rpc get-performance-spu-information {
     description "Show security performance SPU information";
     input {
       leaf fpc {
         description "FPC slot number";
         type uint32 {
           range "0 .. 63";
         }
       }
       leaf pic {
         description "PIC slot number";
         type uint32 {
           range "0 .. 3";
         }
       }
     }
   }
   rpc get-performance-session-information {
     description "Show security performance session information";
     input {
       leaf fpc {
         description "FPC slot number";
         type uint32 {
           range "0 .. 63";
         }
       }
       leaf pic {
         description "PIC slot number";
         type uint32 {
           range "0 .. 3";
         }
       }
     }
   }
   rpc get-userfw-local-auth-table-all {
     description "Show the entire local user authentication table";
     input {
       leaf level {
         default "brief";
         type enumeration {
           enum "brief" {
             description "Show brief output (default)";
           }
           enum "extensive" {
             description "Show extensive output";
           }
         }
       }
     }
   }
   rpc get-userfw-local-auth-table-ip {
     description "Show local user authentication information for the specified ip-address";
     input {
       leaf ip-address {
         description "IP address";
         type ipaddr;
         mandatory true;
       }
     }
   }
   rpc get-userfw-local-auth-table-user {
     description "Show local user authentication information for the specified user";
     input {
       leaf user-name {
         description "User name";
         type string {
           length "1 .. 64";
         }
         mandatory true;
       }
     }
   }
   rpc get-userfw-local-auth-table-role {
     description "Show local user authentication information for the specified role";
     input {
       leaf role-name {
         description "Role name";
         type string {
           length "1 .. 63";
         }
         mandatory true;
       }
     }
   }
   rpc get-userfw-local-auth-table-start {
     description "Show local user authentication table information from a given position";
     input {
       leaf start {
         type uint32 {
           range "1 .. 65535";
         }
         mandatory true;
       }
       leaf count {
         description "Number of local user authentication table entries to show";
         type uint32 {
           range "1 .. 65535";
         }
         mandatory true;
       }
     }
   }
   rpc get-userfw-role-info {
     description "Show all information";
   }
   rpc get-userfw-role-info-start {
     description "Show information from a given position";
     input {
       leaf start {
         type uint32 {
           range "1 .. 65535";
         }
         mandatory true;
       }
       leaf count {
         description "Number of entries to show";
         type uint32 {
           range "1 .. 65535";
         }
         mandatory true;
       }
     }
   }
   rpc get-userfw-user-info {
     description "Show all information";
   }
   rpc get-userfw-user-info-start {
     description "Show information from a given position";
     input {
       leaf start {
         type uint32 {
           range "1 .. 65535";
         }
         mandatory true;
       }
       leaf count {
         description "Number of entries to show";
         type uint32 {
           range "1 .. 65535";
         }
         mandatory true;
       }
     }
   }
   rpc get-userfw-source-identity-info {
     description "Show all information";
   }
   rpc get-userfw-source-identity-info-start {
     description "Show information from a given position";
     input {
       leaf start {
         type uint32 {
           range "1 .. 65535";
         }
         mandatory true;
       }
       leaf count {
         description "Number of entries to show";
         type uint32 {
           range "1 .. 65535";
         }
         mandatory true;
       }
     }
   }
   rpc get-zones-information {
     description "Show security zone information";
     input {
       container lsys {
         choice lsys_c {
           case logical-system {
             leaf logical-system {
               description "Logical-system name";
               type string;
             }
           }
           case root-logical-system {
             leaf root-logical-system {
               description "Root logical-system (default)";
               type empty;
             }
           }
         }
       }
       container filter {
         choice filter_c {
           case name {
             leaf get-zones-named-information {
               description "Show information for a specified zone";
               type string;
             }
           }
           case type {
             leaf type {
               description "Show information for zones of a specified type";
               type enumeration {
                 enum "functional" {
                   description "Show information for functional zones";
                 }
                 enum "security" {
                   description "Show information for security zones";
                 }
               }
             }
           }
         }
       }
       leaf level {
         default "detail";
         type enumeration {
           enum "terse" {
             description "Display terse output";
           }
           enum "detail" {
             description "Display detailed output (default)";
           }
         }
       }
     }
   }
   rpc show-apbr-statistics {
     description "Show advance-policy-based-routing statistics";
   }
   rpc show-apbr-profile {
     description "Show advance-policy-based-routing profile";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc show-apbr-status {
     description "Show advance-policy-based-routing status";
   }
   rpc get-security-gprs-gtp-tunnels {
     description "Show security gtp tunnels";
     input {
       leaf level {
         default "brief";
         type enumeration {
           enum "summary" {
             description "Show the summary of GTP tunnels";
           }
           enum "brief" {
             description "Show a brief of each GTP tunnel (default)";
           }
           enum "detail" {
             description "Show a detail of each GTP tunnel";
           }
         }
       }
     }
   }
   rpc get-security-gprs-gtp-counters {
     description "Show security gtp counters";
     input {
       container counter-type {
         choice counter-type_c {
           case path-rate-limit {
             leaf path-rate-limit {
               description "Show path-rate-limit counters";
               type empty;
             }
           }
           case error {
             leaf error {
               description "Show GTP error counters";
               type empty;
             }
           }
           case tunnel {
             leaf tunnel {
               description "Show GTP tunnel counters";
               type empty;
             }
           }
           case packet {
             leaf packet {
               description "Show GTP packet counters";
               type empty;
             }
           }
           case request {
             leaf request {
               description "Show GTP request counters";
               type empty;
             }
           }
           case data-packet {
             leaf data-packet {
               description "Show GTP-U data packet counters";
               type empty;
             }
           }
           case ha {
             leaf ha {
               description "Show GTP HA counters";
               type empty;
             }
           }
           case all {
             leaf all {
               description "Show all GTP counters";
               type empty;
             }
           }
         }
       }
     }
   }
   rpc get-security-gprs-gtp-counters-message {
     description "Show GTP message counters";
     input {
       container message-type {
         choice message-type_c {
           case v0-create-pdp-req {
             leaf v0-create-pdp-req {
               description "Show GTPv0 create PDP context request message";
               type empty;
             }
           }
           case v0-create-pdp-rsp {
             leaf v0-create-pdp-rsp {
               description "Show GTPv0 create PDP context response message";
               type empty;
             }
           }
           case v0-update-pdp-req {
             leaf v0-update-pdp-req {
               description "Show GTPv0 update PDP context request message";
               type empty;
             }
           }
           case v0-update-pdp-rsp {
             leaf v0-update-pdp-rsp {
               description "Show GTPv0 update PDP context response message";
               type empty;
             }
           }
           case v0-delete-pdp-req {
             leaf v0-delete-pdp-req {
               description "Show GTPv0 delete PDP context request message";
               type empty;
             }
           }
           case v0-delete-pdp-rsp {
             leaf v0-delete-pdp-rsp {
               description "Show GTPv0 delete PDP context response message";
               type empty;
             }
           }
           case v0-create-aa-pdp-req {
             leaf v0-create-aa-pdp-req {
               description "Show GTPv0 create AA PDP context request message";
               type empty;
             }
           }
           case v0-create-aa-pdp-rsp {
             leaf v0-create-aa-pdp-rsp {
               description "Show GTPv0 create AA PDP context response message";
               type empty;
             }
           }
           case v0-delete-aa-pdp-req {
             leaf v0-delete-aa-pdp-req {
               description "Show GTPv0 delete AA PDP context request message";
               type empty;
             }
           }
           case v0-delete-aa-pdp-rsp {
             leaf v0-delete-aa-pdp-rsp {
               description "Show GTPv0 delete AA PDP context response message";
               type empty;
             }
           }
           case v0-sgsn-context-req {
             leaf v0-sgsn-context-req {
               description "Show GTPv0 sgsn context request message";
               type empty;
             }
           }
           case v0-sgsn-context-rsp {
             leaf v0-sgsn-context-rsp {
               description "Show GTPv0 sgsn context response message";
               type empty;
             }
           }
           case v0-sgsn-context-ack {
             leaf v0-sgsn-context-ack {
               description "Show GTPv0 sgsn context acknowledge message";
               type empty;
             }
           }
           case v0-others {
             leaf v0-others {
               description "Show GTPv0 others message";
               type empty;
             }
           }
           case v1-create-pdp-req {
             leaf v1-create-pdp-req {
               description "Show GTPv1 create PDP context request message";
               type empty;
             }
           }
           case v1-create-pdp-rsp {
             leaf v1-create-pdp-rsp {
               description "Show GTPv1 create PDP context response message";
               type empty;
             }
           }
           case v1-update-pdp-req {
             leaf v1-update-pdp-req {
               description "Show GTPv1 update PDP context request message";
               type empty;
             }
           }
           case v1-update-pdp-rsp {
             leaf v1-update-pdp-rsp {
               description "Show GTPv1 update PDP context response message";
               type empty;
             }
           }
           case v1-delete-pdp-req {
             leaf v1-delete-pdp-req {
               description "Show GTPv1 delete PDP context request message";
               type empty;
             }
           }
           case v1-delete-pdp-rsp {
             leaf v1-delete-pdp-rsp {
               description "Show GTPv1 delete PDP context response message";
               type empty;
             }
           }
           case v1-sgsn-context-req {
             leaf v1-sgsn-context-req {
               description "Show GTPv1 sgsn context request message";
               type empty;
             }
           }
           case v1-sgsn-context-rsp {
             leaf v1-sgsn-context-rsp {
               description "Show GTPv1 sgsn context response message";
               type empty;
             }
           }
           case v1-sgsn-context-ack {
             leaf v1-sgsn-context-ack {
               description "Show GTPv1 sgsn context acknowledge message";
               type empty;
             }
           }
           case v1-fwd-reloc-req {
             leaf v1-fwd-reloc-req {
               description "Show GTPv1 forward relocation request message";
               type empty;
             }
           }
           case v1-fwd-reloc-rsp {
             leaf v1-fwd-reloc-rsp {
               description "Show GTPv1 forward relocation response message";
               type empty;
             }
           }
           case v1-others {
             leaf v1-others {
               description "Show GTPv1 others message";
               type empty;
             }
           }
           case v2-create-session-req {
             leaf v2-create-session-req {
               description "Show GTPv2 create session request message";
               type empty;
             }
           }
           case v2-create-session-rsp {
             leaf v2-create-session-rsp {
               description "Show GTPv2 create session response message";
               type empty;
             }
           }
           case v2-delete-session-req {
             leaf v2-delete-session-req {
               description "Show GTPv2 delete session request message";
               type empty;
             }
           }
           case v2-delete-session-rsp {
             leaf v2-delete-session-rsp {
               description "Show GTPv2 delete session response message";
               type empty;
             }
           }
           case v2-create-bearer-req {
             leaf v2-create-bearer-req {
               description "Show GTPv2 create bearer request message";
               type empty;
             }
           }
           case v2-create-bearer-rsp {
             leaf v2-create-bearer-rsp {
               description "Show GTPv2 create bearer response message";
               type empty;
             }
           }
           case v2-modify-bearer-req {
             leaf v2-modify-bearer-req {
               description "Show GTPv2 modify bearer request message";
               type empty;
             }
           }
           case v2-modify-bearer-rsp {
             leaf v2-modify-bearer-rsp {
               description "Show GTPv2 modify bearer response message";
               type empty;
             }
           }
           case v2-delete-bearer-req {
             leaf v2-delete-bearer-req {
               description "Show GTPv2 delete bearer request message";
               type empty;
             }
           }
           case v2-delete-bearer-rsp {
             leaf v2-delete-bearer-rsp {
               description "Show GTPv2 delete bearer response message";
               type empty;
             }
           }
           case v2-context-req {
             leaf v2-context-req {
               description "Show GTPv2 context request message";
               type empty;
             }
           }
           case v2-context-rsp {
             leaf v2-context-rsp {
               description "Show GTPv2 context response message";
               type empty;
             }
           }
           case v2-context-ack {
             leaf v2-context-ack {
               description "Show GTPv2 context acknowledge message";
               type empty;
             }
           }
           case v2-fwd-reloc-req {
             leaf v2-fwd-reloc-req {
               description "Show GTPv2 forward relocation request message";
               type empty;
             }
           }
           case v2-fwd-reloc-rsp {
             leaf v2-fwd-reloc-rsp {
               description "Show GTPv2 forward relocation response message";
               type empty;
             }
           }
           case v2-create-ind-fwd-tnl-req {
             leaf v2-create-ind-fwd-tnl-req {
               description "Show GTPv2 create indirect forward tunnel request message";
               type empty;
             }
           }
           case v2-create-ind-fwd-tnl-rsp {
             leaf v2-create-ind-fwd-tnl-rsp {
               description "Show GTPv2 create indirect forward tunnel response message";
               type empty;
             }
           }
           case v2-others {
             leaf v2-others {
               description "Show GTPv2 others message";
               type empty;
             }
           }
           case brief {
             leaf brief {
               description "Show brief GTP messages";
               type empty;
             }
           }
         }
       }
     }
   }
   rpc get-gtp-gsn-statitics-all {
     description "Show GTP GSN statistics";
   }
   rpc get-security-gprs-sctp-counters {
     description "Show security sctp counters";
   }
   rpc get-sctp-counters-detail {
     description "Show the detailed sctp counter information";
   }
   rpc show-sctp-association {
     description "Show security sctp association";
     input {
       leaf source-ip {
         description "Match association for source IP";
         type ipaddr;
       }
       leaf source-port {
         description "Match association for source port";
         type uint32 {
           range "1 .. 65535";
         }
       }
       leaf destination-ip {
         description "Match association for destination IP";
         type ipaddr;
       }
       leaf destination-port {
         description "Match association for destination port";
         type uint32 {
           range "1 .. 65535";
         }
       }
       leaf guid {
         description "Match association for globally unique identifier";
         type string;
       }
       leaf level {
         type enumeration {
           enum "summary" {
             description "Show output summary";
           }
         }
       }
     }
   }
   rpc get-sctp-association-all {
     description "Show all sctp association entries";
   }
   rpc get-sctp-association-init {
     description "Show init sctp association entries";
   }
   rpc get-mka-session-information {
     description "Show MKA sessions information";
     output {
       container mka-session-information {
         uses mka-session-information-block;
       }
     }
   }
   rpc get-mka-session-interface-information {
     description "Show MKA session on this interface";
     input {
       leaf interface-name {
         description "Show MKA session for this interface";
         default "all";
         type interface-name;
       }
     }
   }
   rpc get-mka-statistics {
     description "Show MKA statistics";
     output {
       container mka-statistics {
         uses mka-statistics-block;
       }
     }
   }
   rpc get-mka-interface-statistics {
     description "Show MKA statistics on this interface";
     input {
       leaf interface-name {
         description "Show MKA statistics for this interface";
         default "all";
         type interface-name;
       }
     }
   }
   rpc get-macsec-connection-information {
     description "Show MAC Security connections information";
     output {
       container macsec-connection-information {
         uses macsec-connection-information-block;
       }
     }
   }
   rpc get-macsec-connection-interface-information {
     description "Show MAC security connections on this interface";
     input {
       leaf interface-name {
         description "Show MAC security connections for this interface";
         default "all";
         type interface-name;
       }
     }
   }
   rpc get-macsec-statistics {
     description "Show MAC Security statistics";
     input {
       leaf verbosity_level {
         default "brief";
         type enumeration {
           enum "brief" {
             description "Display brief output (default)";
           }
           enum "detail" {
             description "Display detailed output";
           }
         }
       }
     }
     output {
       container macsec-statistics {
         uses macsec-statistics-block;
       }
     }
   }
   rpc get-macsec-interface-statistics {
     description "Show MAC security statistics on this interface";
     input {
       leaf verbosity_level {
         default "brief";
         type enumeration {
           enum "brief" {
             description "Display brief output (default)";
           }
           enum "detail" {
             description "Display detailed output";
           }
         }
       }
       leaf interface-name {
         description "Show MAC security statistics for this interface";
         default "all";
         type interface-name;
       }
     }
   }
 grouping security-alarm-information-block {
   container brief {
     description "Information about all active security alarms";
     list security-alarm {
       description "Detailed information about an active security alarm";
       leaf security-alarm-id {
         type string;
         description "Alarm ID";
       }
       leaf security-alarm-time {
         type string;
         description "Time of the alarm";
       }
       leaf security-alarm-message {
         type string;
         description "Full message of the alarm";
       }
     }
   }
   container detail {
     description "Information about all active security alarms";
     list security-alarm {
       description "Detailed information about an active security alarm";
       leaf security-alarm-id {
         type string;
         description "Alarm ID";
       }
       leaf security-alarm-type {
         type string;
         description "Alarm type";
       }
       leaf security-alarm-time {
         type string;
         description "Time of the alarm";
       }
       leaf security-alarm-message {
         type string;
         description "Full message of the alarm";
       }
       leaf severity {
         type string;
         description "Syslog message severity";
       }
       container process {
         description "Process that generated the event";
         leaf name {
           type string;
           description "Syslog message tag name";
         }
         leaf pid {
           type int32;
           description "PID of the process that generated the event";
         }
       }
     }
   }
 }
 grouping security-log-information-block {
   container brief {
     description "Information about all active security events";
     list security-event {
       description "Detailed information about a security event";
       leaf security-event-time {
         type string;
         description "Time of the event";
       }
       leaf security-event-message {
         type string;
         description "Full message of the event";
       }
     }
   }
   container detail {
     description "Information about all active security events";
     list security-event {
       description "Detailed information about a security event";
       leaf security-event-id {
         type string;
         description "Event ID";
       }
       leaf security-event-time {
         type string;
         description "Time of the event";
       }
       leaf security-event-message {
         type string;
         description "Full message of the event";
       }
       leaf severity {
         type string;
         description "Syslog message severity";
       }
       leaf security-event-result {
         type string;
         description "Result of this event (success or failure)";
       }
       leaf security-event-username {
         type string;
         description "Username associated with event";
       }
       leaf security-event-interface-name {
         type string;
         description "Interface name associated with event";
       }
       leaf security-event-protocol {
         type string;
         description "Protocol associated with event";
       }
       leaf security-event-policy-name {
         type string;
         description "Policy name associated with event";
       }
       leaf security-event-destination-address {
         type string;
         description "Destination address associated with event";
       }
       leaf security-event-destination-port {
         type int32;
         description "Destination port associated with event";
       }
       leaf security-event-source-address {
         type string;
         description "Source address associated with event";
       }
       leaf security-event-source-port {
         type int32;
         description "Source port associated with event";
       }
       container process {
         description "Process that generated the event";
         leaf name {
           type string;
           description "Syslog message tag name";
         }
         leaf pid {
           type int32;
           description "PID of the process that generated the event";
         }
       }
     }
   }
 }
 grouping hakr-keychain-information-block {
   container brief {
     list hakr-keychain {
       description "Information about Keychain";
       leaf hakr-keychain-name {
         type string;
         description "Keychain name";
       }
       leaf hakr-keychain-active-send-key {
         type int32;
         description "Transmit key ID";
       }
       leaf hakr-keychain-active-receive-key {
         type int32;
         description "Receive key ID";
       }
       leaf hakr-keychain-next-send-key {
         type string;
         description "Next transmit key";
       }
       leaf hakr-keychain-next-receive-key {
         type string;
         description "Next receive key";
       }
       leaf hakr-keychain-next-key-time {
         type string;
         description "Key transition time";
       }
       leaf hakr-keychain-tolerance {
         type int32;
         description "Clock skew tolerance";
       }
       list hakr-keys {
         description "Information about the clients";
         leaf hakr-key-id {
           type string;
           description "Authentication element identifier";
         }
         leaf hakr-key-algorithm {
           type string;
           description "Authentication algorithm";
         }
         leaf hakr-key-state {
           type string;
           description "Authentication key operational state";
         }
         leaf hakr-key-options {
           type string;
           description "Authentication key options";
         }
         leaf hakr-key-start-time {
           type string;
           description "Time since the current session began (hours:minutes:seconds)";
         }
         leaf hakr-key-mode {
           type string;
           description "Authentication key mode";
         }
       }
     }
     list hakr-keys {
       description "Information about the clients";
     }
   }
   container detail {
     list hakr-keychain {
       description "Information about Keychain";
       leaf hakr-keychain-name {
         type string;
         description "Keychain name";
       }
       leaf hakr-keychain-active-send-key {
         type int32;
         description "Transmit key ID";
       }
       leaf hakr-keychain-active-receive-key {
         type int32;
         description "Receive key ID";
       }
       leaf hakr-keychain-next-send-key {
         type string;
         description "Next transmit key";
       }
       leaf hakr-keychain-next-receive-key {
         type string;
         description "Next receive key";
       }
       leaf hakr-keychain-next-key-time {
         type string;
         description "Key transition time";
       }
       leaf hakr-keychain-tolerance {
         type int32;
         description "Clock skew tolerance";
       }
       leaf hakr-sa-clients {
         type string;
         description "Keychain clients ";
       }
       list hakr-keys {
         description "Information about the clients";
         leaf hakr-key-id {
           type string;
           description "Authentication element identifier";
         }
         leaf hakr-key-algorithm {
           type string;
           description "Authentication algorithm";
         }
         leaf hakr-key-state {
           type string;
           description "Authentication key operational state";
         }
         leaf hakr-key-options {
           type string;
           description "Authentication key options";
         }
         leaf hakr-key-start-time {
           type string;
           description "Time since the current session began (hours:minutes:seconds)";
         }
         leaf hakr-key-mode {
           type string;
           description "Authentication key mode";
         }
       }
     }
     list hakr-keys {
       description "Information about the clients";
       leaf hakr-key-id {
         type string;
         description "Authentication element identifier";
       }
       leaf hakr-key-algorithm {
         type string;
         description "Authentication algorithm";
       }
       leaf hakr-key-state {
         type string;
         description "Authentication key operational state";
       }
       leaf hakr-key-options {
         type string;
         description "Authentication key options";
       }
       leaf hakr-key-start-time {
         type string;
         description "Time since the current session began (hours:minutes:seconds)";
       }
       leaf hakr-key-mode {
         type string;
         description "Authentication key mode";
       }
     }
   }
 }
 grouping x509-pki-certificate-info-list-block {
   container x509-certificate-info {
     description "Detailed information about an X.509 certificate";
     container verbose {
       description "Detailed information about an X.509 certificate";
       leaf identifier {
         type string;
         description "Certificate identifier";
       }
       leaf signature-algorithm {
         type string;
         description "Algorithm used by the CA to sign the certificate";
       }
       container public-key {
         description "Information about an X.509 public key";
         leaf public-key-algorithm {
           type string;
           description "Algorithm used for creating the subject public key";
         }
         leaf public-key-length {
           type int32;
           description "Length of X.509 public";
         }
         leaf public-key-verification-status {
           type string;
           description "Verification status of X.509 public key";
         }
       }
       list fingerprint {
         description "Fingerprint";
       }
       container issuer {
         description "Identifies the CA that issued certificate";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
       container subject {
         description "Information about certificate owner";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
     }
     container brief {
       description "Detailed information about an X.509 certificate";
       leaf identifier {
         type string;
         description "Certificate identifier";
       }
       leaf certificate-type {
         type string;
         description "X.509 certificate type";
       }
       leaf status {
         type string;
       }
       container issue-info {
         leaf recipient {
           type string;
         }
         leaf issued-by {
           type string;
         }
       }
       container public-key {
         description "Information about an X.509 public key";
         leaf public-key-algorithm {
           type string;
           description "Algorithm used for creating the subject public key";
         }
         leaf public-key-length {
           type int32;
           description "Length of X.509 public";
         }
         leaf public-key-verification-status {
           type string;
           description "Verification status of X.509 public key";
         }
       }
       container validity {
         description "Information about validity period for X.509 certificate";
         leaf not-before {
           type string;
           description "Start date of validity period";
         }
         leaf not-after {
           type string;
           description "End date of validity period";
         }
       }
       container issuer {
         description "Identifies the CA that issued certificate";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
       container subject {
         description "Information about certificate owner";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
     }
     container detail {
       description "Detailed information about an X.509 certificate";
       leaf identifier {
         type string;
         description "Certificate identifier";
       }
       leaf certificate-type {
         type string;
         description "X.509 certificate type";
       }
       leaf status {
         type string;
       }
       leaf version {
         type string;
         description "Certificate version";
       }
       leaf signature-algorithm {
         type string;
         description "Algorithm used by the CA to sign the certificate";
       }
       list serial-number-list {
         description "Serial numbers of one or more X.509 certificate";
         leaf serial-number-x509 {
           type string;
           description "Serial number of an X.509 certificate";
         }
       }
       container public-key {
         description "Information about an X.509 public key";
         leaf public-key-algorithm {
           type string;
           description "Algorithm used for creating the subject public key";
         }
         leaf public-key-length {
           type int32;
           description "Length of X.509 public";
         }
         leaf public-key-verification-status {
           type string;
           description "Verification status of X.509 public key";
         }
       }
       list fingerprint {
         description "Fingerprint";
         leaf fingerprint-content {
           type string;
         }
         leaf fingerprint-hash-algorithm {
           type string;
         }
       }
       list public-key-contents-list {
         leaf key-contents {
           type string;
           description "Contents of an X.509 public key";
         }
       }
       list subject-string-list {
         leaf subject-string {
           type string;
           description "Cerificate's distinguished name";
         }
       }
       list alternate-subject-list {
         leaf alternate-subject {
           type string;
           description "Series of alternate subject in X.509 certificate";
         }
       }
       list key-usage-list {
         leaf key-usage {
           type string;
           description "Purpose for which X.509 key is used";
         }
       }
       list distribution-crl-list {
         description "Information about one or more distribution certificate revocation lists";
         leaf distribution-crl {
           type string;
           description "Information about a distribution CRL";
         }
       }
       list authority-information-access-ocsp-list {
         description "Information about one or more ocsp authority-information-access locations";
         leaf authority-information-access-ocsp {
           type string;
           description "Information about ocsp authority-information-access locations";
         }
       }
       list certificate-policy-list {
         description "Certificate policy identifiers";
         leaf certificate-policy {
           type string;
           description "List of certificate policy identifiers";
         }
       }
       container validity {
         description "Information about validity period for X.509 certificate";
         leaf not-before {
           type string;
           description "Start date of validity period";
         }
         leaf not-after {
           type string;
           description "End date of validity period";
         }
       }
       container auto-re-enrollment {
         leaf auto-re-enrollment-status {
           type string;
           description "Auto-re-enrollment information";
         }
         leaf auto-re-enrollment-next-trigger-time {
           type string;
           description "Auto-re-enrollment next trigger time";
         }
       }
       container issuer {
         description "Identifies the CA that issued certificate";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
       container subject {
         description "Information about certificate owner";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
     }
   }
 }
 grouping x509-pkid-crl-information-list-block {
   container pkid-x509-crl-information {
     description "Detailed information about X.509 certificate revocation list";
     container brief {
       description "Detailed information about X.509 certificate revocation list";
       leaf identifier {
         type string;
         description "Certificate identifier";
       }
       leaf crl-version {
         type string;
         description "CRL version";
       }
       leaf crl-number {
         type string;
         description "CRL sequence number";
       }
       leaf crl-issuer {
         type string;
         description "CRL issuer name";
       }
       container crl-validity {
         description "Information about validity period for X.509 certificate revocation list";
         leaf effective-date {
           type string;
           description "Effective date of CRL";
         }
         leaf next-update {
           type string;
           description "Next update of CRL";
         }
       }
     }
     container detail {
       description "Detailed information about X.509 certificate revocation list";
       leaf identifier {
         type string;
         description "Certificate identifier";
       }
       leaf crl-version {
         type string;
         description "CRL version";
       }
       leaf crl-number {
         type string;
         description "CRL sequence number";
       }
       leaf crl-issuer {
         type string;
         description "CRL issuer name";
       }
       list crl-revocation-list {
         leaf revoked-cert-serial-number {
           type string;
           description "Serial number of revoked certificate";
         }
         leaf crl-revocation-date {
           type string;
           description "Revocation date";
         }
       }
       container crl-validity {
         description "Information about validity period for X.509 certificate revocation list";
         leaf effective-date {
           type string;
           description "Effective date of CRL";
         }
         leaf next-update {
           type string;
           description "Next update of CRL";
         }
       }
     }
   }
 }
 grouping security-associations-information-block {
   container brief {
     list security-associations-block {
       description "Information about a single security association block";
       leaf sa-name {
         type string;
         description "Name of the security association";
       }
       leaf sa-block-state {
         type string;
         description "Status of the SA configuration block";
       }
       container sa-tunnel-information {
         leaf sa-no-information {
           type empty;
           description "Output string when there are no security associations present";
         }
       }
       list security-associations {
         description "Information about a single security association";
         leaf sa-direction {
           type string;
           description "Direction of the security association";
         }
         leaf sa-spi {
           type string;
           description "Security Parameter Index";
         }
         leaf sa-aux-spi {
           type string;
           description "Auxiliary Security Parameter Index";
         }
         leaf sa-mode {
           type string;
           description "Mode of the security association";
         }
         leaf sa-type {
           type string;
         }
         leaf sa-protocol {
           type string;
           description "IPSec security protocol";
         }
       }
     }
   }
   container detail {
     list security-associations-block {
       description "Information about a single security association block";
       leaf sa-name {
         type string;
         description "Name of the security association";
       }
       leaf sa-block-state {
         type string;
         description "Status of the SA configuration block";
       }
       container sa-tunnel-information {
         leaf sa-local-gateway-interface {
           type string;
           description "Local gateway  interface";
         }
         leaf sa-local-gateway {
           type ipaddr;
           description "Local gateway address";
         }
         leaf sa-remote-gateway {
           type ipaddr;
           description "Remote gateway address";
         }
         leaf sa-local-identity {
           type string;
           description "Local identity information";
         }
         leaf sa-remote-identity {
           type string;
           description "Remote identity information";
         }
         leaf sa-inside-interface {
           type string;
           description "Name of IPSec interface to internal network";
         }
         leaf sa-tunnel-mtu {
           type int32;
           description "MTU of the IPSec Tunnel";
         }
         leaf sa-udp-encapsulate {
           type string;
           description "UDP encapsulation related information";
         }
         leaf sa-udp-dst-port {
           type string;
           description "UDP encapsulation port related information";
         }
         leaf sa-no-information {
           type empty;
           description "Output string when there are no security associations present";
         }
       }
       list security-associations {
         description "Information about a single security association";
         leaf sa-direction {
           type string;
           description "Direction of the security association";
         }
         leaf sa-spi {
           type string;
           description "Security Parameter Index";
         }
         leaf sa-aux-spi {
           type string;
           description "Auxiliary Security Parameter Index";
         }
         leaf sa-mode {
           type string;
           description "Mode of the security association";
         }
         leaf sa-type {
           type string;
         }
         leaf sa-state {
           type string;
           description "Status of the SA";
         }
         leaf sa-protocol {
           type string;
           description "IPSec security protocol";
         }
         leaf sa-authentication-algorithm {
           type string;
           description "Authentication algorithm";
         }
         leaf sa-encryption-algorithm {
           type string;
           description "Encryption algorithm";
         }
         leaf sa-soft-lifetime {
           type string;
           description "Remaining lifetime, in seconds or kilobytes, before soft lifetime expires";
         }
         leaf sa-hard-lifetime {
           type string;
           description "Remaining lifetime, in seconds or kilobytes, before hard lifetime expires";
         }
         leaf sa-anti-replay-service {
           type string;
           description "Anti-replay service";
         }
         leaf sa-replay-window-size {
           type int32;
           description "Replay window size";
         }
         leaf sa-copy-tos-from-inner-ip-header {
           type string;
           description "Copy ToS from inner ip header";
         }
         leaf sa-tos-value {
           type int32;
           description "ToS value";
         }
         leaf sa-copy-ttl-from-inner-ip-header {
           type string;
           description "Copy TTL from inner ip header";
         }
         leaf sa-ttl-value {
           type int32;
           description "TTL value";
         }
         leaf sa-authentication-key {
           type string;
           description "Authentication key in hexadecimal format";
         }
         leaf sa-encryption-key {
           type string;
           description "Encryption key in hexadecimal format";
         }
       }
     }
   }
 }
 grouping usp-ipsec-total-statistics-information-block {
   leaf pic-name {
     type string;
     description "PIC name";
   }
   leaf service-set-name {
     type string;
     description "Service set name";
   }
   leaf local-gateway {
     type ipaddr;
     description "Local gateway address";
   }
   leaf remote-gateway {
     type ipaddr;
     description "Remote gateway address";
   }
   leaf tunnel-index {
     type int32;
     description "Tunnel index";
   }
   container esp-statistics {
     leaf esp-encrypted-bytes {
       type uint64;
       description "ESP encrypted bytes information";
     }
     leaf esp-decrypted-bytes {
       type uint64;
       description "ESP decrypted bytes information";
     }
     leaf esp-encrypted-packets {
       type uint64;
       description "ESP encrypted packets information";
     }
     leaf esp-decrypted-packets {
       type uint64;
       description "ESP decrypted packets information";
     }
   }
   container ah-statistics {
     leaf ah-input-bytes {
       type uint64;
       description "AH input bytes information";
     }
     leaf ah-output-bytes {
       type uint64;
       description "AH output bytes information";
     }
     leaf ah-input-packets {
       type uint64;
       description "AH input packets information";
     }
     leaf ah-output-packets {
       type uint64;
       description "AH output packets information";
     }
   }
   container d3p-statistics {
     leaf d3p-old-packets {
       type uint64;
       description "D3p packets information";
     }
     leaf d3p-new-packets {
       type uint64;
       description "D3p packets information";
     }
     leaf d3p-no-header-packets {
       type uint64;
       description "D3p packets information";
     }
     leaf d3p-unexpected-header-packets {
       type uint64;
       description "D3p packets information";
     }
   }
   container fail-open-statistics {
     leaf fail-open-packets-received {
       type uint64;
       description "Fail open packets information";
     }
     leaf fail-open-packets-sent {
       type uint64;
       description "Fail open packets information";
     }
   }
   container error-statistics {
     leaf ah-authentication-failures {
       type int32;
       description "AH authentication failures information";
     }
     leaf esp-authentication-failures {
       type int32;
       description "ESP authentication failures information";
     }
     leaf esp-decryption-failures {
       type int32;
       description "ESP decryption failures information";
     }
     leaf bad-headers {
       type int32;
       description "Bad header information";
     }
     leaf bad-trailers {
       type int32;
       description "Bad trailer information";
     }
     leaf replay-before-window-drops {
       type int32;
       description "Replay before window drop information";
     }
     leaf replay-pkts {
       type int32;
       description "Replayed pkt information";
     }
     leaf rule-lookup-fail {
       type int32;
       description "Rule lookup failure information";
     }
     leaf no-sa-errors {
       type int32;
       description "No SA error information";
     }
     leaf ip-integrity-errors {
       type int32;
       description "IP Integrity error information";
     }
     leaf exceeds-tunnel-mtu {
       type int32;
       description "Exceeds Tunnel MTU";
     }
     leaf flow-errors {
       type int32;
       description "Flow error information";
     }
     leaf misc-errors {
       type int32;
       description "Misc error information";
     }
   }
 }
 grouping ipsec-unestablished-tunnel-information-block {
   container brief {
     container ipsec-security-associations {
     }
     container ipsec-security-associations-block {
       container ipsec-security-associations {
         leaf sa-tunnel-index {
           type int32;
           description "Tunnel index";
         }
         leaf sa-port {
           type int32;
           description "Port";
         }
         leaf sa-nego-num {
           type int32;
           description "SA nego num";
         }
         leaf sa-nego-fail {
           type int32;
           description "SA nego fail num";
         }
         leaf sa-flag {
           type int32;
           description "SA flags";
         }
         leaf sa-remote-gateway {
           type ipaddr;
           description "Remote gateway address";
         }
         leaf stats-name {
           type string;
         }
       }
     }
     container ipsec-gvpn-inactive-tunnel-info-block {
       leaf sa-gvpn-server {
         type string;
         description "Group VPN Server Address";
       }
       leaf sa-port {
         type int32;
         description "Port";
       }
       leaf sa-gvpn-groupid {
         type int32;
         description "Group VPN Group Id";
       }
       leaf sa-virtual-system {
         type string;
         description "Virtual System";
       }
       leaf sa-down-reason {
         type string;
         description "Ipsec SA down reason";
       }
     }
   }
   container detail {
     container ipsec-security-associations {
     }
     container ipsec-security-associations-block {
       container ipsec-security-associations {
       }
     }
     container ipsec-gvpn-inactive-tunnel-info-block {
       leaf sa-virtual-system {
         type string;
         description "Virtual System";
       }
       leaf sa-vpn-name {
         type string;
         description "VPN Name";
       }
       leaf sa-local-gateway {
         type ipaddr;
         description "Local gateway address";
       }
       leaf sa-remote-gateway {
         type ipaddr;
         description "Remote gateway address";
       }
       leaf sa-local-identity {
         type string;
         description "Local identity information";
       }
       leaf sa-remote-identity {
         type string;
         description "Remote identity information";
       }
       leaf sa-gvpn-groupid {
         type int32;
         description "Group VPN Group Id";
       }
       leaf sa-match-dir {
         type string;
         description "Group VPN rule match direction";
       }
       leaf sa-tunnel-mtu {
         type int32;
         description "MTU of the IPSec Tunnel";
       }
       container sa-df-bit-policy-name {
         leaf sa-df-bit {
           type string;
           description "Fragmentation bit";
         }
       }
       container ipsec-gvpn-sa-stats {
         leaf ipsec-sa-stats {
           type string;
           description "Ipsec SA stats";
         }
       }
       container gvpn-sa-down-reason {
         leaf sa-down-reason {
           type string;
           description "Ipsec SA down reason";
         }
       }
     }
   }
 }
 grouping ike-show-pre-shared-key-information-block {
   leaf pre-shared-key {
     type string;
   }
 }
 grouping ike-security-associations-information-block {
   container brief {
     list ike-security-associations {
       description "Information about a single security association";
       leaf ike-sa-remote-address {
         type ipaddr;
         description "Remote address";
       }
       leaf ike-sa-state {
         type string;
         description "Status of the SA";
       }
       leaf ike-sa-initiator-cookie {
         type string;
         description "IKE SA initiator cookie";
       }
       leaf ike-sa-responder-cookie {
         type string;
         description "IKE SA responder cookie";
       }
       leaf ike-sa-exchange-type {
         type string;
         description "Exchange type";
       }
       container ike-sa-algorithms {
         description "Algorithms used with the SA information";
       }
       container ike-sa-traffic-statistics {
         description "Number of packets and bytes received and transmitted on the SA";
       }
     }
     container ike-security-associations-block {
       description "Information about a single security association block";
       list ike-security-associations {
         description "Information about a single security association";
         container ike-sa-algorithms {
           description "Algorithms used with the SA information";
         }
         container ike-sa-traffic-statistics {
           description "Number of packets and bytes received and transmitted on the SA";
         }
       }
     }
   }
   container detail {
     list ike-security-associations {
       description "Information about a single security association";
       container ike-sa-algorithms {
         description "Algorithms used with the SA information";
       }
       container ike-sa-traffic-statistics {
         description "Number of packets and bytes received and transmitted on the SA";
       }
     }
     container ike-security-associations-block {
       description "Information about a single security association block";
       leaf ike-sa-remote-address {
         type ipaddr;
         description "Remote address";
       }
       list ike-security-associations {
         description "Information about a single security association";
         leaf ike-sa-role {
           type string;
           description "Role of our end";
         }
         leaf ike-sa-state {
           type string;
           description "Status of the SA";
         }
         leaf ike-sa-initiator-cookie {
           type string;
           description "IKE SA initiator cookie";
         }
         leaf ike-sa-responder-cookie {
           type string;
           description "IKE SA responder cookie";
         }
         leaf ike-sa-exchange-type {
           type string;
           description "Exchange type";
         }
         leaf ike-sa-authentication-method {
           type string;
         }
         leaf ike-sa-local-gateway-interface {
           type string;
           description "Local gateway  interface";
         }
         leaf ike-sa-routing-instance {
           type string;
           description "Local-gateway routing instance";
         }
         leaf ike-sa-local-address {
           type ipaddr;
           description "Local address";
         }
         leaf ike-sa-local-port {
           type int32;
           description "Local port";
         }
         leaf ike-sa-remote-port {
           type int32;
           description "Remote port";
         }
         leaf ike-sa-lifetime {
           type string;
           description "Remaining lifetime before expiration, in seconds or kilobytes";
         }
         container ike-sa-algorithms {
           description "Algorithms used with the SA information";
           leaf ike-sa-authentication-algorithm {
             type string;
             description "Authentication algorithm";
           }
           leaf ike-sa-encryption-algorithm {
             type string;
             description "Encryption algorithm";
           }
           leaf ike-sa-prf-algorithm {
             type string;
             description "PRF algorithm";
           }
           leaf ike-sa-dhgroup {
             type string;
             description "DH group";
           }
         }
         container ike-sa-traffic-statistics {
           description "Number of packets and bytes received and transmitted on the SA";
           leaf ike-sa-input-bytes {
             type int32;
             description "Input bytes, including retransmissions";
           }
           leaf ike-sa-output-bytes {
             type int32;
             description "Output bytes, including retransmissions";
           }
           leaf ike-sa-input-packets {
             type int32;
             description "Input packets, including retransmissions";
           }
           leaf ike-sa-output-packets {
             type int32;
             description "Output packets, including retransmissions";
           }
         }
         container ike-sa-misc {
           description "Miscellaneous IKE SA information";
           leaf ike-sa-flags {
             type string;
             description "IKE SA flags";
           }
           leaf ike-sa-num-ipsec-sas-created {
             type int32;
             description "Number of IPSec SAs created using this SA";
           }
           leaf ike-sa-num-ipsec-sas-deleted {
             type int32;
             description "Number of IPSec SAs deleted using this SA";
           }
           leaf ike-sa-num-phase2-negotiations {
             type int32;
             description "Number of negotiations in progress on this SA";
           }
         }
         list ike-sa-phase2-information {
           description "Information about phase 2 negotiation";
           leaf ike-sa-phase2-type {
             type string;
             description "Type of phase 2 negotiation";
           }
           leaf ike-sa-role {
             type string;
             description "Role of our end";
           }
           leaf ike-sa-msg-id {
             type int32;
             description "Message ID of the quick mode negotiation";
           }
           leaf ike-sa-local-address {
             type ipaddr;
             description "Local address";
           }
           leaf ike-sa-local-port {
             type int32;
             description "Local port";
           }
           leaf ike-sa-remote-address {
             type ipaddr;
             description "Remote address";
           }
           leaf ike-sa-remote-port {
             type int32;
             description "Remote port";
           }
           leaf ike-sa-local-id {
             type string;
             description "Local end identity in phase 2";
           }
           leaf ike-sa-remote-id {
             type string;
             description "Remote end identity in phase 2";
           }
           leaf ike-sa-flags {
             type string;
             description "IKE SA flags";
           }
         }
       }
     }
   }
 }
 grouping ike-active-peers-information-block {
   container brief {
     container ike-active-peers {
       description "IKE active peer and XAUTH assigned IP";
       leaf ike-sa-remote-address {
         type ipaddr;
         description "Remote address";
       }
       leaf ike-sa-remote-port {
         type int32;
         description "Remote port";
       }
       leaf ike-ike-id {
         type string;
         description "IKE ID";
       }
       leaf ike-xauth-username {
         type string;
         description "Xauth username";
       }
       leaf ike-xauth-user-assigned-ip {
         type ipaddr;
         description "IP assigned to Xauth user";
       }
     }
     container ike-active-peers-block {
       description "IKE active peer";
     }
   }
   container detail {
     container ike-active-peers-block {
       description "IKE active peer";
       leaf ike-sa-remote-address {
         type ipaddr;
         description "Remote address";
       }
       leaf ike-sa-remote-port {
         type int32;
         description "Remote port";
       }
       leaf ike-ike-id {
         type string;
         description "IKE ID";
       }
       leaf ike-xauth-username {
         type string;
         description "Xauth username";
       }
       container ike-active-peers {
         description "IKE active peer and XAUTH assigned IP";
         leaf ike-xauth-user-assigned-ip {
           type ipaddr;
           description "IP assigned to Xauth user";
         }
         leaf ike-xauth-user-assigned-mask {
           type ipaddr;
           description "IP mask assigned to Xauth user";
         }
         leaf ike-xauth-user-assigned-dns {
           type ipaddr;
           description "DNS assigned to Xauth user";
         }
         leaf ike-xauth-user-assigned-dns2 {
           type ipaddr;
           description "DNS2 assigned to Xauth user";
         }
         leaf ike-xauth-user-assigned-wins {
           type ipaddr;
           description "WINS assigned to Xauth user";
         }
         leaf ike-xauth-user-assigned-wins2 {
           type ipaddr;
           description "WINS2 assigned to Xauth user";
         }
         leaf ike-user-last-remote-ip {
           type ipaddr;
           description "Remote IP of last vpn connection";
         }
         leaf ike-user-last-remote-port {
           type int32;
           description "Remote port of last vpn connection";
         }
         leaf ike-p1sa-id-list {
           type string;
           description "List of IKE SA indexes";
         }
         leaf ike-peer-ike-sa-negotiated {
           type int32;
           description "Number IKE SA negotiated since the peer connects";
         }
         leaf ike-peer-active-ipsec-sa {
           type int32;
           description "Number IPSec SA active from the peer";
         }
         leaf ike-ipsec-sa-id-list {
           type string;
           description "List of IPSec SA indexes";
         }
       }
     }
   }
 }
 grouping security-ike-debug-info-block {
   leaf ike-debug-status {
     type string;
     description "Show current enabled IKE debug information";
   }
   leaf ike-debug-flag {
     type string;
     description "IKE debug flag";
   }
   leaf ike-debug-level {
     type int32;
     description "IKE debug level";
   }
   leaf ike-sa-local-address {
     type ipaddr;
     description "Local address";
   }
   leaf ike-sa-remote-address {
     type ipaddr;
     description "Remote address";
   }
 }
 grouping iked-tunnel-mapping-information-block {
   container brief {
     list iked-tunnel-map {
       description "Mapping between gateway-id and physical SPU and iked instance";
       leaf gateway-id {
         type int32;
         description "Gateway id";
       }
       leaf gateway-name {
         type string;
         description "Gateway name";
       }
       leaf spu-fpc {
         type int32;
       }
       leaf spu-pic {
         type int32;
       }
       leaf iked-instance {
         type int32;
       }
     }
   }
   container summary {
     list iked-tunnel-map-summary {
       description "Load of each SPU";
       leaf spu-fpc {
         type int32;
       }
       leaf spu-pic {
         type int32;
       }
       leaf spu-load {
         type int32;
       }
     }
   }
 }
 grouping ipsec-security-associations-information-block {
   container brief {
     container ipsec-security-associations {
     }
     container ipsec-security-associations-block {
       container ipsec-security-associations {
         leaf sa-direction {
           type string;
           description "Direction of the security association";
         }
         leaf sa-tunnel-index {
           type int32;
           description "Tunnel index";
         }
         leaf sa-protocol {
           type string;
           description "IPSec security protocol";
         }
         leaf sa-esp-encryption-algorithm {
           type string;
           description "ESP Encryption Algorithm";
         }
         leaf sa-hmac-algorithm {
           type string;
           description "HMAC Authentication Algorithm";
         }
         leaf sa-spi {
           type string;
           description "Security Parameter Index";
         }
         leaf sa-hard-lifetime {
           type string;
           description "Remaining lifetime, in seconds or kilobytes, before hard lifetime expires";
         }
         leaf sa-lifesize-remaining {
           type string;
           description "Lifetime Remaining in Kilo Bytes";
         }
         leaf sa-vpn-monitoring-state {
           type string;
           description "VPN Monitoring State";
         }
         leaf sa-virtual-system {
           type string;
           description "Virtual System";
         }
         leaf sa-port {
           type int32;
           description "Port";
         }
         leaf sa-remote-gateway {
           type ipaddr;
           description "Remote gateway address";
         }
       }
     }
     container ipsec-gvpn-security-associations-block {
       container ipsec-security-associations {
         leaf sa-direction {
           type string;
           description "Direction of the security association";
         }
         leaf sa-tunnel-index {
           type int32;
           description "Tunnel index";
         }
         leaf sa-gvpn-server {
           type string;
           description "Group VPN Server Address";
         }
         leaf sa-port {
           type int32;
           description "Port";
         }
         leaf sa-protocol {
           type string;
           description "IPSec security protocol";
         }
         leaf sa-esp-encryption-algorithm {
           type string;
           description "ESP Encryption Algorithm";
         }
         leaf sa-hmac-algorithm {
           type string;
           description "HMAC Authentication Algorithm";
         }
         leaf sa-spi {
           type string;
           description "Security Parameter Index";
         }
         leaf sa-hard-lifetime {
           type string;
           description "Remaining lifetime, in seconds or kilobytes, before hard lifetime expires";
         }
         leaf sa-lifesize-remaining {
           type string;
           description "Lifetime Remaining in Kilo Bytes";
         }
         leaf sa-gvpn-groupid {
           type int32;
           description "Group VPN Group Id";
         }
         leaf sa-virtual-system {
           type string;
           description "Virtual System";
         }
       }
       container sa-child-tunnel-id-policy {
       }
     }
   }
   container detail {
     container ipsec-security-associations {
     }
     container ipsec-security-associations-block {
       leaf sa-tunnel-index {
         type int32;
         description "Tunnel index";
       }
       leaf sa-virtual-system {
         type string;
         description "Virtual System";
       }
       leaf sa-vpn-name {
         type string;
         description "VPN Name";
       }
       leaf sa-local-gateway {
         type ipaddr;
         description "Local gateway address";
       }
       leaf sa-remote-gateway {
         type ipaddr;
         description "Remote gateway address";
       }
       leaf sa-local-identity {
         type string;
         description "Local identity information";
       }
       leaf sa-remote-identity {
         type string;
         description "Remote identity information";
       }
       leaf sa-ike-version {
         type string;
         description "IKE version number used in negotiation";
       }
       container sa-df-bit-policy-name {
         leaf sa-df-bit {
           type string;
           description "Fragmentation bit";
         }
         leaf sa-policy-name {
           type string;
           description "Policy name";
         }
         leaf sa-bind-interface {
           type string;
           description "VPN bind-interface";
         }
       }
       container sa-dev-info {
         leaf sa-port {
           type int32;
           description "Port";
         }
         leaf sa-nego-num {
           type int32;
           description "SA nego num";
         }
         leaf sa-nego-fail {
           type int32;
           description "SA nego fail num";
         }
         leaf sa-del-num {
           type int32;
           description "SA defer delete count";
         }
         leaf sa-flag {
           type int32;
           description "SA flags";
         }
         leaf stats-name {
           type string;
         }
       }
       container ipsec-security-associations {
         leaf sa-direction {
           type string;
           description "Direction of the security association";
         }
         leaf sa-spi {
           type string;
           description "Security Parameter Index";
         }
         leaf sa-aux-spi {
           type string;
           description "Auxiliary Security Parameter Index";
         }
         leaf sa-mode {
           type string;
           description "Mode of the security association";
         }
         leaf sa-type {
           type string;
         }
         leaf sa-state {
           type string;
           description "Status of the SA";
         }
         leaf sa-vpn-monitoring-state {
           type string;
           description "VPN Monitoring State";
         }
         leaf sa-protocol {
           type string;
           description "IPSec security protocol";
         }
         leaf sa-authentication-algorithm {
           type string;
           description "Authentication algorithm";
         }
         leaf sa-encryption-algorithm {
           type string;
           description "Encryption algorithm";
         }
         leaf sa-soft-lifetime {
           type string;
           description "Remaining lifetime, in seconds or kilobytes, before soft lifetime expires";
         }
         leaf sa-hard-lifetime {
           type string;
           description "Remaining lifetime, in seconds or kilobytes, before hard lifetime expires";
         }
         leaf sa-lifesize-remaining {
           type string;
           description "Lifetime Remaining in Kilo Bytes";
         }
         leaf sa-anti-replay-service {
           type string;
           description "Anti-replay service";
         }
       }
       container sa-location {
         description "Location where SA is processed";
         leaf sa-fpc {
           type int32;
           description "FPC number";
         }
         leaf sa-pic {
           type int32;
           description "PIC number";
         }
         leaf sa-kmd-instance {
           type int32;
           description "KMD instance number";
         }
       }
     }
     container ipsec-gvpn-security-associations-block {
       leaf sa-virtual-system {
         type string;
         description "Virtual System";
       }
       leaf sa-vpn-name {
         type string;
         description "VPN Name";
       }
       leaf sa-local-gateway {
         type ipaddr;
         description "Local gateway address";
       }
       leaf sa-remote-gateway {
         type ipaddr;
         description "Remote gateway address";
       }
       leaf sa-local-identity {
         type string;
         description "Local identity information";
       }
       leaf sa-remote-identity {
         type string;
         description "Remote identity information";
       }
       leaf sa-gvpn-groupid {
         type int32;
         description "Group VPN Group Id";
       }
       leaf sa-match-dir {
         type string;
         description "Group VPN rule match direction";
       }
       leaf sa-tunnel-mtu {
         type int32;
         description "MTU of the IPSec Tunnel";
       }
       leaf sa-gvpn-vrf-name {
         type string;
         description "SA routing instance name";
       }
       container sa-df-bit-policy-name {
         leaf sa-df-bit {
           type string;
           description "Fragmentation bit";
         }
       }
       container ipsec-gvpn-sa-stats {
         leaf ipsec-sa-stats {
           type string;
           description "Ipsec SA stats";
         }
       }
       container ipsec-gvpn-sa-flags {
         leaf sa-rekey-needed {
           type string;
           description "SA rekey needed";
         }
       }
       container ipsec-security-associations {
         leaf sa-direction {
           type string;
           description "Direction of the security association";
         }
         leaf sa-spi {
           type string;
           description "Security Parameter Index";
         }
         leaf sa-aux-spi {
           type string;
           description "Auxiliary Security Parameter Index";
         }
         leaf sa-gvpn-groupid {
           type int32;
           description "Group VPN Group Id";
         }
         leaf sa-mode {
           type string;
           description "Mode of the security association";
         }
         leaf sa-type {
           type string;
         }
         leaf sa-state {
           type string;
           description "Status of the SA";
         }
         leaf sa-protocol {
           type string;
           description "IPSec security protocol";
         }
         leaf sa-hmac-algorithm {
           type string;
           description "HMAC Authentication Algorithm";
         }
         leaf sa-esp-encryption-algorithm {
           type string;
           description "ESP Encryption Algorithm";
         }
         leaf sa-soft-lifetime {
           type string;
           description "Remaining lifetime, in seconds or kilobytes, before soft lifetime expires";
         }
         leaf sa-hard-lifetime {
           type string;
           description "Remaining lifetime, in seconds or kilobytes, before hard lifetime expires";
         }
         leaf sa-activate-lifetime {
           type string;
           description "Activate time";
         }
         leaf sa-lifesize-remaining {
           type string;
           description "Lifetime Remaining in Kilo Bytes";
         }
         leaf sa-anti-replay-service {
           type string;
           description "Anti-replay service";
         }
       }
       container sa-child-tunnel-id-policy {
         leaf sa-tunnel-id {
           type int32;
           description "Tunnel id";
         }
         container sa-child-policy-list {
           leaf sa-policy-source-prefix {
             type string;
             description "Group VPN child sa policy source prefix";
           }
           leaf sa-policy-dest-prefix {
             type string;
             description "Group VPN child sa policy destination prefix";
           }
         }
       }
       container sa-location {
         description "Location where SA is processed";
         leaf sa-fpc {
           type int32;
           description "FPC number";
         }
         leaf sa-pic {
           type int32;
           description "PIC number";
         }
         leaf sa-kmd-instance {
           type int32;
           description "KMD instance number";
         }
       }
     }
   }
 }
 grouping idp-application-system-cache-information-block {
   list idp-application-system-cache-pic {
     leaf pic-name {
       type string;
       description "Pic name";
     }
     list idp-application-system-cache-statistics {
       leaf virtual-system-identifier {
         type uint32;
         description "Virtual system identifier";
       }
       leaf ipv6-address {
         type ipv6addr;
         description "IPV6 address";
       }
       leaf port {
         type uint32;
         description "Application identification port";
       }
       leaf protocol {
         type string;
         description "IP protocol";
       }
       leaf idp-service {
         type string;
         description "IDP service type";
       }
       leaf idp-application {
         type string;
         description "IDP application type";
       }
     }
   }
 }
 grouping idp-version-information-block {
   leaf idp-policy-name {
     type string;
     description "IDP active policy name";
   }
   leaf idp-detector-version {
     type string;
     description "IDP running detector version";
   }
   leaf idp-sigdb-version {
     type string;
     description "IDP compiled signature database version";
   }
 }
 grouping idp-policy-commit-status-block {
   leaf policy-commit-status-detail {
     type string;
     description "Policy commit status output";
   }
 }
 grouping idp-security-package-information-block {
   leaf security-package-version {
     type string;
     description "Security package version";
   }
   leaf detector-version {
     type string;
     description "Detector version";
   }
   leaf policy-template-version {
     type string;
     description "Policy template version";
   }
 }
 grouping idp-recent-security-package-information-block {
   leaf recent-security-package-version {
     type string;
     description "Security package last-known-good version";
   }
 }
 grouping idp-memory-information-block {
   list idp-memory-per-spu-information {
     leaf pic-name {
       type string;
       description "Pic name";
     }
     leaf total-idp-data-plane-memory-in-mb {
       type uint32;
     }
     leaf total-idp-data-plane-memory-used-in-mb {
       type uint32;
     }
     leaf total-idp-data-plane-memory-used-in-kb {
       type uint32;
     }
     leaf total-idp-data-plane-memory-used-in-percentage {
       type string;
     }
     leaf total-idp-data-plane-memory-available-in-mb {
       type uint32;
     }
     leaf total-idp-data-plane-memory-available-in-kb {
       type uint32;
     }
     leaf total-idp-data-plane-memory-available-in-percentage {
       type string;
     }
   }
 }
 grouping idp-subscriber-policy-list-block {
   list idp-subscriber-policy-per-pic-information {
     description "IDP  subscriber policy per pic information";
     leaf pic-name {
       type string;
       description "Pic name";
     }
     list idp-policy-list-entry {
       description "Information about policy list entry";
       leaf id {
         type uint32;
         description "Process id";
       }
       leaf policy-name {
         type string;
         description "Name of the policy";
       }
       leaf sessions {
         type uint32;
         description "Number of session";
       }
       leaf memory {
         type uint32;
         description "Memory";
       }
       leaf idp-detector-versions {
         type string;
         description "IDP detector version";
       }
     }
   }
 }
 grouping idp-status-information-block {
   container idp-uptime {
     leaf idp-status {
       type string;
     }
     leaf date-time {
       type string;
       description "IDP peak packets(or Kbits) per second";
     }
     leaf time-length {
       type string;
     }
   }
   container idp-packets-per-second-information {
     leaf idp-packets-per-second {
       type uint32;
     }
     leaf idp-peak-packets-per-second {
       type uint32;
     }
     leaf date-time {
       type string;
       description "IDP peak packets(or Kbits) per second";
     }
   }
   container idp-kbits-per-second-information {
     leaf idp-kbits-per-second {
       type uint32;
     }
     leaf idp-peak-kbits-per-second {
       type uint32;
     }
     leaf date-time {
       type string;
       description "IDP peak packets(or Kbits) per second";
     }
   }
   container idp-latency {
     leaf minimum-latency-time {
       type string;
     }
     leaf maximum-latency-time {
       type string;
     }
     leaf average-latency-time {
       type string;
     }
   }
   container idp-packet-count {
     leaf icmp-packet-count {
       type uint32;
     }
     leaf tcp-packet-count {
       type uint32;
     }
     leaf udp-packet-count {
       type uint32;
     }
     leaf other-packet-count {
       type uint32;
     }
   }
   container idp-icmp-flow-count {
     leaf current-icmp-flow-count {
       type uint32;
     }
     leaf maximum-icmp-flow-count {
       type uint32;
     }
     leaf date-time {
       type string;
       description "IDP peak packets(or Kbits) per second";
     }
   }
   container idp-tcp-flow-count {
     leaf current-tcp-flow-count {
       type uint32;
     }
     leaf maximum-tcp-flow-count {
       type uint32;
     }
     leaf date-time {
       type string;
       description "IDP peak packets(or Kbits) per second";
     }
   }
   container idp-udp-flow-count {
     leaf current-udp-flow-count {
       type uint32;
     }
     leaf maximum-udp-flow-count {
       type uint32;
     }
     leaf date-time {
       type string;
       description "IDP peak packets(or Kbits) per second";
     }
   }
   container idp-other-flow-count {
     leaf current-other-flow-count {
       type uint32;
     }
     leaf maximum-other-flow-count {
       type uint32;
     }
     leaf date-time {
       type string;
       description "IDP peak packets(or Kbits) per second";
     }
   }
   container idp-session-count {
     leaf icmp-session-count {
       type uint32;
     }
     leaf tcp-session-count {
       type uint32;
     }
     leaf udp-session-count {
       type uint32;
     }
     leaf other-session-count {
       type uint32;
     }
   }
   container idp-ssl-session-information {
     leaf ssl-session-count {
       type uint32;
     }
   }
 }
 grouping idp-detail-status-information-block {
   list idp-status-detail-per-spu-information {
     description "IDP status per PIC information";
     container idp-spu-uptime {
       leaf pic-name {
         type string;
         description "Pic name";
       }
       leaf idp-status {
         type string;
       }
       leaf date-time {
         type string;
         description "IDP peak packets(or Kbits) per second";
       }
       leaf time-length {
         type string;
       }
     }
     container idp-packets-spu-per-second-information {
       leaf idp-packets-per-second {
         type uint32;
       }
       leaf idp-peak-packets-per-second {
         type uint32;
       }
       leaf date-time {
         type string;
         description "IDP peak packets(or Kbits) per second";
       }
     }
     container idp-kbits-spu-per-second-information {
       leaf idp-kbits-per-second {
         type uint32;
       }
       leaf idp-peak-kbits-per-second {
         type uint32;
       }
       leaf date-time {
         type string;
         description "IDP peak packets(or Kbits) per second";
       }
     }
     container idp-spu-latency {
       leaf minimum-latency-time {
         type string;
       }
       leaf maximum-latency-time {
         type string;
       }
       leaf average-latency-time {
         type string;
       }
     }
     container idp-spu-packet-count {
       leaf icmp-packet-count {
         type uint32;
       }
       leaf tcp-packet-count {
         type uint32;
       }
       leaf udp-packet-count {
         type uint32;
       }
       leaf other-packet-count {
         type uint32;
       }
     }
     container idp-spu-icmp-flow-count {
       leaf current-icmp-flow-count {
         type uint32;
       }
       leaf maximum-icmp-flow-count {
         type uint32;
       }
       leaf date-time {
         type string;
         description "IDP peak packets(or Kbits) per second";
       }
     }
     container idp-spu-tcp-flow-count {
       leaf current-tcp-flow-count {
         type uint32;
       }
       leaf maximum-tcp-flow-count {
         type uint32;
       }
       leaf date-time {
         type string;
         description "IDP peak packets(or Kbits) per second";
       }
     }
     container idp-spu-udp-flow-count {
       leaf current-udp-flow-count {
         type uint32;
       }
       leaf maximum-udp-flow-count {
         type uint32;
       }
       leaf date-time {
         type string;
         description "IDP peak packets(or Kbits) per second";
       }
     }
     container idp-spu-other-flow-count {
       leaf current-other-flow-count {
         type uint32;
       }
       leaf maximum-other-flow-count {
         type uint32;
       }
       leaf date-time {
         type string;
         description "IDP peak packets(or Kbits) per second";
       }
     }
     container idp-spu-session-count {
       leaf icmp-session-count {
         type uint32;
       }
       leaf tcp-session-count {
         type uint32;
       }
       leaf udp-session-count {
         type uint32;
       }
       leaf other-session-count {
         type uint32;
       }
     }
     container idp-spu-ssl-session-information {
       leaf ssl-session-count {
         type uint32;
       }
     }
   }
 }
 grouping idp-predefined-attack-groups-block {
   list idp-attack-groups {
     leaf name {
       type string;
       description "Name of this component";
     }
   }
 }
 grouping idp-predefined-attacks-block {
   list idp-attacks-list {
     leaf name {
       type string;
       description "Name of this component";
     }
   }
 }
 grouping idp-counter-information-block {
   list idp-counter-statistics {
     leaf name {
       type string;
       description "Name of this component";
     }
     leaf value {
       type uint32;
       description "Value of this entity";
     }
   }
 }
 grouping idp-attack-description-information-block {
   leaf idp-attack-description {
     type string;
     description "Description of attack";
   }
 }
 grouping idp-attack-detail-information-block {
   leaf idp-attack-detail-name {
     type string;
     description "Display name of attack";
   }
   leaf idp-attack-detail-severity {
     type string;
     description "Severity of attack";
   }
   leaf idp-attack-detail-category {
     type string;
     description "Category of attack";
   }
   leaf idp-attack-detail-recommended {
     type string;
     description "Recommended field of attack";
   }
   leaf idp-attack-detail-recoact {
     type string;
     description "Recommended action for attack";
   }
   leaf idp-attack-detail-type {
     type string;
     description "Type of attack";
   }
   leaf idp-attack-detail-direction {
     type string;
     description "Direction of attack";
   }
   leaf idp-attack-detail-falsepos {
     type string;
     description "False Positives for the attack";
   }
   leaf idp-attack-detail-service {
     type string;
     description "Service of the attack";
   }
   leaf idp-attack-detail-transaction {
     type string;
     description "Transaction of the attack";
   }
   leaf idp-attack-detail-expression {
     type string;
     description "Expression of the attack";
   }
   leaf idp-attack-detail-expression-pcre {
     type string;
     description "PCRE Expression of the attack";
   }
   leaf idp-attack-detail-order {
     type string;
     description "Order of the attack";
   }
   leaf idp-attack-detail-reset {
     type string;
     description "Reset of the attack";
   }
   leaf idp-attack-detail-shellcode {
     type string;
     description "Shellcode of the attack";
   }
   leaf idp-attack-detail-flow {
     type string;
     description "Flow of the attack";
   }
   leaf idp-attack-detail-context {
     type string;
     description "Context of the attack";
   }
   leaf idp-attack-detail-negate {
     type string;
     description "Negate of the attack";
   }
   leaf idp-attack-detail-pattern {
     type string;
     description "Pattern of the attack";
   }
   leaf idp-attack-detail-pattern-pcre {
     type string;
     description "PCRE pattern of the attack";
   }
   leaf idp-attack-detail-regex {
     type string;
     description "Regex of the attack";
   }
   leaf idp-attack-detail-scope {
     type string;
     description "Scope of the attack";
   }
   leaf idp-attack-detail-count {
     type string;
     description "Count of the attack";
   }
   leaf idp-attack-detail-test {
     type string;
     description "Test of the attack";
   }
   leaf idp-attack-detail-value {
     type string;
     description "Value of the attack";
   }
   leaf idp-attack-detail-hidden {
     type string;
     description "Hidden flag of the attack";
   }
   container idp-attack-detail-timebinding {
     description "TimeBinding of the attack";
     leaf idp-attack-detail-timebinding-scope {
       type string;
       description "Display attack detail timebinding scope";
     }
     leaf idp-attack-detail-timebinding-count {
       type string;
       description "Display attack detail timebinding count";
     }
   }
   list idp-chain-attack-members-detail-information {
     leaf idp-chain-attack-members-name {
       type string;
       description "Display chain attack member name of attack";
     }
     leaf idp-chain-attack-members-type {
       type string;
       description "Display chain attack member type of attack";
     }
     leaf idp-chain-attack-members-direction {
       type string;
       description "Display chain attack member direction of attack";
     }
     leaf idp-chain-attack-members-flow {
       type string;
       description "Display chain attack member flow of attack";
     }
     leaf idp-chain-attack-members-shellcode {
       type string;
       description "Display chain attack member shellcode of attack";
     }
     leaf idp-chain-attack-members-context {
       type string;
       description "Display chain attack member context of attack";
     }
     leaf idp-chain-attack-members-negate {
       type string;
       description "Display chain attack member negate of attack";
     }
     leaf idp-chain-attack-members-hidden {
       type string;
       description "Hidden flag of the attack members";
     }
     leaf idp-chain-attack-members-pattern {
       type string;
       description "Display chain attack member pattern of attack";
     }
     leaf idp-chain-attack-members-pattern-pcre {
       type string;
       description "Display chain attack member pcre pattern of attack";
     }
     leaf idp-chain-attack-members-regex {
       type string;
       description "Display chain attack member regex of attack";
     }
     leaf idp-chain-attack-members-test {
       type string;
       description "Test of the attack members";
     }
     leaf idp-chain-attack-members-value {
       type string;
       description "Value of the attack members";
     }
   }
 }
 grouping get-idp-ssl-session-cache-information-block {
   leaf idp-ssl-session-cache-count {
     type uint32;
     description "Number of SSL session cache entries";
   }
   list idp-ssl-session-cache-entry {
     description "Information about SSL session cache entry";
     leaf ssl-session-identifier {
       type string;
       description "SSL Session Identifier";
     }
   }
 }
 grouping idp-ssl-key-information-block {
   leaf idp-ssl-key-count {
     type uint32;
     description "Number of SSL keys";
   }
   list idp-ssl-per-key-information {
     leaf key-name {
       type string;
       description "SSL server private key name";
     }
     leaf destination-address {
       type ipaddr;
       description "Destination address";
     }
   }
   list idp-ssl-port-per-key-information {
     leaf key-name {
       type string;
       description "SSL server private key name";
     }
     leaf destination-address {
       type ipaddr;
       description "Destination address";
     }
     leaf destination-port {
       type int32;
       description "Destination port";
     }
   }
 }
 grouping idp-lsys-policy-association-block {
   list idp-lsys-policy-association-entry {
     leaf logical-system-name {
       type string;
       description "Logical system name";
     }
     leaf idp-policy-name {
       type string;
       description "IDP active policy name";
     }
   }
 }
 grouping idp-session-summary-information-block {
   leaf total-sessions {
     type uint32;
     description "Total sessions";
   }
   list idp-session-summary-per-pic-information {
     description "IDP session summary per PIC information";
     leaf pic-name {
       type string;
       description "Pic name";
     }
     leaf maximum-sessions {
       type uint32;
       description "Maximum sessions";
     }
     leaf active-sessions {
       type uint32;
       description "Number of active sessions";
     }
   }
 }
 grouping mka-session-information-block {
   leaf interface-name {
     type string;
   }
   leaf member-identifier {
     type string;
     description "MKA member identifier";
   }
   leaf cak-name {
     type string;
     description "Connectivity association key name";
   }
   leaf transmit-interval {
     type uint32;
     description "MKA periodic transmit interval in milliseconds";
   }
   leaf sci {
     type string;
     description "MKA outbound secure channel identifier";
   }
   leaf message-number {
     type uint32;
     description "MKA message number last transmitted";
   }
   leaf key-number {
     type uint32;
     description "MKA key number being used";
   }
   leaf key-server {
     type string;
     description "MKA key server status";
   }
   leaf key-server-priority {
     type uint32;
     description "MKA key server priority";
   }
   leaf latest-sak-association-number {
     type uint32;
     description "MKA latest security association key's association number";
   }
   leaf latest-sak-key-identifier {
     type string;
     description "MKA latest security association key's key identifier";
   }
   container session-previous-sak {
     leaf previous-sak-association-number {
       type uint32;
       description "MKA previous security association key's association number";
     }
     leaf previous-sak-key-identifier {
       type string;
       description "MKA previous security association key's key identifier";
     }
   }
   list session-peer-list {
     leaf peer-index {
       type uint32;
       description "MKA peer index number";
     }
     leaf member-identifier {
       type string;
       description "MKA member identifier";
     }
     leaf peer-status {
       type string;
       description "MKA peer status";
     }
     leaf message-number {
       type uint32;
       description "MKA message number last transmitted";
     }
     leaf hold-time {
       type uint32;
       description "MKA peer time to expiry in milli seconds";
     }
     leaf sci {
       type string;
       description "MKA outbound secure channel identifier";
     }
     leaf lowest-acceptable-packet-number {
       type uint32;
       description "MKA lowest acceptable packet number from peer";
     }
   }
 }
 grouping mka-statistics-block {
   leaf interface-name {
     type string;
   }
   leaf received-packets {
     type uint32;
     description "Number of MKA packets received";
   }
   leaf sent-packets {
     type uint32;
     description "Number of MKA packets sent";
   }
   leaf version-error {
     type uint32;
     description "Number of MKA packets with version mismatch";
   }
   leaf cak-error {
     type uint32;
     description "Number of MKA packets with CAK invalid or mismatch";
   }
   leaf integrity-check-value-mismatch {
     type uint32;
     description "Number of MKA packets with integrity check value mismatch";
   }
   leaf duplicate-message-identifier {
     type uint32;
     description "Number of MKA packets with duplicate message identifier";
   }
   leaf duplicate-message-number {
     type uint32;
     description "Number of MKA packets with duplicate message number";
   }
   leaf duplicate-address {
     type uint32;
     description "Number of MKA packets with duplicate address";
   }
   leaf invalid-destination {
     type uint32;
     description "Number of MKA packets with invalid destination";
   }
   leaf format-error {
     type uint32;
     description "Number of MKA packets with format errors";
   }
   leaf old-message-number {
     type uint32;
     description "Number of MKA packets with old or replayed message number";
   }
 }
 grouping macsec-connection-information-block {
   leaf connectivity-association-name {
     type string;
     description "Connectivity association name";
   }
   leaf cipher-suite {
     type string;
     description "Cipher suite name";
   }
   leaf encryption {
     type string;
     description "MAC security encryption status";
   }
   leaf offset {
     type uint32;
     description "MAC security offset";
   }
   leaf include-sci {
     type string;
     description "MAC security SCI inclusion status";
   }
   leaf replay-protect {
     type string;
     description "MAC replay protect status";
   }
   leaf replay-protect-window {
     type uint32;
     description "MAC security replay protect window size";
   }
   list outbound-secure-channel {
     leaf sci {
       type string;
       description "MKA outbound secure channel identifier";
     }
     leaf outgoing-packet-number {
       type uint64;
       description "MAC security outgoing packet number";
     }
     list outbound-secure-association {
       leaf association-number {
         type uint32;
         description "MAC security association number";
       }
       leaf association-number-status {
         type string;
         description "MAC security association number status";
       }
       leaf create-time {
         type string;
         description "MAC security association number creation time";
       }
     }
   }
   list inbound-secure-channel {
     leaf sci {
       type string;
       description "MKA outbound secure channel identifier";
     }
     list inbound-secure-association {
       leaf association-number {
         type uint32;
         description "MAC security association number";
       }
       leaf association-number-status {
         type string;
         description "MAC security association number status";
       }
       leaf create-time {
         type string;
         description "MAC security association number creation time";
       }
     }
   }
 }
 grouping macsec-statistics-block {
   leaf interface-name {
     type string;
   }
   list secure-channel-sent {
     leaf encrypted-packets {
       type uint64;
       description "Macsec encrypted packets sent";
     }
     leaf encrypted-bytes {
       type uint64;
       description "Macsec encrypted bytes sent";
     }
     leaf protected-packets {
       type uint64;
       description "Macsec packets sent with only integrity protection";
     }
     leaf protected-bytes {
       type uint64;
       description "Macsec bytes sent with only integrity protection";
     }
   }
   list secure-association-sent {
     leaf encrypted-packets {
       type uint64;
       description "Macsec encrypted packets sent";
     }
     leaf encrypted-bytes {
       type uint64;
       description "Macsec encrypted bytes sent";
     }
     leaf protected-packets {
       type uint64;
       description "Macsec packets sent with only integrity protection";
     }
     leaf protected-bytes {
       type uint64;
       description "Macsec bytes sent with only integrity protection";
     }
   }
   list secure-channel-received {
     leaf ok-packets {
       type uint64;
       description "Macsec packets accepted";
     }
     leaf decrypted-packets {
       type uint64;
       description "Macsec received packets decrypted";
     }
     leaf decrypted-bytes {
       type uint64;
       description "Macsec received bytes decrypted";
     }
     leaf validated-packets {
       type uint64;
       description "Macsec received packets validated";
     }
     leaf validated-bytes {
       type uint64;
       description "Macsec received bytes validated";
     }
   }
   list secure-association-received {
     leaf ok-packets {
       type uint64;
       description "Macsec packets accepted";
     }
     leaf decrypted-packets {
       type uint64;
       description "Macsec received packets decrypted";
     }
     leaf decrypted-bytes {
       type uint64;
       description "Macsec received bytes decrypted";
     }
     leaf validated-packets {
       type uint64;
       description "Macsec received packets validated";
     }
     leaf validated-bytes {
       type uint64;
       description "Macsec received bytes validated";
     }
   }
   list macsec-error-information {
     list secure-channel-sent-errors {
       leaf untagged-packets {
         type uint64;
         description "Macsec untagged packets";
       }
       leaf toolong-packets {
         type uint64;
         description "Macsec too long packets transmitted on a secure channel";
       }
     }
     list secure-channel-received-errors {
       leaf control-packets {
         type uint64;
         description "Macsec control packets received on a secure channel";
       }
       leaf tagged-miss-packets {
         type uint64;
         description "Macsec tagged miss packets received on a secure channel";
       }
       leaf untagged-hit-packets {
         type uint64;
         description "Macsec untagged hit packets received on a secure channel";
       }
       leaf untagged-packets {
         type uint64;
         description "Macsec untagged packets";
       }
       leaf notag-packets {
         type uint64;
         description "Macsec no tag packets received on a secure channel";
       }
       leaf badtag-packets {
         type uint64;
         description "Macsec bad tag packets received on a secure channel";
       }
       leaf unknown-sci-packets {
         type uint64;
         description "Macsec unknown sci packets received on a secure channel";
       }
       leaf no-sci-packets {
         type uint64;
         description "Macsec no sci packets received on a secure channel";
       }
       leaf control-pass-packets {
         type uint64;
         description "Macsec allowed control packets received on a secure channel";
       }
       leaf control-fail-packets {
         type uint64;
         description "Macsec dropped control packets received on a secure channel";
       }
       leaf uncontrol-pass-packets {
         type uint64;
         description "Macsec allowed uncontrol packets received on a secure channel";
       }
       leaf uncontrol-fail-packets {
         type uint64;
         description "Macsec dropped uncontrol packets received on a secure channel";
       }
     }
     list secure-channel-received-extended {
       leaf hit-dropped-packets {
         type uint64;
         description "Macsec hit dropped packets received on a security channel";
       }
       leaf invalid-packets {
         type uint64;
         description "Macsec invalid packets accepted on a security channel";
       }
       leaf late-packets {
         type uint64;
         description "Macsec late packets dropped on a security channel";
       }
       leaf delayed-packets {
         type uint64;
         description "Macsec delayed packets accepted on a security channel";
       }
       leaf unchecked-packets {
         type uint64;
         description "Macsec unchecked packets accepted on a security channel";
       }
       leaf notvalid-packets {
         type uint64;
         description "Macsec not valid packets dropped on a security channel";
       }
       leaf notusing-sa-packets {
         type uint64;
         description "Macsec not using sa packets received on a security channel";
       }
       leaf unused-sa-packets {
         type uint64;
         description "Macsec unused sa packets received on a security channel";
       }
     }
   }
 }
 }
