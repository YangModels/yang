/*
 * Copyright (c) 2017 Juniper Networks, Inc.
 * All rights reserved.
 */
 module show-agent {
  namespace "http://yang.juniper.net/yang/1.1/jrpc/show-agent/junos-es/17.2R1.13";
  prefix show-agent;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc sensor-information {
     description "Show agentd's installed sensor information";
     output {
       container sensor-information {
         uses sensor-information-block;
       }
     }
   }
 grouping sensor-information-block {
   list sensor {
     description "Show sensor details";
     leaf sensor-name {
       type string;
       description "Sensor name";
     }
     leaf resource-name {
       type string;
       description "Resource name";
     }
     leaf sensor-version {
       type string;
       description "Sensor version";
     }
     leaf sensor-id {
       type uint32;
       description "Sensor-ID Derived from Sensor name";
     }
     leaf resource-filter {
       type string;
       description "Resource filter";
     }
     leaf subscription-id {
       type uint64;
       description "Telemetry subscription ID";
     }
     leaf parent-sensor-name {
       type string;
       description "Parent sensor to which this sensor belongs, Not applicable otherwise";
     }
     leaf components {
       type uint64;
       description "Component(s) to which this sensor belongs, Not applicable otherwise";
     }
     container server-information {
       description "Show server Information";
       leaf server-name {
         type string;
         description "Server name";
       }
       leaf scope-id {
         type string;
         description "Scope-id";
       }
       leaf remote-address {
         type string;
         description "Address of the physical interface.";
       }
       leaf remote-port {
         type uint32;
         description "Port";
       }
       leaf transport {
         type string;
         description "Transport";
       }
     }
     container profile-information {
       description "Show Profile Information";
       leaf profile-name {
         type string;
         description "Profilename";
       }
       leaf rep-interval {
         type int32;
         description "Reporting interval (in seconds)";
       }
       leaf payload-size {
         type int32;
         description "Payload size";
       }
       leaf local-address {
         type string;
         description "Address of the physical interface.";
       }
       leaf local-port {
         type uint32;
         description "Port";
       }
       leaf timestamp {
         type string;
         description "Timestamp";
       }
       leaf serverformat {
         type string;
         description "Format";
       }
       leaf dscp {
         type string;
         description "DSCP";
       }
       leaf forwarding-class {
         type string;
         description "Forwarding-class";
       }
     }
   }
 }
 }
