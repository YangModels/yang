/*
 * Copyright (c) 2017 Juniper Networks, Inc.
 * All rights reserved.
 */
 module show-bgp {
  namespace "http://yang.juniper.net/yang/1.1/jrpc/show-bgp/junos-es/17.2R1.13";
  prefix show-bgp;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-bgp-summary-information {
     description "Show overview of BGP information";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
           }
         }
       }
       leaf group {
         description "Show overview of bgp information for a particular group";
         type string;
       }
       leaf exact-instance {
         description "Show peer information for a particular instance";
         type string;
       }
       leaf instance {
         description "Show peer information for instances with this prefix";
         type string;
       }
     }
     output {
       container bgp-information {
         uses bgp-information-block;
       }
     }
   }
   rpc get-bgp-replication-information {
     description "BGP NSR replication state between master and backup";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container bgp-sync-information {
         uses bgp-sync-information-block;
       }
     }
   }
   rpc get-bgp-group-information {
     description "Show the BGP group database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "summary" {
             description "Display summary output";
           }
           enum "brief" {
             description "Display brief output (default)";
           }
           enum "detail" {
             description "Display detailed output";
           }
         }
       }
       leaf exact-instance {
         description "Show peer information for a particular instance";
         type string;
       }
       leaf instance {
         description "Show peer information for instances with this prefix";
         type string;
       }
       leaf group-name {
         description "Show group information for a particular group";
         type string;
       }
     }
     output {
       container bgp-group-information {
         uses bgp-group-information-block;
       }
     }
   }
   rpc get-bgp-rtf-information {
     description "Show route target filtering information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf group-name {
         description "Show group information for a particular group";
         type string;
       }
     }
     output {
       container bgp-rtf-information {
         uses bgp-rtf-information-block;
       }
     }
   }
   rpc get-bgp-traffic-statistics-information {
     description "Show packet statistics for labeled BGP routes";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
           }
         }
       }
       leaf verbosity_level {
         default "brief";
         type enumeration {
           enum "brief" {
             description "Display brief output (default)";
           }
           enum "detail" {
             description "Display detailed output";
           }
         }
       }
       leaf group-name {
         description "Show group information for a particular group";
         type string;
       }
     }
     output {
       container bgp-traffic-statistics-information {
         uses bgp-traffic-statistics-information-block;
       }
     }
   }
   rpc get-bgp-group-output-queue-information {
     description "Show BGP output queues by priority";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
           }
         }
       }
       leaf group-name {
         description "Show group information for a particular group";
         type string;
       }
     }
   }
   rpc get-bgp-neighbor-information {
     description "Show the BGP neighbor database";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
           }
         }
       }
       leaf exact-instance {
         description "Show peer information for a particular instance";
         type string;
       }
       leaf instance {
         description "Show peer information for instances with this prefix";
         type string;
       }
       leaf neighbor-address {
         description "Show the neighbor database for a particular neighbor";
         type string;
       }
     }
     output {
       container bgp-information {
         uses bgp-information-block;
       }
     }
   }
   rpc get-bgp-orf-information {
     description "Show outbound route filtering information";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
           }
         }
       }
       leaf verbosity_level {
         default "brief";
         type enumeration {
           enum "brief" {
             description "Display brief output (default)";
           }
           enum "detail" {
             description "Display detailed output";
           }
         }
       }
       leaf instance {
         description "Show ORF information for instances with this prefix";
         type string;
       }
       leaf neighbor-address {
         description "Show ORF information for a particular neighbor";
         type string;
       }
     }
     output {
       container bgp-orf-information {
         uses bgp-orf-information-block;
       }
     }
   }
   rpc get-bgp-output-queue-information {
     description "Show outbound routes queue depths by priority";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
           }
         }
       }
       leaf instance {
         description "Show route queue depths for instances with this prefix";
         type string;
       }
       leaf neighbor-address {
         description "Show route queue depths for a particular neighbor";
         type string;
       }
     }
   }
   rpc get-bgp-monitoring-protocol-statistics {
     description "Show BGP Monitoring Protocol information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf station-name {
         description "Show information for a particular station";
         type string;
       }
     }
     output {
       container bgp-information {
         uses bgp-information-block;
       }
     }
   }
 grouping bgp-information-block {
   leaf group-count {
     type int32;
   }
   leaf peer-count {
     type int32;
     description "Total number of peers";
   }
   leaf down-peer-count {
     type int32;
   }
   leaf igp-converging {
     type empty;
     description "This tag is present if BGP is quenched because the IGP is still converging";
   }
   leaf unconfigured-peer-count {
     type int32;
   }
   leaf half-open-peer-count {
     type int32;
   }
   container bgp-family-stat {
     container detail {
       leaf nlri-type {
         type string;
         description "Type of NLRI being limited";
       }
       leaf bgp-nlri-send-time {
         type int32;
         description "Time for initial send by peer";
       }
       leaf bgp-nlri-recv-time {
         type int32;
         description "Time for initial receive by peer";
       }
     }
   }
   list bgp-rib {
     list brief {
       leaf name {
         type string;
       }
       leaf total-prefix-count {
         type int32;
         description "Total number of prefixes in this RIB";
       }
       leaf active-prefix-count {
         type int32;
         description "Number of active prefixes";
       }
       leaf suppressed-prefix-count {
         type int32;
         description "Number of prefixes suppressed due to damping";
       }
       leaf history-prefix-count {
         type int32;
         description "Number of prefixes with damping history maintained";
       }
       leaf damped-prefix-count {
         type int32;
         description "Number of prefixes in any damped state";
       }
       leaf pending-prefix-count {
         type int32;
         description "Number of prefixes with pending changes";
       }
     }
     list terse {
       leaf name {
         type string;
       }
       leaf active-prefix-count {
         type int32;
         description "Number of active prefixes";
       }
       leaf received-prefix-count {
         type int32;
         description "For a peer RIB, number of prefixes received from this peer";
       }
       leaf accepted-prefix-count {
         type int32;
         description "For a peer RIB, number of prefixes from this peer accepted by policy";
       }
       leaf suppressed-prefix-count {
         type int32;
         description "Number of prefixes suppressed due to damping";
       }
     }
     list summary {
       leaf name {
         type string;
       }
       leaf active-prefix-count {
         type int32;
         description "Number of active prefixes";
       }
       leaf received-prefix-count {
         type int32;
         description "For a peer RIB, number of prefixes received from this peer";
       }
       leaf accepted-prefix-count {
         type int32;
         description "For a peer RIB, number of prefixes from this peer accepted by policy";
       }
       leaf suppressed-prefix-count {
         type int32;
         description "Number of prefixes suppressed due to damping";
       }
       leaf active-external-prefix-count {
         type int32;
         description "Number of active prefixes received from external peers";
       }
       leaf total-external-prefix-count {
         type int32;
         description "Total number of prefixes received from external peers";
       }
       leaf accepted-external-prefix-count {
         type int32;
         description "Number of accepted prefixes received from external peers";
       }
       leaf suppressed-external-prefix-count {
         type int32;
         description "Number of external prefixes suppressed due to damping";
       }
       leaf active-internal-prefix-count {
         type int32;
         description "Number of active prefixes received from internal peers";
       }
       leaf total-internal-prefix-count {
         type int32;
         description "Total number of prefixes received from internal peers";
       }
       leaf accepted-internal-prefix-count {
         type int32;
         description "Number of accepted prefixes received from internal peers";
       }
       leaf suppressed-internal-prefix-count {
         type int32;
         description "Number of internal prefixes suppressed due to damping";
       }
     }
     list detail {
       leaf name {
         type string;
       }
       leaf rib-bit {
         type string;
       }
       leaf bgp-rib-state {
         type string;
       }
       leaf vpn-rib-state {
         type string;
       }
       leaf send-state {
         type string;
       }
       leaf active-prefix-count {
         type int32;
         description "Number of active prefixes";
       }
       leaf received-prefix-count {
         type int32;
         description "For a peer RIB, number of prefixes received from this peer";
       }
       leaf accepted-prefix-count {
         type int32;
         description "For a peer RIB, number of prefixes from this peer accepted by policy";
       }
       leaf suppressed-prefix-count {
         type int32;
         description "Number of prefixes suppressed due to damping";
       }
       leaf stale-prefix-count {
         type int32;
         description "Number of prefixes marked as stale";
       }
       leaf llgr-stale-prefix-count {
         type int32;
         description "Number of prefixes marked as LLGR stale";
       }
       leaf active-external-prefix-count {
         type int32;
         description "Number of active prefixes received from external peers";
       }
       leaf total-external-prefix-count {
         type int32;
         description "Total number of prefixes received from external peers";
       }
       leaf suppressed-external-prefix-count {
         type int32;
         description "Number of external prefixes suppressed due to damping";
       }
       leaf active-internal-prefix-count {
         type int32;
         description "Number of active prefixes received from internal peers";
       }
       leaf total-internal-prefix-count {
         type int32;
         description "Total number of prefixes received from internal peers";
       }
       leaf suppressed-internal-prefix-count {
         type int32;
         description "Number of internal prefixes suppressed due to damping";
       }
       leaf advertised-prefix-count {
         type int32;
         description "Number of prefixes present in the RIB-OUT";
       }
     }
   }
   list bgp-peer {
     description "Operational and configuration information for a BGP peer";
     list terse {
       description "Operational and configuration information for a BGP peer";
       leaf bgp-peer.heading {
         type string;
         description "Operational and configuration information for a BGP peer";
       }
       leaf peer-address {
         type ipaddr;
       }
       leaf peer-as {
         type int32;
         description "Peer AS number";
       }
       leaf input-messages {
         type int32;
       }
       leaf output-messages {
         type int32;
       }
       leaf route-queue-count {
         type int32;
         description "Total number of routes queued for output to this peer";
       }
       leaf flap-count {
         type int32;
         description "Number of times BGP sessions have gone down";
       }
       leaf elapsed-time {
         type string;
         description "Time this adjacency or session has been up or down";
       }
       leaf peer-state {
         type string;
       }
       container bgp-option-information {
         container prefix-limit {
         }
         container accepted-prefix-limit {
           description "Limit number of prefixes accepted by policy";
         }
         container addpath-send {
         }
         container addpath-receive {
         }
         container nlri-information {
           leaf nlri-type {
             type string;
             description "Type of NLRI being limited";
           }
           leaf nlri-flow-novalidate {
             type string;
             description "Policy to accept flow routes without validation";
           }
           leaf nlri-output-queue-priority {
             type string;
             description "Default address family output queue priority";
           }
           leaf nlri-route-refresh-priority {
             type string;
             description "Default address family route-refresh priority";
           }
           leaf nlri-withdraw-priority {
             type string;
             description "Default address family withdraw priority";
           }
           container nlri-flags {
             leaf bgp-nlri-flag-explicit-null-for-all-routes {
               type empty;
             }
             leaf bgp-nlri-flag-explicit-null-for-connected-routes {
               type empty;
             }
             leaf bgp-nlri-flag-aggregate-label {
               type empty;
             }
             leaf bgp-nlri-flag-per-prefix-label {
               type empty;
             }
             leaf bgp-nlri-flag-per-group-label {
               type empty;
             }
             leaf bgp-nlri-flag-no-install-forwarding {
               type empty;
             }
             leaf bgp-nlri-flag-delay-route-advt {
               type empty;
             }
             leaf bgp-nlri-flag-traffic-stats {
               type empty;
             }
             leaf bgp-nlri-flag-l2vpn-status-vector {
               type empty;
             }
             leaf bgp-nlri-flag-no-l2vpn-status-vector {
               type empty;
             }
             leaf bgp-nlri-flag-strip-nexthop {
               type empty;
             }
             leaf bgp-nlri-flag-allow-po-add-nexthop {
               type empty;
             }
           }
           container nlri-traffic-stats {
             leaf traffic-stats-interval {
               type int32;
             }
             container tracing-information {
               leaf flags {
                 type string;
                 description "Enabled trace flags";
               }
               leaf filename {
                 type string;
                 description "Name of the trace file";
               }
               leaf filesize {
                 type int32;
                 description "Maximum size of the trace file";
               }
               leaf filelimit {
                 type int32;
                 description "Maximum number of retained trace files";
               }
             }
           }
           container output-queues {
             description "BGP output queues statistics";
             container output-queue {
               description "BGP output queues statistics";
               leaf time-series {
                 type string;
               }
               list class {
                 description "An instance of BGP output queue statistics";
                 leaf priority-type {
                   type string;
                   description "BGP output queue priority type";
                 }
                 leaf rank {
                   type int32;
                   description "BGP output queue rank for priority type";
                 }
                 leaf token-count {
                   type int32;
                   description "BGP output queue token count for priority";
                 }
                 leaf output-queue-route-count {
                   type int32;
                   description "BGP output queue route count for priority";
                 }
               }
             }
           }
         }
       }
       container egress-protection {
         container nlri-egress-protection {
           leaf nlri-type {
             type string;
             description "Type of NLRI being limited";
           }
           leaf bgp-context-id {
             type ipaddr;
           }
           leaf bgp-import-policy {
             type string;
           }
         }
         list ep-backup-table {
           leaf ep-backup-rib-name {
             type string;
             description "Instance backup RIB";
           }
           leaf ep-backup-link {
             type string;
             description "Vt interface";
           }
           leaf ep-backup-rib-id {
             type int32;
             description "RIB Identifier";
           }
           leaf ep-backup-kern-id {
             type int32;
             description "FIB Identifier";
           }
         }
         list ep-instance-table {
           leaf ep-instance-name {
             type string;
           }
           leaf ep-instance-type {
             type string;
             description "Instance type";
           }
           leaf ep-instance-protection-type {
             type string;
             description "Instance request protected";
           }
         }
       }
       list bgp-output-queue {
       }
       list bgp-rib {
         list brief {
           leaf name {
             type string;
           }
           leaf total-prefix-count {
             type int32;
             description "Total number of prefixes in this RIB";
           }
           leaf active-prefix-count {
             type int32;
             description "Number of active prefixes";
           }
           leaf suppressed-prefix-count {
             type int32;
             description "Number of prefixes suppressed due to damping";
           }
           leaf history-prefix-count {
             type int32;
             description "Number of prefixes with damping history maintained";
           }
           leaf damped-prefix-count {
             type int32;
             description "Number of prefixes in any damped state";
           }
           leaf pending-prefix-count {
             type int32;
             description "Number of prefixes with pending changes";
           }
         }
         list terse {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
         }
         list summary {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf active-external-prefix-count {
             type int32;
             description "Number of active prefixes received from external peers";
           }
           leaf total-external-prefix-count {
             type int32;
             description "Total number of prefixes received from external peers";
           }
           leaf accepted-external-prefix-count {
             type int32;
             description "Number of accepted prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf accepted-internal-prefix-count {
             type int32;
             description "Number of accepted prefixes received from internal peers";
           }
           leaf suppressed-internal-prefix-count {
             type int32;
             description "Number of internal prefixes suppressed due to damping";
           }
         }
         list detail {
           leaf name {
             type string;
           }
           leaf rib-bit {
             type string;
           }
           leaf bgp-rib-state {
             type string;
           }
           leaf vpn-rib-state {
             type string;
           }
           leaf send-state {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf stale-prefix-count {
             type int32;
             description "Number of prefixes marked as stale";
           }
           leaf llgr-stale-prefix-count {
             type int32;
             description "Number of prefixes marked as LLGR stale";
           }
           leaf active-external-prefix-count {
             type int32;
             description "Number of active prefixes received from external peers";
           }
           leaf total-external-prefix-count {
             type int32;
             description "Total number of prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf suppressed-internal-prefix-count {
             type int32;
             description "Number of internal prefixes suppressed due to damping";
           }
           leaf advertised-prefix-count {
             type int32;
             description "Number of prefixes present in the RIB-OUT";
           }
         }
       }
       container bgp-family-stat {
         container detail {
           leaf nlri-type {
             type string;
             description "Type of NLRI being limited";
           }
           leaf bgp-nlri-send-time {
             type int32;
             description "Time for initial send by peer";
           }
           leaf bgp-nlri-recv-time {
             type int32;
             description "Time for initial receive by peer";
           }
         }
       }
       list entropy-label-info {
         leaf nlri-type {
           type string;
           description "Type of NLRI being limited";
         }
         leaf entropy-label {
           type string;
           description "Entropy label";
         }
         leaf entropy-label-import-policy {
           type string;
         }
         leaf entropy-label-no-next-hop-validation {
           type string;
           description "Entropy label no next hop validation";
         }
         leaf entropy-label-capability {
           type string;
           description "Local entropy label capability";
         }
         leaf entropy-label-stitching-capability {
           type string;
           description "Entropy label stitching capability";
         }
       }
       container bgp-malformed-attributes {
       }
     }
     list detail {
       description "Operational and configuration information for a BGP peer";
       leaf peer-address {
         type ipaddr;
       }
       leaf peer-as {
         type int32;
         description "Peer AS number";
       }
       leaf local-address {
         type ipaddr;
       }
       leaf local-as {
         type int32;
         description "Local AS number";
       }
       leaf description {
         type string;
       }
       leaf peer-group {
         type string;
         description "BGP peer-group peer belongs to";
       }
       leaf peer-cfg-rti {
         type string;
         description "Routing-instance peer is configured in";
       }
       leaf peer-fwd-rti {
         type string;
         description "Peer's forwarding-context routing-instance";
       }
       leaf peer-type {
         type string;
       }
       leaf peer-state {
         type string;
       }
       leaf route-reflector-client {
         type empty;
       }
       leaf peer-flags {
         type string;
       }
       leaf last-state {
         type string;
       }
       leaf last-event {
         type string;
       }
       leaf last-error {
         type string;
       }
       leaf flap-count {
         type int32;
         description "Number of times BGP sessions have gone down";
       }
       leaf last-flap-event {
         type string;
       }
       leaf peer-id {
         type ipaddr;
       }
       leaf local-id {
         type ipaddr;
       }
       leaf active-holdtime {
         type int32;
       }
       leaf keepalive-interval {
         type int32;
       }
       leaf group-index {
         type int32;
       }
       leaf peer-index {
         type int32;
       }
       leaf local-interface-name {
         type string;
         description "Logical interface name";
       }
       leaf nlri-type-peer {
         type string;
       }
       leaf nlri-type-session {
         type string;
       }
       leaf peer-no-refresh {
         type empty;
         description "Present if this peer does not support refresh";
       }
       leaf peer-refresh-capability {
         type int32;
         description "Version of refresh capability supported by this peer";
       }
       leaf peer-4byte-as-capability-not-supported {
         type empty;
         description "This peer does not support 4 byte AS extension";
       }
       leaf peer-4byte-as-capability-advertised {
         type int32;
         description "4 byte Autonomous System capability advertised by this peer";
       }
       leaf peer-addpath-not-supported {
         type empty;
         description "This peer does not support addpath";
       }
       leaf peer-addpath-ronly-nlri {
         type string;
         description "Types of NLRI for which peer advertised recv capability";
       }
       leaf peer-addpath-sonly-nlri {
         type string;
         description "Types of NLRI for which peer advertised send capability";
       }
       leaf peer-addpath-rs-nlri {
         type string;
         description "Types of NLRI for which peer advertised send/recv cap";
       }
       leaf peer-delay-route-advertisements {
         type string;
       }
       leaf local-ext-nh-nlri {
         type string;
         description "Types of NLRI for which we advertised extend nh cap";
       }
       leaf peer-ext-nh-nlri {
         type string;
         description "Types of NLRI for which peer advertised extend nh cap";
       }
       leaf peer-restart-nlri-configured {
         type string;
       }
       leaf peer-restart-time-configured {
         type string;
       }
       leaf peer-stale-route-time-configured {
         type string;
       }
       leaf peer-no-restart {
         type empty;
         description "Present if this peer does not support graceful restart restarter mode";
       }
       leaf peer-restart-nlri-received {
         type string;
       }
       leaf peer-restart-time-received {
         type int32;
       }
       leaf peer-restart-flags-received {
         type string;
       }
       leaf peer-restart-nlri-can-save-state {
         type string;
       }
       leaf peer-restart-nlri-state-saved {
         type string;
       }
       leaf peer-restart-nlri-negotiated {
         type string;
       }
       leaf peer-end-of-rib-received {
         type string;
       }
       leaf peer-end-of-rib-sent {
         type string;
       }
       leaf peer-delay-end-of-rib {
         type string;
       }
       leaf peer-no-helper {
         type empty;
         description "Present if this peer does not support graceful restart receiver mode";
       }
       leaf peer-restart-nlri-held {
         type string;
       }
       leaf peer-restart-remaining-time {
         type string;
       }
       leaf peer-stale-remaining-time {
         type string;
       }
       leaf peer-llgr-nlri-configured {
         type string;
       }
       leaf peer-no-llgr-restarter {
         type empty;
         description "Present if this peer does not support long-lived graceful restart restarter mode";
       }
       leaf peer-llgr-nlri-restarter {
         type string;
       }
       leaf peer-llgr-nlri-state-saved {
         type string;
       }
       leaf peer-no-llgr-helper {
         type empty;
         description "Present if this peer does not support long-lived graceful restart receiver mode";
       }
       leaf peer-llgr-nlri-times {
         type string;
         description "NLRIs and times before long-lived stale routes are deleted";
       }
       leaf last-received {
         type int32;
       }
       leaf last-sent {
         type int32;
       }
       leaf last-checked {
         type int32;
       }
       leaf input-messages {
         type int32;
       }
       leaf input-updates {
         type int32;
       }
       leaf input-refreshes {
         type int32;
       }
       leaf input-octets {
         type int32;
       }
       leaf output-messages {
         type int32;
       }
       leaf output-updates {
         type int32;
       }
       leaf output-refreshes {
         type int32;
       }
       leaf output-octets {
         type int32;
       }
       leaf input-checksum {
         type int32;
       }
       leaf output-checksum {
         type int32;
       }
       leaf input-checksum-err {
         type int32;
       }
       leaf input-drop-path-attributes {
         type string;
       }
       leaf input-ignore-path-attributes {
         type string;
       }
       leaf buffered-octets-rx {
         type int32;
         description "Number of octets that have been received and are still buffered";
       }
       leaf buffered-octets-tx {
         type int32;
         description "Number of octets in the transmit buffer";
       }
       leaf gather-buffered-octets-tx {
         type int32;
         description "Number of octets in the gather transmit buffer";
       }
       container bgp-option-information {
         leaf export-policy {
           type string;
         }
         leaf import-policy {
           type string;
         }
         leaf advertise-bgp-static-policy {
           type string;
         }
         leaf bgp-options {
           type string;
         }
         leaf bgp-options2 {
           type string;
         }
         leaf bgp-options-extended {
           type string;
         }
         leaf remove-private-options {
           type string;
         }
         leaf authentication-key {
           type string;
         }
         leaf authentication-key-chain {
           type string;
           description "Name of authentication key chain";
         }
         leaf authentication-algorithm {
           type string;
           description "Name of authentication algorithm";
         }
         leaf authentication-configured {
           type empty;
         }
         leaf address-families {
           type string;
         }
         leaf drop-path-attributes {
           type string;
         }
         leaf ignore-path-attributes {
           type string;
         }
         leaf holdtime {
           type int32;
           description "Delay before timing out the adjacency (default is 180 seconds)";
         }
         leaf metric-out {
           type int32;
         }
         leaf preference {
           type int32;
           description "Preference for the route";
         }
         leaf local-preference {
           type int32;
         }
         leaf local-as-private {
           type empty;
         }
         leaf local-system-as {
           type int32;
         }
         leaf receive-buffer-size {
           type int32;
         }
         leaf send-buffer-size {
           type int32;
         }
         leaf outbound-timer {
           type int32;
         }
         leaf med-action {
           type string;
         }
         leaf ipsec-sa {
           type string;
         }
         leaf bgp-bmp-monitor-peers {
           type string;
         }
         leaf bgp-bmp-route-monitoring-none {
           type empty;
         }
         leaf bgp-bmp-route-monitoring-prepolicy {
           type empty;
         }
         leaf bgp-bmp-prepolicy-exclude-non-feasible {
           type empty;
         }
         leaf bgp-bmp-route-monitoring-postpolicy {
           type empty;
         }
         leaf bgp-bmp-postpolicy-exclude-non-eligible {
           type empty;
         }
         container prefix-limit {
         }
         container accepted-prefix-limit {
           description "Limit number of prefixes accepted by policy";
         }
         container addpath-send {
         }
         container addpath-receive {
         }
         container aigp-mode {
           leaf nlri-type {
             type string;
             description "Type of NLRI being limited";
           }
         }
         container family-damping-info {
           leaf nlri-type {
             type string;
             description "Type of NLRI being limited";
           }
         }
         container protection {
           leaf nlri-type {
             type string;
             description "Type of NLRI being limited";
           }
         }
         container nlri-information {
           leaf nlri-type {
             type string;
             description "Type of NLRI being limited";
           }
           leaf nlri-flow-novalidate {
             type string;
             description "Policy to accept flow routes without validation";
           }
           container nlri-flags {
             leaf bgp-nlri-flag-explicit-null-for-all-routes {
               type empty;
             }
             leaf bgp-nlri-flag-explicit-null-for-connected-routes {
               type empty;
             }
             leaf bgp-nlri-flag-aggregate-label {
               type empty;
             }
             leaf bgp-nlri-flag-per-prefix-label {
               type empty;
             }
             leaf bgp-nlri-flag-per-group-label {
               type empty;
             }
             leaf bgp-nlri-flag-no-install-forwarding {
               type empty;
             }
             leaf bgp-nlri-flag-delay-route-advt {
               type empty;
             }
             leaf bgp-nlri-flag-traffic-stats {
               type empty;
             }
             leaf bgp-nlri-flag-l2vpn-status-vector {
               type empty;
             }
             leaf bgp-nlri-flag-no-l2vpn-status-vector {
               type empty;
             }
             leaf bgp-nlri-flag-strip-nexthop {
               type empty;
             }
             leaf bgp-nlri-flag-allow-po-add-nexthop {
               type empty;
             }
           }
           container nlri-traffic-stats {
             leaf traffic-stats-interval {
               type int32;
             }
             container tracing-information {
               leaf flags {
                 type string;
                 description "Enabled trace flags";
               }
               leaf filename {
                 type string;
                 description "Name of the trace file";
               }
               leaf filesize {
                 type int32;
                 description "Maximum size of the trace file";
               }
               leaf filelimit {
                 type int32;
                 description "Maximum number of retained trace files";
               }
             }
           }
           container output-queues {
             description "BGP output queues statistics";
             container output-queue {
               description "BGP output queues statistics";
               leaf time-series {
                 type string;
               }
               list class {
                 description "An instance of BGP output queue statistics";
                 leaf priority-type {
                   type string;
                   description "BGP output queue priority type";
                 }
                 leaf rank {
                   type int32;
                   description "BGP output queue rank for priority type";
                 }
                 leaf token-count {
                   type int32;
                   description "BGP output queue token count for priority";
                 }
                 leaf output-queue-route-count {
                   type int32;
                   description "BGP output queue route count for priority";
                 }
               }
             }
           }
         }
       }
       container bgp-peer-iosession {
         leaf iosession-thread-name {
           type string;
         }
         leaf iosession-state {
           type string;
         }
       }
       container bgp-bfd {
         leaf bfd-configuration-state {
           type string;
           description "BFD configuration state";
         }
         leaf bfd-operational-state {
           type string;
           description "BFD operational state";
         }
       }
       container egress-protection {
         leaf nlri-type {
           type string;
           description "Type of NLRI being limited";
         }
         container nlri-egress-protection {
           leaf bgp-context-id {
             type ipaddr;
           }
           leaf bgp-import-policy {
             type string;
           }
         }
         list ep-backup-table {
           leaf ep-backup-rib-name {
             type string;
             description "Instance backup RIB";
           }
           leaf ep-backup-link {
             type string;
             description "Vt interface";
           }
           leaf ep-backup-rib-id {
             type int32;
             description "RIB Identifier";
           }
           leaf ep-backup-kern-id {
             type int32;
             description "FIB Identifier";
           }
         }
         list ep-instance-table {
           leaf ep-instance-name {
             type string;
           }
           leaf ep-instance-type {
             type string;
             description "Instance type";
           }
           leaf ep-instance-protection-type {
             type string;
             description "Instance request protected";
           }
         }
       }
       list bgp-output-queue {
         leaf number {
           type int32;
         }
         leaf count {
           type int32;
         }
         leaf table-name {
           type string;
           description "Unicast routing table";
         }
         leaf rib-adv-nlri {
           type string;
         }
       }
       list bgp-rib {
         list brief {
           leaf name {
             type string;
           }
           leaf total-prefix-count {
             type int32;
             description "Total number of prefixes in this RIB";
           }
           leaf active-prefix-count {
             type int32;
             description "Number of active prefixes";
           }
           leaf suppressed-prefix-count {
             type int32;
             description "Number of prefixes suppressed due to damping";
           }
           leaf history-prefix-count {
             type int32;
             description "Number of prefixes with damping history maintained";
           }
           leaf damped-prefix-count {
             type int32;
             description "Number of prefixes in any damped state";
           }
           leaf pending-prefix-count {
             type int32;
             description "Number of prefixes with pending changes";
           }
         }
         list terse {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
         }
         list summary {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf active-external-prefix-count {
             type int32;
             description "Number of active prefixes received from external peers";
           }
           leaf total-external-prefix-count {
             type int32;
             description "Total number of prefixes received from external peers";
           }
           leaf accepted-external-prefix-count {
             type int32;
             description "Number of accepted prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf accepted-internal-prefix-count {
             type int32;
             description "Number of accepted prefixes received from internal peers";
           }
           leaf suppressed-internal-prefix-count {
             type int32;
             description "Number of internal prefixes suppressed due to damping";
           }
         }
         list detail {
           leaf name {
             type string;
           }
           leaf rib-bit {
             type string;
           }
           leaf bgp-rib-state {
             type string;
           }
           leaf vpn-rib-state {
             type string;
           }
           leaf send-state {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf stale-prefix-count {
             type int32;
             description "Number of prefixes marked as stale";
           }
           leaf llgr-stale-prefix-count {
             type int32;
             description "Number of prefixes marked as LLGR stale";
           }
           leaf active-external-prefix-count {
             type int32;
             description "Number of active prefixes received from external peers";
           }
           leaf total-external-prefix-count {
             type int32;
             description "Total number of prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf suppressed-internal-prefix-count {
             type int32;
             description "Number of internal prefixes suppressed due to damping";
           }
           leaf advertised-prefix-count {
             type int32;
             description "Number of prefixes present in the RIB-OUT";
           }
         }
       }
       container bgp-family-stat {
         container detail {
           leaf nlri-type {
             type string;
             description "Type of NLRI being limited";
           }
           leaf bgp-nlri-send-time {
             type int32;
             description "Time for initial send by peer";
           }
           leaf bgp-nlri-recv-time {
             type int32;
             description "Time for initial receive by peer";
           }
         }
       }
       list entropy-label-info {
         leaf nlri-type {
           type string;
           description "Type of NLRI being limited";
         }
         leaf entropy-label {
           type string;
           description "Entropy label";
         }
         leaf entropy-label-import-policy {
           type string;
         }
         leaf entropy-label-no-next-hop-validation {
           type string;
           description "Entropy label no next hop validation";
         }
         leaf entropy-label-capability {
           type string;
           description "Local entropy label capability";
         }
         leaf entropy-label-stitching-capability {
           type string;
           description "Entropy label stitching capability";
         }
       }
       container bgp-error {
         leaf name {
           type string;
         }
         leaf send-count {
           type int32;
         }
         leaf receive-count {
           type int32;
         }
       }
       container bgp-malformed-attributes {
         container malformed-information {
           leaf log-interval {
             type int32;
           }
           leaf route-limit {
             type int32;
           }
         }
         container path-attribute {
           leaf name {
             type string;
           }
           leaf code {
             type int32;
           }
           leaf last-recv {
             type int32;
           }
           leaf total-recv {
             type int32;
           }
         }
       }
       container route-queue {
         leaf timer {
           type string;
         }
         leaf state {
           type string;
           description "HFRR profile Current state";
         }
         leaf element {
           type string;
         }
       }
       container tracing-information {
         leaf flags {
           type string;
           description "Enabled trace flags";
         }
         leaf filename {
           type string;
           description "Name of the trace file";
         }
         leaf filesize {
           type int32;
           description "Maximum size of the trace file";
         }
         leaf filelimit {
           type int32;
           description "Maximum number of retained trace files";
         }
       }
     }
     list output-queue {
       description "Operational and configuration information for a BGP peer";
       leaf peer-address {
         type ipaddr;
       }
       leaf peer-as {
         type int32;
         description "Peer AS number";
       }
       leaf local-address {
         type ipaddr;
       }
       leaf local-as {
         type int32;
         description "Local AS number";
       }
       leaf description {
         type string;
       }
       container bgp-option-information {
         container prefix-limit {
         }
         container accepted-prefix-limit {
           description "Limit number of prefixes accepted by policy";
         }
         container addpath-send {
         }
         container addpath-receive {
         }
         container nlri-information {
           leaf nlri-type {
             type string;
             description "Type of NLRI being limited";
           }
           leaf nlri-flow-novalidate {
             type string;
             description "Policy to accept flow routes without validation";
           }
           leaf nlri-output-queue-priority {
             type string;
             description "Default address family output queue priority";
           }
           leaf nlri-route-refresh-priority {
             type string;
             description "Default address family route-refresh priority";
           }
           leaf nlri-withdraw-priority {
             type string;
             description "Default address family withdraw priority";
           }
           container nlri-flags {
             leaf bgp-nlri-flag-explicit-null-for-all-routes {
               type empty;
             }
             leaf bgp-nlri-flag-explicit-null-for-connected-routes {
               type empty;
             }
             leaf bgp-nlri-flag-aggregate-label {
               type empty;
             }
             leaf bgp-nlri-flag-per-prefix-label {
               type empty;
             }
             leaf bgp-nlri-flag-per-group-label {
               type empty;
             }
             leaf bgp-nlri-flag-no-install-forwarding {
               type empty;
             }
             leaf bgp-nlri-flag-delay-route-advt {
               type empty;
             }
             leaf bgp-nlri-flag-traffic-stats {
               type empty;
             }
             leaf bgp-nlri-flag-l2vpn-status-vector {
               type empty;
             }
             leaf bgp-nlri-flag-no-l2vpn-status-vector {
               type empty;
             }
             leaf bgp-nlri-flag-strip-nexthop {
               type empty;
             }
             leaf bgp-nlri-flag-allow-po-add-nexthop {
               type empty;
             }
           }
           container nlri-traffic-stats {
             leaf traffic-stats-interval {
               type int32;
             }
             container tracing-information {
               leaf flags {
                 type string;
                 description "Enabled trace flags";
               }
               leaf filename {
                 type string;
                 description "Name of the trace file";
               }
               leaf filesize {
                 type int32;
                 description "Maximum size of the trace file";
               }
               leaf filelimit {
                 type int32;
                 description "Maximum number of retained trace files";
               }
             }
           }
           container output-queues {
             description "BGP output queues statistics";
             container output-queue {
               description "BGP output queues statistics";
               leaf time-series {
                 type string;
               }
               list class {
                 description "An instance of BGP output queue statistics";
                 leaf priority-type {
                   type string;
                   description "BGP output queue priority type";
                 }
                 leaf rank {
                   type int32;
                   description "BGP output queue rank for priority type";
                 }
                 leaf token-count {
                   type int32;
                   description "BGP output queue token count for priority";
                 }
                 leaf output-queue-route-count {
                   type int32;
                   description "BGP output queue route count for priority";
                 }
               }
             }
           }
         }
       }
       container egress-protection {
         container nlri-egress-protection {
           leaf nlri-type {
             type string;
             description "Type of NLRI being limited";
           }
           leaf bgp-context-id {
             type ipaddr;
           }
           leaf bgp-import-policy {
             type string;
           }
         }
         list ep-backup-table {
           leaf ep-backup-rib-name {
             type string;
             description "Instance backup RIB";
           }
           leaf ep-backup-link {
             type string;
             description "Vt interface";
           }
           leaf ep-backup-rib-id {
             type int32;
             description "RIB Identifier";
           }
           leaf ep-backup-kern-id {
             type int32;
             description "FIB Identifier";
           }
         }
         list ep-instance-table {
           leaf ep-instance-name {
             type string;
           }
           leaf ep-instance-type {
             type string;
             description "Instance type";
           }
           leaf ep-instance-protection-type {
             type string;
             description "Instance request protected";
           }
         }
       }
       list bgp-output-queue {
         leaf number {
           type int32;
         }
         leaf count {
           type int32;
         }
         leaf table-name {
           type string;
           description "Unicast routing table";
         }
         leaf rib-adv-nlri {
           type string;
         }
         leaf time-series {
           type string;
         }
         list class {
           description "An instance of BGP output queue statistics";
           leaf priority-type {
             type string;
             description "BGP output queue priority type";
           }
           leaf rank {
             type int32;
             description "BGP output queue rank for priority type";
           }
           leaf token-count {
             type int32;
             description "BGP output queue token count for priority";
           }
         }
       }
       list bgp-rib {
         list brief {
           leaf name {
             type string;
           }
           leaf total-prefix-count {
             type int32;
             description "Total number of prefixes in this RIB";
           }
           leaf active-prefix-count {
             type int32;
             description "Number of active prefixes";
           }
           leaf suppressed-prefix-count {
             type int32;
             description "Number of prefixes suppressed due to damping";
           }
           leaf history-prefix-count {
             type int32;
             description "Number of prefixes with damping history maintained";
           }
           leaf damped-prefix-count {
             type int32;
             description "Number of prefixes in any damped state";
           }
           leaf pending-prefix-count {
             type int32;
             description "Number of prefixes with pending changes";
           }
         }
         list terse {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
         }
         list summary {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf active-external-prefix-count {
             type int32;
             description "Number of active prefixes received from external peers";
           }
           leaf total-external-prefix-count {
             type int32;
             description "Total number of prefixes received from external peers";
           }
           leaf accepted-external-prefix-count {
             type int32;
             description "Number of accepted prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf accepted-internal-prefix-count {
             type int32;
             description "Number of accepted prefixes received from internal peers";
           }
           leaf suppressed-internal-prefix-count {
             type int32;
             description "Number of internal prefixes suppressed due to damping";
           }
         }
         list detail {
           leaf name {
             type string;
           }
           leaf rib-bit {
             type string;
           }
           leaf bgp-rib-state {
             type string;
           }
           leaf vpn-rib-state {
             type string;
           }
           leaf send-state {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf stale-prefix-count {
             type int32;
             description "Number of prefixes marked as stale";
           }
           leaf llgr-stale-prefix-count {
             type int32;
             description "Number of prefixes marked as LLGR stale";
           }
           leaf active-external-prefix-count {
             type int32;
             description "Number of active prefixes received from external peers";
           }
           leaf total-external-prefix-count {
             type int32;
             description "Total number of prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf suppressed-internal-prefix-count {
             type int32;
             description "Number of internal prefixes suppressed due to damping";
           }
           leaf advertised-prefix-count {
             type int32;
             description "Number of prefixes present in the RIB-OUT";
           }
         }
       }
       container bgp-family-stat {
         container detail {
           leaf nlri-type {
             type string;
             description "Type of NLRI being limited";
           }
           leaf bgp-nlri-send-time {
             type int32;
             description "Time for initial send by peer";
           }
           leaf bgp-nlri-recv-time {
             type int32;
             description "Time for initial receive by peer";
           }
         }
       }
       list entropy-label-info {
         leaf nlri-type {
           type string;
           description "Type of NLRI being limited";
         }
         leaf entropy-label {
           type string;
           description "Entropy label";
         }
         leaf entropy-label-import-policy {
           type string;
         }
         leaf entropy-label-no-next-hop-validation {
           type string;
           description "Entropy label no next hop validation";
         }
         leaf entropy-label-capability {
           type string;
           description "Local entropy label capability";
         }
         leaf entropy-label-stitching-capability {
           type string;
           description "Entropy label stitching capability";
         }
       }
       container bgp-malformed-attributes {
       }
     }
   }
 }
 grouping bgp-sync-information-block {
   container bgp-rsync-master {
     leaf bgp-precision-timers {
       type string;
     }
     leaf bgp-rsync-session-state {
       type string;
       description "State of the BGP resynchronization session";
     }
     leaf bgp-rsync-session-time {
       type string;
       description "Amount of time that the BGP resynchronization session has been Up or Down";
     }
     leaf bgp-rsync-session-flaps {
       type int32;
       description "Number of BGP resynchronization session flaps";
     }
     leaf bgp-rsync-session-last-flap-reason {
       type string;
       description "Reason for most recent BGP resynchronization session flap";
     }
     leaf bgp-rsync-session-last-flap-error {
       type string;
       description "Socket error for most recent BGP resynchronization session flap";
     }
     leaf bgp-rsync-state {
       type string;
     }
     leaf bgp-rsync-state-time {
       type string;
       description "Time since last protocol state change";
     }
     leaf bgp-rsync-flags {
       type string;
     }
     leaf bgp-rsync-rt-state {
       type string;
     }
     leaf bgp-rsync-ackwait {
       type int32;
       description "Number of peers waiting for ESTABLISH-ACK message";
     }
     leaf bgp-rsync-sowait {
       type int32;
       description "Number of peers waiting for socket record boundaries";
     }
     leaf bgp-rsync-sched {
       type int32;
       description "Number of peers being synchronized";
     }
     leaf bgp-rsync-estab-tm {
       type int32;
     }
     leaf bgp-rsync-sendbuf-count {
       type int32;
     }
     leaf bgp-rsync-walker {
       type empty;
     }
     container bgp-rsync-walk {
       leaf bgp-rsync-walk-table {
         type string;
         description "Current table name";
       }
       leaf bgp-rsync-walk-prefix {
         type string;
         description "Current Prefix";
       }
       leaf bgp-rsync-walk-prefixlen {
         type int32;
         description "Current Prefix length";
       }
       leaf queue-count {
         type int32;
         description "Number of entries enqueued";
       }
     }
     container bgp-rsync-estab-type {
     }
     container bgp-rsync-ack-queue {
       list bgp-rsync-queue-entry {
         leaf rsy-queue-instance {
           type int32;
         }
         leaf rsy-queue-addr {
           type string;
         }
         leaf rsy-queue-more {
           type empty;
         }
       }
     }
     container bgp-rsync-commit-sync-queue {
       list bgp-rsync-queue-entry {
         leaf rsy-queue-instance {
           type int32;
         }
         leaf rsy-queue-addr {
           type string;
         }
         leaf rsy-queue-more {
           type empty;
         }
       }
     }
     container bgp-rsync-error-queue {
       list bgp-rsync-queue-entry {
         leaf rsy-queue-instance {
           type int32;
         }
         leaf rsy-queue-addr {
           type string;
         }
         leaf rsy-queue-more {
           type empty;
         }
       }
     }
     container bgp-rsync-stats {
       leaf open-send-count {
         type int32;
       }
       leaf estab-send-count {
         type int32;
       }
       leaf estab-gr-send-count {
         type int32;
       }
       leaf update-send-count {
         type int32;
       }
       leaf gr-stale-label-send-count {
         type int32;
       }
       leaf error-send-count {
         type int32;
       }
       leaf complete-send-count {
         type int32;
       }
       leaf open-receive-count {
         type int32;
       }
       leaf request-wild-receive-count {
         type int32;
       }
       leaf request-tgt-receive-count {
         type int32;
       }
       leaf estab-ack-receive-count {
         type int32;
       }
       leaf estab-gr-ack-receive-count {
         type int32;
       }
       leaf complete-ack-receive-count {
         type int32;
       }
     }
     container bgp-rsync-estab-queue {
       list bgp-rsync-queue-entry {
         leaf rsy-queue-instance {
           type int32;
         }
         leaf rsy-queue-addr {
           type string;
         }
         leaf rsy-queue-more {
           type empty;
         }
       }
     }
   }
   container bgp-standby {
     leaf bgp-standby-state {
       type string;
     }
     leaf bgp-standby-last-trans {
       type string;
     }
     leaf bgp-standby-sendbuf {
       type int32;
     }
     leaf bgp-unsync-timer {
       type string;
     }
     leaf bgp-unsync-pending-tm {
       type string;
     }
     container bgp-unsync-queue {
       list bgp-unsync-entry {
         leaf usy-iid {
           type int32;
         }
         leaf usy-addr {
           type ipaddr;
         }
         leaf usy-elapsed {
           type string;
         }
         leaf usy-flags {
           type string;
         }
         leaf usy-more {
           type empty;
         }
       }
     }
     container bgp-unsync-pending {
       list bgp-unsync-entry {
         leaf usy-iid {
           type int32;
         }
         leaf usy-addr {
           type ipaddr;
         }
         leaf usy-elapsed {
           type string;
         }
         leaf usy-flags {
           type string;
         }
         leaf usy-more {
           type empty;
         }
       }
     }
     container bgp-standby-sync-queue {
       list bgp-standby-sync-entry {
         leaf bstandby-iid {
           type int32;
         }
         leaf bstandby-addr {
           type ipaddr;
         }
       }
     }
   }
 }
 grouping bgp-group-information-block {
   list bgp-group {
     description "Operational and configuration information for a BGP group";
     leaf type {
       type string;
     }
     leaf peer-as {
       type int32;
       description "Peer AS number";
     }
     leaf local-as {
       type int32;
       description "Local AS number";
     }
     leaf group-state {
       type string;
     }
     leaf name {
       type string;
     }
     leaf group-index {
       type int32;
     }
     leaf group-flags {
       type string;
     }
     leaf orr-igp-primary {
       type string;
     }
     leaf orr-igp-backup {
       type string;
     }
     leaf peer-count {
       type int32;
       description "Total number of peers";
     }
     leaf established-count {
       type int32;
       description "Number of peers within the group that are in the established state";
     }
     leaf peer-address {
       type ipaddr;
     }
     leaf igp-protocol {
       type string;
     }
     list summary {
       description "Operational and configuration information for a BGP group";
       leaf bgp-group.heading {
         type string;
         description "Operational and configuration information for a BGP group";
       }
       container unconfigured-peers {
         description "Set of address prefixes from which this group allows peering";
         list route-filter {
           description "Entries in martian table";
           leaf address {
             type ipaddr;
           }
           leaf flags {
             type string;
             description "Enabled trace flags";
           }
           leaf extended-information {
             type string;
           }
         }
       }
       container route-queue {
         leaf timer {
           type string;
         }
         leaf state {
           type string;
           description "HFRR profile Current state";
         }
         leaf element {
           type string;
         }
       }
       list bgp-peer {
         description "Operational and configuration information for a BGP peer";
         list terse {
           description "Operational and configuration information for a BGP peer";
           leaf bgp-peer.heading {
             type string;
             description "Operational and configuration information for a BGP peer";
           }
           leaf peer-address {
             type ipaddr;
           }
           leaf peer-as {
             type int32;
             description "Peer AS number";
           }
           leaf input-messages {
             type int32;
           }
           leaf output-messages {
             type int32;
           }
           leaf route-queue-count {
             type int32;
             description "Total number of routes queued for output to this peer";
           }
           leaf flap-count {
             type int32;
             description "Number of times BGP sessions have gone down";
           }
           leaf elapsed-time {
             type string;
             description "Time this adjacency or session has been up or down";
           }
           leaf peer-state {
             type string;
           }
           container bgp-option-information {
             container prefix-limit {
             }
             container accepted-prefix-limit {
               description "Limit number of prefixes accepted by policy";
             }
             container addpath-send {
             }
             container addpath-receive {
             }
             container nlri-information {
               leaf nlri-type {
                 type string;
                 description "Type of NLRI being limited";
               }
               leaf nlri-flow-novalidate {
                 type string;
                 description "Policy to accept flow routes without validation";
               }
               leaf nlri-output-queue-priority {
                 type string;
                 description "Default address family output queue priority";
               }
               leaf nlri-route-refresh-priority {
                 type string;
                 description "Default address family route-refresh priority";
               }
               leaf nlri-withdraw-priority {
                 type string;
                 description "Default address family withdraw priority";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container egress-protection {
             container nlri-egress-protection {
               leaf nlri-type {
                 type string;
                 description "Type of NLRI being limited";
               }
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-malformed-attributes {
           }
         }
         list detail {
           description "Operational and configuration information for a BGP peer";
           leaf peer-address {
             type ipaddr;
           }
           leaf peer-as {
             type int32;
             description "Peer AS number";
           }
           leaf local-address {
             type ipaddr;
           }
           leaf local-as {
             type int32;
             description "Local AS number";
           }
           leaf description {
             type string;
           }
           leaf peer-group {
             type string;
             description "BGP peer-group peer belongs to";
           }
           leaf peer-cfg-rti {
             type string;
             description "Routing-instance peer is configured in";
           }
           leaf peer-fwd-rti {
             type string;
             description "Peer's forwarding-context routing-instance";
           }
           leaf peer-type {
             type string;
           }
           leaf peer-state {
             type string;
           }
           leaf route-reflector-client {
             type empty;
           }
           leaf peer-flags {
             type string;
           }
           leaf last-state {
             type string;
           }
           leaf last-event {
             type string;
           }
           leaf last-error {
             type string;
           }
           leaf flap-count {
             type int32;
             description "Number of times BGP sessions have gone down";
           }
           leaf last-flap-event {
             type string;
           }
           leaf peer-id {
             type ipaddr;
           }
           leaf local-id {
             type ipaddr;
           }
           leaf active-holdtime {
             type int32;
           }
           leaf keepalive-interval {
             type int32;
           }
           leaf group-index {
             type int32;
           }
           leaf peer-index {
             type int32;
           }
           leaf local-interface-name {
             type string;
             description "Logical interface name";
           }
           leaf nlri-type-peer {
             type string;
           }
           leaf nlri-type-session {
             type string;
           }
           leaf peer-no-refresh {
             type empty;
             description "Present if this peer does not support refresh";
           }
           leaf peer-refresh-capability {
             type int32;
             description "Version of refresh capability supported by this peer";
           }
           leaf peer-4byte-as-capability-not-supported {
             type empty;
             description "This peer does not support 4 byte AS extension";
           }
           leaf peer-4byte-as-capability-advertised {
             type int32;
             description "4 byte Autonomous System capability advertised by this peer";
           }
           leaf peer-addpath-not-supported {
             type empty;
             description "This peer does not support addpath";
           }
           leaf peer-addpath-ronly-nlri {
             type string;
             description "Types of NLRI for which peer advertised recv capability";
           }
           leaf peer-addpath-sonly-nlri {
             type string;
             description "Types of NLRI for which peer advertised send capability";
           }
           leaf peer-addpath-rs-nlri {
             type string;
             description "Types of NLRI for which peer advertised send/recv cap";
           }
           leaf peer-delay-route-advertisements {
             type string;
           }
           leaf local-ext-nh-nlri {
             type string;
             description "Types of NLRI for which we advertised extend nh cap";
           }
           leaf peer-ext-nh-nlri {
             type string;
             description "Types of NLRI for which peer advertised extend nh cap";
           }
           leaf peer-restart-nlri-configured {
             type string;
           }
           leaf peer-restart-time-configured {
             type string;
           }
           leaf peer-stale-route-time-configured {
             type string;
           }
           leaf peer-no-restart {
             type empty;
             description "Present if this peer does not support graceful restart restarter mode";
           }
           leaf peer-restart-nlri-received {
             type string;
           }
           leaf peer-restart-time-received {
             type int32;
           }
           leaf peer-restart-flags-received {
             type string;
           }
           leaf peer-restart-nlri-can-save-state {
             type string;
           }
           leaf peer-restart-nlri-state-saved {
             type string;
           }
           leaf peer-restart-nlri-negotiated {
             type string;
           }
           leaf peer-end-of-rib-received {
             type string;
           }
           leaf peer-end-of-rib-sent {
             type string;
           }
           leaf peer-delay-end-of-rib {
             type string;
           }
           leaf peer-no-helper {
             type empty;
             description "Present if this peer does not support graceful restart receiver mode";
           }
           leaf peer-restart-nlri-held {
             type string;
           }
           leaf peer-restart-remaining-time {
             type string;
           }
           leaf peer-stale-remaining-time {
             type string;
           }
           leaf peer-llgr-nlri-configured {
             type string;
           }
           leaf peer-no-llgr-restarter {
             type empty;
             description "Present if this peer does not support long-lived graceful restart restarter mode";
           }
           leaf peer-llgr-nlri-restarter {
             type string;
           }
           leaf peer-llgr-nlri-state-saved {
             type string;
           }
           leaf peer-no-llgr-helper {
             type empty;
             description "Present if this peer does not support long-lived graceful restart receiver mode";
           }
           leaf peer-llgr-nlri-times {
             type string;
             description "NLRIs and times before long-lived stale routes are deleted";
           }
           leaf last-received {
             type int32;
           }
           leaf last-sent {
             type int32;
           }
           leaf last-checked {
             type int32;
           }
           leaf input-messages {
             type int32;
           }
           leaf input-updates {
             type int32;
           }
           leaf input-refreshes {
             type int32;
           }
           leaf input-octets {
             type int32;
           }
           leaf output-messages {
             type int32;
           }
           leaf output-updates {
             type int32;
           }
           leaf output-refreshes {
             type int32;
           }
           leaf output-octets {
             type int32;
           }
           leaf input-checksum {
             type int32;
           }
           leaf output-checksum {
             type int32;
           }
           leaf input-checksum-err {
             type int32;
           }
           leaf input-drop-path-attributes {
             type string;
           }
           leaf input-ignore-path-attributes {
             type string;
           }
           leaf buffered-octets-rx {
             type int32;
             description "Number of octets that have been received and are still buffered";
           }
           leaf buffered-octets-tx {
             type int32;
             description "Number of octets in the transmit buffer";
           }
           leaf gather-buffered-octets-tx {
             type int32;
             description "Number of octets in the gather transmit buffer";
           }
           container bgp-option-information {
             leaf export-policy {
               type string;
             }
             leaf import-policy {
               type string;
             }
             leaf advertise-bgp-static-policy {
               type string;
             }
             leaf bgp-options {
               type string;
             }
             leaf bgp-options2 {
               type string;
             }
             leaf bgp-options-extended {
               type string;
             }
             leaf remove-private-options {
               type string;
             }
             leaf authentication-key {
               type string;
             }
             leaf authentication-key-chain {
               type string;
               description "Name of authentication key chain";
             }
             leaf authentication-algorithm {
               type string;
               description "Name of authentication algorithm";
             }
             leaf authentication-configured {
               type empty;
             }
             leaf address-families {
               type string;
             }
             leaf drop-path-attributes {
               type string;
             }
             leaf ignore-path-attributes {
               type string;
             }
             leaf holdtime {
               type int32;
               description "Delay before timing out the adjacency (default is 180 seconds)";
             }
             leaf metric-out {
               type int32;
             }
             leaf preference {
               type int32;
               description "Preference for the route";
             }
             leaf local-preference {
               type int32;
             }
             leaf local-as-private {
               type empty;
             }
             leaf local-system-as {
               type int32;
             }
             leaf receive-buffer-size {
               type int32;
             }
             leaf send-buffer-size {
               type int32;
             }
             leaf outbound-timer {
               type int32;
             }
             leaf med-action {
               type string;
             }
             leaf ipsec-sa {
               type string;
             }
             leaf bgp-bmp-monitor-peers {
               type string;
             }
             leaf bgp-bmp-route-monitoring-none {
               type empty;
             }
             leaf bgp-bmp-route-monitoring-prepolicy {
               type empty;
             }
             leaf bgp-bmp-prepolicy-exclude-non-feasible {
               type empty;
             }
             leaf bgp-bmp-route-monitoring-postpolicy {
               type empty;
             }
             leaf bgp-bmp-postpolicy-exclude-non-eligible {
               type empty;
             }
             container prefix-limit {
             }
             container accepted-prefix-limit {
               description "Limit number of prefixes accepted by policy";
             }
             container addpath-send {
             }
             container addpath-receive {
             }
             container aigp-mode {
               leaf nlri-type {
                 type string;
                 description "Type of NLRI being limited";
               }
             }
             container family-damping-info {
               leaf nlri-type {
                 type string;
                 description "Type of NLRI being limited";
               }
             }
             container protection {
               leaf nlri-type {
                 type string;
                 description "Type of NLRI being limited";
               }
             }
             container nlri-information {
               leaf nlri-type {
                 type string;
                 description "Type of NLRI being limited";
               }
               leaf nlri-flow-novalidate {
                 type string;
                 description "Policy to accept flow routes without validation";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container bgp-peer-iosession {
             leaf iosession-thread-name {
               type string;
             }
             leaf iosession-state {
               type string;
             }
           }
           container bgp-bfd {
             leaf bfd-configuration-state {
               type string;
               description "BFD configuration state";
             }
             leaf bfd-operational-state {
               type string;
               description "BFD operational state";
             }
           }
           container egress-protection {
             leaf nlri-type {
               type string;
               description "Type of NLRI being limited";
             }
             container nlri-egress-protection {
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
             leaf number {
               type int32;
             }
             leaf count {
               type int32;
             }
             leaf table-name {
               type string;
               description "Unicast routing table";
             }
             leaf rib-adv-nlri {
               type string;
             }
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-error {
             leaf name {
               type string;
             }
             leaf send-count {
               type int32;
             }
             leaf receive-count {
               type int32;
             }
           }
           container bgp-malformed-attributes {
             container malformed-information {
               leaf log-interval {
                 type int32;
               }
               leaf route-limit {
                 type int32;
               }
             }
             container path-attribute {
               leaf name {
                 type string;
               }
               leaf code {
                 type int32;
               }
               leaf last-recv {
                 type int32;
               }
               leaf total-recv {
                 type int32;
               }
             }
           }
           container route-queue {
             leaf timer {
               type string;
             }
             leaf state {
               type string;
               description "HFRR profile Current state";
             }
             leaf element {
               type string;
             }
           }
           container tracing-information {
             leaf flags {
               type string;
               description "Enabled trace flags";
             }
             leaf filename {
               type string;
               description "Name of the trace file";
             }
             leaf filesize {
               type int32;
               description "Maximum size of the trace file";
             }
             leaf filelimit {
               type int32;
               description "Maximum number of retained trace files";
             }
           }
         }
         list output-queue {
           description "Operational and configuration information for a BGP peer";
           leaf peer-address {
             type ipaddr;
           }
           leaf peer-as {
             type int32;
             description "Peer AS number";
           }
           leaf local-address {
             type ipaddr;
           }
           leaf local-as {
             type int32;
             description "Local AS number";
           }
           leaf description {
             type string;
           }
           container bgp-option-information {
             container prefix-limit {
             }
             container accepted-prefix-limit {
               description "Limit number of prefixes accepted by policy";
             }
             container addpath-send {
             }
             container addpath-receive {
             }
             container nlri-information {
               leaf nlri-type {
                 type string;
                 description "Type of NLRI being limited";
               }
               leaf nlri-flow-novalidate {
                 type string;
                 description "Policy to accept flow routes without validation";
               }
               leaf nlri-output-queue-priority {
                 type string;
                 description "Default address family output queue priority";
               }
               leaf nlri-route-refresh-priority {
                 type string;
                 description "Default address family route-refresh priority";
               }
               leaf nlri-withdraw-priority {
                 type string;
                 description "Default address family withdraw priority";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container egress-protection {
             container nlri-egress-protection {
               leaf nlri-type {
                 type string;
                 description "Type of NLRI being limited";
               }
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
             leaf number {
               type int32;
             }
             leaf count {
               type int32;
             }
             leaf table-name {
               type string;
               description "Unicast routing table";
             }
             leaf rib-adv-nlri {
               type string;
             }
             leaf time-series {
               type string;
             }
             list class {
               description "An instance of BGP output queue statistics";
               leaf priority-type {
                 type string;
                 description "BGP output queue priority type";
               }
               leaf rank {
                 type int32;
                 description "BGP output queue rank for priority type";
               }
               leaf token-count {
                 type int32;
                 description "BGP output queue token count for priority";
               }
             }
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-malformed-attributes {
           }
         }
       }
       container bgp-option-information {
         leaf export-policy {
           type string;
         }
         leaf import-policy {
           type string;
         }
         leaf advertise-bgp-static-policy {
           type string;
         }
         leaf bgp-options {
           type string;
         }
         leaf bgp-options2 {
           type string;
         }
         leaf bgp-options-extended {
           type string;
         }
         leaf remove-private-options {
           type string;
         }
         leaf authentication-key {
           type string;
         }
         leaf authentication-key-chain {
           type string;
           description "Name of authentication key chain";
         }
         leaf authentication-algorithm {
           type string;
           description "Name of authentication algorithm";
         }
         leaf authentication-configured {
           type empty;
         }
         leaf address-families {
           type string;
         }
         leaf drop-path-attributes {
           type string;
         }
         leaf ignore-path-attributes {
           type string;
         }
         leaf local-address {
           type ipaddr;
         }
         leaf holdtime {
           type int32;
           description "Delay before timing out the adjacency (default is 180 seconds)";
         }
         leaf metric-out {
           type int32;
         }
         leaf preference {
           type int32;
           description "Preference for the route";
         }
         leaf local-preference {
           type int32;
         }
         leaf local-as {
           type int32;
           description "Local AS number";
         }
         leaf local-as-private {
           type empty;
         }
         leaf local-system-as {
           type int32;
         }
         leaf receive-buffer-size {
           type int32;
         }
         leaf send-buffer-size {
           type int32;
         }
         leaf outbound-timer {
           type int32;
         }
         leaf med-action {
           type string;
         }
         leaf ipsec-sa {
           type string;
         }
         leaf bgp-bmp-monitor-peers {
           type string;
         }
         leaf bgp-bmp-route-monitoring-none {
           type empty;
         }
         leaf bgp-bmp-route-monitoring-prepolicy {
           type empty;
         }
         leaf bgp-bmp-prepolicy-exclude-non-feasible {
           type empty;
         }
         leaf bgp-bmp-route-monitoring-postpolicy {
           type empty;
         }
         leaf bgp-bmp-postpolicy-exclude-non-eligible {
           type empty;
         }
         container prefix-limit {
         }
         container accepted-prefix-limit {
           description "Limit number of prefixes accepted by policy";
         }
         container addpath-send {
         }
         container addpath-receive {
         }
         container nlri-information {
           leaf nlri-type {
             type string;
             description "Type of NLRI being limited";
           }
           leaf nlri-flow-novalidate {
             type string;
             description "Policy to accept flow routes without validation";
           }
           leaf nlri-output-queue-priority {
             type string;
             description "Default address family output queue priority";
           }
           leaf nlri-route-refresh-priority {
             type string;
             description "Default address family route-refresh priority";
           }
           leaf nlri-withdraw-priority {
             type string;
             description "Default address family withdraw priority";
           }
           container nlri-flags {
             leaf bgp-nlri-flag-explicit-null-for-all-routes {
               type empty;
             }
             leaf bgp-nlri-flag-explicit-null-for-connected-routes {
               type empty;
             }
             leaf bgp-nlri-flag-aggregate-label {
               type empty;
             }
             leaf bgp-nlri-flag-per-prefix-label {
               type empty;
             }
             leaf bgp-nlri-flag-per-group-label {
               type empty;
             }
             leaf bgp-nlri-flag-no-install-forwarding {
               type empty;
             }
             leaf bgp-nlri-flag-delay-route-advt {
               type empty;
             }
             leaf bgp-nlri-flag-traffic-stats {
               type empty;
             }
             leaf bgp-nlri-flag-l2vpn-status-vector {
               type empty;
             }
             leaf bgp-nlri-flag-no-l2vpn-status-vector {
               type empty;
             }
             leaf bgp-nlri-flag-strip-nexthop {
               type empty;
             }
             leaf bgp-nlri-flag-allow-po-add-nexthop {
               type empty;
             }
           }
           container nlri-traffic-stats {
             leaf traffic-stats-interval {
               type int32;
             }
             container tracing-information {
               leaf flags {
                 type string;
                 description "Enabled trace flags";
               }
               leaf filename {
                 type string;
                 description "Name of the trace file";
               }
               leaf filesize {
                 type int32;
                 description "Maximum size of the trace file";
               }
               leaf filelimit {
                 type int32;
                 description "Maximum number of retained trace files";
               }
             }
           }
           container output-queues {
             description "BGP output queues statistics";
             container output-queue {
               description "BGP output queues statistics";
               leaf time-series {
                 type string;
               }
               list class {
                 description "An instance of BGP output queue statistics";
                 leaf priority-type {
                   type string;
                   description "BGP output queue priority type";
                 }
                 leaf rank {
                   type int32;
                   description "BGP output queue rank for priority type";
                 }
                 leaf token-count {
                   type int32;
                   description "BGP output queue token count for priority";
                 }
                 leaf output-queue-route-count {
                   type int32;
                   description "BGP output queue route count for priority";
                 }
               }
             }
           }
         }
       }
       container tracing-information {
         leaf flags {
           type string;
           description "Enabled trace flags";
         }
         leaf filename {
           type string;
           description "Name of the trace file";
         }
         leaf filesize {
           type int32;
           description "Maximum size of the trace file";
         }
         leaf filelimit {
           type int32;
           description "Maximum number of retained trace files";
         }
       }
       list bgp-rib {
         list brief {
           leaf name {
             type string;
           }
           leaf total-prefix-count {
             type int32;
             description "Total number of prefixes in this RIB";
           }
           leaf active-prefix-count {
             type int32;
             description "Number of active prefixes";
           }
           leaf suppressed-prefix-count {
             type int32;
             description "Number of prefixes suppressed due to damping";
           }
           leaf history-prefix-count {
             type int32;
             description "Number of prefixes with damping history maintained";
           }
           leaf damped-prefix-count {
             type int32;
             description "Number of prefixes in any damped state";
           }
           leaf pending-prefix-count {
             type int32;
             description "Number of prefixes with pending changes";
           }
         }
         list terse {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
         }
         list summary {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf active-external-prefix-count {
             type int32;
             description "Number of active prefixes received from external peers";
           }
           leaf total-external-prefix-count {
             type int32;
             description "Total number of prefixes received from external peers";
           }
           leaf accepted-external-prefix-count {
             type int32;
             description "Number of accepted prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf accepted-internal-prefix-count {
             type int32;
             description "Number of accepted prefixes received from internal peers";
           }
           leaf suppressed-internal-prefix-count {
             type int32;
             description "Number of internal prefixes suppressed due to damping";
           }
         }
         list detail {
           leaf name {
             type string;
           }
           leaf rib-bit {
             type string;
           }
           leaf bgp-rib-state {
             type string;
           }
           leaf vpn-rib-state {
             type string;
           }
           leaf send-state {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf stale-prefix-count {
             type int32;
             description "Number of prefixes marked as stale";
           }
           leaf llgr-stale-prefix-count {
             type int32;
             description "Number of prefixes marked as LLGR stale";
           }
           leaf active-external-prefix-count {
             type int32;
             description "Number of active prefixes received from external peers";
           }
           leaf total-external-prefix-count {
             type int32;
             description "Total number of prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf suppressed-internal-prefix-count {
             type int32;
             description "Number of internal prefixes suppressed due to damping";
           }
           leaf advertised-prefix-count {
             type int32;
             description "Number of prefixes present in the RIB-OUT";
           }
         }
       }
     }
     list brief {
       description "Operational and configuration information for a BGP group";
       leaf type {
         type string;
       }
       leaf peer-as {
         type int32;
         description "Peer AS number";
       }
       leaf local-as {
         type int32;
         description "Local AS number";
       }
       leaf group-state {
         type string;
       }
       leaf name {
         type string;
       }
       leaf group-index {
         type int32;
       }
       leaf group-flags {
         type string;
       }
       leaf orr-igp-primary {
         type string;
       }
       leaf orr-igp-backup {
         type string;
       }
       leaf peer-count {
         type int32;
         description "Total number of peers";
       }
       leaf established-count {
         type int32;
         description "Number of peers within the group that are in the established state";
       }
       leaf peer-address {
         type ipaddr;
       }
       leaf igp-protocol {
         type string;
       }
       container unconfigured-peers {
         description "Set of address prefixes from which this group allows peering";
         list route-filter {
           description "Entries in martian table";
           leaf address {
             type ipaddr;
           }
           leaf flags {
             type string;
             description "Enabled trace flags";
           }
           leaf extended-information {
             type string;
           }
         }
       }
       container route-queue {
         leaf timer {
           type string;
         }
         leaf state {
           type string;
           description "HFRR profile Current state";
         }
         leaf element {
           type string;
         }
       }
       list bgp-peer {
         description "Operational and configuration information for a BGP peer";
         list terse {
           description "Operational and configuration information for a BGP peer";
           leaf bgp-peer.heading {
             type string;
             description "Operational and configuration information for a BGP peer";
           }
           leaf peer-address {
             type ipaddr;
           }
           leaf peer-as {
             type int32;
             description "Peer AS number";
           }
           leaf input-messages {
             type int32;
           }
           leaf output-messages {
             type int32;
           }
           leaf route-queue-count {
             type int32;
             description "Total number of routes queued for output to this peer";
           }
           leaf flap-count {
             type int32;
             description "Number of times BGP sessions have gone down";
           }
           leaf elapsed-time {
             type string;
             description "Time this adjacency or session has been up or down";
           }
           leaf peer-state {
             type string;
           }
           container bgp-option-information {
             container prefix-limit {
             }
             container accepted-prefix-limit {
               description "Limit number of prefixes accepted by policy";
             }
             container addpath-send {
             }
             container addpath-receive {
             }
             container nlri-information {
               leaf nlri-type {
                 type string;
                 description "Type of NLRI being limited";
               }
               leaf nlri-flow-novalidate {
                 type string;
                 description "Policy to accept flow routes without validation";
               }
               leaf nlri-output-queue-priority {
                 type string;
                 description "Default address family output queue priority";
               }
               leaf nlri-route-refresh-priority {
                 type string;
                 description "Default address family route-refresh priority";
               }
               leaf nlri-withdraw-priority {
                 type string;
                 description "Default address family withdraw priority";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container egress-protection {
             container nlri-egress-protection {
               leaf nlri-type {
                 type string;
                 description "Type of NLRI being limited";
               }
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-malformed-attributes {
           }
         }
         list detail {
           description "Operational and configuration information for a BGP peer";
           leaf peer-address {
             type ipaddr;
           }
           leaf peer-as {
             type int32;
             description "Peer AS number";
           }
           leaf local-address {
             type ipaddr;
           }
           leaf local-as {
             type int32;
             description "Local AS number";
           }
           leaf description {
             type string;
           }
           leaf peer-group {
             type string;
             description "BGP peer-group peer belongs to";
           }
           leaf peer-cfg-rti {
             type string;
             description "Routing-instance peer is configured in";
           }
           leaf peer-fwd-rti {
             type string;
             description "Peer's forwarding-context routing-instance";
           }
           leaf peer-type {
             type string;
           }
           leaf peer-state {
             type string;
           }
           leaf route-reflector-client {
             type empty;
           }
           leaf peer-flags {
             type string;
           }
           leaf last-state {
             type string;
           }
           leaf last-event {
             type string;
           }
           leaf last-error {
             type string;
           }
           leaf flap-count {
             type int32;
             description "Number of times BGP sessions have gone down";
           }
           leaf last-flap-event {
             type string;
           }
           leaf peer-id {
             type ipaddr;
           }
           leaf local-id {
             type ipaddr;
           }
           leaf active-holdtime {
             type int32;
           }
           leaf keepalive-interval {
             type int32;
           }
           leaf group-index {
             type int32;
           }
           leaf peer-index {
             type int32;
           }
           leaf local-interface-name {
             type string;
             description "Logical interface name";
           }
           leaf nlri-type-peer {
             type string;
           }
           leaf nlri-type-session {
             type string;
           }
           leaf peer-no-refresh {
             type empty;
             description "Present if this peer does not support refresh";
           }
           leaf peer-refresh-capability {
             type int32;
             description "Version of refresh capability supported by this peer";
           }
           leaf peer-4byte-as-capability-not-supported {
             type empty;
             description "This peer does not support 4 byte AS extension";
           }
           leaf peer-4byte-as-capability-advertised {
             type int32;
             description "4 byte Autonomous System capability advertised by this peer";
           }
           leaf peer-addpath-not-supported {
             type empty;
             description "This peer does not support addpath";
           }
           leaf peer-addpath-ronly-nlri {
             type string;
             description "Types of NLRI for which peer advertised recv capability";
           }
           leaf peer-addpath-sonly-nlri {
             type string;
             description "Types of NLRI for which peer advertised send capability";
           }
           leaf peer-addpath-rs-nlri {
             type string;
             description "Types of NLRI for which peer advertised send/recv cap";
           }
           leaf peer-delay-route-advertisements {
             type string;
           }
           leaf local-ext-nh-nlri {
             type string;
             description "Types of NLRI for which we advertised extend nh cap";
           }
           leaf peer-ext-nh-nlri {
             type string;
             description "Types of NLRI for which peer advertised extend nh cap";
           }
           leaf peer-restart-nlri-configured {
             type string;
           }
           leaf peer-restart-time-configured {
             type string;
           }
           leaf peer-stale-route-time-configured {
             type string;
           }
           leaf peer-no-restart {
             type empty;
             description "Present if this peer does not support graceful restart restarter mode";
           }
           leaf peer-restart-nlri-received {
             type string;
           }
           leaf peer-restart-time-received {
             type int32;
           }
           leaf peer-restart-flags-received {
             type string;
           }
           leaf peer-restart-nlri-can-save-state {
             type string;
           }
           leaf peer-restart-nlri-state-saved {
             type string;
           }
           leaf peer-restart-nlri-negotiated {
             type string;
           }
           leaf peer-end-of-rib-received {
             type string;
           }
           leaf peer-end-of-rib-sent {
             type string;
           }
           leaf peer-delay-end-of-rib {
             type string;
           }
           leaf peer-no-helper {
             type empty;
             description "Present if this peer does not support graceful restart receiver mode";
           }
           leaf peer-restart-nlri-held {
             type string;
           }
           leaf peer-restart-remaining-time {
             type string;
           }
           leaf peer-stale-remaining-time {
             type string;
           }
           leaf peer-llgr-nlri-configured {
             type string;
           }
           leaf peer-no-llgr-restarter {
             type empty;
             description "Present if this peer does not support long-lived graceful restart restarter mode";
           }
           leaf peer-llgr-nlri-restarter {
             type string;
           }
           leaf peer-llgr-nlri-state-saved {
             type string;
           }
           leaf peer-no-llgr-helper {
             type empty;
             description "Present if this peer does not support long-lived graceful restart receiver mode";
           }
           leaf peer-llgr-nlri-times {
             type string;
             description "NLRIs and times before long-lived stale routes are deleted";
           }
           leaf last-received {
             type int32;
           }
           leaf last-sent {
             type int32;
           }
           leaf last-checked {
             type int32;
           }
           leaf input-messages {
             type int32;
           }
           leaf input-updates {
             type int32;
           }
           leaf input-refreshes {
             type int32;
           }
           leaf input-octets {
             type int32;
           }
           leaf output-messages {
             type int32;
           }
           leaf output-updates {
             type int32;
           }
           leaf output-refreshes {
             type int32;
           }
           leaf output-octets {
             type int32;
           }
           leaf input-checksum {
             type int32;
           }
           leaf output-checksum {
             type int32;
           }
           leaf input-checksum-err {
             type int32;
           }
           leaf input-drop-path-attributes {
             type string;
           }
           leaf input-ignore-path-attributes {
             type string;
           }
           leaf buffered-octets-rx {
             type int32;
             description "Number of octets that have been received and are still buffered";
           }
           leaf buffered-octets-tx {
             type int32;
             description "Number of octets in the transmit buffer";
           }
           leaf gather-buffered-octets-tx {
             type int32;
             description "Number of octets in the gather transmit buffer";
           }
           container bgp-option-information {
             leaf export-policy {
               type string;
             }
             leaf import-policy {
               type string;
             }
             leaf advertise-bgp-static-policy {
               type string;
             }
             leaf bgp-options {
               type string;
             }
             leaf bgp-options2 {
               type string;
             }
             leaf bgp-options-extended {
               type string;
             }
             leaf remove-private-options {
               type string;
             }
             leaf authentication-key {
               type string;
             }
             leaf authentication-key-chain {
               type string;
               description "Name of authentication key chain";
             }
             leaf authentication-algorithm {
               type string;
               description "Name of authentication algorithm";
             }
             leaf authentication-configured {
               type empty;
             }
             leaf address-families {
               type string;
             }
             leaf drop-path-attributes {
               type string;
             }
             leaf ignore-path-attributes {
               type string;
             }
             leaf holdtime {
               type int32;
               description "Delay before timing out the adjacency (default is 180 seconds)";
             }
             leaf metric-out {
               type int32;
             }
             leaf preference {
               type int32;
               description "Preference for the route";
             }
             leaf local-preference {
               type int32;
             }
             leaf local-as-private {
               type empty;
             }
             leaf local-system-as {
               type int32;
             }
             leaf receive-buffer-size {
               type int32;
             }
             leaf send-buffer-size {
               type int32;
             }
             leaf outbound-timer {
               type int32;
             }
             leaf med-action {
               type string;
             }
             leaf ipsec-sa {
               type string;
             }
             leaf bgp-bmp-monitor-peers {
               type string;
             }
             leaf bgp-bmp-route-monitoring-none {
               type empty;
             }
             leaf bgp-bmp-route-monitoring-prepolicy {
               type empty;
             }
             leaf bgp-bmp-prepolicy-exclude-non-feasible {
               type empty;
             }
             leaf bgp-bmp-route-monitoring-postpolicy {
               type empty;
             }
             leaf bgp-bmp-postpolicy-exclude-non-eligible {
               type empty;
             }
             container prefix-limit {
             }
             container accepted-prefix-limit {
               description "Limit number of prefixes accepted by policy";
             }
             container addpath-send {
             }
             container addpath-receive {
             }
             container aigp-mode {
               leaf nlri-type {
                 type string;
                 description "Type of NLRI being limited";
               }
             }
             container family-damping-info {
               leaf nlri-type {
                 type string;
                 description "Type of NLRI being limited";
               }
             }
             container protection {
               leaf nlri-type {
                 type string;
                 description "Type of NLRI being limited";
               }
             }
             container nlri-information {
               leaf nlri-type {
                 type string;
                 description "Type of NLRI being limited";
               }
               leaf nlri-flow-novalidate {
                 type string;
                 description "Policy to accept flow routes without validation";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container bgp-peer-iosession {
             leaf iosession-thread-name {
               type string;
             }
             leaf iosession-state {
               type string;
             }
           }
           container bgp-bfd {
             leaf bfd-configuration-state {
               type string;
               description "BFD configuration state";
             }
             leaf bfd-operational-state {
               type string;
               description "BFD operational state";
             }
           }
           container egress-protection {
             leaf nlri-type {
               type string;
               description "Type of NLRI being limited";
             }
             container nlri-egress-protection {
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
             leaf number {
               type int32;
             }
             leaf count {
               type int32;
             }
             leaf table-name {
               type string;
               description "Unicast routing table";
             }
             leaf rib-adv-nlri {
               type string;
             }
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-error {
             leaf name {
               type string;
             }
             leaf send-count {
               type int32;
             }
             leaf receive-count {
               type int32;
             }
           }
           container bgp-malformed-attributes {
             container malformed-information {
               leaf log-interval {
                 type int32;
               }
               leaf route-limit {
                 type int32;
               }
             }
             container path-attribute {
               leaf name {
                 type string;
               }
               leaf code {
                 type int32;
               }
               leaf last-recv {
                 type int32;
               }
               leaf total-recv {
                 type int32;
               }
             }
           }
           container route-queue {
             leaf timer {
               type string;
             }
             leaf state {
               type string;
               description "HFRR profile Current state";
             }
             leaf element {
               type string;
             }
           }
           container tracing-information {
             leaf flags {
               type string;
               description "Enabled trace flags";
             }
             leaf filename {
               type string;
               description "Name of the trace file";
             }
             leaf filesize {
               type int32;
               description "Maximum size of the trace file";
             }
             leaf filelimit {
               type int32;
               description "Maximum number of retained trace files";
             }
           }
         }
         list output-queue {
           description "Operational and configuration information for a BGP peer";
           leaf peer-address {
             type ipaddr;
           }
           leaf peer-as {
             type int32;
             description "Peer AS number";
           }
           leaf local-address {
             type ipaddr;
           }
           leaf local-as {
             type int32;
             description "Local AS number";
           }
           leaf description {
             type string;
           }
           container bgp-option-information {
             container prefix-limit {
             }
             container accepted-prefix-limit {
               description "Limit number of prefixes accepted by policy";
             }
             container addpath-send {
             }
             container addpath-receive {
             }
             container nlri-information {
               leaf nlri-type {
                 type string;
                 description "Type of NLRI being limited";
               }
               leaf nlri-flow-novalidate {
                 type string;
                 description "Policy to accept flow routes without validation";
               }
               leaf nlri-output-queue-priority {
                 type string;
                 description "Default address family output queue priority";
               }
               leaf nlri-route-refresh-priority {
                 type string;
                 description "Default address family route-refresh priority";
               }
               leaf nlri-withdraw-priority {
                 type string;
                 description "Default address family withdraw priority";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container egress-protection {
             container nlri-egress-protection {
               leaf nlri-type {
                 type string;
                 description "Type of NLRI being limited";
               }
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
             leaf number {
               type int32;
             }
             leaf count {
               type int32;
             }
             leaf table-name {
               type string;
               description "Unicast routing table";
             }
             leaf rib-adv-nlri {
               type string;
             }
             leaf time-series {
               type string;
             }
             list class {
               description "An instance of BGP output queue statistics";
               leaf priority-type {
                 type string;
                 description "BGP output queue priority type";
               }
               leaf rank {
                 type int32;
                 description "BGP output queue rank for priority type";
               }
               leaf token-count {
                 type int32;
                 description "BGP output queue token count for priority";
               }
             }
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-malformed-attributes {
           }
         }
       }
       container bgp-option-information {
         leaf export-policy {
           type string;
         }
         leaf import-policy {
           type string;
         }
         leaf advertise-bgp-static-policy {
           type string;
         }
         leaf bgp-options {
           type string;
         }
         leaf bgp-options2 {
           type string;
         }
         leaf bgp-options-extended {
           type string;
         }
         leaf remove-private-options {
           type string;
         }
         leaf authentication-key {
           type string;
         }
         leaf authentication-key-chain {
           type string;
           description "Name of authentication key chain";
         }
         leaf authentication-algorithm {
           type string;
           description "Name of authentication algorithm";
         }
         leaf authentication-configured {
           type empty;
         }
         leaf address-families {
           type string;
         }
         leaf drop-path-attributes {
           type string;
         }
         leaf ignore-path-attributes {
           type string;
         }
         leaf local-address {
           type ipaddr;
         }
         leaf holdtime {
           type int32;
           description "Delay before timing out the adjacency (default is 180 seconds)";
         }
         leaf metric-out {
           type int32;
         }
         leaf preference {
           type int32;
           description "Preference for the route";
         }
         leaf local-preference {
           type int32;
         }
         leaf local-as {
           type int32;
           description "Local AS number";
         }
         leaf local-as-private {
           type empty;
         }
         leaf local-system-as {
           type int32;
         }
         leaf receive-buffer-size {
           type int32;
         }
         leaf send-buffer-size {
           type int32;
         }
         leaf outbound-timer {
           type int32;
         }
         leaf med-action {
           type string;
         }
         leaf ipsec-sa {
           type string;
         }
         leaf bgp-bmp-monitor-peers {
           type string;
         }
         leaf bgp-bmp-route-monitoring-none {
           type empty;
         }
         leaf bgp-bmp-route-monitoring-prepolicy {
           type empty;
         }
         leaf bgp-bmp-prepolicy-exclude-non-feasible {
           type empty;
         }
         leaf bgp-bmp-route-monitoring-postpolicy {
           type empty;
         }
         leaf bgp-bmp-postpolicy-exclude-non-eligible {
           type empty;
         }
         container prefix-limit {
         }
         container accepted-prefix-limit {
           description "Limit number of prefixes accepted by policy";
         }
         container addpath-send {
         }
         container addpath-receive {
         }
         container nlri-information {
           leaf nlri-type {
             type string;
             description "Type of NLRI being limited";
           }
           leaf nlri-flow-novalidate {
             type string;
             description "Policy to accept flow routes without validation";
           }
           leaf nlri-output-queue-priority {
             type string;
             description "Default address family output queue priority";
           }
           leaf nlri-route-refresh-priority {
             type string;
             description "Default address family route-refresh priority";
           }
           leaf nlri-withdraw-priority {
             type string;
             description "Default address family withdraw priority";
           }
           container nlri-flags {
             leaf bgp-nlri-flag-explicit-null-for-all-routes {
               type empty;
             }
             leaf bgp-nlri-flag-explicit-null-for-connected-routes {
               type empty;
             }
             leaf bgp-nlri-flag-aggregate-label {
               type empty;
             }
             leaf bgp-nlri-flag-per-prefix-label {
               type empty;
             }
             leaf bgp-nlri-flag-per-group-label {
               type empty;
             }
             leaf bgp-nlri-flag-no-install-forwarding {
               type empty;
             }
             leaf bgp-nlri-flag-delay-route-advt {
               type empty;
             }
             leaf bgp-nlri-flag-traffic-stats {
               type empty;
             }
             leaf bgp-nlri-flag-l2vpn-status-vector {
               type empty;
             }
             leaf bgp-nlri-flag-no-l2vpn-status-vector {
               type empty;
             }
             leaf bgp-nlri-flag-strip-nexthop {
               type empty;
             }
             leaf bgp-nlri-flag-allow-po-add-nexthop {
               type empty;
             }
           }
           container nlri-traffic-stats {
             leaf traffic-stats-interval {
               type int32;
             }
             container tracing-information {
               leaf flags {
                 type string;
                 description "Enabled trace flags";
               }
               leaf filename {
                 type string;
                 description "Name of the trace file";
               }
               leaf filesize {
                 type int32;
                 description "Maximum size of the trace file";
               }
               leaf filelimit {
                 type int32;
                 description "Maximum number of retained trace files";
               }
             }
           }
           container output-queues {
             description "BGP output queues statistics";
             container output-queue {
               description "BGP output queues statistics";
               leaf time-series {
                 type string;
               }
               list class {
                 description "An instance of BGP output queue statistics";
                 leaf priority-type {
                   type string;
                   description "BGP output queue priority type";
                 }
                 leaf rank {
                   type int32;
                   description "BGP output queue rank for priority type";
                 }
                 leaf token-count {
                   type int32;
                   description "BGP output queue token count for priority";
                 }
                 leaf output-queue-route-count {
                   type int32;
                   description "BGP output queue route count for priority";
                 }
               }
             }
           }
         }
       }
       container tracing-information {
         leaf flags {
           type string;
           description "Enabled trace flags";
         }
         leaf filename {
           type string;
           description "Name of the trace file";
         }
         leaf filesize {
           type int32;
           description "Maximum size of the trace file";
         }
         leaf filelimit {
           type int32;
           description "Maximum number of retained trace files";
         }
       }
       list bgp-rib {
         list brief {
           leaf name {
             type string;
           }
           leaf total-prefix-count {
             type int32;
             description "Total number of prefixes in this RIB";
           }
           leaf active-prefix-count {
             type int32;
             description "Number of active prefixes";
           }
           leaf suppressed-prefix-count {
             type int32;
             description "Number of prefixes suppressed due to damping";
           }
           leaf history-prefix-count {
             type int32;
             description "Number of prefixes with damping history maintained";
           }
           leaf damped-prefix-count {
             type int32;
             description "Number of prefixes in any damped state";
           }
           leaf pending-prefix-count {
             type int32;
             description "Number of prefixes with pending changes";
           }
         }
         list terse {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
         }
         list summary {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf active-external-prefix-count {
             type int32;
             description "Number of active prefixes received from external peers";
           }
           leaf total-external-prefix-count {
             type int32;
             description "Total number of prefixes received from external peers";
           }
           leaf accepted-external-prefix-count {
             type int32;
             description "Number of accepted prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf accepted-internal-prefix-count {
             type int32;
             description "Number of accepted prefixes received from internal peers";
           }
           leaf suppressed-internal-prefix-count {
             type int32;
             description "Number of internal prefixes suppressed due to damping";
           }
         }
         list detail {
           leaf name {
             type string;
           }
           leaf rib-bit {
             type string;
           }
           leaf bgp-rib-state {
             type string;
           }
           leaf vpn-rib-state {
             type string;
           }
           leaf send-state {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf stale-prefix-count {
             type int32;
             description "Number of prefixes marked as stale";
           }
           leaf llgr-stale-prefix-count {
             type int32;
             description "Number of prefixes marked as LLGR stale";
           }
           leaf active-external-prefix-count {
             type int32;
             description "Number of active prefixes received from external peers";
           }
           leaf total-external-prefix-count {
             type int32;
             description "Total number of prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf suppressed-internal-prefix-count {
             type int32;
             description "Number of internal prefixes suppressed due to damping";
           }
           leaf advertised-prefix-count {
             type int32;
             description "Number of prefixes present in the RIB-OUT";
           }
         }
       }
     }
     list detail {
       description "Operational and configuration information for a BGP group";
       leaf type {
         type string;
       }
       leaf peer-as {
         type int32;
         description "Peer AS number";
       }
       leaf local-as {
         type int32;
         description "Local AS number";
       }
       leaf group-state {
         type string;
       }
       leaf name {
         type string;
       }
       leaf group-index {
         type int32;
       }
       leaf group-flags {
         type string;
       }
       leaf orr-igp-primary {
         type string;
       }
       leaf orr-igp-backup {
         type string;
       }
       leaf peer-count {
         type int32;
         description "Total number of peers";
       }
       leaf established-count {
         type int32;
         description "Number of peers within the group that are in the established state";
       }
       leaf peer-address {
         type ipaddr;
       }
       leaf igp-protocol {
         type string;
       }
       container unconfigured-peers {
         description "Set of address prefixes from which this group allows peering";
         list route-filter {
           description "Entries in martian table";
           leaf address {
             type ipaddr;
           }
           leaf flags {
             type string;
             description "Enabled trace flags";
           }
           leaf extended-information {
             type string;
           }
         }
       }
       container route-queue {
         leaf timer {
           type string;
         }
         leaf state {
           type string;
           description "HFRR profile Current state";
         }
         leaf element {
           type string;
         }
       }
       list bgp-peer {
         description "Operational and configuration information for a BGP peer";
         list terse {
           description "Operational and configuration information for a BGP peer";
           leaf bgp-peer.heading {
             type string;
             description "Operational and configuration information for a BGP peer";
           }
           leaf peer-address {
             type ipaddr;
           }
           leaf peer-as {
             type int32;
             description "Peer AS number";
           }
           leaf input-messages {
             type int32;
           }
           leaf output-messages {
             type int32;
           }
           leaf route-queue-count {
             type int32;
             description "Total number of routes queued for output to this peer";
           }
           leaf flap-count {
             type int32;
             description "Number of times BGP sessions have gone down";
           }
           leaf elapsed-time {
             type string;
             description "Time this adjacency or session has been up or down";
           }
           leaf peer-state {
             type string;
           }
           container bgp-option-information {
             container prefix-limit {
             }
             container accepted-prefix-limit {
               description "Limit number of prefixes accepted by policy";
             }
             container addpath-send {
             }
             container addpath-receive {
             }
             container nlri-information {
               leaf nlri-type {
                 type string;
                 description "Type of NLRI being limited";
               }
               leaf nlri-flow-novalidate {
                 type string;
                 description "Policy to accept flow routes without validation";
               }
               leaf nlri-output-queue-priority {
                 type string;
                 description "Default address family output queue priority";
               }
               leaf nlri-route-refresh-priority {
                 type string;
                 description "Default address family route-refresh priority";
               }
               leaf nlri-withdraw-priority {
                 type string;
                 description "Default address family withdraw priority";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container egress-protection {
             container nlri-egress-protection {
               leaf nlri-type {
                 type string;
                 description "Type of NLRI being limited";
               }
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-malformed-attributes {
           }
         }
         list detail {
           description "Operational and configuration information for a BGP peer";
           leaf peer-address {
             type ipaddr;
           }
           leaf peer-as {
             type int32;
             description "Peer AS number";
           }
           leaf local-address {
             type ipaddr;
           }
           leaf local-as {
             type int32;
             description "Local AS number";
           }
           leaf description {
             type string;
           }
           leaf peer-group {
             type string;
             description "BGP peer-group peer belongs to";
           }
           leaf peer-cfg-rti {
             type string;
             description "Routing-instance peer is configured in";
           }
           leaf peer-fwd-rti {
             type string;
             description "Peer's forwarding-context routing-instance";
           }
           leaf peer-type {
             type string;
           }
           leaf peer-state {
             type string;
           }
           leaf route-reflector-client {
             type empty;
           }
           leaf peer-flags {
             type string;
           }
           leaf last-state {
             type string;
           }
           leaf last-event {
             type string;
           }
           leaf last-error {
             type string;
           }
           leaf flap-count {
             type int32;
             description "Number of times BGP sessions have gone down";
           }
           leaf last-flap-event {
             type string;
           }
           leaf peer-id {
             type ipaddr;
           }
           leaf local-id {
             type ipaddr;
           }
           leaf active-holdtime {
             type int32;
           }
           leaf keepalive-interval {
             type int32;
           }
           leaf group-index {
             type int32;
           }
           leaf peer-index {
             type int32;
           }
           leaf local-interface-name {
             type string;
             description "Logical interface name";
           }
           leaf nlri-type-peer {
             type string;
           }
           leaf nlri-type-session {
             type string;
           }
           leaf peer-no-refresh {
             type empty;
             description "Present if this peer does not support refresh";
           }
           leaf peer-refresh-capability {
             type int32;
             description "Version of refresh capability supported by this peer";
           }
           leaf peer-4byte-as-capability-not-supported {
             type empty;
             description "This peer does not support 4 byte AS extension";
           }
           leaf peer-4byte-as-capability-advertised {
             type int32;
             description "4 byte Autonomous System capability advertised by this peer";
           }
           leaf peer-addpath-not-supported {
             type empty;
             description "This peer does not support addpath";
           }
           leaf peer-addpath-ronly-nlri {
             type string;
             description "Types of NLRI for which peer advertised recv capability";
           }
           leaf peer-addpath-sonly-nlri {
             type string;
             description "Types of NLRI for which peer advertised send capability";
           }
           leaf peer-addpath-rs-nlri {
             type string;
             description "Types of NLRI for which peer advertised send/recv cap";
           }
           leaf peer-delay-route-advertisements {
             type string;
           }
           leaf local-ext-nh-nlri {
             type string;
             description "Types of NLRI for which we advertised extend nh cap";
           }
           leaf peer-ext-nh-nlri {
             type string;
             description "Types of NLRI for which peer advertised extend nh cap";
           }
           leaf peer-restart-nlri-configured {
             type string;
           }
           leaf peer-restart-time-configured {
             type string;
           }
           leaf peer-stale-route-time-configured {
             type string;
           }
           leaf peer-no-restart {
             type empty;
             description "Present if this peer does not support graceful restart restarter mode";
           }
           leaf peer-restart-nlri-received {
             type string;
           }
           leaf peer-restart-time-received {
             type int32;
           }
           leaf peer-restart-flags-received {
             type string;
           }
           leaf peer-restart-nlri-can-save-state {
             type string;
           }
           leaf peer-restart-nlri-state-saved {
             type string;
           }
           leaf peer-restart-nlri-negotiated {
             type string;
           }
           leaf peer-end-of-rib-received {
             type string;
           }
           leaf peer-end-of-rib-sent {
             type string;
           }
           leaf peer-delay-end-of-rib {
             type string;
           }
           leaf peer-no-helper {
             type empty;
             description "Present if this peer does not support graceful restart receiver mode";
           }
           leaf peer-restart-nlri-held {
             type string;
           }
           leaf peer-restart-remaining-time {
             type string;
           }
           leaf peer-stale-remaining-time {
             type string;
           }
           leaf peer-llgr-nlri-configured {
             type string;
           }
           leaf peer-no-llgr-restarter {
             type empty;
             description "Present if this peer does not support long-lived graceful restart restarter mode";
           }
           leaf peer-llgr-nlri-restarter {
             type string;
           }
           leaf peer-llgr-nlri-state-saved {
             type string;
           }
           leaf peer-no-llgr-helper {
             type empty;
             description "Present if this peer does not support long-lived graceful restart receiver mode";
           }
           leaf peer-llgr-nlri-times {
             type string;
             description "NLRIs and times before long-lived stale routes are deleted";
           }
           leaf last-received {
             type int32;
           }
           leaf last-sent {
             type int32;
           }
           leaf last-checked {
             type int32;
           }
           leaf input-messages {
             type int32;
           }
           leaf input-updates {
             type int32;
           }
           leaf input-refreshes {
             type int32;
           }
           leaf input-octets {
             type int32;
           }
           leaf output-messages {
             type int32;
           }
           leaf output-updates {
             type int32;
           }
           leaf output-refreshes {
             type int32;
           }
           leaf output-octets {
             type int32;
           }
           leaf input-checksum {
             type int32;
           }
           leaf output-checksum {
             type int32;
           }
           leaf input-checksum-err {
             type int32;
           }
           leaf input-drop-path-attributes {
             type string;
           }
           leaf input-ignore-path-attributes {
             type string;
           }
           leaf buffered-octets-rx {
             type int32;
             description "Number of octets that have been received and are still buffered";
           }
           leaf buffered-octets-tx {
             type int32;
             description "Number of octets in the transmit buffer";
           }
           leaf gather-buffered-octets-tx {
             type int32;
             description "Number of octets in the gather transmit buffer";
           }
           container bgp-option-information {
             leaf export-policy {
               type string;
             }
             leaf import-policy {
               type string;
             }
             leaf advertise-bgp-static-policy {
               type string;
             }
             leaf bgp-options {
               type string;
             }
             leaf bgp-options2 {
               type string;
             }
             leaf bgp-options-extended {
               type string;
             }
             leaf remove-private-options {
               type string;
             }
             leaf authentication-key {
               type string;
             }
             leaf authentication-key-chain {
               type string;
               description "Name of authentication key chain";
             }
             leaf authentication-algorithm {
               type string;
               description "Name of authentication algorithm";
             }
             leaf authentication-configured {
               type empty;
             }
             leaf address-families {
               type string;
             }
             leaf drop-path-attributes {
               type string;
             }
             leaf ignore-path-attributes {
               type string;
             }
             leaf holdtime {
               type int32;
               description "Delay before timing out the adjacency (default is 180 seconds)";
             }
             leaf metric-out {
               type int32;
             }
             leaf preference {
               type int32;
               description "Preference for the route";
             }
             leaf local-preference {
               type int32;
             }
             leaf local-as-private {
               type empty;
             }
             leaf local-system-as {
               type int32;
             }
             leaf receive-buffer-size {
               type int32;
             }
             leaf send-buffer-size {
               type int32;
             }
             leaf outbound-timer {
               type int32;
             }
             leaf med-action {
               type string;
             }
             leaf ipsec-sa {
               type string;
             }
             leaf bgp-bmp-monitor-peers {
               type string;
             }
             leaf bgp-bmp-route-monitoring-none {
               type empty;
             }
             leaf bgp-bmp-route-monitoring-prepolicy {
               type empty;
             }
             leaf bgp-bmp-prepolicy-exclude-non-feasible {
               type empty;
             }
             leaf bgp-bmp-route-monitoring-postpolicy {
               type empty;
             }
             leaf bgp-bmp-postpolicy-exclude-non-eligible {
               type empty;
             }
             container prefix-limit {
             }
             container accepted-prefix-limit {
               description "Limit number of prefixes accepted by policy";
             }
             container addpath-send {
             }
             container addpath-receive {
             }
             container aigp-mode {
               leaf nlri-type {
                 type string;
                 description "Type of NLRI being limited";
               }
             }
             container family-damping-info {
               leaf nlri-type {
                 type string;
                 description "Type of NLRI being limited";
               }
             }
             container protection {
               leaf nlri-type {
                 type string;
                 description "Type of NLRI being limited";
               }
             }
             container nlri-information {
               leaf nlri-type {
                 type string;
                 description "Type of NLRI being limited";
               }
               leaf nlri-flow-novalidate {
                 type string;
                 description "Policy to accept flow routes without validation";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container bgp-peer-iosession {
             leaf iosession-thread-name {
               type string;
             }
             leaf iosession-state {
               type string;
             }
           }
           container bgp-bfd {
             leaf bfd-configuration-state {
               type string;
               description "BFD configuration state";
             }
             leaf bfd-operational-state {
               type string;
               description "BFD operational state";
             }
           }
           container egress-protection {
             leaf nlri-type {
               type string;
               description "Type of NLRI being limited";
             }
             container nlri-egress-protection {
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
             leaf number {
               type int32;
             }
             leaf count {
               type int32;
             }
             leaf table-name {
               type string;
               description "Unicast routing table";
             }
             leaf rib-adv-nlri {
               type string;
             }
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-error {
             leaf name {
               type string;
             }
             leaf send-count {
               type int32;
             }
             leaf receive-count {
               type int32;
             }
           }
           container bgp-malformed-attributes {
             container malformed-information {
               leaf log-interval {
                 type int32;
               }
               leaf route-limit {
                 type int32;
               }
             }
             container path-attribute {
               leaf name {
                 type string;
               }
               leaf code {
                 type int32;
               }
               leaf last-recv {
                 type int32;
               }
               leaf total-recv {
                 type int32;
               }
             }
           }
           container route-queue {
             leaf timer {
               type string;
             }
             leaf state {
               type string;
               description "HFRR profile Current state";
             }
             leaf element {
               type string;
             }
           }
           container tracing-information {
             leaf flags {
               type string;
               description "Enabled trace flags";
             }
             leaf filename {
               type string;
               description "Name of the trace file";
             }
             leaf filesize {
               type int32;
               description "Maximum size of the trace file";
             }
             leaf filelimit {
               type int32;
               description "Maximum number of retained trace files";
             }
           }
         }
         list output-queue {
           description "Operational and configuration information for a BGP peer";
           leaf peer-address {
             type ipaddr;
           }
           leaf peer-as {
             type int32;
             description "Peer AS number";
           }
           leaf local-address {
             type ipaddr;
           }
           leaf local-as {
             type int32;
             description "Local AS number";
           }
           leaf description {
             type string;
           }
           container bgp-option-information {
             container prefix-limit {
             }
             container accepted-prefix-limit {
               description "Limit number of prefixes accepted by policy";
             }
             container addpath-send {
             }
             container addpath-receive {
             }
             container nlri-information {
               leaf nlri-type {
                 type string;
                 description "Type of NLRI being limited";
               }
               leaf nlri-flow-novalidate {
                 type string;
                 description "Policy to accept flow routes without validation";
               }
               leaf nlri-output-queue-priority {
                 type string;
                 description "Default address family output queue priority";
               }
               leaf nlri-route-refresh-priority {
                 type string;
                 description "Default address family route-refresh priority";
               }
               leaf nlri-withdraw-priority {
                 type string;
                 description "Default address family withdraw priority";
               }
               container nlri-flags {
                 leaf bgp-nlri-flag-explicit-null-for-all-routes {
                   type empty;
                 }
                 leaf bgp-nlri-flag-explicit-null-for-connected-routes {
                   type empty;
                 }
                 leaf bgp-nlri-flag-aggregate-label {
                   type empty;
                 }
                 leaf bgp-nlri-flag-per-prefix-label {
                   type empty;
                 }
                 leaf bgp-nlri-flag-per-group-label {
                   type empty;
                 }
                 leaf bgp-nlri-flag-no-install-forwarding {
                   type empty;
                 }
                 leaf bgp-nlri-flag-delay-route-advt {
                   type empty;
                 }
                 leaf bgp-nlri-flag-traffic-stats {
                   type empty;
                 }
                 leaf bgp-nlri-flag-l2vpn-status-vector {
                   type empty;
                 }
                 leaf bgp-nlri-flag-no-l2vpn-status-vector {
                   type empty;
                 }
                 leaf bgp-nlri-flag-strip-nexthop {
                   type empty;
                 }
                 leaf bgp-nlri-flag-allow-po-add-nexthop {
                   type empty;
                 }
               }
               container nlri-traffic-stats {
                 leaf traffic-stats-interval {
                   type int32;
                 }
                 container tracing-information {
                   leaf flags {
                     type string;
                     description "Enabled trace flags";
                   }
                   leaf filename {
                     type string;
                     description "Name of the trace file";
                   }
                   leaf filesize {
                     type int32;
                     description "Maximum size of the trace file";
                   }
                   leaf filelimit {
                     type int32;
                     description "Maximum number of retained trace files";
                   }
                 }
               }
               container output-queues {
                 description "BGP output queues statistics";
                 container output-queue {
                   description "BGP output queues statistics";
                   leaf time-series {
                     type string;
                   }
                   list class {
                     description "An instance of BGP output queue statistics";
                     leaf priority-type {
                       type string;
                       description "BGP output queue priority type";
                     }
                     leaf rank {
                       type int32;
                       description "BGP output queue rank for priority type";
                     }
                     leaf token-count {
                       type int32;
                       description "BGP output queue token count for priority";
                     }
                     leaf output-queue-route-count {
                       type int32;
                       description "BGP output queue route count for priority";
                     }
                   }
                 }
               }
             }
           }
           container egress-protection {
             container nlri-egress-protection {
               leaf nlri-type {
                 type string;
                 description "Type of NLRI being limited";
               }
               leaf bgp-context-id {
                 type ipaddr;
               }
               leaf bgp-import-policy {
                 type string;
               }
             }
             list ep-backup-table {
               leaf ep-backup-rib-name {
                 type string;
                 description "Instance backup RIB";
               }
               leaf ep-backup-link {
                 type string;
                 description "Vt interface";
               }
               leaf ep-backup-rib-id {
                 type int32;
                 description "RIB Identifier";
               }
               leaf ep-backup-kern-id {
                 type int32;
                 description "FIB Identifier";
               }
             }
             list ep-instance-table {
               leaf ep-instance-name {
                 type string;
               }
               leaf ep-instance-type {
                 type string;
                 description "Instance type";
               }
               leaf ep-instance-protection-type {
                 type string;
                 description "Instance request protected";
               }
             }
           }
           list bgp-output-queue {
             leaf number {
               type int32;
             }
             leaf count {
               type int32;
             }
             leaf table-name {
               type string;
               description "Unicast routing table";
             }
             leaf rib-adv-nlri {
               type string;
             }
             leaf time-series {
               type string;
             }
             list class {
               description "An instance of BGP output queue statistics";
               leaf priority-type {
                 type string;
                 description "BGP output queue priority type";
               }
               leaf rank {
                 type int32;
                 description "BGP output queue rank for priority type";
               }
               leaf token-count {
                 type int32;
                 description "BGP output queue token count for priority";
               }
             }
           }
           list bgp-rib {
             list brief {
               leaf name {
                 type string;
               }
               leaf total-prefix-count {
                 type int32;
                 description "Total number of prefixes in this RIB";
               }
               leaf active-prefix-count {
                 type int32;
                 description "Number of active prefixes";
               }
               leaf suppressed-prefix-count {
                 type int32;
                 description "Number of prefixes suppressed due to damping";
               }
               leaf history-prefix-count {
                 type int32;
                 description "Number of prefixes with damping history maintained";
               }
               leaf damped-prefix-count {
                 type int32;
                 description "Number of prefixes in any damped state";
               }
               leaf pending-prefix-count {
                 type int32;
                 description "Number of prefixes with pending changes";
               }
             }
             list terse {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
             }
             list summary {
               leaf name {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf active-external-prefix-count {
                 type int32;
                 description "Number of active prefixes received from external peers";
               }
               leaf total-external-prefix-count {
                 type int32;
                 description "Total number of prefixes received from external peers";
               }
               leaf accepted-external-prefix-count {
                 type int32;
                 description "Number of accepted prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf accepted-internal-prefix-count {
                 type int32;
                 description "Number of accepted prefixes received from internal peers";
               }
               leaf suppressed-internal-prefix-count {
                 type int32;
                 description "Number of internal prefixes suppressed due to damping";
               }
             }
             list detail {
               leaf name {
                 type string;
               }
               leaf rib-bit {
                 type string;
               }
               leaf bgp-rib-state {
                 type string;
               }
               leaf vpn-rib-state {
                 type string;
               }
               leaf send-state {
                 type string;
               }
               leaf active-prefix-count {
                 type int32;
                 description "Number of active prefixes";
               }
               leaf received-prefix-count {
                 type int32;
                 description "For a peer RIB, number of prefixes received from this peer";
               }
               leaf accepted-prefix-count {
                 type int32;
                 description "For a peer RIB, number of prefixes from this peer accepted by policy";
               }
               leaf suppressed-prefix-count {
                 type int32;
                 description "Number of prefixes suppressed due to damping";
               }
               leaf stale-prefix-count {
                 type int32;
                 description "Number of prefixes marked as stale";
               }
               leaf llgr-stale-prefix-count {
                 type int32;
                 description "Number of prefixes marked as LLGR stale";
               }
               leaf active-external-prefix-count {
                 type int32;
                 description "Number of active prefixes received from external peers";
               }
               leaf total-external-prefix-count {
                 type int32;
                 description "Total number of prefixes received from external peers";
               }
               leaf suppressed-external-prefix-count {
                 type int32;
                 description "Number of external prefixes suppressed due to damping";
               }
               leaf active-internal-prefix-count {
                 type int32;
                 description "Number of active prefixes received from internal peers";
               }
               leaf total-internal-prefix-count {
                 type int32;
                 description "Total number of prefixes received from internal peers";
               }
               leaf suppressed-internal-prefix-count {
                 type int32;
                 description "Number of internal prefixes suppressed due to damping";
               }
               leaf advertised-prefix-count {
                 type int32;
                 description "Number of prefixes present in the RIB-OUT";
               }
             }
           }
           container bgp-family-stat {
             container detail {
               leaf nlri-type {
                 type string;
                 description "Type of NLRI being limited";
               }
               leaf bgp-nlri-send-time {
                 type int32;
                 description "Time for initial send by peer";
               }
               leaf bgp-nlri-recv-time {
                 type int32;
                 description "Time for initial receive by peer";
               }
             }
           }
           list entropy-label-info {
             leaf nlri-type {
               type string;
               description "Type of NLRI being limited";
             }
             leaf entropy-label {
               type string;
               description "Entropy label";
             }
             leaf entropy-label-import-policy {
               type string;
             }
             leaf entropy-label-no-next-hop-validation {
               type string;
               description "Entropy label no next hop validation";
             }
             leaf entropy-label-capability {
               type string;
               description "Local entropy label capability";
             }
             leaf entropy-label-stitching-capability {
               type string;
               description "Entropy label stitching capability";
             }
           }
           container bgp-malformed-attributes {
           }
         }
       }
       container bgp-option-information {
         leaf export-policy {
           type string;
         }
         leaf import-policy {
           type string;
         }
         leaf advertise-bgp-static-policy {
           type string;
         }
         leaf bgp-options {
           type string;
         }
         leaf bgp-options2 {
           type string;
         }
         leaf bgp-options-extended {
           type string;
         }
         leaf remove-private-options {
           type string;
         }
         leaf authentication-key {
           type string;
         }
         leaf authentication-key-chain {
           type string;
           description "Name of authentication key chain";
         }
         leaf authentication-algorithm {
           type string;
           description "Name of authentication algorithm";
         }
         leaf authentication-configured {
           type empty;
         }
         leaf address-families {
           type string;
         }
         leaf drop-path-attributes {
           type string;
         }
         leaf ignore-path-attributes {
           type string;
         }
         leaf local-address {
           type ipaddr;
         }
         leaf holdtime {
           type int32;
           description "Delay before timing out the adjacency (default is 180 seconds)";
         }
         leaf metric-out {
           type int32;
         }
         leaf preference {
           type int32;
           description "Preference for the route";
         }
         leaf local-preference {
           type int32;
         }
         leaf local-as {
           type int32;
           description "Local AS number";
         }
         leaf local-as-private {
           type empty;
         }
         leaf local-system-as {
           type int32;
         }
         leaf receive-buffer-size {
           type int32;
         }
         leaf send-buffer-size {
           type int32;
         }
         leaf outbound-timer {
           type int32;
         }
         leaf med-action {
           type string;
         }
         leaf ipsec-sa {
           type string;
         }
         leaf bgp-bmp-monitor-peers {
           type string;
         }
         leaf bgp-bmp-route-monitoring-none {
           type empty;
         }
         leaf bgp-bmp-route-monitoring-prepolicy {
           type empty;
         }
         leaf bgp-bmp-prepolicy-exclude-non-feasible {
           type empty;
         }
         leaf bgp-bmp-route-monitoring-postpolicy {
           type empty;
         }
         leaf bgp-bmp-postpolicy-exclude-non-eligible {
           type empty;
         }
         container prefix-limit {
         }
         container accepted-prefix-limit {
           description "Limit number of prefixes accepted by policy";
         }
         container addpath-send {
         }
         container addpath-receive {
         }
         container nlri-information {
           leaf nlri-type {
             type string;
             description "Type of NLRI being limited";
           }
           leaf nlri-flow-novalidate {
             type string;
             description "Policy to accept flow routes without validation";
           }
           leaf nlri-output-queue-priority {
             type string;
             description "Default address family output queue priority";
           }
           leaf nlri-route-refresh-priority {
             type string;
             description "Default address family route-refresh priority";
           }
           leaf nlri-withdraw-priority {
             type string;
             description "Default address family withdraw priority";
           }
           container nlri-flags {
             leaf bgp-nlri-flag-explicit-null-for-all-routes {
               type empty;
             }
             leaf bgp-nlri-flag-explicit-null-for-connected-routes {
               type empty;
             }
             leaf bgp-nlri-flag-aggregate-label {
               type empty;
             }
             leaf bgp-nlri-flag-per-prefix-label {
               type empty;
             }
             leaf bgp-nlri-flag-per-group-label {
               type empty;
             }
             leaf bgp-nlri-flag-no-install-forwarding {
               type empty;
             }
             leaf bgp-nlri-flag-delay-route-advt {
               type empty;
             }
             leaf bgp-nlri-flag-traffic-stats {
               type empty;
             }
             leaf bgp-nlri-flag-l2vpn-status-vector {
               type empty;
             }
             leaf bgp-nlri-flag-no-l2vpn-status-vector {
               type empty;
             }
             leaf bgp-nlri-flag-strip-nexthop {
               type empty;
             }
             leaf bgp-nlri-flag-allow-po-add-nexthop {
               type empty;
             }
           }
           container nlri-traffic-stats {
             leaf traffic-stats-interval {
               type int32;
             }
             container tracing-information {
               leaf flags {
                 type string;
                 description "Enabled trace flags";
               }
               leaf filename {
                 type string;
                 description "Name of the trace file";
               }
               leaf filesize {
                 type int32;
                 description "Maximum size of the trace file";
               }
               leaf filelimit {
                 type int32;
                 description "Maximum number of retained trace files";
               }
             }
           }
           container output-queues {
             description "BGP output queues statistics";
             container output-queue {
               description "BGP output queues statistics";
               leaf time-series {
                 type string;
               }
               list class {
                 description "An instance of BGP output queue statistics";
                 leaf priority-type {
                   type string;
                   description "BGP output queue priority type";
                 }
                 leaf rank {
                   type int32;
                   description "BGP output queue rank for priority type";
                 }
                 leaf token-count {
                   type int32;
                   description "BGP output queue token count for priority";
                 }
                 leaf output-queue-route-count {
                   type int32;
                   description "BGP output queue route count for priority";
                 }
               }
             }
           }
         }
       }
       container tracing-information {
         leaf flags {
           type string;
           description "Enabled trace flags";
         }
         leaf filename {
           type string;
           description "Name of the trace file";
         }
         leaf filesize {
           type int32;
           description "Maximum size of the trace file";
         }
         leaf filelimit {
           type int32;
           description "Maximum number of retained trace files";
         }
       }
       list bgp-rib {
         list brief {
           leaf name {
             type string;
           }
           leaf total-prefix-count {
             type int32;
             description "Total number of prefixes in this RIB";
           }
           leaf active-prefix-count {
             type int32;
             description "Number of active prefixes";
           }
           leaf suppressed-prefix-count {
             type int32;
             description "Number of prefixes suppressed due to damping";
           }
           leaf history-prefix-count {
             type int32;
             description "Number of prefixes with damping history maintained";
           }
           leaf damped-prefix-count {
             type int32;
             description "Number of prefixes in any damped state";
           }
           leaf pending-prefix-count {
             type int32;
             description "Number of prefixes with pending changes";
           }
         }
         list terse {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
         }
         list summary {
           leaf name {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf active-external-prefix-count {
             type int32;
             description "Number of active prefixes received from external peers";
           }
           leaf total-external-prefix-count {
             type int32;
             description "Total number of prefixes received from external peers";
           }
           leaf accepted-external-prefix-count {
             type int32;
             description "Number of accepted prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf accepted-internal-prefix-count {
             type int32;
             description "Number of accepted prefixes received from internal peers";
           }
           leaf suppressed-internal-prefix-count {
             type int32;
             description "Number of internal prefixes suppressed due to damping";
           }
         }
         list detail {
           leaf name {
             type string;
           }
           leaf rib-bit {
             type string;
           }
           leaf bgp-rib-state {
             type string;
           }
           leaf vpn-rib-state {
             type string;
           }
           leaf send-state {
             type string;
           }
           leaf active-prefix-count {
             type int32;
             description "Number of active prefixes";
           }
           leaf received-prefix-count {
             type int32;
             description "For a peer RIB, number of prefixes received from this peer";
           }
           leaf accepted-prefix-count {
             type int32;
             description "For a peer RIB, number of prefixes from this peer accepted by policy";
           }
           leaf suppressed-prefix-count {
             type int32;
             description "Number of prefixes suppressed due to damping";
           }
           leaf stale-prefix-count {
             type int32;
             description "Number of prefixes marked as stale";
           }
           leaf llgr-stale-prefix-count {
             type int32;
             description "Number of prefixes marked as LLGR stale";
           }
           leaf active-external-prefix-count {
             type int32;
             description "Number of active prefixes received from external peers";
           }
           leaf total-external-prefix-count {
             type int32;
             description "Total number of prefixes received from external peers";
           }
           leaf suppressed-external-prefix-count {
             type int32;
             description "Number of external prefixes suppressed due to damping";
           }
           leaf active-internal-prefix-count {
             type int32;
             description "Number of active prefixes received from internal peers";
           }
           leaf total-internal-prefix-count {
             type int32;
             description "Total number of prefixes received from internal peers";
           }
           leaf suppressed-internal-prefix-count {
             type int32;
             description "Number of internal prefixes suppressed due to damping";
           }
           leaf advertised-prefix-count {
             type int32;
             description "Number of prefixes present in the RIB-OUT";
           }
         }
       }
     }
   }
   container bgp-information {
     description "Operational and configuration information for BGP";
     leaf group-count {
       type int32;
     }
     leaf peer-count {
       type int32;
       description "Total number of peers";
     }
     leaf external-peer-count {
       type int32;
     }
     leaf internal-peer-count {
       type int32;
     }
     leaf down-peer-count {
       type int32;
     }
     leaf flap-count {
       type int32;
       description "Number of times BGP sessions have gone down";
     }
     container bgp-family-stat {
       container detail {
         leaf nlri-type {
           type string;
           description "Type of NLRI being limited";
         }
         leaf bgp-nlri-send-time {
           type int32;
           description "Time for initial send by peer";
         }
         leaf bgp-nlri-recv-time {
           type int32;
           description "Time for initial receive by peer";
         }
       }
     }
     list bgp-rib {
       list brief {
         leaf name {
           type string;
         }
         leaf total-prefix-count {
           type int32;
           description "Total number of prefixes in this RIB";
         }
         leaf active-prefix-count {
           type int32;
           description "Number of active prefixes";
         }
         leaf suppressed-prefix-count {
           type int32;
           description "Number of prefixes suppressed due to damping";
         }
         leaf history-prefix-count {
           type int32;
           description "Number of prefixes with damping history maintained";
         }
         leaf damped-prefix-count {
           type int32;
           description "Number of prefixes in any damped state";
         }
         leaf pending-prefix-count {
           type int32;
           description "Number of prefixes with pending changes";
         }
       }
       list terse {
         leaf name {
           type string;
         }
         leaf active-prefix-count {
           type int32;
           description "Number of active prefixes";
         }
         leaf received-prefix-count {
           type int32;
           description "For a peer RIB, number of prefixes received from this peer";
         }
         leaf accepted-prefix-count {
           type int32;
           description "For a peer RIB, number of prefixes from this peer accepted by policy";
         }
         leaf suppressed-prefix-count {
           type int32;
           description "Number of prefixes suppressed due to damping";
         }
       }
       list summary {
         leaf name {
           type string;
         }
         leaf active-prefix-count {
           type int32;
           description "Number of active prefixes";
         }
         leaf received-prefix-count {
           type int32;
           description "For a peer RIB, number of prefixes received from this peer";
         }
         leaf accepted-prefix-count {
           type int32;
           description "For a peer RIB, number of prefixes from this peer accepted by policy";
         }
         leaf suppressed-prefix-count {
           type int32;
           description "Number of prefixes suppressed due to damping";
         }
         leaf active-external-prefix-count {
           type int32;
           description "Number of active prefixes received from external peers";
         }
         leaf total-external-prefix-count {
           type int32;
           description "Total number of prefixes received from external peers";
         }
         leaf accepted-external-prefix-count {
           type int32;
           description "Number of accepted prefixes received from external peers";
         }
         leaf suppressed-external-prefix-count {
           type int32;
           description "Number of external prefixes suppressed due to damping";
         }
         leaf active-internal-prefix-count {
           type int32;
           description "Number of active prefixes received from internal peers";
         }
         leaf total-internal-prefix-count {
           type int32;
           description "Total number of prefixes received from internal peers";
         }
         leaf accepted-internal-prefix-count {
           type int32;
           description "Number of accepted prefixes received from internal peers";
         }
         leaf suppressed-internal-prefix-count {
           type int32;
           description "Number of internal prefixes suppressed due to damping";
         }
       }
       list detail {
         leaf name {
           type string;
         }
         leaf rib-bit {
           type string;
         }
         leaf bgp-rib-state {
           type string;
         }
         leaf vpn-rib-state {
           type string;
         }
         leaf send-state {
           type string;
         }
         leaf active-prefix-count {
           type int32;
           description "Number of active prefixes";
         }
         leaf received-prefix-count {
           type int32;
           description "For a peer RIB, number of prefixes received from this peer";
         }
         leaf accepted-prefix-count {
           type int32;
           description "For a peer RIB, number of prefixes from this peer accepted by policy";
         }
         leaf suppressed-prefix-count {
           type int32;
           description "Number of prefixes suppressed due to damping";
         }
         leaf stale-prefix-count {
           type int32;
           description "Number of prefixes marked as stale";
         }
         leaf llgr-stale-prefix-count {
           type int32;
           description "Number of prefixes marked as LLGR stale";
         }
         leaf active-external-prefix-count {
           type int32;
           description "Number of active prefixes received from external peers";
         }
         leaf total-external-prefix-count {
           type int32;
           description "Total number of prefixes received from external peers";
         }
         leaf suppressed-external-prefix-count {
           type int32;
           description "Number of external prefixes suppressed due to damping";
         }
         leaf active-internal-prefix-count {
           type int32;
           description "Number of active prefixes received from internal peers";
         }
         leaf total-internal-prefix-count {
           type int32;
           description "Total number of prefixes received from internal peers";
         }
         leaf suppressed-internal-prefix-count {
           type int32;
           description "Number of internal prefixes suppressed due to damping";
         }
         leaf advertised-prefix-count {
           type int32;
           description "Number of prefixes present in the RIB-OUT";
         }
       }
     }
     list bgp-peer {
       description "Operational and configuration information for a BGP peer";
       list terse {
         description "Operational and configuration information for a BGP peer";
         leaf bgp-peer.heading {
           type string;
           description "Operational and configuration information for a BGP peer";
         }
         leaf peer-address {
           type ipaddr;
         }
         leaf peer-as {
           type int32;
           description "Peer AS number";
         }
         leaf input-messages {
           type int32;
         }
         leaf output-messages {
           type int32;
         }
         leaf route-queue-count {
           type int32;
           description "Total number of routes queued for output to this peer";
         }
         leaf flap-count {
           type int32;
           description "Number of times BGP sessions have gone down";
         }
         leaf elapsed-time {
           type string;
           description "Time this adjacency or session has been up or down";
         }
         leaf peer-state {
           type string;
         }
         container bgp-option-information {
           container prefix-limit {
           }
           container accepted-prefix-limit {
             description "Limit number of prefixes accepted by policy";
           }
           container addpath-send {
           }
           container addpath-receive {
           }
           container nlri-information {
             leaf nlri-type {
               type string;
               description "Type of NLRI being limited";
             }
             leaf nlri-flow-novalidate {
               type string;
               description "Policy to accept flow routes without validation";
             }
             leaf nlri-output-queue-priority {
               type string;
               description "Default address family output queue priority";
             }
             leaf nlri-route-refresh-priority {
               type string;
               description "Default address family route-refresh priority";
             }
             leaf nlri-withdraw-priority {
               type string;
               description "Default address family withdraw priority";
             }
             container nlri-flags {
               leaf bgp-nlri-flag-explicit-null-for-all-routes {
                 type empty;
               }
               leaf bgp-nlri-flag-explicit-null-for-connected-routes {
                 type empty;
               }
               leaf bgp-nlri-flag-aggregate-label {
                 type empty;
               }
               leaf bgp-nlri-flag-per-prefix-label {
                 type empty;
               }
               leaf bgp-nlri-flag-per-group-label {
                 type empty;
               }
               leaf bgp-nlri-flag-no-install-forwarding {
                 type empty;
               }
               leaf bgp-nlri-flag-delay-route-advt {
                 type empty;
               }
               leaf bgp-nlri-flag-traffic-stats {
                 type empty;
               }
               leaf bgp-nlri-flag-l2vpn-status-vector {
                 type empty;
               }
               leaf bgp-nlri-flag-no-l2vpn-status-vector {
                 type empty;
               }
               leaf bgp-nlri-flag-strip-nexthop {
                 type empty;
               }
               leaf bgp-nlri-flag-allow-po-add-nexthop {
                 type empty;
               }
             }
             container nlri-traffic-stats {
               leaf traffic-stats-interval {
                 type int32;
               }
               container tracing-information {
                 leaf flags {
                   type string;
                   description "Enabled trace flags";
                 }
                 leaf filename {
                   type string;
                   description "Name of the trace file";
                 }
                 leaf filesize {
                   type int32;
                   description "Maximum size of the trace file";
                 }
                 leaf filelimit {
                   type int32;
                   description "Maximum number of retained trace files";
                 }
               }
             }
             container output-queues {
               description "BGP output queues statistics";
               container output-queue {
                 description "BGP output queues statistics";
                 leaf time-series {
                   type string;
                 }
                 list class {
                   description "An instance of BGP output queue statistics";
                   leaf priority-type {
                     type string;
                     description "BGP output queue priority type";
                   }
                   leaf rank {
                     type int32;
                     description "BGP output queue rank for priority type";
                   }
                   leaf token-count {
                     type int32;
                     description "BGP output queue token count for priority";
                   }
                   leaf output-queue-route-count {
                     type int32;
                     description "BGP output queue route count for priority";
                   }
                 }
               }
             }
           }
         }
         container egress-protection {
           container nlri-egress-protection {
             leaf nlri-type {
               type string;
               description "Type of NLRI being limited";
             }
             leaf bgp-context-id {
               type ipaddr;
             }
             leaf bgp-import-policy {
               type string;
             }
           }
           list ep-backup-table {
             leaf ep-backup-rib-name {
               type string;
               description "Instance backup RIB";
             }
             leaf ep-backup-link {
               type string;
               description "Vt interface";
             }
             leaf ep-backup-rib-id {
               type int32;
               description "RIB Identifier";
             }
             leaf ep-backup-kern-id {
               type int32;
               description "FIB Identifier";
             }
           }
           list ep-instance-table {
             leaf ep-instance-name {
               type string;
             }
             leaf ep-instance-type {
               type string;
               description "Instance type";
             }
             leaf ep-instance-protection-type {
               type string;
               description "Instance request protected";
             }
           }
         }
         list bgp-output-queue {
         }
         list bgp-rib {
           list brief {
             leaf name {
               type string;
             }
             leaf total-prefix-count {
               type int32;
               description "Total number of prefixes in this RIB";
             }
             leaf active-prefix-count {
               type int32;
               description "Number of active prefixes";
             }
             leaf suppressed-prefix-count {
               type int32;
               description "Number of prefixes suppressed due to damping";
             }
             leaf history-prefix-count {
               type int32;
               description "Number of prefixes with damping history maintained";
             }
             leaf damped-prefix-count {
               type int32;
               description "Number of prefixes in any damped state";
             }
             leaf pending-prefix-count {
               type int32;
               description "Number of prefixes with pending changes";
             }
           }
           list terse {
             leaf name {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
           }
           list summary {
             leaf name {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
             leaf active-external-prefix-count {
               type int32;
               description "Number of active prefixes received from external peers";
             }
             leaf total-external-prefix-count {
               type int32;
               description "Total number of prefixes received from external peers";
             }
             leaf accepted-external-prefix-count {
               type int32;
               description "Number of accepted prefixes received from external peers";
             }
             leaf suppressed-external-prefix-count {
               type int32;
               description "Number of external prefixes suppressed due to damping";
             }
             leaf active-internal-prefix-count {
               type int32;
               description "Number of active prefixes received from internal peers";
             }
             leaf total-internal-prefix-count {
               type int32;
               description "Total number of prefixes received from internal peers";
             }
             leaf accepted-internal-prefix-count {
               type int32;
               description "Number of accepted prefixes received from internal peers";
             }
             leaf suppressed-internal-prefix-count {
               type int32;
               description "Number of internal prefixes suppressed due to damping";
             }
           }
           list detail {
             leaf name {
               type string;
             }
             leaf rib-bit {
               type string;
             }
             leaf bgp-rib-state {
               type string;
             }
             leaf vpn-rib-state {
               type string;
             }
             leaf send-state {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
             leaf stale-prefix-count {
               type int32;
               description "Number of prefixes marked as stale";
             }
             leaf llgr-stale-prefix-count {
               type int32;
               description "Number of prefixes marked as LLGR stale";
             }
             leaf active-external-prefix-count {
               type int32;
               description "Number of active prefixes received from external peers";
             }
             leaf total-external-prefix-count {
               type int32;
               description "Total number of prefixes received from external peers";
             }
             leaf suppressed-external-prefix-count {
               type int32;
               description "Number of external prefixes suppressed due to damping";
             }
             leaf active-internal-prefix-count {
               type int32;
               description "Number of active prefixes received from internal peers";
             }
             leaf total-internal-prefix-count {
               type int32;
               description "Total number of prefixes received from internal peers";
             }
             leaf suppressed-internal-prefix-count {
               type int32;
               description "Number of internal prefixes suppressed due to damping";
             }
             leaf advertised-prefix-count {
               type int32;
               description "Number of prefixes present in the RIB-OUT";
             }
           }
         }
         container bgp-family-stat {
           container detail {
             leaf nlri-type {
               type string;
               description "Type of NLRI being limited";
             }
             leaf bgp-nlri-send-time {
               type int32;
               description "Time for initial send by peer";
             }
             leaf bgp-nlri-recv-time {
               type int32;
               description "Time for initial receive by peer";
             }
           }
         }
         list entropy-label-info {
           leaf nlri-type {
             type string;
             description "Type of NLRI being limited";
           }
           leaf entropy-label {
             type string;
             description "Entropy label";
           }
           leaf entropy-label-import-policy {
             type string;
           }
           leaf entropy-label-no-next-hop-validation {
             type string;
             description "Entropy label no next hop validation";
           }
           leaf entropy-label-capability {
             type string;
             description "Local entropy label capability";
           }
           leaf entropy-label-stitching-capability {
             type string;
             description "Entropy label stitching capability";
           }
         }
         container bgp-malformed-attributes {
         }
       }
       list detail {
         description "Operational and configuration information for a BGP peer";
         leaf peer-address {
           type ipaddr;
         }
         leaf peer-as {
           type int32;
           description "Peer AS number";
         }
         leaf local-address {
           type ipaddr;
         }
         leaf local-as {
           type int32;
           description "Local AS number";
         }
         leaf description {
           type string;
         }
         leaf peer-group {
           type string;
           description "BGP peer-group peer belongs to";
         }
         leaf peer-cfg-rti {
           type string;
           description "Routing-instance peer is configured in";
         }
         leaf peer-fwd-rti {
           type string;
           description "Peer's forwarding-context routing-instance";
         }
         leaf peer-type {
           type string;
         }
         leaf peer-state {
           type string;
         }
         leaf route-reflector-client {
           type empty;
         }
         leaf peer-flags {
           type string;
         }
         leaf last-state {
           type string;
         }
         leaf last-event {
           type string;
         }
         leaf last-error {
           type string;
         }
         leaf flap-count {
           type int32;
           description "Number of times BGP sessions have gone down";
         }
         leaf last-flap-event {
           type string;
         }
         leaf peer-id {
           type ipaddr;
         }
         leaf local-id {
           type ipaddr;
         }
         leaf active-holdtime {
           type int32;
         }
         leaf keepalive-interval {
           type int32;
         }
         leaf group-index {
           type int32;
         }
         leaf peer-index {
           type int32;
         }
         leaf local-interface-name {
           type string;
           description "Logical interface name";
         }
         leaf nlri-type-peer {
           type string;
         }
         leaf nlri-type-session {
           type string;
         }
         leaf peer-no-refresh {
           type empty;
           description "Present if this peer does not support refresh";
         }
         leaf peer-refresh-capability {
           type int32;
           description "Version of refresh capability supported by this peer";
         }
         leaf peer-4byte-as-capability-not-supported {
           type empty;
           description "This peer does not support 4 byte AS extension";
         }
         leaf peer-4byte-as-capability-advertised {
           type int32;
           description "4 byte Autonomous System capability advertised by this peer";
         }
         leaf peer-addpath-not-supported {
           type empty;
           description "This peer does not support addpath";
         }
         leaf peer-addpath-ronly-nlri {
           type string;
           description "Types of NLRI for which peer advertised recv capability";
         }
         leaf peer-addpath-sonly-nlri {
           type string;
           description "Types of NLRI for which peer advertised send capability";
         }
         leaf peer-addpath-rs-nlri {
           type string;
           description "Types of NLRI for which peer advertised send/recv cap";
         }
         leaf peer-delay-route-advertisements {
           type string;
         }
         leaf local-ext-nh-nlri {
           type string;
           description "Types of NLRI for which we advertised extend nh cap";
         }
         leaf peer-ext-nh-nlri {
           type string;
           description "Types of NLRI for which peer advertised extend nh cap";
         }
         leaf peer-restart-nlri-configured {
           type string;
         }
         leaf peer-restart-time-configured {
           type string;
         }
         leaf peer-stale-route-time-configured {
           type string;
         }
         leaf peer-no-restart {
           type empty;
           description "Present if this peer does not support graceful restart restarter mode";
         }
         leaf peer-restart-nlri-received {
           type string;
         }
         leaf peer-restart-time-received {
           type int32;
         }
         leaf peer-restart-flags-received {
           type string;
         }
         leaf peer-restart-nlri-can-save-state {
           type string;
         }
         leaf peer-restart-nlri-state-saved {
           type string;
         }
         leaf peer-restart-nlri-negotiated {
           type string;
         }
         leaf peer-end-of-rib-received {
           type string;
         }
         leaf peer-end-of-rib-sent {
           type string;
         }
         leaf peer-delay-end-of-rib {
           type string;
         }
         leaf peer-no-helper {
           type empty;
           description "Present if this peer does not support graceful restart receiver mode";
         }
         leaf peer-restart-nlri-held {
           type string;
         }
         leaf peer-restart-remaining-time {
           type string;
         }
         leaf peer-stale-remaining-time {
           type string;
         }
         leaf peer-llgr-nlri-configured {
           type string;
         }
         leaf peer-no-llgr-restarter {
           type empty;
           description "Present if this peer does not support long-lived graceful restart restarter mode";
         }
         leaf peer-llgr-nlri-restarter {
           type string;
         }
         leaf peer-llgr-nlri-state-saved {
           type string;
         }
         leaf peer-no-llgr-helper {
           type empty;
           description "Present if this peer does not support long-lived graceful restart receiver mode";
         }
         leaf peer-llgr-nlri-times {
           type string;
           description "NLRIs and times before long-lived stale routes are deleted";
         }
         leaf last-received {
           type int32;
         }
         leaf last-sent {
           type int32;
         }
         leaf last-checked {
           type int32;
         }
         leaf input-messages {
           type int32;
         }
         leaf input-updates {
           type int32;
         }
         leaf input-refreshes {
           type int32;
         }
         leaf input-octets {
           type int32;
         }
         leaf output-messages {
           type int32;
         }
         leaf output-updates {
           type int32;
         }
         leaf output-refreshes {
           type int32;
         }
         leaf output-octets {
           type int32;
         }
         leaf input-checksum {
           type int32;
         }
         leaf output-checksum {
           type int32;
         }
         leaf input-checksum-err {
           type int32;
         }
         leaf input-drop-path-attributes {
           type string;
         }
         leaf input-ignore-path-attributes {
           type string;
         }
         leaf buffered-octets-rx {
           type int32;
           description "Number of octets that have been received and are still buffered";
         }
         leaf buffered-octets-tx {
           type int32;
           description "Number of octets in the transmit buffer";
         }
         leaf gather-buffered-octets-tx {
           type int32;
           description "Number of octets in the gather transmit buffer";
         }
         container bgp-option-information {
           leaf export-policy {
             type string;
           }
           leaf import-policy {
             type string;
           }
           leaf advertise-bgp-static-policy {
             type string;
           }
           leaf bgp-options {
             type string;
           }
           leaf bgp-options2 {
             type string;
           }
           leaf bgp-options-extended {
             type string;
           }
           leaf remove-private-options {
             type string;
           }
           leaf authentication-key {
             type string;
           }
           leaf authentication-key-chain {
             type string;
             description "Name of authentication key chain";
           }
           leaf authentication-algorithm {
             type string;
             description "Name of authentication algorithm";
           }
           leaf authentication-configured {
             type empty;
           }
           leaf address-families {
             type string;
           }
           leaf drop-path-attributes {
             type string;
           }
           leaf ignore-path-attributes {
             type string;
           }
           leaf holdtime {
             type int32;
             description "Delay before timing out the adjacency (default is 180 seconds)";
           }
           leaf metric-out {
             type int32;
           }
           leaf preference {
             type int32;
             description "Preference for the route";
           }
           leaf local-preference {
             type int32;
           }
           leaf local-as-private {
             type empty;
           }
           leaf local-system-as {
             type int32;
           }
           leaf receive-buffer-size {
             type int32;
           }
           leaf send-buffer-size {
             type int32;
           }
           leaf outbound-timer {
             type int32;
           }
           leaf med-action {
             type string;
           }
           leaf ipsec-sa {
             type string;
           }
           leaf bgp-bmp-monitor-peers {
             type string;
           }
           leaf bgp-bmp-route-monitoring-none {
             type empty;
           }
           leaf bgp-bmp-route-monitoring-prepolicy {
             type empty;
           }
           leaf bgp-bmp-prepolicy-exclude-non-feasible {
             type empty;
           }
           leaf bgp-bmp-route-monitoring-postpolicy {
             type empty;
           }
           leaf bgp-bmp-postpolicy-exclude-non-eligible {
             type empty;
           }
           container prefix-limit {
           }
           container accepted-prefix-limit {
             description "Limit number of prefixes accepted by policy";
           }
           container addpath-send {
           }
           container addpath-receive {
           }
           container aigp-mode {
             leaf nlri-type {
               type string;
               description "Type of NLRI being limited";
             }
           }
           container family-damping-info {
             leaf nlri-type {
               type string;
               description "Type of NLRI being limited";
             }
           }
           container protection {
             leaf nlri-type {
               type string;
               description "Type of NLRI being limited";
             }
           }
           container nlri-information {
             leaf nlri-type {
               type string;
               description "Type of NLRI being limited";
             }
             leaf nlri-flow-novalidate {
               type string;
               description "Policy to accept flow routes without validation";
             }
             container nlri-flags {
               leaf bgp-nlri-flag-explicit-null-for-all-routes {
                 type empty;
               }
               leaf bgp-nlri-flag-explicit-null-for-connected-routes {
                 type empty;
               }
               leaf bgp-nlri-flag-aggregate-label {
                 type empty;
               }
               leaf bgp-nlri-flag-per-prefix-label {
                 type empty;
               }
               leaf bgp-nlri-flag-per-group-label {
                 type empty;
               }
               leaf bgp-nlri-flag-no-install-forwarding {
                 type empty;
               }
               leaf bgp-nlri-flag-delay-route-advt {
                 type empty;
               }
               leaf bgp-nlri-flag-traffic-stats {
                 type empty;
               }
               leaf bgp-nlri-flag-l2vpn-status-vector {
                 type empty;
               }
               leaf bgp-nlri-flag-no-l2vpn-status-vector {
                 type empty;
               }
               leaf bgp-nlri-flag-strip-nexthop {
                 type empty;
               }
               leaf bgp-nlri-flag-allow-po-add-nexthop {
                 type empty;
               }
             }
             container nlri-traffic-stats {
               leaf traffic-stats-interval {
                 type int32;
               }
               container tracing-information {
                 leaf flags {
                   type string;
                   description "Enabled trace flags";
                 }
                 leaf filename {
                   type string;
                   description "Name of the trace file";
                 }
                 leaf filesize {
                   type int32;
                   description "Maximum size of the trace file";
                 }
                 leaf filelimit {
                   type int32;
                   description "Maximum number of retained trace files";
                 }
               }
             }
             container output-queues {
               description "BGP output queues statistics";
               container output-queue {
                 description "BGP output queues statistics";
                 leaf time-series {
                   type string;
                 }
                 list class {
                   description "An instance of BGP output queue statistics";
                   leaf priority-type {
                     type string;
                     description "BGP output queue priority type";
                   }
                   leaf rank {
                     type int32;
                     description "BGP output queue rank for priority type";
                   }
                   leaf token-count {
                     type int32;
                     description "BGP output queue token count for priority";
                   }
                   leaf output-queue-route-count {
                     type int32;
                     description "BGP output queue route count for priority";
                   }
                 }
               }
             }
           }
         }
         container bgp-peer-iosession {
           leaf iosession-thread-name {
             type string;
           }
           leaf iosession-state {
             type string;
           }
         }
         container bgp-bfd {
           leaf bfd-configuration-state {
             type string;
             description "BFD configuration state";
           }
           leaf bfd-operational-state {
             type string;
             description "BFD operational state";
           }
         }
         container egress-protection {
           leaf nlri-type {
             type string;
             description "Type of NLRI being limited";
           }
           container nlri-egress-protection {
             leaf bgp-context-id {
               type ipaddr;
             }
             leaf bgp-import-policy {
               type string;
             }
           }
           list ep-backup-table {
             leaf ep-backup-rib-name {
               type string;
               description "Instance backup RIB";
             }
             leaf ep-backup-link {
               type string;
               description "Vt interface";
             }
             leaf ep-backup-rib-id {
               type int32;
               description "RIB Identifier";
             }
             leaf ep-backup-kern-id {
               type int32;
               description "FIB Identifier";
             }
           }
           list ep-instance-table {
             leaf ep-instance-name {
               type string;
             }
             leaf ep-instance-type {
               type string;
               description "Instance type";
             }
             leaf ep-instance-protection-type {
               type string;
               description "Instance request protected";
             }
           }
         }
         list bgp-output-queue {
           leaf number {
             type int32;
           }
           leaf count {
             type int32;
           }
           leaf table-name {
             type string;
             description "Unicast routing table";
           }
           leaf rib-adv-nlri {
             type string;
           }
         }
         list bgp-rib {
           list brief {
             leaf name {
               type string;
             }
             leaf total-prefix-count {
               type int32;
               description "Total number of prefixes in this RIB";
             }
             leaf active-prefix-count {
               type int32;
               description "Number of active prefixes";
             }
             leaf suppressed-prefix-count {
               type int32;
               description "Number of prefixes suppressed due to damping";
             }
             leaf history-prefix-count {
               type int32;
               description "Number of prefixes with damping history maintained";
             }
             leaf damped-prefix-count {
               type int32;
               description "Number of prefixes in any damped state";
             }
             leaf pending-prefix-count {
               type int32;
               description "Number of prefixes with pending changes";
             }
           }
           list terse {
             leaf name {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
           }
           list summary {
             leaf name {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
             leaf active-external-prefix-count {
               type int32;
               description "Number of active prefixes received from external peers";
             }
             leaf total-external-prefix-count {
               type int32;
               description "Total number of prefixes received from external peers";
             }
             leaf accepted-external-prefix-count {
               type int32;
               description "Number of accepted prefixes received from external peers";
             }
             leaf suppressed-external-prefix-count {
               type int32;
               description "Number of external prefixes suppressed due to damping";
             }
             leaf active-internal-prefix-count {
               type int32;
               description "Number of active prefixes received from internal peers";
             }
             leaf total-internal-prefix-count {
               type int32;
               description "Total number of prefixes received from internal peers";
             }
             leaf accepted-internal-prefix-count {
               type int32;
               description "Number of accepted prefixes received from internal peers";
             }
             leaf suppressed-internal-prefix-count {
               type int32;
               description "Number of internal prefixes suppressed due to damping";
             }
           }
           list detail {
             leaf name {
               type string;
             }
             leaf rib-bit {
               type string;
             }
             leaf bgp-rib-state {
               type string;
             }
             leaf vpn-rib-state {
               type string;
             }
             leaf send-state {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
             leaf stale-prefix-count {
               type int32;
               description "Number of prefixes marked as stale";
             }
             leaf llgr-stale-prefix-count {
               type int32;
               description "Number of prefixes marked as LLGR stale";
             }
             leaf active-external-prefix-count {
               type int32;
               description "Number of active prefixes received from external peers";
             }
             leaf total-external-prefix-count {
               type int32;
               description "Total number of prefixes received from external peers";
             }
             leaf suppressed-external-prefix-count {
               type int32;
               description "Number of external prefixes suppressed due to damping";
             }
             leaf active-internal-prefix-count {
               type int32;
               description "Number of active prefixes received from internal peers";
             }
             leaf total-internal-prefix-count {
               type int32;
               description "Total number of prefixes received from internal peers";
             }
             leaf suppressed-internal-prefix-count {
               type int32;
               description "Number of internal prefixes suppressed due to damping";
             }
             leaf advertised-prefix-count {
               type int32;
               description "Number of prefixes present in the RIB-OUT";
             }
           }
         }
         container bgp-family-stat {
           container detail {
             leaf nlri-type {
               type string;
               description "Type of NLRI being limited";
             }
             leaf bgp-nlri-send-time {
               type int32;
               description "Time for initial send by peer";
             }
             leaf bgp-nlri-recv-time {
               type int32;
               description "Time for initial receive by peer";
             }
           }
         }
         list entropy-label-info {
           leaf nlri-type {
             type string;
             description "Type of NLRI being limited";
           }
           leaf entropy-label {
             type string;
             description "Entropy label";
           }
           leaf entropy-label-import-policy {
             type string;
           }
           leaf entropy-label-no-next-hop-validation {
             type string;
             description "Entropy label no next hop validation";
           }
           leaf entropy-label-capability {
             type string;
             description "Local entropy label capability";
           }
           leaf entropy-label-stitching-capability {
             type string;
             description "Entropy label stitching capability";
           }
         }
         container bgp-error {
           leaf name {
             type string;
           }
           leaf send-count {
             type int32;
           }
           leaf receive-count {
             type int32;
           }
         }
         container bgp-malformed-attributes {
           container malformed-information {
             leaf log-interval {
               type int32;
             }
             leaf route-limit {
               type int32;
             }
           }
           container path-attribute {
             leaf name {
               type string;
             }
             leaf code {
               type int32;
             }
             leaf last-recv {
               type int32;
             }
             leaf total-recv {
               type int32;
             }
           }
         }
         container route-queue {
           leaf timer {
             type string;
           }
           leaf state {
             type string;
             description "HFRR profile Current state";
           }
           leaf element {
             type string;
           }
         }
         container tracing-information {
           leaf flags {
             type string;
             description "Enabled trace flags";
           }
           leaf filename {
             type string;
             description "Name of the trace file";
           }
           leaf filesize {
             type int32;
             description "Maximum size of the trace file";
           }
           leaf filelimit {
             type int32;
             description "Maximum number of retained trace files";
           }
         }
       }
       list output-queue {
         description "Operational and configuration information for a BGP peer";
         leaf peer-address {
           type ipaddr;
         }
         leaf peer-as {
           type int32;
           description "Peer AS number";
         }
         leaf local-address {
           type ipaddr;
         }
         leaf local-as {
           type int32;
           description "Local AS number";
         }
         leaf description {
           type string;
         }
         container bgp-option-information {
           container prefix-limit {
           }
           container accepted-prefix-limit {
             description "Limit number of prefixes accepted by policy";
           }
           container addpath-send {
           }
           container addpath-receive {
           }
           container nlri-information {
             leaf nlri-type {
               type string;
               description "Type of NLRI being limited";
             }
             leaf nlri-flow-novalidate {
               type string;
               description "Policy to accept flow routes without validation";
             }
             leaf nlri-output-queue-priority {
               type string;
               description "Default address family output queue priority";
             }
             leaf nlri-route-refresh-priority {
               type string;
               description "Default address family route-refresh priority";
             }
             leaf nlri-withdraw-priority {
               type string;
               description "Default address family withdraw priority";
             }
             container nlri-flags {
               leaf bgp-nlri-flag-explicit-null-for-all-routes {
                 type empty;
               }
               leaf bgp-nlri-flag-explicit-null-for-connected-routes {
                 type empty;
               }
               leaf bgp-nlri-flag-aggregate-label {
                 type empty;
               }
               leaf bgp-nlri-flag-per-prefix-label {
                 type empty;
               }
               leaf bgp-nlri-flag-per-group-label {
                 type empty;
               }
               leaf bgp-nlri-flag-no-install-forwarding {
                 type empty;
               }
               leaf bgp-nlri-flag-delay-route-advt {
                 type empty;
               }
               leaf bgp-nlri-flag-traffic-stats {
                 type empty;
               }
               leaf bgp-nlri-flag-l2vpn-status-vector {
                 type empty;
               }
               leaf bgp-nlri-flag-no-l2vpn-status-vector {
                 type empty;
               }
               leaf bgp-nlri-flag-strip-nexthop {
                 type empty;
               }
               leaf bgp-nlri-flag-allow-po-add-nexthop {
                 type empty;
               }
             }
             container nlri-traffic-stats {
               leaf traffic-stats-interval {
                 type int32;
               }
               container tracing-information {
                 leaf flags {
                   type string;
                   description "Enabled trace flags";
                 }
                 leaf filename {
                   type string;
                   description "Name of the trace file";
                 }
                 leaf filesize {
                   type int32;
                   description "Maximum size of the trace file";
                 }
                 leaf filelimit {
                   type int32;
                   description "Maximum number of retained trace files";
                 }
               }
             }
             container output-queues {
               description "BGP output queues statistics";
               container output-queue {
                 description "BGP output queues statistics";
                 leaf time-series {
                   type string;
                 }
                 list class {
                   description "An instance of BGP output queue statistics";
                   leaf priority-type {
                     type string;
                     description "BGP output queue priority type";
                   }
                   leaf rank {
                     type int32;
                     description "BGP output queue rank for priority type";
                   }
                   leaf token-count {
                     type int32;
                     description "BGP output queue token count for priority";
                   }
                   leaf output-queue-route-count {
                     type int32;
                     description "BGP output queue route count for priority";
                   }
                 }
               }
             }
           }
         }
         container egress-protection {
           container nlri-egress-protection {
             leaf nlri-type {
               type string;
               description "Type of NLRI being limited";
             }
             leaf bgp-context-id {
               type ipaddr;
             }
             leaf bgp-import-policy {
               type string;
             }
           }
           list ep-backup-table {
             leaf ep-backup-rib-name {
               type string;
               description "Instance backup RIB";
             }
             leaf ep-backup-link {
               type string;
               description "Vt interface";
             }
             leaf ep-backup-rib-id {
               type int32;
               description "RIB Identifier";
             }
             leaf ep-backup-kern-id {
               type int32;
               description "FIB Identifier";
             }
           }
           list ep-instance-table {
             leaf ep-instance-name {
               type string;
             }
             leaf ep-instance-type {
               type string;
               description "Instance type";
             }
             leaf ep-instance-protection-type {
               type string;
               description "Instance request protected";
             }
           }
         }
         list bgp-output-queue {
           leaf number {
             type int32;
           }
           leaf count {
             type int32;
           }
           leaf table-name {
             type string;
             description "Unicast routing table";
           }
           leaf rib-adv-nlri {
             type string;
           }
           leaf time-series {
             type string;
           }
           list class {
             description "An instance of BGP output queue statistics";
             leaf priority-type {
               type string;
               description "BGP output queue priority type";
             }
             leaf rank {
               type int32;
               description "BGP output queue rank for priority type";
             }
             leaf token-count {
               type int32;
               description "BGP output queue token count for priority";
             }
           }
         }
         list bgp-rib {
           list brief {
             leaf name {
               type string;
             }
             leaf total-prefix-count {
               type int32;
               description "Total number of prefixes in this RIB";
             }
             leaf active-prefix-count {
               type int32;
               description "Number of active prefixes";
             }
             leaf suppressed-prefix-count {
               type int32;
               description "Number of prefixes suppressed due to damping";
             }
             leaf history-prefix-count {
               type int32;
               description "Number of prefixes with damping history maintained";
             }
             leaf damped-prefix-count {
               type int32;
               description "Number of prefixes in any damped state";
             }
             leaf pending-prefix-count {
               type int32;
               description "Number of prefixes with pending changes";
             }
           }
           list terse {
             leaf name {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
           }
           list summary {
             leaf name {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
             leaf active-external-prefix-count {
               type int32;
               description "Number of active prefixes received from external peers";
             }
             leaf total-external-prefix-count {
               type int32;
               description "Total number of prefixes received from external peers";
             }
             leaf accepted-external-prefix-count {
               type int32;
               description "Number of accepted prefixes received from external peers";
             }
             leaf suppressed-external-prefix-count {
               type int32;
               description "Number of external prefixes suppressed due to damping";
             }
             leaf active-internal-prefix-count {
               type int32;
               description "Number of active prefixes received from internal peers";
             }
             leaf total-internal-prefix-count {
               type int32;
               description "Total number of prefixes received from internal peers";
             }
             leaf accepted-internal-prefix-count {
               type int32;
               description "Number of accepted prefixes received from internal peers";
             }
             leaf suppressed-internal-prefix-count {
               type int32;
               description "Number of internal prefixes suppressed due to damping";
             }
           }
           list detail {
             leaf name {
               type string;
             }
             leaf rib-bit {
               type string;
             }
             leaf bgp-rib-state {
               type string;
             }
             leaf vpn-rib-state {
               type string;
             }
             leaf send-state {
               type string;
             }
             leaf active-prefix-count {
               type int32;
               description "Number of active prefixes";
             }
             leaf received-prefix-count {
               type int32;
               description "For a peer RIB, number of prefixes received from this peer";
             }
             leaf accepted-prefix-count {
               type int32;
               description "For a peer RIB, number of prefixes from this peer accepted by policy";
             }
             leaf suppressed-prefix-count {
               type int32;
               description "Number of prefixes suppressed due to damping";
             }
             leaf stale-prefix-count {
               type int32;
               description "Number of prefixes marked as stale";
             }
             leaf llgr-stale-prefix-count {
               type int32;
               description "Number of prefixes marked as LLGR stale";
             }
             leaf active-external-prefix-count {
               type int32;
               description "Number of active prefixes received from external peers";
             }
             leaf total-external-prefix-count {
               type int32;
               description "Total number of prefixes received from external peers";
             }
             leaf suppressed-external-prefix-count {
               type int32;
               description "Number of external prefixes suppressed due to damping";
             }
             leaf active-internal-prefix-count {
               type int32;
               description "Number of active prefixes received from internal peers";
             }
             leaf total-internal-prefix-count {
               type int32;
               description "Total number of prefixes received from internal peers";
             }
             leaf suppressed-internal-prefix-count {
               type int32;
               description "Number of internal prefixes suppressed due to damping";
             }
             leaf advertised-prefix-count {
               type int32;
               description "Number of prefixes present in the RIB-OUT";
             }
           }
         }
         container bgp-family-stat {
           container detail {
             leaf nlri-type {
               type string;
               description "Type of NLRI being limited";
             }
             leaf bgp-nlri-send-time {
               type int32;
               description "Time for initial send by peer";
             }
             leaf bgp-nlri-recv-time {
               type int32;
               description "Time for initial receive by peer";
             }
           }
         }
         list entropy-label-info {
           leaf nlri-type {
             type string;
             description "Type of NLRI being limited";
           }
           leaf entropy-label {
             type string;
             description "Entropy label";
           }
           leaf entropy-label-import-policy {
             type string;
           }
           leaf entropy-label-no-next-hop-validation {
             type string;
             description "Entropy label no next hop validation";
           }
           leaf entropy-label-capability {
             type string;
             description "Local entropy label capability";
           }
           leaf entropy-label-stitching-capability {
             type string;
             description "Entropy label stitching capability";
           }
         }
         container bgp-malformed-attributes {
         }
       }
     }
   }
 }
 grouping bgp-rtf-information-block {
   list bgp-rtf-brief {
     leaf group-name {
       type string;
     }
     leaf table-name {
       type string;
       description "Unicast routing table";
     }
     leaf bgp-rtf-state-flags {
       type string;
     }
     leaf bgp-rtf-entries {
       type int32;
     }
   }
   list bgp-rtf-group {
     leaf group-name {
       type string;
     }
     leaf group-index {
       type int32;
     }
     leaf rtarget-recv-mask {
       type string;
     }
     leaf default-mask {
       type string;
     }
     list bgp-rtf-state {
       leaf table-name {
         type string;
         description "Unicast routing table";
       }
       leaf bgp-rtf-state-flags {
         type string;
       }
       leaf bgp-rtf-entries {
         type int32;
       }
       container bgp-rtf-entry {
         leaf rtarget {
           type string;
           description "Route target community";
         }
         leaf rtarget-mask {
           type string;
         }
       }
     }
   }
 }
 grouping bgp-traffic-statistics-information-block {
   container bgp-traffic-statistics-header {
     leaf group-name {
       type string;
     }
     leaf group-index {
       type int32;
     }
     leaf nlri-name {
       type string;
     }
   }
   container bgp-traffic-statistics {
     leaf bgp-prefix {
       type string;
     }
     leaf bgp-traffic-error {
       type string;
       description "Error encountered when querying the statistics";
     }
     leaf bgp-traffic-statistics-packet-count {
       type int32;
       description "Number of packets";
     }
     leaf bgp-traffic-statistics-byte-count {
       type int32;
       description "Number of bytes";
     }
     leaf bgp-traffic-statistics-egress-as {
       type string;
       description "Egress AS for traffic destined for this prefix";
     }
     leaf bgp-traffic-statistics-advertised-fec-label {
       type int32;
       description "Label advertised for routes in FEC";
     }
   }
   container bgp-traffic-statistics-error {
     leaf bgp-traffic-error {
       type string;
       description "Error encountered when querying the statistics";
     }
   }
 }
 grouping bgp-orf-information-block {
   container bgp-orf {
     leaf peer-address {
       type ipaddr;
     }
     leaf peer-type {
       type string;
     }
     leaf group-name {
       type string;
     }
     list bgp-orf-nlri-info {
       leaf nlri-name {
         type string;
       }
       leaf filter-out-updates {
         type int32;
       }
       leaf filter-qcount {
         type int32;
       }
       leaf filter-in-updates {
         type int32;
       }
       leaf immediate-count {
         type int32;
       }
       list bgp-orf-filter-information {
         leaf filter-type {
           type string;
         }
         leaf filter-mode {
           type string;
         }
         container bgp-orf-filter-info {
           list bgp-orf-extcomm-filter {
             leaf extended-community {
               type string;
               description "Extended community";
             }
           }
           list bgp-orf-prefix-filter {
             leaf prefix-orf {
               type string;
               description "Prefix-based outbound route filter";
             }
           }
         }
       }
     }
   }
 }
 }
