/*
 * Copyright (c) 2017 Juniper Networks, Inc.
 * All rights reserved.
 */
 module show-ospf3 {
  namespace "http://yang.juniper.net/yang/1.1/jrpc/show-ospf3/junos-es/17.2R1.13";
  prefix show-ospf3;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ospf3-overview-information {
     description "Show overview of OSPFv3 information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "extensive" {
             description "Display extensive output";
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       container ospf3-overview-information {
         uses ospf3-overview-information-block;
       }
     }
   }
   rpc get-ospf3-database-information {
     description "Show OSPFv3 link-state database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf level {
         default "brief";
         type enumeration {
           enum "brief" {
             description "Display brief output (default)";
           }
           enum "detail" {
             description "Display detailed output";
           }
           enum "extensive" {
             description "Display extensive output";
           }
           enum "summary" {
             description "Display summary output";
           }
         }
       }
       leaf lsa-type {
         type enumeration {
           enum "router" {
             description "Router LSAs";
           }
           enum "network" {
             description "Network LSAs";
           }
           enum "inter-area-prefix" {
             description "Inter-area-prefix LSAs";
           }
           enum "inter-area-router" {
             description "Inter-area-router LSAs";
           }
           enum "external" {
             description "External LSAs";
           }
           enum "nssa" {
             description "NSSA LSAs";
           }
           enum "link" {
             description "Link LSAs";
           }
           enum "link-local" {
             description "Link-local LSAs";
           }
           enum "intra-area-prefix" {
             description "Intra-area-prefix LSAs";
           }
         }
       }
       leaf area {
         description "Area ID of OSPFv3 area";
         default "all";
         type string;
       }
       leaf lsa-id {
         description "ID of link-state advertisement";
         default "all";
         type string;
       }
       leaf advertising-router {
         description "Router ID of advertising router";
         type string;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       container ospf3-database-information {
         uses ospf3-database-information-block;
       }
     }
   }
   rpc get-ospf3-interface-information {
     description "Show OSPFv3 interface status";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf interface-name {
         description "Name of logical interface";
         type string;
       }
       leaf area {
         description "OSPF area ID";
         type areaid;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       container ospf3-interface-information {
         uses ospf3-interface-information-block;
       }
     }
   }
   rpc get-ospf3-neighbor-information {
     description "Show OSPFv3 neighbor status";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf interface {
         description "Name of logical interface";
         type string;
       }
       leaf area {
         description "OSPF area ID";
         type areaid;
       }
       leaf neighbor {
         description "IP address or ID of neighbor";
         type string;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       container ospf3-neighbor-information {
         uses ospf3-neighbor-information-block;
       }
     }
   }
   rpc get-ospf3-route-information {
     description "Show the OSPFv3 routing table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPF instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "transit" {
             description "Display routes to pseudonodes";
           }
           enum "network" {
             description "Display routes to networks";
           }
         }
       }
       leaf no-backup-coverage {
         description "Display routes with no backup coverage";
         type empty;
       }
       leaf destination {
         description "Address and optional prefix length of destination";
         type ipprefix;
       }
       leaf verbosity_level {
         default "brief";
         type enumeration {
           enum "brief" {
             description "Display brief output (default)";
           }
           enum "detail" {
             description "Display detailed output";
           }
           enum "extensive" {
             description "Display extensive output";
           }
         }
       }
     }
     output {
       container ospf3-route-information {
         uses ospf3-route-information-block;
       }
     }
   }
   rpc get-ospf3-statistics-information {
     description "Show OSPFv3 statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       container ospf3-statistics-information {
         uses ospf3-statistics-information-block;
       }
     }
   }
   rpc get-ospf3-io-statistics-information {
     description "Show OSPFv3 I/O statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container ospf3-io-statistics-information {
         uses ospf3-io-statistics-information-block;
       }
     }
   }
   rpc get-ospf3-log-information {
     description "Show OSPFv3 SPF log";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       container ospf3-log-information {
         uses ospf3-log-information-block;
       }
     }
   }
   rpc get-ospf3-backup-spf-information {
     description "Show OSPFv3 backup SPF calculations information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPF instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf area {
         description "OSPF area ID";
         type areaid;
       }
       leaf no-coverage {
         description "Entries with no backup coverage";
         type empty;
       }
       leaf node-id {
         description "Display nodes matching the node-id";
         type string;
       }
       leaf verbosity_level {
         default "brief";
         type enumeration {
           enum "brief" {
             description "Display brief output (default)";
           }
           enum "detail" {
             description "Display detailed output";
           }
         }
       }
     }
     output {
       container ospf3-backup-spf-information {
         uses ospf3-backup-spf-information-block;
       }
     }
   }
   rpc get-ospf3-backup-lsp-information {
     description "Show OSPFv3 MPLS backup LSP information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
   }
   rpc get-ospf3-backup-coverage-information {
     description "Show OSPFv3 backup coverage";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPF instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       container ospf3-backup-coverage-information {
         uses ospf3-backup-coverage-information-block;
       }
     }
   }
   rpc get-ospf3-backup-neighbor-information {
     description "Show OSPFv3 backup neighbors";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPF instance";
         type string;
       }
       leaf area {
         description "OSPF area ID";
         type areaid;
       }
     }
     output {
       container ospf3-backup-neighbor-information {
         uses ospf3-backup-neighbor-information-block;
       }
     }
   }
   rpc get-ospf-bgporr-information {
     description "Show BGP optimal route-reflection groups";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf group {
         description "BGP optimal route-reflection peer group name";
         type string;
       }
       leaf topology {
         description "Name of topology";
         type string;
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "transit" {
             description "Display routes to pseudonodes";
           }
           enum "network" {
             description "Display routes to networks";
           }
         }
       }
       leaf destination {
         description "Address and optional prefix length of destination";
         type ipprefix;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf instance {
         description "Name of OSPF instance";
         type string;
       }
       leaf verbosity_level {
         default "brief";
         type enumeration {
           enum "brief" {
             description "Display brief output (default)";
           }
           enum "detail" {
             description "Display detailed output";
           }
           enum "extensive" {
             description "Display extensive output";
           }
         }
       }
     }
   }
 grouping ospf3-overview-information-block {
   container ospf-overview {
     description "Overview information for an OSPF instance";
     leaf instance-name {
       type string;
     }
     leaf ospf-router-id {
       type ipaddr;
       description "OSPF router ID";
     }
     leaf ospf-route-table-index {
       type uint32;
       description "Route table index";
     }
     leaf ospf-configured-overload {
       type empty;
       description "Instance is configured to be in overload";
     }
     leaf ospf-configured-overload-remaining-time {
       type string;
       description "Time remaining on configured overload timeout";
     }
     leaf ospf-abr {
       type empty;
       description "Router is an area border router";
     }
     leaf ospf-asbr {
       type empty;
       description "Router is an autonomous system boundary router";
     }
     leaf ospf-nssa-router {
       type empty;
       description "Router is a not-so-stubby area router";
     }
     leaf no-rfc-1583 {
       type empty;
       description "RFC1583 compatibility is disabled";
     }
     leaf forwarding-address-to-broadcast {
       type empty;
       description "Set forwarding address in Type 5 LSA in broadcast network";
     }
     leaf ospf-lsa-refresh-time {
       type uint32;
       description "Refresh period for link-state advertisement (in minutes)";
     }
     leaf ospf-traffic-engineering {
       type empty;
       description "Traffic engineering is enabled";
     }
     leaf ospf-dna-uncapable {
       type empty;
       description "Not safe to generate DoNotAge LSAs";
     }
     leaf ospf-as-dc-bit-clear-count {
       type uint32;
       description "Number of AS scope link-state advertisements received with DC bit clear";
     }
     leaf ospf-area-dc-bit-clear-count {
       type uint32;
       description "Number of area scope link-state advertisements received with DC bit clear";
     }
     leaf ospf-area-indications-count {
       type uint32;
       description "Number of indication link-state advertisements received";
     }
     leaf ospf-link-dc-bit-clear-count {
       type uint32;
       description "Number of link local scope link-state advertisements received with no DC bit clear";
     }
     container ospf-restart {
       description "OSPF restart parameters";
       leaf ospf-restart-enabled {
         type string;
         description "OSPF restart mode";
       }
       leaf ospf-restart-duration {
         type uint32;
         description "Duration of OSPF restart (seconds)";
       }
       leaf ospf-restart-grace-period {
         type uint32;
         description "Grace period for OSPF restart (seconds)";
       }
       leaf ospf-standard-graceful-restart-helper-mode {
         type string;
         description "OSPF graceful restart (RFC3623) helper mode";
       }
       leaf ospf-restart-signaling-helper-mode {
         type string;
         description "OSPF restart-signaling helper mode";
       }
     }
     container tracing-information {
       leaf flags {
         type string;
         description "Enabled trace flags";
       }
       leaf filename {
         type string;
         description "Name of the trace file";
       }
       leaf filesize {
         type int32;
         description "Maximum size of the trace file";
       }
       leaf filelimit {
         type int32;
         description "Maximum number of retained trace files";
       }
     }
     container ospf-db-protection-overview {
       description "OSPF database protection overview information";
       leaf ospf-db-protection-state {
         type string;
         description "Database protection state";
       }
       leaf ospf-db-protection-remaining-time {
         type uint32;
         description "Time remaining in the current state";
       }
       leaf ospf-db-protection-warning-threshold {
         type uint32;
         description "Warning threshold as percentage";
       }
       leaf ospf-db-protection-warning-only {
         type empty;
         description "Configured to generate warning only";
       }
       leaf ospf-db-protection-lsa-current {
         type uint32;
         description "Current number of non self-generated LSAs";
       }
       leaf ospf-db-protection-lsa-warning {
         type uint32;
         description "Warning number of non self-generated LSAs";
       }
       leaf ospf-db-protection-lsa-maximum {
         type uint32;
         description "Allowed number of non self-generated LSAs";
       }
       leaf ospf-db-protection-ignore-time {
         type uint32;
         description "Configured value of ignore time";
       }
       leaf ospf-db-protection-reset-time {
         type uint32;
         description "Configured value of reset time";
       }
       leaf ospf-db-protection-ignore-current {
         type uint32;
         description "Current number of transitions to Ignore state";
       }
       leaf ospf-db-protection-ignore-maximum {
         type uint32;
         description "Allowed number of transitions to Ignore state";
       }
     }
     list ospf-area-overview {
       description "Overview information for an OSPF area";
       leaf ospf-area {
         type string;
         description "Area ID";
       }
       leaf ospf-stub-type {
         type string;
         description "Stub type of area";
       }
       leaf ospf-stub-cost {
         type uint32;
         description "Cost of default route in stub area";
       }
       leaf ospf-virtual-transit {
         type empty;
         description "Area is transit for virtual links";
       }
       leaf authentication-type {
         type string;
         description "Type of authentication";
       }
       leaf ospf-abr-count {
         type uint32;
         description "Number of area border routers";
       }
       leaf ospf-asbr-count {
         type uint32;
         description "Number of autonomous system boundary routers";
       }
       leaf ospf-dna-uncapable {
         type empty;
         description "Not safe to generate DoNotAge LSAs";
       }
       leaf ospf-area-dc-bit-clear-count {
         type uint32;
         description "Number of area scope link-state advertisements received with DC bit clear";
       }
       leaf ospf-area-indications-count {
         type uint32;
         description "Number of indication link-state advertisements received";
       }
       leaf ospf-area-self-indicating {
         type empty;
         description "Router generated an indication link-state advertisement";
       }
       leaf ospf-link-dc-bit-clear-count {
         type uint32;
         description "Number of link local scope link-state advertisements received with no DC bit clear";
       }
       container ospf-nbr-overview {
         leaf ospf-nbr-up-count {
           type uint32;
           description "Number of neighbors in full state";
         }
       }
     }
     list ospf-topology-overview {
       description "OSPF topology specific overview information";
       leaf ospf-topology-name {
         type string;
         description "OSPF topology name";
       }
       leaf ospf-topology-id {
         type int32;
         description "OSPF topology id";
       }
       leaf ospf-topology-configured-overload {
         type empty;
         description "Topology is configured to be in overload";
       }
       leaf ospf-topology-dynamic-overload {
         type empty;
         description "Topology is in dynamic overload i.e. prefix limit was exceeded";
       }
       leaf ospf-prefix-export-count {
         type uint32;
         description "Number of prefixes exported into the topology";
       }
       leaf ospf-prefix-export-limit {
         type uint32;
         description "Number of prefixes we are allowed to exported into the topology";
       }
       leaf ospf-full-spf-count {
         type uint32;
         description "Number of full SPF calculations";
       }
       leaf ospf-spf-delay {
         type string;
         description "Delay before performing consecutive SPF calculations";
       }
       leaf ospf-spf-holddown {
         type string;
         description "Time to hold down before running an SPF";
       }
       leaf ospf-spf-rapid-runs {
         type string;
         description "Number of rapid SPF runs before SPF holddown";
       }
       leaf ospf-backup-spf-status {
         type string;
         description "Backup SPF status";
       }
       leaf ospf-backup-spf-remote-backup-calculation {
         type empty;
         description "Remote-LFA backup calculations enabled";
       }
       leaf ospf-backup-spf-downstream-only {
         type empty;
         description "Topology is configured to use only downstream backup paths";
       }
       leaf ospf-backup-spf-node-link-degradation {
         type empty;
         description "Topology is configured to use node link degradation";
       }
       leaf ospf-te-shortcuts {
         type empty;
         description "Traffic engineering shortcuts are enabled";
       }
       leaf ospf-topo-sessid-count {
         type uint32;
         description "Number of Session IDs associated with routes in this toplogy";
       }
     }
     container ospf-spring-overview {
       description "OSPF spring parameters";
       leaf ospf-spring-enabled {
         type string;
         description "OSPF SPRING";
       }
       leaf ospf-node-segment-enabled {
         type string;
         description "OSPF node segments";
       }
       container ospf-node-segment {
         description "Node segments related information";
         leaf ospf-node-segment-ipv4-index {
           type int32;
           description "Ipv4 node segment index for this device";
         }
         leaf ospf-node-segment-index-range {
           type int32;
           description "Range of node segment indices configured";
         }
         leaf ospf-node-segment-block-header {
           type empty;
           description "Node segment blocks";
         }
         container ospf-node-segment-block {
           description "Node segment blocks related information";
           leaf ospf-node-segment-block-start-index {
             type int32;
             description "Starting index for the specific node segment block";
           }
           leaf ospf-node-segment-block-size {
             type int32;
             description "Size of the specific node segment block";
           }
           leaf ospf-node-segment-block-first-label {
             type int32;
             description "First label allocated for the specific node segment block";
           }
           leaf ospf-node-segment-block-last-label {
             type int32;
             description "Last label allocated for the specific node segment block";
           }
         }
       }
     }
   }
 }
 grouping ospf3-database-information-block {
   container ospf3-area-header {
     leaf ospf-area {
       type string;
       description "Area ID";
     }
   }
   container ospf3-intf-header {
     leaf ospf-intf {
       type string;
       description "Name of interface";
     }
     leaf ospf-area {
       type string;
       description "Area ID";
     }
   }
   list ospf3-database {
     leaf ospf3-database.external-heading {
       type string;
     }
     leaf ospf3-database.heading {
       type string;
     }
     leaf lsa-type {
       type string;
     }
     leaf our-entry {
       type empty;
     }
     leaf lsa-id {
       type string;
     }
     leaf advertising-router {
       type ipaddr;
     }
     leaf sequence-number {
       type int32;
       description "History event number";
     }
     leaf age {
       type string;
     }
     leaf ospf-do-not-age {
       type empty;
       description "DoNotAge bit is set on the link-state advertisement received";
     }
     leaf checksum {
       type int32;
     }
     leaf lsa-length {
       type int32;
     }
     container ospf3-router-lsa {
       leaf bits {
         type int32;
       }
       leaf ospf3-options {
         type int32;
       }
       list ospf3-link {
         leaf link-type-name {
           type string;
           description "OSPF LSA link type";
         }
         leaf link-type-value {
           type int32;
         }
         leaf link-metric {
           type int32;
         }
         leaf link-intf-id {
           type int32;
         }
         leaf nbr-intf-id {
           type int32;
         }
         leaf nbr-rtr-id {
           type string;
         }
       }
       list ospf3-lsa-topology {
         description "OSPFv3 topology information for a LSA";
         list ospf3-lsa-topology-link {
           description "OSPFv3 topology information for a set of links to a LSA";
           leaf link-type-name {
             type string;
             description "OSPF LSA link type";
           }
           leaf ospf-lsa-topology-link-node-id {
             type string;
             description "LSA ID of the node representing the remote LSA";
           }
           leaf ospf-lsa-topology-link-metric {
             type int32;
             description "Minimum metric of the set of links";
           }
           leaf ospf-lsa-topology-link-state {
             type string;
             description "State of the set of links";
           }
         }
       }
     }
     container ospf3-network-lsa {
       leaf ospf3-options {
         type int32;
       }
       leaf attached-router {
         type ipaddr;
       }
       list ospf3-lsa-topology {
         description "OSPFv3 topology information for a LSA";
         list ospf3-lsa-topology-link {
           description "OSPFv3 topology information for a set of links to a LSA";
           leaf link-type-name {
             type string;
             description "OSPF LSA link type";
           }
           leaf ospf-lsa-topology-link-node-id {
             type string;
             description "LSA ID of the node representing the remote LSA";
           }
           leaf ospf-lsa-topology-link-metric {
             type int32;
             description "Minimum metric of the set of links";
           }
           leaf ospf-lsa-topology-link-state {
             type string;
             description "State of the set of links";
           }
         }
       }
     }
     container ospf3-inter-area-prefix-lsa {
       leaf ospf3-prefix {
         type string;
       }
       leaf ospf3-prefix-options {
         type int32;
       }
       leaf metric {
         type int32;
       }
     }
     container ospf3-inter-area-router-lsa {
       leaf destination-router-id {
         type string;
       }
       leaf ospf3-options {
         type int32;
       }
       leaf metric {
         type int32;
       }
     }
     container ospf3-external-lsa {
       leaf ospf3-prefix {
         type string;
       }
       leaf ospf3-prefix-options {
         type int32;
       }
       leaf metric {
         type int32;
       }
       leaf type-value {
         type int32;
       }
       leaf forward-address {
         type ipaddr;
       }
       leaf tag {
         type ipaddr;
       }
     }
     container ospf3-link-lsa {
       leaf linklocal-address {
         type string;
       }
       leaf ospf3-options {
         type int32;
       }
       leaf router-priority {
         type int32;
         description "Router priority used in DR election on broadcast or NBMA interface";
       }
       leaf prefix-count {
         type int32;
         description "Number of prefixes accepted before action is taken";
       }
       leaf ospf3-prefix {
         type string;
       }
       leaf ospf3-prefix-options {
         type int32;
       }
     }
     container ospf3-intra-area-prefix-lsa {
       leaf reference-lsa-type {
         type string;
       }
       leaf reference-lsa-id {
         type string;
       }
       leaf reference-lsa-router-id {
         type string;
       }
       leaf prefix-count {
         type int32;
         description "Number of prefixes accepted before action is taken";
       }
       leaf ospf3-prefix {
         type string;
       }
       leaf ospf3-prefix-options {
         type int32;
       }
       leaf ospf3-prefix-metric {
         type int32;
       }
     }
     container ospf-database-extensive {
       leaf generation-timer {
         type string;
       }
       leaf aging-timer {
         type string;
       }
       leaf installation-time {
         type string;
       }
       leaf expiration-time {
         type string;
       }
       leaf send-time {
         type string;
       }
       leaf lsa-changed-time {
         type string;
         description "Time elapsed since the link-state advertisement changed";
       }
       leaf lsa-change-count {
         type int32;
         description "Number of times link-state advertisement changed";
       }
       leaf indication-lsa {
         type empty;
         description "Indication link-state advertisement";
       }
       leaf database-entry-state {
         type string;
       }
       leaf database-telink-id {
         type int32;
       }
       leaf standby-flood-status {
         type string;
         description "Flooding status to standby Routing Engine";
       }
     }
     list ospf-opaque-link-local-lsa {
       container ospf-link-local-grace-lsa {
         leaf tlv-grace-type-name {
           type string;
         }
         leaf tlv-grace-value {
           type string;
         }
       }
       container ospf-link-local-te-lsa {
         container ospf-link-local-te-tlv {
           leaf link-local-te-tlv-type-name {
             type string;
           }
           leaf tlv-type-value {
             type int32;
           }
           leaf tlv-length {
             type int32;
           }
           leaf bytes-left {
             type int32;
           }
           leaf formatted-tlv-data {
             type string;
           }
         }
         container ospf-link-local-te-subtlv {
           leaf link-local-te-tlv-type-name {
             type string;
           }
           leaf tlv-type-value {
             type int32;
           }
           leaf tlv-length {
             type int32;
           }
           leaf bytes-left {
             type int32;
           }
           leaf formatted-tlv-data {
             type string;
           }
         }
       }
     }
   }
   container ospf3-database-summary {
     leaf ospf-area {
       type string;
       description "Area ID";
     }
     leaf ospf-intf {
       type string;
       description "Name of interface";
     }
     leaf ospf3-database-summary.external-heading {
       type string;
     }
     leaf ospf-lsa-count {
       type int32;
     }
     leaf ospf-lsa-type {
       type string;
     }
   }
 }
 grouping ospf3-interface-information-block {
   list ospf3-interface {
     leaf interface-name {
       type string;
       description "Name of interface";
     }
     leaf ospf-interface-state {
       type string;
     }
     leaf ospf-area {
       type string;
       description "Area ID";
     }
     leaf dr-id {
       type ipaddr;
     }
     leaf bdr-id {
       type ipaddr;
     }
     leaf neighbor-count {
       type int32;
       description "Number of neighbors on PIM interface";
     }
     leaf interface-address {
       type ipaddr;
     }
     leaf prefix-length {
       type int32;
     }
     leaf virtual-link-transit-area {
       type ipaddr;
       description "Virtual link transit area";
     }
     leaf virtual-link-destination {
       type string;
       description "Virtual link destination address";
     }
     leaf ospf3-interface-index {
       type int32;
     }
     leaf interface-type {
       type string;
     }
     leaf mtu {
       type int32;
       description "MTU along an interface";
     }
     leaf interface-cost {
       type int32;
       description "Cost associated with this interface";
     }
     leaf router-priority {
       type int32;
       description "Router priority used in DR election on broadcast or NBMA interface";
     }
     leaf adj-count {
       type int32;
       description "Count of fully adjacent neighbors";
     }
     leaf ospf3-router-lsa-id {
       type int32;
     }
     leaf interface-secondary {
       type empty;
       description "OSPF interface is secondary";
     }
     leaf interface-flood-reduction {
       type empty;
       description "Flood reduction is enabled";
     }
     leaf passive {
       type string;
     }
     leaf dr-address {
       type ipaddr;
       description "IP address of DR";
     }
     leaf bdr-address {
       type ipaddr;
       description "IP address of BDR";
     }
     leaf hello-interval {
       type int32;
       description "Interval between two successive hellos";
     }
     leaf poll-interval {
       type int32;
     }
     leaf dead-interval {
       type int32;
     }
     leaf retransmit-interval {
       type int32;
     }
     leaf ospf-stub-type {
       type string;
       description "Stub type of area";
     }
     leaf ipsec-sa {
       type string;
     }
     leaf ospf-interface-protection-type {
       type string;
     }
     leaf ospf-interface-no-eligible-backup {
       type empty;
     }
     leaf igp-ldp-sync-state {
       type string;
       description "State of synchronization between Label Distribution Protocol (LDP) and the interior gateway protocol (IGP)";
     }
     leaf igp-ldp-sync-last-change {
       type string;
       description "Time since the state of synchronization between Label Distribution Protocol (LDP) and the interior gateway protocol (IGP) last changed";
     }
     leaf igp-ldp-sync-reason {
       type string;
       description "Reason for the change in the state of synchronization between Label Distribution Protocol (LDP) and the interior gateway protocol (IGP)";
     }
     leaf igp-ldp-sync-holdtime {
       type string;
       description "Length of time during which the maximum metric is advertised for an interface that is in the hold-down state because synchronization was lost between Label Distribution Protocol (LDP) and the interior gateway protocol (IGP)";
     }
     leaf igp-ldp-sync-timeleft {
       type int32;
       description "Remaining amount of time the interface will remain in the hold-down state because synchronization was lost between Label Distribution Protocol (LDP) and the interior gateway protocol (IGP)";
     }
     leaf lsa-list {
       type string;
     }
     leaf interface-flood-list-count {
       type int32;
     }
     leaf flood-list-count {
       type int32;
     }
     leaf interface-description-list {
       type string;
     }
   }
 }
 grouping ospf3-neighbor-information-block {
   container ospf3-neighbor {
     leaf neighbor-id {
       type ipaddr;
     }
     leaf interface-name {
       type string;
       description "Name of interface";
     }
     leaf ospf-neighbor-state {
       type string;
     }
     leaf neighbor-priority {
       type int32;
     }
     leaf activity-timer {
       type int32;
     }
     leaf neighbor-address {
       type ipaddr;
       description "IP address of this neighbor";
     }
     leaf ospf-area {
       type string;
       description "Area ID";
     }
     leaf options {
       type int32;
     }
     leaf neighbor-secondary {
       type empty;
       description "OSPF neighbor is on secondary interface";
     }
     leaf ospf3-interface-index {
       type int32;
     }
     leaf neighbor-cost {
       type int32;
       description "Cost associated with this neighbor";
     }
     leaf dr-id {
       type ipaddr;
     }
     leaf bdr-id {
       type ipaddr;
     }
     leaf neighbor-up-time {
       type string;
       description "Time when neighbor came up";
     }
     leaf neighbor-adjacency-time {
       type string;
       description "Time when neighbor became adjacent";
     }
     leaf neighbor-suppress-hello {
       type int32;
       description "Time when neighbor suppressed hellos";
     }
     leaf master-slave {
       type string;
     }
     leaf sequence-number {
       type int32;
       description "History event number";
     }
     leaf dbd-retransmit-time {
       type int32;
       description "Seconds until DBD is retransmitted";
     }
     leaf lsreq-retransmit-time {
       type int32;
       description "Seconds until LSREQ is retransmitted";
     }
     leaf lsreq-enqueued {
       type empty;
     }
     leaf lsreq-active {
       type empty;
     }
     leaf lsa-list {
       type string;
     }
   }
 }
 grouping ospf3-route-information-block {
   list ospf3-route {
     list ospf3-route-entry {
       leaf address-prefix {
         type ipaddr;
       }
       leaf route-path-type {
         type string;
       }
       leaf route-type {
         type string;
       }
       leaf next-hop-type {
         type string;
       }
       leaf interface-cost {
         type int32;
         description "Cost associated with this interface";
       }
       leaf ospf-area {
         type string;
         description "Area ID";
       }
       leaf route-origin {
         type ipaddr;
       }
       leaf type7 {
         type empty;
       }
       leaf pbit {
         type empty;
       }
       leaf forward-nz {
         type empty;
       }
       leaf optional-capability {
         type int32;
         description "VEB bits received in the router LSA";
       }
       leaf route-priority {
         type string;
       }
       leaf ospf-valid-backups {
         type empty;
       }
       leaf ospf-bgp-orr-gen-id {
         type uint32;
       }
       list ospf-next-hop {
         container next-hop-name {
         }
         container next-hop-address {
         }
       }
       container ospf-backup-next-hop {
       }
       list ospf-rt-sessid {
         description "Session ID associated with the route";
       }
       container ospf-valid-backup-next-hop {
       }
     }
   }
 }
 grouping ospf3-statistics-information-block {
   container ospf-statistics {
     leaf dbds-retransmit {
       type uint64;
     }
     leaf dbds-retransmit-5seconds {
       type int32;
     }
     leaf lsas-flooded {
       type uint64;
     }
     leaf lsas-flooded-5seconds {
       type int32;
     }
     leaf lsas-high-prio-flooded {
       type uint64;
     }
     leaf lsas-high-prio-flooded-5seconds {
       type int32;
     }
     leaf lsas-retransmit {
       type uint64;
     }
     leaf lsas-retransmit-5seconds {
       type int32;
     }
     leaf lsas-nbr-transmit {
       type uint64;
     }
     leaf lsas-nbr-transmit-5seconds {
       type int32;
     }
     leaf lsas-requested {
       type uint64;
     }
     leaf lsas-requested-5seconds {
       type int32;
     }
     leaf lsas-acknowledged {
       type uint64;
     }
     leaf lsas-acknowledged-5seconds {
       type int32;
     }
     leaf max-age-lsas-received {
       type uint64;
     }
     leaf max-age-lsas-received-5seconds {
       type int32;
     }
     leaf flood-queue-depth {
       type int32;
     }
     leaf total-retransmits {
       type int32;
     }
     leaf total-database-summaries {
       type int32;
     }
     leaf total-linkstate-request {
       type int32;
     }
     list packet-statistics {
       leaf ospf-packet-type {
         type string;
       }
       leaf packets-sent {
         type uint64;
       }
       leaf packets-received {
         type uint64;
       }
       leaf packets-sent-5seconds {
         type int32;
       }
       leaf packets-received-5seconds {
         type int32;
       }
     }
     container ospf-errors {
       leaf runt-header-error {
         type int32;
       }
       leaf short-packets-error {
         type int32;
       }
       leaf bad-version-error {
         type int32;
       }
       leaf truncated-packets-error {
         type int32;
       }
       leaf checksum-error {
         type int32;
       }
       leaf subnet-mismatch-error {
         type int32;
       }
       leaf virtual-link-error {
         type int32;
       }
       leaf area-mismatch-error {
         type int32;
       }
       leaf authentication-mismatch-error {
         type int32;
       }
       leaf authentication-failure-error {
         type int32;
       }
       leaf bad-packettype-error {
         type int32;
       }
       leaf netmask-mismatch-error {
         type int32;
       }
       leaf hello-interval-mismatch-error {
         type int32;
       }
       leaf dead-interval-mismatch-error {
         type int32;
       }
       leaf stub-area-mismatch-error {
         type int32;
       }
       leaf nssa-mismatch-error {
         type int32;
       }
       leaf default-exclusion-mismatch-error {
         type int32;
       }
       leaf mtu-mismatch-error {
         type int32;
       }
       leaf hello-received-error {
         type int32;
       }
       leaf no-router-id-error {
         type int32;
       }
       leaf instance-id-mismatch-error {
         type int32;
       }
       leaf lanp2p-cfgmismatch-error {
         type int32;
       }
       leaf no-error {
         type empty;
       }
     }
   }
 }
 grouping ospf3-io-statistics-information-block {
   container ospf-io-statistics {
     leaf packets-read {
       type int32;
     }
     leaf average-per-run {
       type int32;
     }
     leaf max-run {
       type int32;
     }
     container ospf-errors {
       leaf no-interface-error {
         type int32;
       }
       leaf no-error {
         type empty;
       }
     }
   }
 }
 grouping ospf3-log-information-block {
   container ospf-log-instance {
     list log-element {
       leaf timestamp {
         type string;
         description "Time when something occurs";
       }
       leaf ospf-log-type {
         type string;
       }
       leaf elapsed-time {
         type string;
         description "Time this adjacency or session has been up or down";
       }
     }
   }
   container ospf-log-maximum-length {
     list log-element {
       leaf timestamp {
         type string;
         description "Time when something occurs";
       }
       leaf ospf-log-type {
         type string;
       }
       leaf elapsed-time {
         type string;
         description "Time this adjacency or session has been up or down";
       }
     }
   }
   container ospf-log-events {
     leaf number-events {
       type int32;
     }
     list log-element {
       leaf timestamp {
         type string;
         description "Time when something occurs";
       }
       leaf ospf-log-type {
         type string;
       }
       leaf elapsed-time {
         type string;
         description "Time this adjacency or session has been up or down";
       }
     }
   }
 }
 grouping ospf3-backup-spf-information-block {
   list ospf3-topology-backup-spf {
     description "OSPFv3 topology specific backup SPF results";
     list ospf3-topology-area-backup-spf {
       description "OSPFv3 topology area specific backup SPF results";
       leaf ospf-area {
         type string;
         description "Area ID";
       }
       list ospf3-backup-spf-node {
         description "OSPFv3 node specific backup SPF information";
         leaf lsa-id {
           type string;
         }
         leaf ospf-node-metric {
           type int32;
           description "Self to destination metric";
         }
         container ospf-node-id {
           description "OSPF node ID";
           leaf advertising-router {
             type ipaddr;
           }
         }
         list ospf-parent-node-id {
           description "OSPF parent node ID";
           leaf ospf-parent-advertising-router {
             type ipaddr;
             description "Advertising router for the parent node";
           }
           leaf ospf-parent-lsa-id {
             type string;
             description "LSA ID for the parent node";
           }
         }
         list ospf-next-hop {
           container next-hop-name {
           }
           container next-hop-address {
           }
         }
         container ospf-backup-next-hop {
           leaf ospf-backup-next-hop-interface {
             type string;
           }
           leaf ospf-backup-next-hop-address {
             type string;
           }
           leaf ospf-backup-next-hop-lsp {
             type string;
           }
           leaf ospf-backup-next-hop-lsp-out-if {
             type string;
           }
         }
         list ospf3-backup-spf-result {
           description "OSPFv3 backup SPF result";
           leaf ospf-backup-neighbor {
             type ipaddr;
             description "Backup neighbor router-id";
           }
           leaf ospf-backup-neighbor-via {
             type string;
             description "Backup neighbor via direct/RSVP/LDP";
           }
           leaf ospf-backup-neighbor-is-lsp-endpoint {
             type empty;
             description "Backup neighbor is an LSP endpoint";
           }
           leaf ospf-backup-metric {
             type int32;
             description "Backup neighbor to destination metric";
           }
           leaf ospf-backup-neighbor-from-metric {
             type int32;
             description "Backup neighbor to self metric";
           }
           leaf ospf-backup-neighbor-to-metric {
             type int32;
             description "Self to backup neighbor metric";
           }
           leaf ospf-backup-preference {
             type int32;
             description "Backup neighbor preference";
           }
           leaf ospf-track-item {
             type string;
             description "Backup SPF result track item";
           }
           leaf ospf-rev-track-item {
             type string;
             description "Backup RSPF result track item";
           }
           leaf ospf-backup-result-status {
             type string;
             description "Backup SPF result status";
           }
           leaf ospf-backup-result-no-coverage-reason {
             type string;
             description "Backup SPF result no coverage reason";
           }
           leaf ospf-backup-spf-result-path {
             type empty;
             description "Path to the neighbour from backup root";
           }
           leaf ospf-backup-result-path-nodes {
             type string;
             description "Backup node in the path";
           }
         }
       }
     }
   }
 }
 grouping ospf3-backup-coverage-information-block {
   container ospf3-topology-backup-coverage {
     container ospf3-backup-node-coverage {
       leaf ospf-area {
         type string;
         description "Area ID";
       }
       leaf ospf-covered-nodes {
         type int32;
         description "Number of nodes covered by backup nexthops";
       }
       leaf ospf-total-nodes {
         type int32;
         description "Total number of nodes in the area";
       }
       leaf ospf-node-coverage {
         type string;
         description "Percent of nodes covered by backup nexthops";
       }
     }
     container ospf3-backup-route-coverage {
       leaf ospf-path-type {
         type string;
         description "Route path type";
       }
       leaf ospf-covered-routes {
         type int32;
         description "Number of routes covered by backup nexthops";
       }
       leaf ospf-total-routes {
         type int32;
         description "Total number of routes in the area";
       }
       leaf ospf-route-coverage {
         type string;
         description "Percent of routes covered by backup nexthops";
       }
     }
   }
 }
 grouping ospf3-backup-neighbor-information-block {
   list ospf3-topology-backup-neighbor {
     description "OSPFv3 topology specific backup neighbors";
     list ospf3-topology-area-backup-neighbor {
       description "OSPFv3 topology area specific backup neighbors";
       leaf ospf-area {
         type string;
         description "Area ID";
       }
       list ospf3-backup-neighbor-node {
         description "OSPFv3 backup neighbor node";
         leaf ospf-backup-neighbor {
           type ipaddr;
           description "Backup neighbor router-id";
         }
         leaf ospf-backup-neighbor-is-lsp-endpoint {
           type empty;
           description "Backup neighbor is an LSP endpoint";
         }
         leaf ospf-backup-neighbor-from-metric {
           type int32;
           description "Backup neighbor to self metric";
         }
         leaf ospf-backup-neighbor-to-metric {
           type int32;
           description "Self to backup neighbor metric";
         }
         container ospf-backup-next-hop {
           leaf ospf-backup-next-hop-interface {
             type string;
           }
           leaf ospf-backup-next-hop-address {
             type string;
           }
           leaf ospf-backup-next-hop-lsp {
             type string;
           }
           leaf ospf-backup-next-hop-lsp-out-if {
             type string;
           }
         }
       }
     }
   }
 }
 }
