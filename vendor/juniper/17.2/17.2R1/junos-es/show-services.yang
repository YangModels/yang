/*
 * Copyright (c) 2017 Juniper Networks, Inc.
 * All rights reserved.
 */
 module show-services {
  namespace "http://yang.juniper.net/yang/1.1/jrpc/show-services/junos-es/17.2R1.13";
  prefix show-services;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-probe-results {
     description "Show probe results";
     input {
       leaf owner {
         description "Name of owner";
         type string {
           length "1 .. 32";
         }
       }
       leaf test {
         description "Name of test";
         type string {
           length "1 .. 32";
         }
       }
     }
     output {
       container probe-results {
         uses probe-results-block;
       }
     }
   }
   rpc get-history-results {
     description "Show history results";
     input {
       leaf verbosity_level {
         default "brief";
         type enumeration {
           enum "brief" {
             description "Display brief output (default)";
           }
           enum "detail" {
             description "Display detailed output";
           }
         }
       }
       leaf owner {
         description "Name of owner";
         type string {
           length "1 .. 32";
         }
       }
       leaf test {
         description "Name of test";
         type string {
           length "1 .. 32";
         }
       }
       leaf since {
         description "Show history since YYYY-MM-DD.HH:MM:SS";
         type time;
       }
     }
     output {
       container history-results {
         uses history-results-block;
       }
     }
   }
   rpc get-active-servers {
     description "Show configured servers";
     output {
       container active-servers {
         uses active-servers-block;
       }
     }
   }
   rpc get-uac-policies {
     description "Access policies from infranet controller";
     input {
       leaf detail {
         description "Display detail output";
         type empty;
       }
       leaf identifier {
         description "Show specified policy information";
         type string;
       }
     }
   }
   rpc get-uac-auth-table {
     description "Show authentication table configured from infranet controller";
     input {
       leaf detail {
         description "Display detail output";
         type empty;
       }
       leaf identifier {
         description "Show specified authentication entry";
         type string;
       }
       leaf extended {
         description "Show authentication entries with all roles";
         type empty;
       }
       leaf role {
         description "Show authentication entries matching the role";
         type string;
       }
       leaf ip {
         description "Show authentication entries matching the ip";
         type string;
       }
       leaf user {
         description "Show authentication entries matching the user";
         type string;
       }
     }
   }
   rpc get-uac-status {
     description "Show connection status with infranet controller";
   }
   rpc get-uac-role-entries {
     description "Show list of available roles";
   }
   rpc get-uac-counters {
     description "Show unified access control(uac) service related counters";
     output {
       container uac-counters {
         uses uac-counters-block;
       }
     }
   }
   rpc get-appid-application-signature-detail {
     description "Show application signature details";
     input {
       leaf application-name {
         type string;
       }
       leaf start {
         description "Show application details from a given position";
         type uint32 {
           range "1 .. 65535";
         }
       }
       leaf count {
         description "Number of applications to show";
         type uint32 {
           range "1 .. 65535";
         }
       }
     }
   }
   rpc get-appid-application-signature-summary {
     description "Show application signature summary";
   }
   rpc get-appid-application-group-detail {
     description "Show application group details";
     input {
       leaf group-name {
         type string;
       }
     }
   }
   rpc get-appid-application-group-summary {
     description "Show application group summary";
   }
   rpc get-appid-application-system-cache {
     description "Show application system cache";
     input {
       leaf logical-system {
         description "Logical-system name";
         default "all";
         type string;
       }
     }
     output {
       container appid-application-system-cache-information {
         uses appid-application-system-cache-information-block;
       }
     }
   }
   rpc get-appid-counter {
     description "Show the application identification counters";
     output {
       container appid-counter-information {
         uses appid-counter-information-block;
       }
     }
   }
   rpc get-appid-counter-encrypted {
     description "Counters for SSL encrypted sessions";
     status deprecated;
     output {
       container appid-counter-information {
         uses appid-counter-information-block;
       }
     }
   }
   rpc get-commit-status {
     description "Show config commit status";
     output {
       container appid-commit-status {
         uses appid-commit-status-block;
       }
     }
   }
   rpc get-appid-application-statistics {
     description "Show the application statistics";
     input {
       leaf interval {
         description "Time interval for application statistics";
         default "1";
         type uint32 {
           range "1 .. 8";
         }
       }
     }
     output {
       container appid-application-statistics-information {
         uses appid-application-statistics-information-block;
       }
     }
   }
   rpc get-appid-application-group-statistics {
     description "Show the application group statistics";
     input {
       leaf interval {
         description "Time interval for application group statistics";
         default "1";
         type uint32 {
           range "1 .. 8";
         }
       }
     }
     output {
       container appid-application-group-statistics-information {
         uses appid-application-group-statistics-information-block;
       }
     }
   }
   rpc get-application-id-status-information {
     description "Show the application identification status";
     output {
       container appid-status-information {
         uses appid-status-information-block;
       }
     }
   }
   rpc get-appid-package-version {
     description "Show the current application package version";
     output {
       container appid-package-version {
         uses appid-package-version-block;
       }
     }
   }
   rpc get-ssl-proxy-statistics {
     description "Show ssl proxy statistics";
   }
   rpc show-secintel-category-feed {
     description "Show category detail information";
     input {
       leaf category-name {
         description "Category name";
         type string;
         mandatory true;
       }
       leaf feed-name {
         description "Feed name";
         type string;
         mandatory true;
       }
       leaf start {
         description "Start number";
         type uint32;
         mandatory true;
       }
       leaf count {
         description "Total number";
         type uint32;
         mandatory true;
       }
     }
   }
   rpc show-secintel-category-list {
     description "Show all category names";
   }
   rpc show-secintel-category-summary {
     description "Show category summary";
     input {
       leaf category-name {
         description "Show specified category summary";
         type string;
       }
     }
   }
   rpc show-secintel-recommended-action {
     description "Show security intelligence recommended action ";
     input {
       leaf category-name {
         description "Show category recommended action";
         type string;
       }
     }
   }
   rpc show-secintel-redirect-files {
     description "Show redirect files information";
     input {
       leaf file-name {
         description "Show redirect-file content";
         type string {
           junos:posix-pattern "![*]";
           junos:pattern-message "File name cannot contain '*', please use tab for filename completion";
         }
       }
     }
   }
   rpc show-secintel-update-status {
     description "Show update status";
   }
   rpc show-secintel-statistics {
     description "Show security intelligence statistics";
   }
   rpc show-secintel-statistics-profile {
     description "Show security intelligence profile statistics";
     input {
       leaf profile-name {
         description "Profile name";
         type string;
         mandatory true;
       }
     }
   }
   rpc show-aamw-statistics {
     description "Show advanced-anti-malware statistics";
   }
   rpc show-aamw-policy {
     description "Show advanced-anti-malware policy";
     input {
       leaf policy-name {
         description "Policy name";
         type string;
       }
     }
   }
   rpc show-aamw-profile {
     description "Show advanced-anti-malware profile";
     input {
       leaf profile-name {
         description "Profile name";
         type string;
       }
     }
   }
   rpc show-aamw-status {
     description "Show advanced-anti-malware status";
   }
   rpc show-aamw-version {
     description "Show advanced-anti-malware version";
   }
   rpc show-aamw-session-summary {
     description "Show advanced-anti-malware session summary";
     status deprecated;
   }
   rpc get-auth-table-counter-information {
     description "Show authentication table entry internal counter";
   }
   rpc get-auth-table-by-address-information {
     description "Show authentication table entry by ip-address";
     input {
       leaf ip-address {
         description "IP address";
         type ipaddr;
         mandatory true;
       }
     }
   }
   rpc get-auth-table-all-information {
     description "Show the entire authentication table in the userid daemon";
     input {
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc Show-authentication-table-all-by-group {
     description "Show authentication table entry by group name";
     input {
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc Show-authentication-table-all-by-user {
     description "Show authentication table entry by user name";
     input {
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc get-aruba-clearpass-information {
     description "Authentication source from Aruba ClearPass";
     input {
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc Show-authentication-table-aruba-by-group {
     description "Show authentication table entry by group name";
     input {
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc Show-authentication-table-aruba-by-user {
     description "Show authentication table entry by user name";
     input {
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc get-ad-information {
     description "Show the active directory authentication table";
     input {
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc get-auth-table-ad-by-group-information {
     description "Show authentication table entry by group name";
     input {
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc get-auth-table-ad-by-user-information {
     description "Show authentication table entry by user name";
     input {
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc get-domain-controller-status {
     description "Show domain-controller status";
     input {
       leaf domain {
         description "Show domain-controller status per domain";
         type string {
           length "1 .. 65";
         }
       }
       leaf level {
         default "brief";
         type enumeration {
           enum "brief" {
             description "Show brief output (default)";
           }
           enum "extensive" {
             description "Show extensive output";
           }
         }
       }
     }
   }
   rpc get-ip-user-mapping-stat-information {
     description "Show ip-user-mapping statistics";
     input {
       leaf domain {
         description "Show ip-user-mapping statistics per domain";
         type string {
           length "1 .. 65";
         }
       }
     }
   }
   rpc get-ip-user-probe-stat-information {
     description "Show ip-user-probe statistics";
     input {
       leaf domain {
         description "Show ip-user-probe statistics per domain";
         type string {
           length "1 .. 65";
         }
       }
     }
   }
   rpc get-user-group-mapping-stat-information {
     description "Show user-group-mapping statistics";
     input {
       leaf domain {
         description "Show user-group-mapping statistics per domain";
         type string {
           length "1 .. 65";
         }
       }
     }
   }
   rpc get-all-configuration-information {
     description "Show active-directory-access configuration";
   }
   rpc get-users-information {
     description "Show specified group's users. If timeout, wait several minutes and try again.";
     input {
       leaf group-name {
         description "Specified group name";
         type string {
           length "1 .. 65";
         }
         mandatory true;
       }
       leaf domain {
         description "Show users per domain";
         type string {
           length "1 .. 65";
         }
         mandatory true;
       }
     }
   }
   rpc get-groups-information {
     description "Show specified user's groups. If timeout, wait several minutes and try again.";
     input {
       leaf user-name {
         description "Specified user name";
         type string {
           length "1 .. 65";
         }
         mandatory true;
       }
       leaf domain {
         description "Show groups per domain";
         type string {
           length "1 .. 65";
         }
         mandatory true;
       }
     }
   }
   rpc get-user-group-mapping-status-information {
     description "Show user-group-mapping status";
     input {
       leaf domain {
         description "Show user-group-mapping status per domain";
         type string {
           length "1 .. 65";
         }
       }
     }
   }
   rpc get-all-groups-information {
     description "Show all groups";
     input {
       leaf domain {
         description "Show groups per domain";
         type string {
           length "1 .. 65";
         }
       }
       leaf start {
         description "Start of show";
         type uint32 {
           range "1 .. 65535";
         }
       }
       leaf count {
         description "Number of show";
         type uint32 {
           range "1 .. 65535";
         }
       }
     }
   }
   rpc get-all-users-information {
     description "Show all users";
     input {
       leaf domain {
         description "Show groups per domain";
         type string {
           length "1 .. 65";
         }
       }
       leaf start {
         description "Start of show";
         type uint32 {
           range "1 .. 65535";
         }
       }
       leaf count {
         description "Number of show";
         type uint32 {
           range "1 .. 65535";
         }
       }
     }
   }
   rpc get-ad-auth-table-all-information {
     description "Show the entire active directory authentication table";
     input {
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc get-ad-auth-table-by-address-information {
     description "Show active directory authentication table entry by ip-address";
     input {
       leaf ip-address {
         description "IP address";
         type ipaddr;
         mandatory true;
       }
     }
   }
   rpc get-ad-auth-table-by-group-information {
     description "Show active directory authentication table entry by group name";
     input {
       leaf group-name {
         description "Group name";
         type string {
           length "1 .. 65";
         }
         mandatory true;
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc get-ad-auth-table-by-user-information {
     description "Show active directory authentication table entry by user name";
     input {
       leaf user-name {
         description "User name";
         type string {
           length "1 .. 65";
         }
         mandatory true;
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type uint32 {
           range "1 .. 65535";
         }
       }
       leaf count {
         description "Number of show";
         type uint32 {
           range "1 .. 65535";
         }
       }
     }
   }
   rpc get-cp-user-query-statistics {
     description "Show ClearPass user query counters";
   }
   rpc get-cp-user-query-status {
     description "Show ClearPass user query status";
   }
   rpc get-dispatcher-statistics {
     description "Show statistics";
   }
   rpc get-lrf-statistics {
     description "Show lrf statistics";
     output {
       container lrf-statistics-summary {
         uses lrf-statistics-summary-block;
       }
     }
   }
   rpc get-lrf-collector-statistics {
     description "Show lrf collector statistics";
     input {
       leaf collector-name {
         description "Name of collector";
         type string;
       }
     }
     output {
       container lrf-collector-statistics-summary {
         uses lrf-collector-statistics-summary-block;
       }
     }
   }
   rpc get-lrf-rule-statistics {
     description "Show lrf rule statistics";
     input {
       leaf rule-name {
         description "Name of rule";
         type string;
       }
     }
     output {
       container lrf-rule-statistics-summary {
         uses lrf-rule-statistics-summary-block;
       }
     }
   }
   rpc get-lrf-template {
     description "Show lrf template";
     input {
       leaf template-type {
         description "Template type";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type (IBM specific)";
           }
           enum "ipflow-tcp" {
             description "IPFLOW TCP type";
           }
           enum "video" {
             description "Video type";
           }
           enum "dns" {
             description "DNS type";
           }
           enum "status-code-distribution" {
             description "Status code distribution for HTTP and DNS";
           }
           enum "pcc" {
             description "PCC type";
           }
         }
         mandatory true;
       }
     }
     output {
       container lrf-template {
         uses lrf-template-block;
       }
     }
   }
   rpc get-service-accounting-information {
     description "Show sampled accounting service";
   }
   rpc get-service-accounting-status-information {
     description "Show service accounting parameters";
     input {
       leaf status-information {
         description "Name of service, wildcard, or 'all'";
         type string;
       }
     }
   }
   rpc get-service-accounting-status-inline-jflow-information {
     description "Show service accounting inline Jflow parameters";
     input {
       leaf inline-jflow-information {
         description "FPC Slot for inline Jflow";
         type uint32 {
           range "0 .. 63";
         }
       }
     }
   }
   rpc get-service-accounting-usage-information {
     description "Show CPU usage";
     input {
       leaf usage-information {
         description "Name of service, wildcard, or 'all'";
         type string;
       }
     }
   }
   rpc get-service-accounting-memory-information {
     description "Show memory information";
     input {
       leaf memory-information {
         description "Name of service, wildcard, or 'all'";
         type string;
       }
     }
   }
   rpc get-service-accounting-flow-information {
     description "Show flow information";
     input {
       leaf flow-information {
         description "Name of service, wildcard, or 'all'";
         type string;
       }
       leaf logical-system {
         description "Name of logical system";
         type string {
           junos:posix-pattern "^[a-zA-Z0-9_-]{1,63}$";
           junos:pattern-message "Logical-system name is a string consisting of up         to 63 letters, numbers, dashes and underscores";
         }
       }
     }
   }
   rpc get-service-accounting-status-inline-jflow-flow-information {
     description "Show service accounting inline Jflow flow information";
     input {
       leaf inline-jflow-flow-information {
         description "FPC Slot for inline Jflow";
         type uint32 {
           range "0 .. 63";
         }
       }
     }
   }
   rpc get-service-accounting-flow-detail {
     description "Show flow detail";
     input {
       leaf flow-detail-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf destination-prefix {
         description "Filter term destination prefix";
         type string;
       }
       leaf source-port {
         description "Filter term source port";
         type uint32;
       }
       leaf destination-port {
         description "Filter term destination port";
         type uint32;
       }
       leaf input-snmp-interface-index {
         description "Filter term input SNMP interface index";
         type uint32;
       }
       leaf output-snmp-interface-index {
         description "Filter term output SNMP interface index";
         type uint32;
       }
       leaf source-as {
         description "Filter term source AS";
         type uint32;
       }
       leaf destination-as {
         description "Filter term destination AS";
         type uint32;
       }
       leaf tos {
         description "Filter term ToS";
         type uint32;
       }
       leaf proto {
         description "Filter term protocol";
         type uint32;
       }
     }
   }
   rpc get-service-accounting-aggregation-information {
     description "Show aggregation information";
   }
   rpc get-service-accounting-aggregation-as-information {
     description "Show aggregation type AS";
     input {
       leaf as-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-as {
         description "Filter term source-as";
         type uint32;
       }
       leaf destination-as {
         description "Filter term destination AS";
         type uint32;
       }
       leaf input-snmp-interface-index {
         description "Filter term input SNMP interface index";
         type uint32;
       }
       leaf output-snmp-interface-index {
         description "Filter term output SNMP interface index";
         type uint32;
       }
     }
   }
   rpc get-service-accounting-aggregation-protocol-port-information {
     description "Show aggregation type protocol-port";
     input {
       leaf protocol-port-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf proto {
         description "Filter term protocol";
         type uint32;
       }
       leaf source-port {
         description "Filter term source port";
         type uint32;
       }
       leaf destination-port {
         description "Filter term destination port";
         type uint32;
       }
     }
   }
   rpc get-service-accounting-aggregation-source-prefix-information {
     description "Show aggregation type source-prefix";
     input {
       leaf source-prefix-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type uint32;
       }
       leaf input-snmp-interface-index {
         description "Filter term input SNMP interface index";
         type uint32;
       }
     }
   }
   rpc get-service-accounting-aggregation-destination-prefix-information {
     description "Show aggregation type destination-prefix";
     input {
       leaf destination-prefix-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf destination-prefix {
         description "Filter term destination prefix";
         type string;
       }
       leaf destination-as {
         description "Filter term destination-as";
         type uint32;
       }
       leaf output-snmp-interface-index {
         description "Filter term output SNMP interface index";
         type uint32;
       }
     }
   }
   rpc get-service-accounting-aggregation-source-destination-prefix-information {
     description "Show aggregation type source-destination-prefix";
     input {
       leaf source-destination-prefix-information {
         description "Name of service, wildcard, or 'all'";
         type string;
       }
       leaf limit {
         description "Maximum number of flows to display";
         type uint32;
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type uint32;
       }
       leaf input-snmp-interface-index {
         description "Filter term input SNMP interface index";
         type uint32;
       }
       leaf destination-prefix {
         description "Filter term destination prefix";
         type string;
       }
       leaf destination-as {
         description "Filter term destination-as";
         type uint32;
       }
       leaf output-snmp-interface-index {
         description "Filter term output SNMP interface index";
         type uint32;
       }
     }
   }
   rpc get-service-accounting-aggregation-template-information {
     description "Show aggregation type template";
     input {
       leaf template-name {
         description "Name of template";
         type string;
         mandatory true;
       }
       leaf logical-system {
         description "Name of logical system";
         type string {
           junos:posix-pattern "^[a-zA-Z0-9_-]{1,63}$";
           junos:pattern-message "Logical-system name is a string consisting of up         to 63 letters, numbers, dashes and underscores";
         }
       }
       leaf display {
         default "terse";
         type enumeration {
           enum "extensive" {
             description "Display extensive output";
           }
           enum "detail" {
             description "Display detailed output";
           }
           enum "terse" {
             description "Display terse output (default)";
           }
         }
       }
     }
   }
   rpc get-service-accounting-errors-information {
     description "Show error statistics";
     input {
       leaf error-information {
         description "Name of service, wildcard, or 'all'";
         type string;
       }
     }
   }
   rpc get-service-accounting-error-inline-jflow-information {
     description "Show service accounting inline Jflow error information";
     input {
       leaf inline-jflow-error-information {
         description "FPC Slot for inline Jflow";
         type uint32 {
           range "0 .. 63";
         }
       }
     }
   }
   rpc get-packet-distribution-information {
     description "Show packet size distribution";
     input {
       leaf packet-size-distribution-information {
         description "Name of service, wildcard, or 'all'";
         type string;
       }
     }
   }
   rpc get-service-mss-sessions-information {
     description "Show mobile subscriber data sessions";
     input {
       leaf imsi {
         description "IMSI of subscriber";
         type string {
           length "5 .. 15";
         }
       }
     }
   }
   rpc get-service-hcm-sessions-stats {
     description "Show hcm session statistics";
     input {
       leaf imsi {
         description "IMSI of subscriber";
         type string {
           length "5 .. 15";
         }
         mandatory true;
       }
     }
   }
   rpc get-service-tdf-sessions-information {
     description "Show traffic-detection-function subscriber data sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-tdf-hcm-sessions-stats {
     description "Show hcm session statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-crtp-params-information {
     description "Show Compressed Real-Time Protocol information";
     input {
       leaf interface {
         description "Name of link services interface";
         type string;
       }
     }
   }
   rpc get-service-crtp-extensive-information {
     description "Show CRTP extensive output";
     input {
       leaf interface {
         description "Name of link services interface";
         type string;
       }
     }
   }
   rpc get-service-crtp-flow-table-information {
     description "Show CRTP flow table entries";
     input {
       leaf interface {
         description "Name of link services interface";
         type string;
       }
     }
     output {
       container service-crtp-flow-table-information {
         uses service-crtp-flow-table-information-block;
       }
     }
   }
   rpc get-global-pcp-statistics-information {
     description "Show global PCP statistics";
     input {
       leaf interface {
         description "Name of adaptive services interface";
         type string;
       }
       leaf level {
         type enumeration {
           enum "protocol" {
             description "Display PCP protocol statistics";
           }
         }
       }
     }
   }
   rpc get-services-redundancy-group-information {
     description "Show services redundancy-group information";
     input {
       leaf verbose {
         default "terse";
         type enumeration {
           enum "terse" {
             description "Display terse output(default)";
           }
           enum "brief" {
             description "Display brief output";
           }
           enum "extensive" {
             description "Display detailed output";
           }
         }
       }
     }
   }
   rpc get-services-redundancy-group-id-information {
     description "Show redundancy group-id information";
     input {
       leaf verbose {
         default "terse";
         type enumeration {
           enum "terse" {
             description "Display terse output(default)";
           }
           enum "brief" {
             description "Display brief output";
           }
           enum "extensive" {
             description "Display detailed output";
           }
         }
       }
       leaf id {
         description "Show redundancy group-id information";
         type uint32;
         mandatory true;
       }
     }
   }
   rpc get-ip-monitoring-status {
     description "Ip monitoring status";
     input {
       leaf policy {
         description "Policy name";
         type string;
       }
     }
   }
   rpc get-traffic-load-balance-statistics {
     description "Traffic load balance statistics";
     input {
       leaf verbose {
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
     }
   }
   rpc get-url-filter-statistics {
     description "Show url-filter statistics";
     input {
       leaf profile {
         description "Url-filter profile specific statistics";
         type string;
         mandatory true;
       }
       leaf template {
         description "Url-filter template specific statistics";
         type string;
       }
       leaf fpc-slot {
         description "FPC slot number";
         type uint32;
       }
       leaf pic-slot {
         description "PIC slot number";
         type uint32;
       }
     }
     output {
       container url-filter-statistics {
         uses url-filter-statistics-block;
       }
     }
   }
   rpc get-url-filter-dns-resolution {
     description "Show url-filter dns-resolution";
     input {
       leaf profile {
         description "Url-filter profile specific DNS resolution information";
         type string;
         mandatory true;
       }
       leaf template {
         description "Url-filter template specific DNS resolution informartion";
         type string;
       }
     }
     output {
       container url-filter-dns-resolution {
         uses url-filter-dns-resolution-block;
       }
     }
   }
   rpc get-url-filter-dns-resolution-statistics {
     description "Show url-filter dns-resolution statistics";
     input {
       leaf profile {
         description "Url-filter profile specific DNS resolution information";
         type string;
         mandatory true;
       }
       leaf template {
         description "Url-filter template specific DNS resolution informartion";
         type string;
         mandatory true;
       }
       leaf verbosity_level {
         type enumeration {
           enum "summary" {
             description "Display summary output";
           }
           enum "extensive" {
             description "Display extensive output";
           }
         }
         mandatory true;
       }
     }
     output {
       container url-filter-dns-resolution-statistics {
         uses url-filter-dns-resolution-statistics-block;
       }
     }
   }
 grouping probe-results-block {
   list probe-test-results {
     leaf owner {
       type string;
       description "Test owner name";
     }
     leaf test-name {
       type string;
       description "Name of test";
     }
     leaf target-address {
       type string;
       description "Target address of test";
     }
     leaf target-url {
       type string;
       description "Target URL of test";
     }
     leaf source-address {
       type string;
       description "Source address of test";
     }
     leaf probe-type {
       type string;
       description "Name of the probe";
     }
     leaf icmp-id {
       type uint32;
       description "Icmp id for icmp-ping probes";
     }
     leaf test-size {
       type uint32;
       description "Number of probes in test";
     }
     leaf server-address {
       type ipaddr;
       description "Server address";
     }
     leaf server-port {
       type uint32;
       description "Server port";
     }
     leaf client-address {
       type ipaddr;
       description "Client address";
     }
     leaf client-port {
       type uint32;
       description "Client port";
     }
     leaf reflector-address {
       type ipaddr;
       description "Reflector address";
     }
     leaf reflector-port {
       type uint32;
       description "Reflector port";
     }
     leaf sender-address {
       type ipaddr;
       description "Sender address";
     }
     leaf sender-port {
       type uint32;
       description "Sender port";
     }
     leaf routing-instance-name {
       type string;
       description "Routing Instance Name";
     }
     leaf destination-interface {
       type string;
       description "Name of output interface for probes";
     }
     leaf http-status {
       type uint32;
       description "HTTP Status Code";
     }
     container probe-single-results {
       leaf probe-sent-time {
         type string;
         description "Time at which probe was sent";
       }
       leaf probe-status {
         type string;
         description "Operation response status from probes";
       }
       leaf probe-time {
         type string;
         description "Time at which probe response was received or timed out";
       }
       leaf hardware-timestamp-status {
         type string;
         description "Use of hardware timestamps in probes";
       }
       leaf rtt {
         type uint32;
         description "Round trip time of probes";
       }
       leaf ingress {
         type uint32;
         description "Ingress trip time of probes";
       }
       leaf egress {
         type uint32;
         description "Egress trip time of probes";
       }
       leaf egress-jitter {
         type int32;
         description "Egress jitter of probes";
       }
       leaf ingress-jitter {
         type int32;
         description "Ingress jitter of probes";
       }
       leaf round-trip-jitter {
         type int32;
         description "Round trip jitter of probes";
       }
       leaf egress-interarrival-jitter {
         type int32;
         description "Egress interarrival jitter of probes";
       }
       leaf ingress-interarrival-jitter {
         type int32;
         description "Ingress interarrival jitter of probes";
       }
       leaf round-trip-interarrival-jitter {
         type int32;
         description "Round trip interarrival jitter of probes";
       }
       container verbose {
       }
       container brief {
         leaf owner {
           type string;
           description "Test owner name";
         }
         leaf test-name {
           type string;
           description "Name of test";
         }
         leaf probe-sent-time {
           type string;
           description "Time at which probe was sent";
         }
         leaf probe-time {
           type string;
           description "Time at which probe response was received or timed out";
         }
         leaf rtt {
           type uint32;
           description "Round trip time of probes";
         }
         leaf probe-status {
           type string;
           description "Operation response status from probes";
         }
       }
     }
     container probe-test-current-results {
       container probe-test-generic-results {
         leaf results-scope {
           type string;
           description "Scope of results";
         }
         leaf probes-sent {
           type uint32;
           description "Number of probes sent";
         }
         leaf probe-responses {
           type uint32;
           description "Responses from probes";
         }
         leaf loss-percentage {
           type string;
           description "Percentage of probes lost (no response)";
         }
         container probe-last-test-info {
           leaf last-test-time {
             type string;
             description "Time at which last test was completed";
           }
         }
         container probe-test-rtt {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-egress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-ingress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
       }
     }
     container probe-last-test-results {
       container probe-test-generic-results {
         leaf results-scope {
           type string;
           description "Scope of results";
         }
         leaf probes-sent {
           type uint32;
           description "Number of probes sent";
         }
         leaf probe-responses {
           type uint32;
           description "Responses from probes";
         }
         leaf loss-percentage {
           type string;
           description "Percentage of probes lost (no response)";
         }
         container probe-last-test-info {
           leaf last-test-time {
             type string;
             description "Time at which last test was completed";
           }
         }
         container probe-test-rtt {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-egress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-ingress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
       }
     }
     container probe-test-moving-results {
       container probe-test-generic-results {
         leaf results-scope {
           type string;
           description "Scope of results";
         }
         leaf probes-sent {
           type uint32;
           description "Number of probes sent";
         }
         leaf probe-responses {
           type uint32;
           description "Responses from probes";
         }
         leaf loss-percentage {
           type string;
           description "Percentage of probes lost (no response)";
         }
         container probe-last-test-info {
           leaf last-test-time {
             type string;
             description "Time at which last test was completed";
           }
         }
         container probe-test-rtt {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-egress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-ingress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
       }
     }
     container probe-test-global-results {
       container probe-test-generic-results {
         leaf results-scope {
           type string;
           description "Scope of results";
         }
         leaf probes-sent {
           type uint32;
           description "Number of probes sent";
         }
         leaf probe-responses {
           type uint32;
           description "Responses from probes";
         }
         leaf loss-percentage {
           type string;
           description "Percentage of probes lost (no response)";
         }
         container probe-last-test-info {
           leaf last-test-time {
             type string;
             description "Time at which last test was completed";
           }
         }
         container probe-test-rtt {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-egress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-ingress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
       }
     }
     container probe-test-hwts-err-stats {
       leaf invalid-client-recv-ts-cntr {
         type uint32;
         description "Client recv timestamp less than Client send timestamp";
       }
       leaf invalid-server-send-ts-cntr {
         type uint32;
         description "Server send timestamp less than Server recv timestamp";
       }
       leaf invalid-server-spent-time-cntr {
         type uint32;
         description "Server side spent time greater than RTT";
       }
     }
   }
 }
 grouping history-results-block {
   list history-test-results {
     list verbose {
       leaf owner {
         type string;
         description "Test owner name";
       }
       leaf test-name {
         type string;
         description "Name of test";
       }
       leaf probe-type {
         type string;
         description "Name of the probe";
       }
       leaf icmp-id {
         type uint32;
         description "Icmp id for icmp-ping probes";
       }
       leaf target-address {
         type string;
         description "Target address of test";
       }
       leaf target-url {
         type string;
         description "Target URL of test";
       }
       leaf source-address {
         type string;
         description "Source address of test";
       }
       leaf destination-interface {
         type string;
         description "Name of output interface for probes";
       }
       leaf loss-thresh-total {
         type uint32;
         description "Maximum number of all lost probes";
       }
       leaf loss-thresh-succ {
         type uint32;
         description "Maximum number of successive lost probes";
       }
       leaf delay-thresh {
         type uint32;
         description "Maximum delay threshold";
       }
       leaf jitter-thresh {
         type uint32;
         description "Maximum jitter threshold";
       }
       leaf stddev-thresh {
         type uint32;
         description "Maximum standard deviation threshold";
       }
       leaf egress-thresh {
         type uint32;
         description "Maximum egress delay threshold";
       }
       leaf egress-jitter-thresh {
         type uint32;
         description "Maximum egress jitter threshold";
       }
       leaf ingress-thresh {
         type uint32;
         description "Maximum ingress delay threshold";
       }
       leaf ingress-jitter-thresh {
         type uint32;
         description "Maximum ingress jitter threshold";
       }
       container probe-single-results {
         container brief {
           leaf probe-sent-time {
             type string;
             description "Time at which probe was sent";
           }
           leaf probe-time {
             type string;
             description "Time at which probe response was received or timed out";
           }
           leaf rtt {
             type uint32;
             description "Round trip time of probes";
           }
           leaf probe-status {
             type string;
             description "Operation response status from probes";
           }
         }
       }
       container probe-test-current-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
         }
       }
     }
     list brief {
       container probe-single-results {
         container verbose {
           leaf probe-sent-time {
             type string;
             description "Time at which probe was sent";
           }
           leaf probe-status {
             type string;
             description "Operation response status from probes";
           }
           leaf probe-time {
             type string;
             description "Time at which probe response was received or timed out";
           }
           leaf hardware-timestamp-status {
             type string;
             description "Use of hardware timestamps in probes";
           }
           leaf http-status {
             type uint32;
             description "HTTP Status Code";
           }
           leaf rtt {
             type uint32;
             description "Round trip time of probes";
           }
           leaf ingress {
             type uint32;
             description "Ingress trip time of probes";
           }
           leaf egress {
             type uint32;
             description "Egress trip time of probes";
           }
           leaf egress-jitter {
             type int32;
             description "Egress jitter of probes";
           }
           leaf ingress-jitter {
             type int32;
             description "Ingress jitter of probes";
           }
           leaf round-trip-jitter {
             type int32;
             description "Round trip jitter of probes";
           }
           leaf egress-interarrival-jitter {
             type int32;
             description "Egress interarrival jitter of probes";
           }
           leaf ingress-interarrival-jitter {
             type int32;
             description "Ingress interarrival jitter of probes";
           }
           leaf round-trip-interarrival-jitter {
             type int32;
             description "Round trip interarrival jitter of probes";
           }
         }
         container brief {
           leaf owner {
             type string;
             description "Test owner name";
           }
           leaf test-name {
             type string;
             description "Name of test";
           }
           leaf probe-sent-time {
             type string;
             description "Time at which probe was sent";
           }
           leaf probe-time {
             type string;
             description "Time at which probe response was received or timed out";
           }
           leaf rtt {
             type uint32;
             description "Round trip time of probes";
           }
           leaf probe-status {
             type string;
             description "Operation response status from probes";
           }
         }
       }
       container probe-test-current-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
         }
       }
     }
   }
 }
 grouping active-servers-block {
   list configured-servers {
     leaf protocol {
       type string;
       description "Protocol";
     }
     leaf port {
       type uint32;
       description "Port";
     }
     leaf destination-interface {
       type string;
       description "Name of output interface for probes";
     }
   }
 }
 grouping uac-counters-block {
   list uac-counter {
     description "UAC counter for the PFE";
     leaf pfe-name {
       type string;
       description "PFE";
     }
     leaf allowed-policy-action {
       type uint32;
       description "Sessions allowed due to policy action";
     }
     leaf allowed-timeout-action {
       type uint32;
       description "Sessions allowed due to timeout action";
     }
     leaf denied-unauthenticated {
       type uint32;
       description "Sessions denied due to lack of authentication";
     }
     leaf denied-policy-action {
       type uint32;
       description "Sessions denied due to policy action";
     }
     leaf denied-policy-unmatched {
       type uint32;
       description "Sessions denied due to unmatched policy";
     }
     leaf denied-timeout-action {
       type uint32;
       description "Sessions denied due to timeout action";
     }
     leaf terminated-reevaluation {
       type uint32;
       description "Sessions terminated due to reevaluation";
     }
     leaf terminated-signout {
       type uint32;
       description "Sessions terminated due to user signout";
     }
     leaf auth-added {
       type uint32;
       description "Auth entry added to PFE";
     }
     leaf auth-deleted {
       type uint32;
       description "Auth entry deleted from PFE";
     }
     leaf current-auth-cnt {
       type uint32;
       description "UAC total auth count";
     }
   }
 }
 grouping appid-application-system-cache-information-block {
   leaf pic {
     type string;
     description "FPC index/PIC index";
   }
   leaf message {
     type string;
     description "CLI ouput message";
   }
   container appid-cache-configuration {
     leaf appid-asc-enable {
       type string;
       description "Show application cache (on|off)";
     }
     leaf appid-cache-timeout {
       type uint32;
       description "Show cache entry timeout (seconds)";
     }
   }
   list appid-application-system-cache {
     container asc-entry {
       leaf application-groups {
         type string;
         description "Application groups";
       }
       leaf virtual-system-identifier {
         type string;
         description "Virtual system identifier";
       }
       leaf ip-address {
         type ipaddr;
         description "IP address in application system cache";
       }
       leaf port {
         type int32;
         description "Port number";
       }
       leaf protocol {
         type string;
       }
       leaf appid-application {
         type string;
         description "Application type";
       }
       leaf classification-path {
         type string;
         description "Application classification path";
       }
     }
   }
   list appid-application-system-cache-usp {
     leaf application-groups {
       type string;
       description "Application groups";
     }
     leaf virtual-system-identifier {
       type string;
       description "Virtual system identifier";
     }
     leaf ipv6-address {
       type ipv6addr;
       description "IPV6 address in application system cache";
     }
     leaf port {
       type int32;
       description "Port number";
     }
     leaf protocol {
       type string;
     }
     leaf appid-application {
       type string;
       description "Application type";
     }
     leaf is_encrypted {
       type string;
       description "Is Encrypted";
     }
     leaf classification-path {
       type string;
       description "Application classification path";
     }
   }
 }
 grouping appid-counter-information-block {
   leaf pic {
     type string;
     description "FPC index/PIC index";
   }
   leaf message {
     type string;
     description "CLI ouput message";
   }
   list appid-counter-usp {
     leaf counter-name {
       type string;
       description "Counter name";
     }
     leaf counter-value {
       type uint32;
       description "Counter value";
     }
   }
   list appid-counter {
     container counter {
       leaf counter-name {
         type string;
         description "Counter name";
       }
       leaf counter-value {
         type uint32;
         description "Counter value";
       }
     }
   }
 }
 grouping appid-commit-status-block {
   leaf appid-commit-status-detail {
     type string;
     description "Custom signatures commit status";
   }
 }
 grouping appid-application-statistics-information-block {
   container last-reset-stats {
     leaf last-reset {
       type string;
       description "Last reset timestamp";
     }
     leaf elapsed-time {
       type string;
       description "Elapsed time";
     }
   }
   list appid-application-statistics-usp {
     leaf application-name {
       type string;
       description "Name of an application or nested application";
     }
     leaf sessions {
       type uint32;
       description "Sessions per application";
     }
     leaf bytes {
       type uint32;
       description "Byte count";
     }
     leaf is_encrypted {
       type string;
       description "Is Encrypted";
     }
   }
   list appid-application-statistics {
     leaf application-name {
       type string;
       description "Name of an application or nested application";
     }
     leaf sessions {
       type uint32;
       description "Sessions per application";
     }
     leaf bytes {
       type uint32;
       description "Byte count";
     }
   }
 }
 grouping appid-application-group-statistics-information-block {
   container last-reset-group-stats {
     leaf last-reset {
       type string;
       description "Last reset timestamp";
     }
     leaf elapsed-time {
       type string;
       description "Elapsed time";
     }
   }
   list appid-application-group-statistics {
     leaf application-name {
       type string;
       description "Name of an application or nested application";
     }
     leaf sessions {
       type uint32;
       description "Sessions per application";
     }
     leaf bytes {
       type uint32;
       description "Byte count";
     }
   }
 }
 grouping appid-status-information-block {
   leaf pic {
     type string;
     description "FPC index/PIC index";
   }
   list appid-module-status {
     container status {
       leaf status-name {
         type string;
         description "Status name";
       }
       leaf status-value {
         type string;
         description "Status value";
       }
     }
   }
   list appid-asc-status {
     container status {
       leaf status-name {
         type string;
         description "Status name";
       }
       leaf status-value {
         type string;
         description "Status value";
       }
     }
   }
   list appid-protobundle-status {
     container status {
       leaf status-name {
         type string;
         description "Status name";
       }
       leaf status-value {
         type string;
         description "Status value";
       }
     }
   }
   list appid-protobundle-slot1-status {
     container status {
       leaf status-name {
         type string;
         description "Status name";
       }
       leaf status-value {
         type string;
         description "Status value";
       }
     }
   }
   list appid-protobundle-slot2-status {
     container status {
       leaf status-name {
         type string;
         description "Status name";
       }
       leaf status-value {
         type string;
         description "Status value";
       }
     }
   }
 }
 grouping appid-package-version-block {
   leaf version-detail {
     type int32;
     description "Application package version";
   }
 }
 grouping lrf-statistics-summary-block {
   list lrf-statistics {
     description "LRF statistics";
     leaf interface-name {
       type string;
       description "Name of the adaptive services interface";
     }
     leaf flow-packets {
       type int32;
       description "Flow packets";
     }
     leaf flow-bytes {
       type int32;
       description "Flow bytes";
     }
     leaf active-flows {
       type int32;
       description "Active flows";
     }
     leaf total-flows {
       type int32;
       description "Total flows";
     }
   }
 }
 grouping lrf-collector-statistics-summary-block {
   list lrf-collector-statistics {
     description "LRF collector statistics";
     leaf interface-name {
       type string;
       description "Name of the adaptive services interface";
     }
     leaf tmpl-reg {
       type int32;
       description "Templates registered";
     }
     leaf tmpl-reg-failures {
       type int32;
       description "Template registration failures";
     }
     leaf tmpl-active {
       type int32;
       description "Templates active";
     }
     leaf sessions-received {
       type int32;
       description "Sessions received";
     }
     leaf sessions-ignored {
       type int32;
       description "Sessions ignored";
     }
     leaf records-logged {
       type int32;
       description "Records logged";
     }
     leaf rec-export {
       type int32;
       description "Records exported";
     }
     leaf rec-export-failures {
       type int32;
       description "Record export failures";
     }
     leaf rec-export-volume {
       type int32;
       description "Records exported for volume";
     }
     leaf rec-export-time {
       type int32;
       description "Records exported for time";
     }
     leaf rec-export-session-close {
       type int32;
       description "Records exported for session close";
     }
   }
 }
 grouping lrf-rule-statistics-summary-block {
   list lrf-rule-statistics {
     description "LRF rule statistics";
     leaf interface-name {
       type string;
       description "Name of the adaptive services interface";
     }
     leaf rule-name {
       type string;
       description "Rule name";
     }
     leaf rule-tmpl-name {
       type string;
       description "Template name";
     }
     leaf rule-tmpl-reg {
       type int32;
       description "Templates registered";
     }
     leaf rule-tmpl-reg-failures {
       type int32;
       description "Template registration failures";
     }
     leaf rule-coll-name {
       type string;
       description "Collector name";
     }
     leaf rule-sessions-received {
       type int32;
       description "Sessions received";
     }
     leaf rule-sessions-ignored {
       type int32;
       description "Sessions ignored";
     }
     leaf rule-sessions-logged {
       type int32;
       description "Sessions logged";
     }
     leaf rule-rec-export {
       type int32;
       description "Records exported";
     }
     leaf rule-rec-export-failures {
       type int32;
       description "Record export failures";
     }
     leaf rule-rec-export-volume {
       type int32;
       description "Records exported for volume";
     }
     leaf rule-rec-export-time {
       type int32;
       description "Records exported for time";
     }
     leaf rule-rec-export-session-close {
       type int32;
       description "Records exported for session close";
     }
   }
 }
 grouping lrf-template-block {
   leaf export-field {
     type string;
   }
   leaf export-field-id {
     type int32;
   }
   leaf export-field-len {
     type int32;
   }
   leaf export-field-vendor {
     type string;
   }
 }
 grouping service-crtp-flow-table-information-block {
   list crtp-per-interface-flow-table {
     description "CRTP flows sorted by interface";
     leaf interface-name {
       type string;
       description "Name of the adaptive services interface";
     }
     list service-crtp-flow-table {
       description "CRTP flows";
       list crtp-flow-entry {
         description "CRTP flow information";
         leaf crtp-flow-type {
           type string;
           description "Flow type";
         }
         leaf crtp-flow-source-info {
           type string;
           description "Flow source information (IP address and UDP port)";
         }
         leaf crtp-flow-destination-info {
           type string;
           description "Flow destination information (IP address and UDP port)";
         }
         leaf crtp-flow-rtp-id {
           type int32;
           description "RTP SSRC identifier";
         }
         leaf crtp-flow-context-id {
           type int32;
           description "Context identifier";
         }
       }
     }
   }
 }
 grouping url-filter-statistics-block {
   container normal {
     description "Url-filter statistics";
     container url-filter-statistics-information {
       description "Url filter statistics";
       leaf act-accept-session-cnt {
         type uint64;
         description "Accept session count";
       }
       leaf act-accept-uplink-packet-cnt {
         type uint64;
         description "Accept uplink packet count";
       }
       leaf act-accept-uplink-bytes {
         type uint64;
         description "Accept uplink bytes";
       }
       leaf act-accept-downlink-packet-cnt {
         type uint64;
         description "Accept downlink packet count";
       }
       leaf act-accept-downlink-bytes {
         type uint64;
         description "Accept downlink bytes";
       }
       leaf act-custom-page-session-cnt {
         type uint64;
         description "Custom page session count";
       }
       leaf act-custom-page-uplink-packet-cnt {
         type uint64;
         description "Custom page uplink packet count";
       }
       leaf act-custom-page-uplink-bytes {
         type uint64;
         description "Custom page uplink bytes";
       }
       leaf act-custom-page-downlink-packet-cnt {
         type uint64;
         description "Custom page downlink packet count";
       }
       leaf act-custom-page-downlink-bytes {
         type uint64;
         description "Custom page downlink bytes";
       }
       leaf act-http-scode-session-cnt {
         type uint64;
         description "Http scode session count";
       }
       leaf act-http-scode-uplink-packet-cnt {
         type uint64;
         description "Http scode uplink packet count";
       }
       leaf act-http-scode-uplink-bytes {
         type uint64;
         description "Http scode uplink bytes";
       }
       leaf act-http-scode-downlink-packet-cnt {
         type uint64;
         description "Http scode downlink packet count";
       }
       leaf act-http-scode-downlink-bytes {
         type uint64;
         description "Http scode downlink bytes";
       }
       leaf act-redirect-url-session-cnt {
         type uint64;
         description "Redirect url session count";
       }
       leaf act-redirect-url-uplink-packet-cnt {
         type uint64;
         description "Redirect url uplink packet count";
       }
       leaf act-redirect-url-uplink-bytes {
         type uint64;
         description "Redirect url uplink bytes";
       }
       leaf act-redirect-url-downlink-packet-cnt {
         type uint64;
         description "Redirect url downlink packet count";
       }
       leaf act-redirect-url-downlink-bytes {
         type uint64;
         description "Redirect url downlink bytes";
       }
       leaf act-tcp-reset-session-cnt {
         type uint64;
         description "Tcp reset session count";
       }
       leaf act-tcp-reset-uplink-packet-cnt {
         type uint64;
         description "Tcp reset uplink packet count";
       }
       leaf act-tcp-reset-uplink-bytes {
         type uint64;
         description "Tcp reset uplink bytes";
       }
       leaf act-tcp-reset-downlink-packet-cnt {
         type uint64;
         description "Tcp reset downlink packet count";
       }
       leaf act-tcp-reset-downlink-bytes {
         type uint64;
         description "Tcp reset downlink bytes";
       }
     }
   }
 }
 grouping url-filter-dns-resolution-block {
   container normal {
     description "Url-filter DNS resolution information";
     leaf profile-name {
       type string;
       description "Profile Name";
     }
     list url-filter-template-dns-resolution-information {
       description "Url-filter DNS resolution information";
     }
   }
 }
 grouping url-filter-dns-resolution-statistics-block {
   container normal {
     description "Url-filter DNS resolution staistics information";
     leaf profile-name {
       type string;
       description "Profile Name";
     }
     list url-filter-template-dns-resolution-statistics-information {
       description "Url-filter DNS resolution statistics";
     }
   }
 }
 }
