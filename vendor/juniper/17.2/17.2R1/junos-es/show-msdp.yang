/*
 * Copyright (c) 2017 Juniper Networks, Inc.
 * All rights reserved.
 */
 module show-msdp {
  namespace "http://yang.juniper.net/yang/1.1/jrpc/show-msdp/junos-es/17.2R1.13";
  prefix show-msdp;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-msdp-information {
     description "Show Multicast Source Discovery Protocol information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf peer {
         description "IPv4 address and optional prefix length of MSDP peers";
         type ipv4prefix;
       }
       leaf verbosity_level {
         default "brief";
         type enumeration {
           enum "brief" {
             description "Display brief output (default)";
           }
           enum "detail" {
             description "Display detailed output";
           }
         }
       }
     }
     output {
       container msdp-peer-information {
         uses msdp-peer-information-block;
       }
     }
   }
   rpc get-msdp-statistics-information {
     description "Show MSDP statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf peer {
         description "IPv4 address and optional prefix length of MSDP peers";
         type ipv4addr;
       }
     }
     output {
       container msdp-statistics-information {
         uses msdp-statistics-information-block;
       }
     }
   }
   rpc get-msdp-source-information {
     description "Show multicast sources learned from MSDP";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf source {
         description "IP address and optional prefix length of source";
         type ipv4addr;
       }
     }
     output {
       container msdp-source-information {
         uses msdp-source-information-block;
       }
     }
   }
   rpc get-msdp-source-active-information {
     description "Show the source-active (SA) cache";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf group {
         description "Name of group";
         type string;
       }
       leaf source {
         description "Name of source";
         type string;
       }
       leaf peer {
         description "IPv4 address of peer";
         type ipv4addr;
       }
       leaf local {
         description "Display SA cache entries originating at this router";
         type empty;
       }
       leaf originator {
         description "IPv4 address of peer that originated SA cache entries";
         type ipv4addr;
       }
       leaf verbosity_level {
         default "brief";
         type enumeration {
           enum "brief" {
             description "Display brief output (default)";
           }
           enum "detail" {
             description "Display detailed output";
           }
         }
       }
     }
     output {
       container msdp-source-active-information {
         uses msdp-source-active-information-block;
       }
     }
   }
 grouping msdp-peer-information-block {
   leaf msdp-no-peers {
     type empty;
   }
   list msdp-peer {
     list brief {
       leaf msdp-peer-address {
         type ipaddr;
       }
       leaf msdp-local-address {
         type ipaddr;
       }
       leaf msdp-state {
         type string;
       }
       leaf msdp-state-change {
         type string;
       }
       leaf msdp-group-name {
         type string;
       }
       leaf msdp-sa-accepted {
         type int32;
         description "Number of SAs accepted from peer";
       }
       leaf msdp-sa-received {
         type int32;
         description "Number of SAs received from peer";
       }
     }
     list detail {
       leaf msdp-peer-address {
         type ipaddr;
       }
       leaf msdp-group-name {
         type string;
       }
       leaf msdp-local-address {
         type ipaddr;
       }
       leaf msdp-state {
         type string;
       }
       leaf msdp-connect-retries {
         type int32;
       }
       leaf msdp-state-timeout {
         type int32;
       }
       leaf msdp-peer-timeout {
         type int32;
       }
       leaf msdp-sa-accepted {
         type int32;
         description "Number of SAs accepted from peer";
       }
       leaf msdp-sa-received {
         type int32;
         description "Number of SAs received from peer";
       }
       leaf msdp-active-source-limit-maximum {
         type uint32;
       }
       leaf msdp-active-source-limit-threshold {
         type uint32;
       }
       leaf msdp-active-source-limit-log-warning {
         type uint32;
       }
       leaf msdp-active-source-limit-log-interval {
         type uint32;
       }
     }
     list socket-handler {
       leaf msdp-peer-address {
         type ipaddr;
       }
       leaf msdp-group-name {
         type string;
       }
       leaf msdp-local-address {
         type ipaddr;
       }
       leaf msdp-state {
         type string;
       }
       leaf msdp-socket-primary {
         type int32;
         description "MSDP Peer Socket on Primary";
       }
       leaf msdp-socket-secondary {
         type int32;
         description "MSDP Peer Socket on Secondary";
       }
       leaf msdp-socket-handler {
         type uint32;
         description "Socket Replication Handler";
       }
     }
   }
 }
 grouping msdp-statistics-information-block {
   leaf msdp-no-peer {
     type ipaddr;
   }
   list msdp-instance {
     leaf instance-name {
       type string;
     }
     leaf msdp-global-active-source-limit-exceeded {
       type int32;
     }
     leaf msdp-global-active-source-limit-maximum {
       type uint32;
     }
     leaf msdp-global-active-source-limit-threshold {
       type uint32;
     }
     leaf msdp-global-active-source-limit-log-warning {
       type uint32;
     }
     leaf msdp-global-active-source-limit-log-interval {
       type uint32;
     }
     list msdp-route {
       leaf multicast-group-address {
         type ipaddr;
         description "Group address";
       }
       leaf multicast-source-address {
         type ipaddr;
         description "Source address";
       }
       list msdp-route-peer {
         leaf msdp-peer-address {
           type ipaddr;
         }
         leaf msdp-originator {
           type ipaddr;
         }
         container msdp-route-peer-flags {
         }
       }
     }
     list msdp-source {
       leaf msdp-source-prefix {
         type ipaddr;
       }
       leaf msdp-source-prefix-length {
         type uint32;
       }
       leaf msdp-source-type {
         type string;
       }
       leaf msdp-source-limit-maximum {
         type string;
       }
       leaf msdp-source-limit-threshold {
         type string;
       }
       leaf msdp-source-limit-exceeded {
         type int32;
       }
       leaf msdp-source-limit-log-warning {
         type string;
       }
       leaf msdp-source-limit-log-interval {
         type string;
       }
     }
     list msdp-peer-statistics {
       leaf msdp-peer-address {
         type ipaddr;
       }
       leaf msdp-state-change-absolute {
         type string;
       }
       leaf msdp-state-change {
         type string;
       }
       leaf msdp-message-received-absolute {
         type string;
       }
       leaf msdp-message-received {
         type string;
       }
       leaf msdp-rpf-failures {
         type int32;
       }
       leaf msdp-remote-closes {
         type int32;
       }
       leaf msdp-peer-timeouts {
         type int32;
       }
       leaf msdp-sa-messages-sent {
         type int32;
       }
       leaf msdp-sa-messages-received {
         type int32;
       }
       leaf msdp-sa-requests-sent {
         type int32;
       }
       leaf msdp-sa-requests-received {
         type int32;
       }
       leaf msdp-sa-responses-sent {
         type int32;
       }
       leaf msdp-sa-responses-received {
         type int32;
       }
       leaf msdp-active-source-limit-exceeded {
         type int32;
       }
       leaf msdp-active-source-limit-maximum {
         type uint32;
       }
       leaf msdp-active-source-limit-threshold {
         type uint32;
       }
       leaf msdp-active-source-limit-log-warning {
         type uint32;
       }
       leaf msdp-active-source-limit-log-interval {
         type uint32;
       }
       leaf msdp-keepalives-sent {
         type int32;
       }
       leaf msdp-keepalives-received {
         type int32;
       }
       leaf msdp-unknowns-received {
         type int32;
       }
       leaf msdp-sa-zero-entry-received {
         type uint32;
       }
       leaf msdp-errors-received {
         type int32;
       }
     }
   }
 }
 grouping msdp-source-information-block {
   list msdp-instance {
     leaf instance-name {
       type string;
     }
     leaf msdp-no-source {
       type ipaddr;
     }
     list msdp-route {
       leaf multicast-group-address {
         type ipaddr;
         description "Group address";
       }
       leaf multicast-source-address {
         type ipaddr;
         description "Source address";
       }
       list msdp-route-peer {
         leaf msdp-peer-address {
           type ipaddr;
         }
         leaf msdp-originator {
           type ipaddr;
         }
         container msdp-route-peer-flags {
         }
       }
     }
     list msdp-source {
       leaf msdp-source-prefix {
         type ipaddr;
       }
       leaf msdp-source-prefix-length {
         type uint32;
       }
       leaf msdp-source-type {
         type string;
       }
       leaf msdp-source-limit-maximum {
         type string;
       }
       leaf msdp-source-limit-threshold {
         type string;
       }
       leaf msdp-source-limit-exceeded {
         type int32;
       }
       leaf msdp-source-limit-log-warning {
         type string;
       }
       leaf msdp-source-limit-log-interval {
         type string;
       }
     }
     list msdp-peer-statistics {
       leaf msdp-peer-address {
         type ipaddr;
       }
       leaf msdp-state-change-absolute {
         type string;
       }
       leaf msdp-state-change {
         type string;
       }
       leaf msdp-message-received-absolute {
         type string;
       }
       leaf msdp-message-received {
         type string;
       }
       leaf msdp-rpf-failures {
         type int32;
       }
       leaf msdp-remote-closes {
         type int32;
       }
       leaf msdp-peer-timeouts {
         type int32;
       }
       leaf msdp-sa-messages-sent {
         type int32;
       }
       leaf msdp-sa-messages-received {
         type int32;
       }
       leaf msdp-sa-requests-sent {
         type int32;
       }
       leaf msdp-sa-requests-received {
         type int32;
       }
       leaf msdp-sa-responses-sent {
         type int32;
       }
       leaf msdp-sa-responses-received {
         type int32;
       }
       leaf msdp-active-source-limit-exceeded {
         type int32;
       }
       leaf msdp-active-source-limit-maximum {
         type uint32;
       }
       leaf msdp-active-source-limit-threshold {
         type uint32;
       }
       leaf msdp-active-source-limit-log-warning {
         type uint32;
       }
       leaf msdp-active-source-limit-log-interval {
         type uint32;
       }
       leaf msdp-keepalives-sent {
         type int32;
       }
       leaf msdp-keepalives-received {
         type int32;
       }
       leaf msdp-unknowns-received {
         type int32;
       }
       leaf msdp-sa-zero-entry-received {
         type uint32;
       }
       leaf msdp-errors-received {
         type int32;
       }
     }
   }
 }
 grouping msdp-source-active-information-block {
   list msdp-instance {
     leaf instance-name {
       type string;
     }
     leaf msdp-no-routes {
       type ipaddr;
     }
     leaf msdp-global-active-source-limit-exceeded {
       type int32;
     }
     leaf msdp-global-active-source-limit-maximum {
       type uint32;
     }
     leaf msdp-global-active-source-limit-threshold {
       type uint32;
     }
     leaf msdp-global-active-source-limit-log-warning {
       type uint32;
     }
     leaf msdp-global-active-source-limit-log-interval {
       type uint32;
     }
     list msdp-route {
       leaf multicast-group-address {
         type ipaddr;
         description "Group address";
       }
       leaf multicast-source-address {
         type ipaddr;
         description "Source address";
       }
       list msdp-route-peer {
         leaf msdp-peer-address {
           type ipaddr;
         }
         leaf msdp-originator {
           type ipaddr;
         }
         container msdp-route-peer-flags {
         }
       }
     }
     list msdp-source {
       leaf msdp-source-prefix {
         type ipaddr;
       }
       leaf msdp-source-prefix-length {
         type uint32;
       }
       leaf msdp-source-type {
         type string;
       }
       leaf msdp-source-limit-maximum {
         type string;
       }
       leaf msdp-source-limit-threshold {
         type string;
       }
       leaf msdp-source-limit-exceeded {
         type int32;
       }
       leaf msdp-source-limit-log-warning {
         type string;
       }
       leaf msdp-source-limit-log-interval {
         type string;
       }
     }
     list msdp-peer-statistics {
       leaf msdp-peer-address {
         type ipaddr;
       }
       leaf msdp-state-change-absolute {
         type string;
       }
       leaf msdp-state-change {
         type string;
       }
       leaf msdp-message-received-absolute {
         type string;
       }
       leaf msdp-message-received {
         type string;
       }
       leaf msdp-rpf-failures {
         type int32;
       }
       leaf msdp-remote-closes {
         type int32;
       }
       leaf msdp-peer-timeouts {
         type int32;
       }
       leaf msdp-sa-messages-sent {
         type int32;
       }
       leaf msdp-sa-messages-received {
         type int32;
       }
       leaf msdp-sa-requests-sent {
         type int32;
       }
       leaf msdp-sa-requests-received {
         type int32;
       }
       leaf msdp-sa-responses-sent {
         type int32;
       }
       leaf msdp-sa-responses-received {
         type int32;
       }
       leaf msdp-active-source-limit-exceeded {
         type int32;
       }
       leaf msdp-active-source-limit-maximum {
         type uint32;
       }
       leaf msdp-active-source-limit-threshold {
         type uint32;
       }
       leaf msdp-active-source-limit-log-warning {
         type uint32;
       }
       leaf msdp-active-source-limit-log-interval {
         type uint32;
       }
       leaf msdp-keepalives-sent {
         type int32;
       }
       leaf msdp-keepalives-received {
         type int32;
       }
       leaf msdp-unknowns-received {
         type int32;
       }
       leaf msdp-sa-zero-entry-received {
         type uint32;
       }
       leaf msdp-errors-received {
         type int32;
       }
     }
   }
 }
 }
