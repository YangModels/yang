/*
 * Copyright (c) 2017 Juniper Networks, Inc.
 * All rights reserved.
 */
 module show-performance-monitoring {
  namespace "http://yang.juniper.net/yang/1.1/jrpc/show-performance-monitoring/junos-es/17.2R1.13";
  prefix show-performance-monitoring;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-pm-mpls-lsp-information {
     input {
       leaf level {
         default "brief";
         type enumeration {
           enum "brief" {
             description "Display brief output (default)";
           }
           enum "detail" {
             description "Display detailed output";
           }
           enum "extensive" {
             description "Display extensive output";
           }
         }
       }
       leaf regex {
         description "Regular expression for LSP names to match";
         type string;
       }
     }
     output {
       container performance-monitor-mpls-lsp-information {
         uses performance-monitor-mpls-lsp-information-block;
       }
     }
   }
 grouping performance-monitor-mpls-lsp-information-block {
   leaf performance-monitor-lsp-name {
     type string;
     description "Name of MPLS LSP";
   }
   leaf performance-monitor-session-state {
     type string;
     description "State of PM session";
   }
   container loss-measurement-information {
     leaf duration {
       type string;
       description "Time since loss measurement data is being collected";
     }
     leaf pm-traffic-class {
       type string;
       description "Traffic class of the loss measurement session";
     }
     leaf queries-sent {
       type uint32;
       description "Number of loss measurement queries sent";
     }
     leaf responses-received {
       type uint32;
       description "Number of loss measurement responses received";
     }
     leaf responses-errored {
       type uint32;
       description "Number of error loss measurement responses";
     }
     leaf queries-timedout {
       type uint32;
       description "Number of queries time out";
     }
     container forward-loss-measurement-information {
       leaf average-packet-loss {
         type uint64;
         description "Average packet loss over time";
       }
       leaf average-packet-throughput {
         type string;
         description "Average packet throughput over time";
       }
       leaf average-octet-loss {
         type uint64;
         description "Average octet loss over time";
       }
       leaf average-octet-throughput {
         type string;
         description "Average octet throughput over time";
       }
       container packet-loss-information {
         description "Packet loss measurement samples";
         leaf packet-loss {
           type uint64;
           description "Packet loss measurement value";
         }
       }
       container packet-throughput-information {
         description "Packet throughput measurement samples";
         leaf packet-throughput {
           type string;
           description "Packet throughput measurement value";
         }
       }
       container octet-loss-information {
         description "Octet loss measurement samples";
         leaf octet-loss {
           type uint64;
           description "Octet loss measurement value";
         }
       }
       container octet-throughput-information {
         description "Octet throughput measurement samples";
         leaf octet-throughput {
           type string;
           description "Octet througput measurement value";
         }
       }
     }
     container reverse-loss-measurement-information {
       leaf average-packet-loss {
         type uint64;
         description "Average packet loss over time";
       }
       leaf average-packet-throughput {
         type string;
         description "Average packet throughput over time";
       }
       leaf average-octet-loss {
         type uint64;
         description "Average octet loss over time";
       }
       leaf average-octet-throughput {
         type string;
         description "Average octet throughput over time";
       }
       container packet-loss-information {
         description "Packet loss measurement samples";
         leaf packet-loss {
           type uint64;
           description "Packet loss measurement value";
         }
       }
       container packet-throughput-information {
         description "Packet throughput measurement samples";
         leaf packet-throughput {
           type string;
           description "Packet throughput measurement value";
         }
       }
       container octet-loss-information {
         description "Octet loss measurement samples";
         leaf octet-loss {
           type uint64;
           description "Octet loss measurement value";
         }
       }
       container octet-throughput-information {
         description "Octet throughput measurement samples";
         leaf octet-throughput {
           type string;
           description "Octet througput measurement value";
         }
       }
     }
   }
   container delay-measurement-information {
     leaf duration {
       type string;
       description "Time since loss measurement data is being collected";
     }
     leaf pm-traffic-class {
       type string;
       description "Traffic class of the loss measurement session";
     }
     leaf queries-sent {
       type uint32;
       description "Number of loss measurement queries sent";
     }
     leaf responses-received {
       type uint32;
       description "Number of loss measurement responses received";
     }
     leaf responses-errored {
       type uint32;
       description "Number of error loss measurement responses";
     }
     leaf queries-timedout {
       type uint32;
       description "Number of queries time out";
     }
     leaf best-two-way-channel-delay {
       type string;
       description "Best two way channel delay";
     }
     leaf worst-two-way-channel-delay {
       type string;
       description "Worst two way channel delay";
     }
     leaf best-round-trip-time {
       type string;
       description "Best round trip time";
     }
     leaf worst-round-trip-time {
       type string;
       description "Worst round trip time";
     }
     leaf average-absolute-forward-delay-variation {
       type string;
       description "Average absolute forward inter packet delay variation";
     }
     leaf average-absolute-reverse-delay-variation {
       type string;
       description "Average absolute reverse inter packet delay variation";
     }
     container two-way-channel-delay-information {
       description "Two-way delay";
       leaf two-way-channel-delay {
         type string;
         description "Two way channel delay";
       }
     }
     container two-way-round-trip-time-information {
       description "Two-way round-trip time";
       leaf two-way-round-trip-time {
         type string;
         description "Two way round trip time";
       }
     }
   }
 }
 }
