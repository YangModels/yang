/*
 * Copyright (c) 2017 Juniper Networks, Inc.
 * All rights reserved.
 */
 module show-helper {
  namespace "http://yang.juniper.net/yang/1.1/jrpc/show-helper/junos-es/17.2R1.13";
  prefix show-helper;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-helper-statistics-information {
     description "Show helper statistics";
     output {
       container helper-statistics-information {
         uses helper-statistics-information-block;
       }
     }
   }
 grouping helper-statistics-information-block {
   list helper-statistics-service-information {
     description "Port forwarding helper statistics for a particular service";
     leaf service-name {
       type string;
       description "Name of this service";
     }
     leaf received-packets {
       type int32;
       description "Number of packets received";
     }
     leaf forwarded-packets {
       type int32;
       description "Number of packets forwarded";
     }
     leaf dropped-packets {
       type int32;
       description "Number of packets dropped";
     }
     leaf dropped-packets-nointerface {
       type int32;
       description "Number of packets dropped because of no interface";
     }
     leaf dropped-packets-nortinst {
       type int32;
       description "Number of packets dropped because of no routing instance";
     }
     leaf dropped-packets-badread {
       type int32;
       description "Number of packets dropped because of an error during the packet read";
     }
     leaf dropped-packets-badsend {
       type int32;
       description "Number of packets dropped because of an error during the packet send";
     }
     leaf dropped-packets-badaddr {
       type int32;
       description "Number of packets dropped because of an invalid server address";
     }
     leaf dropped-packets-nolocaladdr {
       type int32;
       description "Number of packets dropped because of no valid local address";
     }
     leaf dropped-packets-noroute {
       type int32;
       description "Number of packets dropped because of no route to server/client";
     }
   }
 }
 }
