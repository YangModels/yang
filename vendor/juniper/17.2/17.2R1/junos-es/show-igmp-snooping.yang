/*
 * Copyright (c) 2017 Juniper Networks, Inc.
 * All rights reserved.
 */
 module show-igmp-snooping {
  namespace "http://yang.juniper.net/yang/1.1/jrpc/show-igmp-snooping/junos-es/17.2R1.13";
  prefix show-igmp-snooping;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-igmp-snooping-membership-information {
     description "Show igmp-snooping membership";
     input {
       leaf verbosity_level {
         default "brief";
         type enumeration {
           enum "brief" {
             description "Display brief output (default)";
           }
           enum "detail" {
             description "Display detailed output";
           }
         }
       }
       leaf vlan {
         description "Groups on specified VLAN";
         type string;
       }
       leaf interface {
         description "Groups with membership on interface";
         type interface-name;
       }
     }
   }
   rpc get-igmp-snooping-flow-information {
     description "Show igmp-snooping flows";
     input {
       leaf verbosity_level {
         default "brief";
         type enumeration {
           enum "brief" {
             description "Display brief output (default)";
           }
           enum "detail" {
             description "Display detailed output";
           }
         }
       }
     }
   }
   rpc get-igmp-snooping-vlan-information {
     description "VLAN information";
     input {
       leaf verbosity_level {
         default "brief";
         type enumeration {
           enum "brief" {
             description "Display brief output (default)";
           }
           enum "detail" {
             description "Display detailed output";
           }
         }
       }
       leaf vlan {
         description "VLAN name";
         type string;
       }
     }
   }
   rpc get-igmp-snooping-statistics-information {
     description "Show igmp-snooping statistics";
     input {
       leaf interface {
         description "Name of interface";
         type interface-name;
       }
       leaf vlan {
         description "Name of VLAN";
         type string;
       }
     }
   }
   rpc get-igmp-snooping-routing-information {
     description "Show routing information";
     input {
       leaf family {
         default "ethernet-switching";
         type enumeration {
           enum "ethernet-switching" {
             description "Ethernet-switching multicast routes";
           }
           enum "inet" {
             description "Family inet multicast routes";
           }
         }
       }
       leaf verbosity_level {
         default "brief";
         type enumeration {
           enum "brief" {
             description "Display brief output (default)";
           }
           enum "detail" {
             description "Display detailed output";
           }
         }
       }
       leaf vlan {
         description "Show entries for a specific VLAN";
         type string;
       }
     }
   }
   rpc get-igmp-snooping-task-information {
     description "Show IGMP snooping task information";
     input {
       leaf level {
         default "summary";
         type enumeration {
           enum "summary" {
             description "Display summary output (default)";
           }
         }
       }
     }
     output {
       container task-summary-information {
         uses task-summary-information-block;
       }
     }
   }
   rpc get-igmp-snooping-task-accounting {
     description "Per-task CPU accounting";
     input {
       leaf verbosity_level {
         default "brief";
         type enumeration {
           enum "brief" {
             description "Display brief output (default)";
           }
           enum "detail" {
             description "Display detailed output";
           }
         }
       }
     }
     output {
       container task-accounting-information {
         uses task-accounting-information-block;
       }
     }
   }
   rpc get-igmp-snooping-task-io {
     description "Show task I/O statistics";
     output {
       container task-io-information {
         uses task-io-information-block;
       }
     }
   }
   rpc get-igmp-snooping-task-jobs {
     description "Show scheduled jobs";
     output {
       container task-jobs-information {
         uses task-jobs-information-block;
       }
     }
   }
   rpc get-igmp-snooping-task-timers {
     description "Task timers";
     input {
       leaf level {
         default "brief";
         type enumeration {
           enum "brief" {
             description "Display brief output (default)";
           }
           enum "expired" {
             description "Display expired timers";
           }
           enum "detail" {
             description "Display timer detail";
           }
         }
       }
     }
     output {
       container task-timer-information {
         uses task-timer-information-block;
       }
     }
   }
   rpc get-igmp-snooping-task-statistics {
     description "Task statistics";
     output {
       container task-statistics-information {
         uses task-statistics-information-block;
       }
     }
   }
   rpc get-igmp-snooping-task-memory {
     description "Show memory utilization of IGMP snooping tasks";
     input {
       leaf level {
         type enumeration {
           enum "summary" {
             description "Display current and maximum memory usage";
           }
           enum "brief" {
             description "Display current/maximum/available memory";
           }
           enum "detail" {
             description "Display memory usage by individual users";
           }
           enum "history" {
             description "Display memory usage in the recent past";
           }
           enum "fragmentation" {
             description "Display memory allocator fragmentation";
           }
         }
       }
     }
     output {
       container task-memory-information {
         uses task-memory-information-block;
       }
     }
   }
 grouping task-summary-information-block {
   leaf task-summary-priority {
     type int32;
   }
   leaf task-summary-task-name {
     type string;
   }
   leaf task-summary-protocol {
     type string;
   }
   leaf task-summary-port {
     type string;
   }
   leaf task-summary-socket {
     type string;
   }
   leaf task-summary-flags {
     type string;
   }
 }
 grouping task-accounting-information-block {
   leaf task-acc-status {
     type string;
   }
   leaf task-acc-task-name {
     type string;
   }
   leaf task-acc-task-started {
     type int32;
   }
   leaf task-acc-task-user-time {
     type int32;
   }
   leaf task-acc-task-system-time {
     type int32;
   }
   leaf task-acc-task-longest-run {
     type int32;
   }
 }
 grouping task-io-information-block {
   leaf task-io-task-name {
     type string;
   }
   leaf task-io-read {
     type int32;
   }
   leaf task-io-write {
     type int32;
   }
   leaf task-io-received {
     type int32;
   }
   leaf task-io-sent {
     type int32;
   }
   leaf task-io-dropped {
     type int32;
   }
 }
 grouping task-jobs-information-block {
   leaf task-jobs-fg-priority {
     type int32;
   }
   leaf task-jobs-fg-task-name {
     type string;
   }
   leaf task-jobs-fg-wait {
     type int32;
   }
   leaf task-jobs-fg-flags {
     type string;
   }
   leaf task-jobs-bg-priority {
     type int32;
   }
   leaf task-jobs-bg-task-name {
     type string;
   }
   leaf task-jobs-bg-runs {
     type int32;
   }
   leaf task-jobs-bg-misses {
     type int32;
   }
   leaf task-jobs-bg-wait {
     type int32;
   }
   leaf task-jobs-bg-flags {
     type string;
   }
 }
 grouping task-timer-information-block {
   list task {
     list task-timer {
       leaf timer-name {
         type string;
         description "Timer name";
       }
       leaf timer-late {
         type empty;
         description "Timer is expired but is still running";
       }
       leaf timer-expires {
         type string;
         description "Time after which timer expires";
       }
       leaf timer-jitter {
         type string;
         description "Jitter, in percent";
       }
       leaf timer-interval {
         type string;
         description "Time to sleep between timer jobs";
       }
       leaf timer-flags {
         type string;
       }
     }
     container task-timer-priority {
       leaf task-timer-type {
         type string;
       }
     }
     container task-timer-summary {
       leaf task-timer-leaf {
         type int32;
       }
       leaf task-timer-parent {
         type int32;
       }
       leaf task-timer-expired {
         type int32;
       }
     }
   }
 }
 grouping task-statistics-information-block {
   leaf task-stat-event-name {
     type string;
   }
   leaf tast-stat-event-count {
     type int32;
   }
 }
 grouping task-memory-information-block {
   container summary {
     leaf task-memory-in-use-size {
       type int32;
     }
     leaf task-memory-in-use-avail {
       type string;
     }
     leaf task-memory-max-size {
       type int32;
     }
     leaf task-memory-max-avail {
       type string;
     }
     container task-memory-overall-report {
       container task-size-block-list {
       }
       container task-memory-stats-list {
       }
     }
     container task-memory-allocator-report {
       container task-block-list {
       }
       container task-lite-page-list {
       }
     }
     container task-memory-malloc-usage-report {
       container task-malloc-list {
       }
     }
   }
   container brief {
     leaf task-memory-in-use-size {
       type int32;
     }
     leaf task-memory-in-use-avail {
       type string;
     }
     leaf task-memory-max-size {
       type int32;
     }
     leaf task-memory-max-avail {
       type string;
     }
     leaf task-memory-max-when {
       type string;
     }
     leaf task-memory-free-size {
       type int32;
     }
     container task-memory-overall-report {
       container task-size-block-list {
       }
       container task-memory-stats-list {
       }
     }
     container task-memory-allocator-report {
       container task-block-list {
       }
       container task-lite-page-list {
       }
     }
     container task-memory-malloc-usage-report {
       container task-malloc-list {
       }
     }
   }
   container detail {
     leaf task-memory-dynamic-allocs {
       type string;
     }
     leaf task-memory-max-dynamic-allocs {
       type string;
     }
     leaf task-memory-bss-bytes {
       type string;
     }
     leaf task-memory-max-bss-bytes {
       type string;
     }
     leaf task-memory-page-data-bytes {
       type string;
     }
     leaf task-memory-max-page-data-bytes {
       type string;
     }
     leaf task-memory-dir-bytes {
       type string;
     }
     leaf task-memory-max-dir-bytes {
       type string;
     }
     leaf task-memory-total-bytes-in-use {
       type string;
     }
     leaf task-memory-total-bytes-percent {
       type string;
     }
     container task-memory-overall-report {
       leaf task-memory-total-bytes {
         type int32;
       }
       leaf task-memory-total-max-bytes {
         type int32;
       }
       leaf task-memory-total-free-bytes {
         type int32;
       }
       container task-size-block-list {
         list task-size-block {
           leaf tsb-size {
             type int32;
             description "Size of this block";
           }
           leaf tsb-terse-transient {
             type empty;
           }
           leaf tsb-terse-exclusive {
             type empty;
           }
           leaf tsb-terse-fullpage {
             type empty;
           }
           leaf tsb-allocs {
             type string;
             description "Number of items allocated now not using malloc";
           }
           leaf tsb-mallocs {
             type string;
             description "Number of items allocated using malloc";
           }
           leaf tsb-alloc-bytes {
             type string;
             description "Number of items allocated in bytes";
           }
           leaf tsb-max-allocs {
             type string;
             description "Maximum items ever allocated";
           }
           leaf tsb-max-bytes {
             type string;
             description "Maximum items ever allocated in bytes";
           }
           leaf tsb-free-bytes {
             type string;
             description "Number of free bytes";
           }
         }
       }
       container task-memory-stats-list {
         list task-memory-stats {
           leaf tms-name {
             type string;
           }
           leaf tms-allocs {
             type string;
             description "Number of items allocated";
           }
           leaf tms-mallocs {
             type string;
             description "Number of items allocated using malloc";
           }
           leaf tms-alloc-bytes {
             type string;
             description "Number of bytes now allocated";
           }
           leaf tms-max-allocs {
             type string;
             description "Maximum items ever allocated";
           }
           leaf tms-max-bytes {
             type string;
             description "Maximum bytes ever allocated";
           }
           leaf tms-free-bytes {
             type string;
           }
         }
       }
     }
     container task-memory-allocator-report {
       leaf task-memory-total-bytes {
         type int32;
       }
       leaf task-memory-total-max-bytes {
         type int32;
       }
       container task-block-list {
         list task-block {
           leaf tb-name {
             type string;
             description "Name for this block";
           }
           leaf tb-size {
             type int32;
             description "Actual size of this block";
           }
           leaf tb-alloc-size {
             type string;
             description "Allocated size for this block";
           }
           leaf tb-terse-debug {
             type empty;
           }
           leaf tb-terse-transient {
             type empty;
           }
           leaf tb-terse-exclusive {
             type empty;
           }
           leaf tb-terse-fullpage {
             type empty;
           }
           leaf tb-alloc-blocks {
             type string;
             description "Number of allocated structures";
           }
           leaf tb-alloc-bytes {
             type string;
             description "Number of allocated bytes";
           }
           leaf tb-max-alloc-blocks {
             type int32;
             description "Maximum number of structures ever allocated";
           }
           leaf tb-max-alloc-bytes {
             type int32;
             description "Maximum number of bytes ever allocated";
           }
         }
       }
       container task-lite-page-list {
         container task-lite-page {
           leaf tlp-name {
             type string;
             description "Name of this pool";
           }
           leaf tlp-alloc-pages {
             type string;
             description "Number of pages allocated";
           }
           leaf tlp-alloc-bytes {
             type string;
             description "Number of bytes allocated";
           }
           leaf tlp-max-alloc-pages {
             type string;
             description "Maximum pages ever allocated";
           }
           leaf tlp-max-alloc-bytes {
             type string;
             description "Maximum bytes ever allocated";
           }
         }
       }
     }
     container task-memory-malloc-usage-report {
       leaf task-memory-total-bytes {
         type int32;
       }
       leaf task-memory-total-max-bytes {
         type int32;
       }
       container task-malloc-list {
         container task-malloc {
           leaf tm-name {
             type string;
           }
           leaf tm-allocs {
             type string;
             description "Number of allocations out";
           }
           leaf tm-alloc-bytes {
             type string;
             description "Number of bytes allocated";
           }
           leaf tm-max-allocs {
             type string;
             description "Maximum allocations ever out";
           }
           leaf tm-max-alloc-bytes {
             type string;
             description "Maximum bytes allocated";
           }
           leaf tm-function-calls {
             type int32;
             description "Number of function calls";
           }
         }
       }
     }
   }
 }
 }
