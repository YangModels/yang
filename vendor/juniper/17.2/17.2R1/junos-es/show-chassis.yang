/*
 * Copyright (c) 2017 Juniper Networks, Inc.
 * All rights reserved.
 */
 module show-chassis {
  namespace "http://yang.juniper.net/yang/1.1/jrpc/show-chassis/junos-es/17.2R1.13";
  prefix show-chassis;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-power-usage-information {
     description "Show Chassis Power Usages";
     output {
       container power-usage-information {
         uses power-usage-information-block;
       }
     }
   }
   rpc get-fru-power-on-sequence {
     description "Show chassis fru power on sequence";
     output {
       container fru-power-on-sequence {
         uses fru-power-on-sequence-block;
       }
     }
   }
   rpc get-alarm-information {
     description "Show alarm status";
     output {
       container alarm-information {
         uses alarm-information-block;
       }
     }
   }
   rpc get-chassis-beacon-information {
     description "Show beacon status";
     input {
       container which-arg {
         choice which-arg_c {
           case all {
             leaf all {
               description "Beacons in ON/OFF state";
               type enumeration {
                 enum "off" {
                   description "Beacons in OFF state";
                 }
                 enum "on" {
                   description "Beacons in ON state";
                 }
               }
             }
           }
           case fpc {
             leaf fpc {
               description "Flexible PIC Controller slot number";
               type uint32 {
                 range "0 .. 63";
               }
             }
           }
           case cb {
           }
           case service-node {
           }
         }
       }
       container port-num {
         choice port-num_c {
           case port {
           }
           case port-range {
           }
         }
       }
       leaf lower-limit {
         description "Port range lower limit";
         type uint32 {
           range "0 .. 127";
         }
       }
       leaf upper-limit {
         description "Port range upper limit";
         type uint32 {
           range "0 .. 127";
         }
       }
     }
     output {
       container chassis-beacon-information {
         uses chassis-beacon-information-block;
       }
     }
   }
   rpc network-services {
     description "Show chassis network services";
     output {
       container network-services {
         uses network-services-block;
       }
     }
   }
   rpc get-craft-information {
     description "Show craft interface status";
     output {
       container craft-information {
         uses craft-information-block;
       }
     }
   }
   rpc get-ethernet-switch-information {
     description "Show Ethernet switch information";
   }
   rpc get-ioc-npc-connectivity-information {
     description "Show connectivity between IOC and NPC";
     output {
       container ioc-npc-connectivity {
         uses ioc-npc-connectivity-block;
       }
     }
   }
   rpc get-environment-information {
     description "Show component status and temperature, cooling system speeds";
     output {
       container environment-information {
         uses environment-information-block;
       }
     }
   }
   rpc get-environment-fpc-information {
     description "Show Flexible PIC Concentrator information";
     input {
       leaf fpc-slot {
         description "FPC slot number";
         type uint32 {
           range "0 .. 63";
         }
       }
     }
     output {
       container environment-component-information {
         uses environment-component-information-block;
       }
     }
   }
   rpc get-environment-fpm-information {
     description "Show craft interface information";
     output {
       container environment-component-information {
         uses environment-component-information-block;
       }
     }
   }
   rpc get-environment-cb-information {
     description "Show Control Board information";
     input {
       leaf slot {
         description "CB slot number";
         type uint32 {
           range "0 .. 2";
         }
       }
     }
     output {
       container environment-component-information {
         uses environment-component-information-block;
       }
     }
   }
   rpc get-environment-pem-information {
     description "Show Power Entry Module information";
     input {
       leaf slot {
         description "PEM slot number";
         type uint32 {
           range "0 .. 63";
         }
       }
     }
     output {
       container environment-component-information {
         uses environment-component-information-block;
       }
     }
   }
   rpc get-environment-re-information {
     description "Show Routing Engine information";
     input {
       leaf slot {
         description "Routing Engine slot number";
         type uint32 {
           range "0 .. 32";
         }
       }
     }
     output {
       container environment-component-information {
         uses environment-component-information-block;
       }
     }
   }
   rpc get-firmware-information {
     description "Show firmware and operating system version for components";
     output {
       container firmware-information {
         uses firmware-information-block;
       }
     }
   }
   rpc get-usb-storage-status {
     description "Show USB storage status";
   }
   rpc get-fpc-information {
     description "Show Flexible PIC Concentrator status";
     input {
       leaf detail {
         description "Display detailed output";
         type empty;
       }
       leaf fpc-slot {
         description "FPC slot number";
         type uint32 {
           range "0 .. 63";
         }
       }
     }
     output {
       container fpc-information {
         uses fpc-information-block;
       }
     }
   }
   rpc get-pic-information {
     description "Show Physical Interface Cards installed in FPC";
     input {
       leaf slot {
         description "FPC slot number";
         type uint32 {
           range "0 .. 63";
         }
       }
     }
     output {
       container fpc-information {
         uses fpc-information-block;
       }
     }
   }
   rpc get-fpc-port-information {
     description "Show Port status installed in FPC";
     input {
       leaf slot {
         description "FPC slot number";
         type uint32 {
           range "0 .. 63";
         }
       }
     }
     output {
       container fpc-port-information {
         uses fpc-port-information-block;
       }
     }
   }
   rpc get-fpc-error-information {
     description "Show ASIC errors on all the FPC's";
     output {
       container fpc-error-information {
         uses fpc-error-information-block;
       }
     }
   }
   rpc get-pic-detail {
     description "Show Physical Interface Card state, type, and uptime";
     input {
       leaf fpc-slot {
         description "Slot number of FPC that houses PIC";
         type uint32 {
           range "0 .. 63";
         }
       }
       leaf pic-slot {
         description "PIC slot number";
         type int32 {
           range "0 .. 3";
         }
         mandatory true;
       }
     }
     output {
       container fpc-information {
         uses fpc-information-block;
       }
     }
   }
   rpc get-fm-fpc-state-information {
     description "Show summary fabric management FPC state from Routing Engine";
     output {
       container fm-fpc-state-information {
         uses fm-fpc-state-information-block;
       }
     }
   }
   rpc get-fm-degradation-information {
     description "Show FPC fabric bandwidth degradation information";
   }
   rpc get-fm-degradation-information-details {
     description "Show fpc fabric degradation action history";
   }
   rpc get-fm-fabric-destinations-state {
     description "Show fabric destinations state for all FPCs";
     input {
       leaf fpc {
         description "FPC slot number";
         type uint32 {
           range "0 .. 63";
         }
       }
     }
     output {
       container fm-fabric-destinations-state {
         uses fm-fabric-destinations-state-block;
       }
     }
   }
   rpc get-fm-plane-location-information {
     description "Show fabric plane location";
     output {
       container fm-plane-location-information {
         uses fm-plane-location-information-block;
       }
     }
   }
   rpc get-fm-topology {
     description "Show fabric topology for plane";
     input {
       leaf plane {
         description "Fabric plane number";
         type uint32 {
           range "0 .. 21";
         }
       }
     }
     output {
       container fm-topology {
         uses fm-topology-block;
       }
     }
   }
   rpc get-fm-plane-state-information {
     description "Show state of fabric management plane";
     input {
       leaf display {
         type enumeration {
           enum "terse" {
             description "Show terse output";
           }
           enum "detail" {
             description "Show detail output";
           }
           enum "extensive" {
             description "Show extensive output";
           }
         }
       }
       leaf number {
         description "Fabric plane number";
         type uint32 {
           range "0 .. 4";
         }
       }
     }
     output {
       container fm-plane-state-information {
         uses fm-plane-state-information-block;
       }
     }
   }
   rpc get-fm-state-information {
     description "Show summary fabric management state";
     output {
       container fm-state-information {
         uses fm-state-information-block;
       }
     }
   }
   rpc get-fm-ext-state-information {
     description "Show extended summary fabric management state";
     output {
       container fm-ext-state-information {
         uses fm-ext-state-information-block;
       }
     }
   }
   rpc get-fm-fabric-reachability-information {
     description "Show current status of fabric reachability";
     input {
       leaf detail {
         description "Show reachability output in detail";
         type empty;
       }
     }
     output {
       container fm-fabric-reachability-information {
         uses fm-fabric-reachability-information-block;
       }
     }
   }
   rpc get-chassis-inventory {
     description "Show installed hardware components";
     input {
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
     output {
       container chassis-inventory {
         uses chassis-inventory-block;
       }
     }
   }
   rpc get-chassis-mac-addresses {
     description "Show media access control addresses";
     output {
       container chassis-mac-addresses {
         uses chassis-mac-addresses-block;
       }
     }
   }
   rpc get-route-engine-information {
     description "Show Routing Engine status";
     input {
       leaf slot {
         description "Routing Engine slot number";
         type uint32 {
           range "0 .. 32";
         }
       }
     }
     output {
       container route-engine-information {
         uses route-engine-information-block;
       }
     }
   }
   rpc get-bios-version-information {
     description "Show BIOS firmware version";
   }
   rpc get-chassis-routing-engine-errors {
     description "Show re errors";
   }
   rpc get-fwdd-information {
     description "Show forwarding process (fwdd) status";
     output {
       container scb-information {
         uses scb-information-block;
       }
     }
   }
   rpc get-tfeb-information {
     description "Show Compact Forwarding Engine Board status";
     output {
       container scb-information {
         uses scb-information-block;
       }
     }
   }
   rpc get-chassis-location {
     description "Show physical location of chassis";
     output {
       container chassis-location {
         uses chassis-location-block;
       }
     }
   }
   rpc get-temperature-threshold-information {
     description "Show chassis temperature threshold settings";
     output {
       container temperature-threshold-information {
         uses temperature-threshold-information-block;
       }
     }
   }
   rpc get-power-management {
     description "Show power ratings for the router";
     output {
       container power-management-information {
         uses power-management-information-block;
       }
     }
   }
   rpc get-chassis-oss-map {
     description "Show Operation Supported System's translated model";
     output {
       container chassis-oss-map {
         uses chassis-oss-map-block;
       }
     }
   }
   rpc get-chassis-cluster-interfaces {
     description "Display chassis cluster interfaces";
   }
   rpc get-chassis-cluster-control-plane-statistics {
     description "Display control-plane statistics";
   }
   rpc get-chassis-cluster-data-plane-statistics {
     description "Display data-plane statistics";
   }
   rpc get-chassis-cluster-data-plane-interfaces {
     description "Display data-plane interfaces";
   }
   rpc get-chassis-cluster-statistics {
     description "Display chassis cluster statistics";
   }
   rpc get-chassis-cluster-status {
     description "Display chassis cluster status";
     input {
       leaf redundancy-group {
         description "Display chassis cluster status per redundancy-group";
         type uint8 {
           range "0 .. 128";
         }
       }
     }
   }
   rpc get-chassis-cluster-information {
     description "Show chassis cluster information";
   }
   rpc get-chassis-cluster-configuration-synchronization-information {
     description "Display configuration synchronization information";
   }
   rpc get-chassis-cluster-issu-information {
     description "Display ISSU information";
   }
   rpc get-chassis-cluster-ip-monitoring-status {
     description "Display IP monitoring status";
   }
   rpc get-chassis-cluster-ip-monitoring-status-redundancy-group {
     description "Show IP monitoring status of a specific redundancy-group";
     input {
       leaf redundancy-group-identifier {
         description "Redundancy-group identifier";
         type uint8 {
           range "0 .. 128";
         }
         mandatory true;
       }
     }
   }
   rpc get-chassis-cluster-ethernet-switching-status {
     description "Display chassis cluster ethernet switching status";
   }
   rpc get-chassis-cluster-switch-fabric-probe-statistics {
     description "Display chassis cluster switch fabric probe statistics";
   }
   rpc get-chassis-cluster-switch-fabric-link-interfaces {
     description "Display chassis cluster switch fabric link interfaces";
   }
 grouping power-usage-information-block {
   container power-usage-item {
     leaf name {
       type string;
       description "Name of this component";
     }
     leaf status {
       type string;
       description "Status of clock synchronization source";
     }
     leaf state {
       type string;
       description "Status of the component";
     }
     container ac-input-detail {
       leaf ac-input {
         type string;
         description "AC input state";
       }
       leaf ac-expect-feed {
         type uint32;
         description "Expect power input feed";
       }
       leaf ac-actual-feed {
         type uint32;
         description "Actual power input feed";
       }
     }
     container ac-input-detail2 {
       leaf ac-input_status {
         type string;
         description "AC input status";
       }
       leaf str-ac-expect-feed {
         type string;
         description "Expect power input feed";
       }
       leaf str-ac-actual-feed {
         type string;
         description "Actual power input feed";
       }
     }
     container dc-input-detail {
       leaf dc-input {
         type string;
         description "DC input state";
       }
       leaf dc-expect-feed {
         type uint32;
         description "Expect power input feed";
       }
       leaf dc-actual-feed {
         type uint32;
         description "Actual power input feed";
       }
       leaf reference-voltage {
         type string;
         description "Voltage of the item in Volts";
       }
       leaf actual-voltage {
         type int32;
         description "Voltage of the item in mVlots";
       }
     }
     container dc-input-detail2 {
       leaf dc-input-status {
         type string;
         description "DC input status";
       }
       leaf str-dc-expect-feed {
         type string;
         description "Expect power input feed";
       }
       leaf str-dc-actual-feed {
         type string;
         description "Actual power input feed";
       }
     }
     container dc-output-detail {
       leaf dc-power {
         type uint32;
       }
       leaf zone {
         type uint32;
         description "Power zone";
       }
       leaf dc-current {
         type uint32;
       }
       leaf dc-voltage {
         type uint32;
       }
       leaf dc-load {
         type uint32;
       }
     }
     container dc-output-detail2 {
       leaf str-dc-power {
         type string;
       }
       leaf str-zone {
         type string;
         description "Power zone";
       }
       leaf str-dc-current {
         type string;
       }
       leaf str-dc-voltage {
         type string;
       }
       leaf str-dc-load {
         type string;
       }
     }
     container dc-output-detail3 {
       leaf str2-dc-power {
         type string;
       }
       leaf str2-dc-current {
         type string;
       }
       leaf str2-dc-voltage {
         type string;
       }
       leaf str2-dc-load {
         type string;
       }
     }
     container pem-capacity-detail {
       leaf capacity-actual {
         type uint32;
         description "Actual capacity in volt";
       }
       leaf capacity-max {
         type uint32;
         description "Maximum capacity in volt";
       }
     }
   }
   container power-usage-system {
     leaf capacity-res-power {
       type uint32;
     }
     leaf capacity-sys-actual {
       type uint32;
     }
     leaf capacity-sys-max {
       type uint32;
     }
     leaf capacity-sys-remaining {
       type uint32;
     }
     container power-usage-zone-information {
       leaf zone {
         type uint32;
         description "Power zone";
       }
       leaf str-zone {
         type string;
         description "Power zone";
       }
       leaf capacity-actual {
         type uint32;
         description "Actual capacity in volt";
       }
       leaf capacity-max {
         type uint32;
         description "Maximum capacity in volt";
       }
       leaf capacity-allocated {
         type uint32;
         description "Allocated capacity in volt";
       }
       leaf capacity-remaining {
         type uint32;
         description "Remaining capacity in volt";
       }
       leaf capacity-actual-usage {
         type uint32;
         description "Actual usage in volt";
       }
     }
   }
   container power-usage-system2 {
     container power-usage-zone-information2 {
       leaf capacity-actual {
         type uint32;
         description "Actual capacity in volt";
       }
       leaf capacity-max {
         type uint32;
         description "Maximum capacity in volt";
       }
       leaf capacity-allocated {
         type uint32;
         description "Allocated capacity in volt";
       }
       leaf capacity-remaining {
         type uint32;
         description "Remaining capacity in volt";
       }
       leaf capacity-actual-usage {
         type uint32;
         description "Actual usage in volt";
       }
     }
   }
   container power-usage-total {
     leaf dc-power {
       type uint32;
     }
   }
   container power-usage-voltage-total {
     leaf dc-power {
       type uint32;
     }
   }
   container power-usage-pdu-item {
     leaf slot {
       type int32;
     }
     leaf dc-power {
       type uint32;
     }
     container power-usage-psm-item {
       container power-usage-psm-input {
         leaf name {
           type string;
           description "Name of this component";
         }
         leaf dc-voltage {
           type uint32;
         }
       }
     }
   }
   container power-usage-psm-item1 {
     leaf slot {
       type int32;
     }
     container power-usage-psm-input1 {
       leaf name {
         type string;
         description "Name of this component";
       }
       leaf dc-voltage {
         type uint32;
       }
       leaf dc-power {
         type uint32;
       }
     }
   }
   container power-usage-fru-item {
     leaf name {
       type string;
       description "Name of this component";
     }
     leaf dc-power {
       type uint32;
     }
   }
 }
 grouping fru-power-on-sequence-block {
   leaf sequence {
     type string;
   }
 }
 grouping alarm-information-block {
   container alarm-summary {
     description "Number of alarms currently active";
     leaf active-alarm-count {
       type int32;
       description "Number of active alarms";
     }
     leaf no-active-alarms {
       type empty;
       description "No active alarms";
     }
     container satellite {
       description "Number of alarms currently active";
       leaf active-fpc-slot {
         type int32;
         description "FPC slot with active alarms";
       }
     }
   }
   list alarm-detail {
     description "Detailed information about an active alarm";
     leaf alarm-time {
       type string;
       description "Time of the alarm";
     }
     leaf alarm-class {
       type string;
       description "Class of the alarm";
     }
     leaf alarm-description {
       type string;
       description "Description of the alarm";
     }
   }
 }
 grouping chassis-beacon-information-block {
   container chassis-beacon-item {
     leaf beacon-name {
       type string;
     }
     leaf beacon-state {
       type string;
     }
   }
 }
 grouping network-services-block {
   container network-services-information {
     leaf name {
       type string;
       description "Name of this component";
     }
   }
 }
 grouping craft-information-block {
   leaf output {
     type string;
     description "Formatted ASCII output displayed by the CLI";
   }
   container front-panel {
     description "Information from the craft interface";
     container display-panel {
       description "Text currently appearing on the craft interface display";
     }
     container re-panel {
       description "State of status LEDs on the craft interface for one or more Routing Engines. The front panel of each Routing Engine has the same LEDs.";
       container re {
         description "State of status LEDs on the craft interface for a Routing Engine. The front panel of the Routing Engine has the same LEDs.";
       }
     }
     container alarm-indicators {
       description "Information about alarms from the craft interface";
     }
     container fpc-panel {
       description "State of status LEDs on the craft interface for Flexible PIC Concentrators";
       list fpc {
         container pic-detail {
           container port-information {
           }
           container package-information {
             container package {
             }
           }
           container port-speed-information {
           }
         }
       }
     }
     container sib-panel {
       description "State of the status LEDs on the faceplate of one or more Switch Interface Boards. Some of the LEDs also appear on the craft interface.";
       container sib {
       }
     }
     container ccg-panel {
       description "State of the status LEDs on the faceplate of one or more SONET ClockGenerators";
       container ccg {
         description "State of the CCG status LEDs on the craft interface";
       }
     }
     container fan-tray-panel {
       description "State of status LEDs on the craft interface for Fan Trays";
       container fan-tray {
         description "State of the status LEDs on the craft interface for a fan tray";
       }
     }
     container power-supply-panel {
       description "State of the status LEDs on the faceplate of one or more power supplies";
       container power-supply {
         description "State of the status LEDs on the faceplate of a power supply";
       }
       container pdu {
         description "State of the PDU status LEDs on the craft interface";
         container psm {
           description "State of the PSM status LEDs on the craft interface";
         }
       }
     }
   }
   container recb-panel {
     description "Information about LEDs from the craft interface";
     container ha-led {
       description "State of the HA LED on the craft interface";
     }
     container rps-led {
       description "State of the RPS LED on the craft interface";
     }
     container mpim1-led {
       description "State of the MPIM1 LED on the craft interface";
     }
     container mpim2-led {
       description "State of the MPIM2 LED on the craft interface";
     }
     container storage-led {
       description "State of the external storage LED on the craft interface";
     }
     container sfb-led {
       description "State of the SFB LED on the craft interface";
     }
     container cfm-ok-fail-led {
       description "State of the CFM Ok/Fail LED on the craft interface";
     }
     container cfm-service-led {
       description "State of the CFM Service LED on the craft interface";
     }
     container sysio-status-led {
       description "State of the SYSIO Status LED on the craft interface";
     }
   }
   container mcs-panel {
     description "State of the status LEDs on the faceplate of one or more Miscellaneous Control Subsystems";
     container mcs {
       description "State of the status LEDs on the faceplate of a Miscellaneous Control Subsystem";
     }
   }
   container sfm-panel {
     description "State of the status LEDs on the faceplate of one or more Switching and Forwarding Modules";
     container sfm {
       description "State of the status LEDs on the faceplate of a Switching andForwarding Module";
     }
   }
   container pcg-panel {
     description "State of the status LEDs on the faceplate of one or more Packet Forwarding Engine Clock Generators";
     container pcg {
       description "State of the status LEDs on the faceplate of a Packet Forwarding Engine Clock Generator";
     }
   }
   container cb-panel {
     description "State of status LEDs on one or more Control Boards";
     container cb {
       description "State of status LEDs on a Control Board";
     }
   }
   container sib-panel {
     description "State of the status LEDs on the faceplate of one or more Switch Interface Boards. Some of the LEDs also appear on the craft interface.";
     container sib {
     }
   }
   container scg-panel {
     description "State of the status LEDs on the faceplate of one or more SONET ClockGenerators";
     container scg {
       description "State of the status LEDs on the faceplate of a SONET Clock Generator";
     }
   }
   container feb-panel {
     description "State of the status LEDs on the faceplate of one or more Forwarding Engine Boards";
     container feb {
       description "State of the status LEDs on the faceplate of a Forwarding Engine Board";
     }
   }
   container power-supply-panel {
     description "State of the status LEDs on the faceplate of one or more power supplies";
     container power-supply {
       description "State of the status LEDs on the faceplate of a power supply";
     }
     container pdu {
       description "State of the PDU status LEDs on the craft interface";
       container psm {
         description "State of the PSM status LEDs on the craft interface";
       }
     }
   }
   container fan-tray-panel {
     description "State of status LEDs on the craft interface for Fan Trays";
     container fan-tray {
       description "State of the status LEDs on the craft interface for a fan tray";
     }
   }
 }
 grouping ioc-npc-connectivity-block {
   list ioc-npc-connectivity-item {
     description "NPC connectivity information for an IOC";
     leaf ioc-slot {
       type int32;
     }
     leaf ioc-type {
       type string;
       description "IOC type";
     }
     leaf ioc-state {
       type string;
       description "IOC state";
     }
     leaf npc-slot {
       type int32;
     }
     leaf no-npc-slot {
       type empty;
     }
     leaf npc-state {
       type string;
     }
     leaf fpc-link-status {
       type string;
       description "FPC link status";
     }
   }
 }
 grouping environment-information-block {
   list environment-item {
     leaf class {
       type string;
     }
     leaf name {
       type string;
       description "Name of this component";
     }
     leaf status {
       type string;
       description "Status of clock synchronization source";
     }
     leaf temperature {
       type string;
       description "Temperature of the item";
     }
     leaf comment {
       type string;
     }
   }
 }
 grouping environment-component-information-block {
   list environment-component-item {
     description "Chassis environment component";
     leaf name {
       type string;
       description "Name of this component";
     }
     leaf state {
       type string;
       description "Status of the component";
     }
     leaf bus-revision {
       type int32;
       description "Bus revision";
     }
     leaf cmb-revision {
       type int32;
       description "CMB revision";
     }
     leaf fpga-revision {
       type int32;
       description "FPGA revision";
     }
     leaf ac-feed0-voltage {
       type string;
       description "AC feed0 voltage";
     }
     leaf ac-feed0-current {
       type string;
       description "AC feed0 current";
     }
     leaf ac-feed0-power {
       type string;
       description "AC feed0 power";
     }
     leaf ac-feed1-voltage {
       type string;
       description "AC feed1 voltage";
     }
     leaf ac-feed1-current {
       type string;
       description "AC feed1 current";
     }
     leaf ac-feed1-power {
       type string;
       description "AC feed1 power";
     }
     leaf reason {
       type string;
       description "Reason";
     }
     leaf frequency {
       type string;
       description "Frequency";
     }
     leaf slave-revision {
       type uint32;
       description "Slave revision";
     }
     leaf load {
       type string;
       description "Load";
     }
     leaf time-used {
       type string;
       description "Length of time this component has been used";
     }
     container temperature-reading {
       leaf temperature-name {
         type string;
       }
       leaf temperature {
         type string;
         description "Temperature of the item";
       }
     }
     container fan-speed-reading {
       leaf fan-name {
         type string;
       }
       leaf fan-speed {
         type string;
         description "Fan speed in RPM";
       }
     }
     container fpga-revision-detail {
       description "FPGA revision in detail";
       leaf fpga-revision-name {
         type string;
       }
       leaf fpga-revision-value {
         type string;
       }
     }
     container revision {
       leaf revision-name {
         type string;
         description "Revision Name";
       }
       leaf revision-number {
         type uint32;
         description "Revision Number";
       }
     }
     container slave-registers-information {
       leaf slave-registers-title {
         type string;
         description "Title for the dump of slave registers";
       }
       container slave-registers {
         description "Slave register values";
       }
     }
     container cowra-registers-information {
       leaf cowra-registers-title {
         type string;
         description "Title for the dump of cowra registers";
       }
       container cowra-registers {
         description "Cowra register values";
       }
     }
     container fpga-registers {
       description "FPGA register values";
       leaf fpga-registers-type {
         type string;
       }
       leaf fpga-registers-name {
         type string;
       }
       leaf fpga-registers-value {
         type string;
       }
     }
     list firmware {
       description "Firmware version";
       leaf firmware-name {
         type string;
         description "Name of this component";
       }
       leaf firmware-version {
         type string;
         description "Firmware version string for this component";
       }
     }
     container power-information {
       leaf voltage-title {
         type string;
         description "Title for the display of voltage";
       }
       leaf max-power-consumption-ambient-temp {
         type int32;
       }
       leaf psm-hours-used {
         type uint32;
         description "Hours used for this component";
       }
       container power-title {
       }
       container voltage {
       }
       container current {
       }
       container voltage-power {
       }
     }
     container pcg-frequency {
       description "PCG Frequency";
       leaf pcg-frequency-setting {
         type string;
       }
       leaf pcg-frequency-measurement {
         type string;
       }
     }
     container dc-information {
       leaf dc-feed0-voltage {
         type string;
         description "DC feed0 voltage";
       }
       leaf dc-feed0-current {
         type string;
         description "DC feed0 current";
       }
       leaf dc-feed0-power {
         type string;
         description "DC feed0 power";
       }
       leaf dc-feed1-voltage {
         type string;
         description "DC feed1 voltage";
       }
       leaf dc-feed1-current {
         type string;
         description "DC feed1 current";
       }
       leaf dc-feed1-power {
         type string;
         description "DC feed1 power";
       }
       leaf dc-input {
         type string;
         description "DC input state";
       }
       leaf dc-output {
         type string;
         description "DC output state";
       }
       leaf ac-input {
         type string;
         description "AC input state";
       }
       leaf ac-output {
         type string;
         description "AC output state";
       }
       container dc-detail {
         description "Detailed DC information";
       }
       container dc-in-detail2 {
         description "Detailed DC input information";
       }
       container dc-detail2 {
         description "Detailed DC information";
       }
     }
     container pmbus-table {
       container pmbus-table-entry {
         description "Power Management Bus Device information";
       }
     }
     container airflow-direction {
       leaf airflow {
         type string;
       }
       leaf direction {
         type string;
         description "Airflow direction";
       }
     }
     container input-voltage {
       leaf voltage-name {
         type string;
         description "Input voltage";
       }
       leaf voltage-value {
         type uint32;
       }
     }
     container output-detail {
       description "Detailed power output information";
       leaf output-voltage {
         type uint32;
       }
       leaf output-current {
         type uint32;
         description "Output Current in Ampere(A)";
       }
     }
     container pdu-information {
       leaf hours-used {
         type uint32;
         description "Hours used for this component";
       }
       container efuse {
         description "PDU efuse information";
         leaf name {
           type string;
           description "Name of this component";
         }
         leaf state {
           type string;
           description "Status of the component";
         }
       }
       container pdu-firmware {
         description "PDU firmware information";
         leaf firmware-name {
           type string;
           description "Name of this component";
         }
         leaf firmware-version {
           type string;
           description "Firmware version string for this component";
         }
       }
       container pdu-component {
         description "PDU specific component information";
         leaf component-name {
           type string;
           description "PDU component name";
         }
         leaf component-state {
           type string;
           description "PDU component state";
         }
       }
     }
     container psm-information {
       leaf temperature {
         type string;
         description "Temperature of the item";
       }
       leaf hours-used {
         type uint32;
         description "Hours used for this component";
       }
       leaf firmware-version {
         type string;
         description "Firmware version string for this component";
       }
       container psm-status {
         leaf psm-health-check-status {
           type string;
           description "Show health check status of all PSMs";
         }
         leaf fans {
           type string;
           description "Fan status for this component";
         }
         leaf dc-input {
           type string;
           description "DC input state";
         }
         leaf dc-input1 {
           type string;
           description "DC input1 state";
         }
         leaf dc-input2 {
           type string;
           description "DC input2 state";
         }
         leaf ac-input {
           type string;
           description "AC input state";
         }
         leaf ac-input1 {
           type string;
           description "AC input1 state";
         }
         leaf ac-input2 {
           type string;
           description "AC input2 state";
         }
         leaf check-input1-alarm {
           type string;
           description "Check input1 alarm";
         }
         leaf check-input2-alarm {
           type string;
           description "Check input2 alarm";
         }
         leaf dc-output {
           type string;
           description "DC output state";
         }
         leaf ac-output {
           type string;
           description "AC output state";
         }
       }
     }
     container pem-information {
       leaf fpc-slot {
         type int32;
         description "FPC slot";
       }
       leaf pem-slot {
         type uint32;
       }
       leaf pem-state {
         type string;
         description "State of power supply unit";
       }
       leaf pem-temperature {
         type uint32;
         description "Temperature in (C)";
       }
       leaf input-current {
         type uint32;
         description "Input Current in Ampere(A)";
       }
       leaf input-volt {
         type uint32;
         description "Input Volt in Volt(V)";
       }
       leaf input-power {
         type uint32;
         description "Input Power in Watt(W)";
       }
       leaf output-current {
         type uint32;
         description "Output Current in Ampere(A)";
       }
       leaf output-volt {
         type uint32;
         description "Output Volt in Volt(V)";
       }
       leaf output-power {
         type uint32;
         description "Output Power in Watt(W)";
       }
     }
   }
 }
 grouping firmware-information-block {
   container chassis {
     description "Hardware inventory of this chassis";
     container inventory {
       description "Hardware inventory of this chassis";
       leaf name {
         type string;
         description "Name of this component";
       }
       leaf version {
         type string;
         description "Version of this component";
       }
       leaf part-number {
         type string;
         description "Part number of this component";
       }
       leaf serial-number {
         type string;
         description "Serial number of this component";
       }
       leaf description {
         type string;
         description "Description of this component";
       }
       leaf hardware-incomplete {
         type empty;
       }
       container i2c-information {
         leaf jedec-code {
           type string;
         }
         leaf eeprom-version {
           type string;
         }
         leaf assembly-identifier {
           type string;
         }
         leaf assembly-version {
           type string;
         }
         leaf manufacture-date {
           type string;
           description "Date this component was manufactured";
         }
         leaf assembly-flags {
           type string;
         }
         leaf i2c-version {
           type string;
         }
         leaf clei-code {
           type string;
           description "Common Language Equipment Identifier code of this component";
         }
         leaf i2c-identifier {
           type string;
         }
         leaf model-number {
           type string;
           description "Model number of this component";
         }
         leaf board-information-record {
           type string;
           description "Hex dump of board information record";
         }
         leaf i2c-data {
           type string;
           description "Hex dump of I2C data";
         }
       }
       list chassis-module {
         leaf name {
           type string;
           description "Name of this component";
         }
         leaf version {
           type string;
           description "Version of this component";
         }
         leaf part-number {
           type string;
           description "Part number of this component";
         }
         leaf serial-number {
           type string;
           description "Serial number of this component";
         }
         leaf description {
           type string;
           description "Description of this component";
         }
         leaf ir-mode {
           type string;
           description "R/IR mode configured";
         }
         leaf license-mode {
           type string;
           description "PTX R/IR mode configured";
         }
         container i2c-information {
           leaf jedec-code {
             type string;
           }
           leaf eeprom-version {
             type string;
           }
           leaf assembly-identifier {
             type string;
           }
           leaf assembly-version {
             type string;
           }
           leaf manufacture-date {
             type string;
             description "Date this component was manufactured";
           }
           leaf assembly-flags {
             type string;
           }
           leaf i2c-version {
             type string;
           }
           leaf clei-code {
             type string;
             description "Common Language Equipment Identifier code of this component";
           }
           leaf i2c-identifier {
             type string;
           }
           leaf model-number {
             type string;
             description "Model number of this component";
           }
           leaf board-information-record {
             type string;
             description "Hex dump of board information record";
           }
           leaf i2c-data {
             type string;
             description "Hex dump of I2C data";
           }
         }
         list chassis-sub-module {
           leaf name {
             type string;
             description "Name of this component";
           }
           leaf version {
             type string;
             description "Version of this component";
           }
           leaf part-number {
             type string;
             description "Part number of this component";
           }
           leaf serial-number {
             type string;
             description "Serial number of this component";
           }
           leaf description {
             type string;
             description "Description of this component";
           }
           container i2c-information {
             leaf jedec-code {
               type string;
             }
             leaf eeprom-version {
               type string;
             }
             leaf assembly-identifier {
               type string;
             }
             leaf assembly-version {
               type string;
             }
             leaf manufacture-date {
               type string;
               description "Date this component was manufactured";
             }
             leaf assembly-flags {
               type string;
             }
             leaf i2c-version {
               type string;
             }
             leaf clei-code {
               type string;
               description "Common Language Equipment Identifier code of this component";
             }
             leaf i2c-identifier {
               type string;
             }
             leaf model-number {
               type string;
               description "Model number of this component";
             }
             leaf board-information-record {
               type string;
               description "Hex dump of board information record";
             }
             leaf i2c-data {
               type string;
               description "Hex dump of I2C data";
             }
           }
           list chassis-sub-sub-module {
             leaf name {
               type string;
               description "Name of this component";
             }
             leaf version {
               type string;
               description "Version of this component";
             }
             leaf part-number {
               type string;
               description "Part number of this component";
             }
             leaf serial-number {
               type string;
               description "Serial number of this component";
             }
             leaf description {
               type string;
               description "Description of this component";
             }
             list chassis-sub-sub-sub-module {
             }
           }
         }
         list chassis-re-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
         list chassis-re-usb-module {
           leaf name {
             type string;
             description "Name of this component";
           }
           leaf product {
             type string;
           }
           leaf product-number {
             type int32;
           }
           leaf vendor {
             type string;
           }
           leaf description {
             type string;
             description "Description of this component";
           }
         }
         list chassis-re-dimm-module {
           leaf name {
             type string;
             description "Name of this component";
           }
           leaf part-number {
             type string;
             description "Part number of this component";
           }
           leaf die-rev {
             type string;
             description " DIE revision of the DIMM";
           }
           leaf pcb-rev {
             type string;
             description "PCB revision ";
           }
           leaf mfr-id {
             type string;
             description "Manufacture Id of the DIMM";
           }
         }
         list chassis-compute-node-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
       }
     }
     container model-inventory {
       description "Hardware inventory of this chassis";
       list chassis-module {
         leaf name {
           type string;
           description "Name of this component";
         }
         leaf version {
           type string;
           description "Version of this component";
         }
         leaf part-number {
           type string;
           description "Part number of this component";
         }
         leaf serial-number {
           type string;
           description "Serial number of this component";
         }
         leaf model-number {
           type string;
           description "Model number of this component";
         }
         list chassis-sub-module {
           list chassis-sub-sub-module {
             list chassis-sub-sub-sub-module {
             }
           }
         }
       }
     }
     container clei-model-inventory {
       description "Hardware inventory of this chassis";
       list chassis-module {
         leaf name {
           type string;
           description "Name of this component";
         }
         leaf version {
           type string;
           description "Version of this component";
         }
         leaf part-number {
           type string;
           description "Part number of this component";
         }
         leaf clei-code {
           type string;
           description "Common Language Equipment Identifier code of this component";
         }
         leaf model-number {
           type string;
           description "Model number of this component";
         }
         list chassis-sub-module {
           list chassis-sub-sub-module {
             list chassis-sub-sub-sub-module {
             }
           }
         }
       }
     }
     container firmware {
       description "Hardware inventory of this chassis";
       list chassis-module {
         leaf name {
           type string;
           description "Name of this component";
         }
         list chassis-sub-module {
           list chassis-sub-sub-module {
             list chassis-sub-sub-sub-module {
             }
           }
         }
       }
     }
   }
 }
 grouping fpc-information-block {
   list terse {
     list fpc {
       leaf slot {
         type int32;
       }
       leaf state {
         type string;
         description "Status of the component";
       }
       leaf comment {
         type string;
       }
       leaf temperature {
         type string;
         description "Temperature of the item";
       }
       container pic-detail {
         container port-information {
         }
         container package-information {
           container package {
           }
         }
         container port-speed-information {
         }
       }
     }
   }
   list brief {
     leaf fpc-slot {
       type int32;
       description "FPC slot";
     }
     leaf fpc-status {
       type string;
       description "FPC status";
     }
     leaf fpc-power-limit {
       type string;
       description "FPC power limit";
     }
     leaf fpc-power {
       type string;
       description "Total FPC power consumption";
     }
     leaf fpc-priority {
       type string;
       description "Priority options";
     }
     leaf fpc-firmware-version {
       type string;
       description "POE firmware version";
     }
     list fpc {
       leaf slot {
         type int32;
       }
       leaf state {
         type string;
         description "Status of the component";
       }
       leaf comment {
         type string;
       }
       leaf temperature {
         type string;
         description "Temperature of the item";
       }
       leaf cpu-total {
         type int32;
         description "Percentage of CPU utilized";
       }
       leaf cpu-interrupt {
         type int32;
         description "Percentage of CPU utilized by interrupt processing";
       }
       leaf cpu-1min-avg {
         type int32;
         description "Percentage of one min average CPU utilized";
       }
       leaf cpu-5min-avg {
         type int32;
         description "Percentage of five min average CPU utilized";
       }
       leaf cpu-15min-avg {
         type int32;
         description "Percentage of fifteen min average CPU utilized";
       }
       leaf memory-dram-size {
         type int32;
         description "DRAM";
       }
       leaf memory-heap-utilization {
         type int32;
         description "Percentage of heap memory utilized";
       }
       leaf memory-buffer-utilization {
         type int32;
         description "Percentage of buffer memory utilized";
       }
       container pic-detail {
         container port-information {
         }
         container package-information {
           container package {
           }
         }
         container port-speed-information {
         }
       }
     }
   }
   list brief-bsys {
     list fpc {
       leaf slot {
         type int32;
       }
       leaf state {
         type string;
         description "Status of the component";
       }
       leaf comment {
         type string;
       }
       leaf temperature {
         type string;
         description "Temperature of the item";
       }
       leaf cpu-total {
         type int32;
         description "Percentage of CPU utilized";
       }
       leaf cpu-interrupt {
         type int32;
         description "Percentage of CPU utilized by interrupt processing";
       }
       leaf cpu-1min-avg {
         type int32;
         description "Percentage of one min average CPU utilized";
       }
       leaf cpu-5min-avg {
         type int32;
         description "Percentage of five min average CPU utilized";
       }
       leaf cpu-15min-avg {
         type int32;
         description "Percentage of fifteen min average CPU utilized";
       }
       leaf memory-dram-size {
         type int32;
         description "DRAM";
       }
       leaf memory-heap-utilization {
         type int32;
         description "Percentage of heap memory utilized";
       }
       leaf memory-buffer-utilization {
         type int32;
         description "Percentage of buffer memory utilized";
       }
       leaf gnf-id {
         type string;
       }
       container pic-detail {
         container port-information {
         }
         container package-information {
           container package {
           }
         }
         container port-speed-information {
         }
       }
     }
   }
   list verbose {
     list fpc {
       leaf slot {
         type int32;
       }
       leaf state {
         type string;
         description "Status of the component";
       }
       leaf error-code {
         type int32;
         description "Code resulting from major or minor error";
       }
       leaf logical-slot {
         type int32;
       }
       leaf temperature {
         type string;
         description "Temperature of the item";
       }
       leaf cpu-less-info-str {
         type string;
         description "Flexible PIC Concentrator (FPC) without CPU";
       }
       leaf memory-dram-size {
         type int32;
         description "DRAM";
       }
       leaf memory-sram-size {
         type int32;
         description "SRAM";
       }
       leaf memory-sdram-size {
         type int32;
         description "SDRAM";
       }
       leaf memory-notification-sdram-size {
         type int32;
         description "Notification SDRAM";
       }
       leaf memory-rldram-size {
         type int32;
         description "RLDRAM";
       }
       leaf memory-xr2-size {
         type int32;
         description "XR2";
       }
       leaf memory-ddr-dram-size {
         type int32;
         description "DDR DRAM";
       }
       leaf asic-information {
         type string;
       }
       leaf start-time {
         type string;
         description "Time this component was started";
       }
       leaf up-time {
         type string;
         description "Length of time this component has been operational";
       }
       leaf comment {
         type string;
       }
       leaf max-power-consumption {
         type int32;
       }
       leaf max-mpc-base-power-consumption {
         type int32;
         description "Max MPC base power consumption";
       }
       leaf max-mic0-power-consumption {
         type int32;
         description "Max MIC0 power consumption";
       }
       leaf max-mic1-power-consumption {
         type int32;
         description "Max MIC1 power consumption";
       }
       leaf max-mpc-total-power-consumption {
         type int32;
         description "Max MPC total power consumption";
       }
       container pic-detail {
         container port-information {
         }
         container package-information {
           container package {
           }
         }
         container port-speed-information {
         }
       }
     }
   }
   list pic-style {
     list fpc {
       leaf slot {
         type int32;
       }
       leaf state {
         type string;
         description "Status of the component";
       }
       leaf description {
         type string;
         description "Description of this component";
       }
       leaf gnf-id {
         type string;
       }
       list pic {
         leaf pic-slot {
           type int32;
         }
         leaf pic-state {
           type string;
         }
         leaf pic-type {
           type string;
         }
         leaf comment {
           type string;
         }
       }
       container pic-detail {
         container port-information {
         }
         container package-information {
           container package {
           }
         }
         container port-speed-information {
         }
       }
     }
   }
   list pic-style-detail {
     list fpc {
       container pic-detail {
         leaf slot {
           type int32;
         }
         leaf pic-slot {
           type int32;
         }
         leaf pic-type {
           type string;
         }
         leaf comment {
           type string;
         }
         leaf asic-type {
           type string;
           description "Type of ASIC on the PIC";
         }
         leaf account-layer2-overhead {
           type string;
           description "Account Layer2 Overhead Knob Status";
         }
         leaf state {
           type string;
           description "Status of the component";
         }
         leaf pic-version {
           type string;
           description "PIC hardware version";
         }
         leaf cpu-sw-version {
           type string;
           description "Version of operating system running on the PIC";
         }
         leaf cpu-rom-version {
           type string;
           description "PIC ROM version";
         }
         leaf cpu-total {
           type int32;
           description "Percentage of CPU utilized";
         }
         leaf cpu-interrupt {
           type int32;
           description "Percentage of CPU utilized by interrupt processing";
         }
         leaf memory-dram-size {
           type int32;
           description "DRAM";
         }
         leaf memory-buffer-utilization {
           type int32;
           description "Percentage of buffer memory utilized";
         }
         leaf memory-heap-utilization {
           type int32;
           description "Percentage of heap memory utilized";
         }
         leaf up-time {
           type string;
           description "Length of time this component has been operational";
         }
         leaf pic-package {
           type string;
         }
         leaf pic-clock-sync {
           type string;
           description "PIC Clock Synchronization";
         }
         leaf pic-multirate-mode {
           type string;
         }
         leaf pic-channelization-mode {
           type string;
           description "PIC Channelization Mode";
         }
         leaf configured-mode {
           type string;
         }
         leaf control-cores {
           type int32;
         }
         leaf data-cores {
           type int32;
         }
         leaf object-cache-size {
           type int32;
         }
         leaf policy-db-size {
           type int32;
         }
         leaf forwarding-db-size {
           type int32;
         }
         leaf wired-process-mem-size {
           type int32;
         }
         leaf wired-max-processes {
           type int32;
         }
         container port-information {
           container port {
             leaf port-number {
               type int32;
               description "Port number on the PIC";
             }
             leaf cable-type {
               type string;
               description "Port cable type";
             }
             leaf fiber-mode {
               type string;
               description "Single or multi-mode";
             }
             leaf sfp-vendor-name {
               type string;
               description "SFP vendor name";
             }
             leaf sfp-vendor-pno {
               type string;
               description "SFP vendor part number";
             }
             leaf wavelength {
               type string;
               description "Wavelength of the optical transceiver";
             }
             leaf sfp-vendor-fw-ver {
               type string;
               description "Vendor firmware version";
             }
           }
         }
         container pic-transport-information {
           leaf pic-transport-admin-state {
             type string;
           }
           leaf pic-transport-oper-state {
             type string;
           }
         }
         container package-information {
           container package {
           }
         }
         container port-speed-information {
           container port {
             leaf port-number1 {
               type int32;
               description "PIC port number";
             }
             leaf speed-capability {
               type string;
               description "Port speed capabilities";
             }
           }
         }
       }
     }
   }
   list detail {
     leaf fpc-slot {
       type int32;
       description "FPC slot";
     }
     leaf fpc-status {
       type string;
       description "FPC status";
     }
     leaf fpc-power-limit {
       type string;
       description "FPC power limit";
     }
     leaf fpc-power {
       type string;
       description "Total FPC power consumption";
     }
     leaf fpc-priority {
       type string;
       description "Priority options";
     }
     leaf fpc-firmware-version {
       type string;
       description "POE firmware version";
     }
     list fpc {
       container pic-detail {
         container port-information {
         }
         container package-information {
           container package {
           }
         }
         container port-speed-information {
         }
       }
     }
   }
 }
 grouping fpc-port-information-block {
   container brief {
     description "Display the port stats for FPC";
     list fpc {
       leaf slot {
         type int32;
       }
       leaf port-num {
         type int32;
       }
       leaf port-config-map {
         type string;
       }
       leaf port-map {
         type string;
       }
       container pic-detail {
         container port-information {
         }
         container package-information {
           container package {
           }
         }
         container port-speed-information {
         }
       }
     }
   }
 }
 grouping fpc-error-information-block {
   container brief {
     description "Display the ASIC error stats for FPC";
     list fpc {
       leaf slot {
         type int32;
       }
       leaf minor-level-occured {
         type uint32;
       }
       leaf minor-level-cleared {
         type uint32;
       }
       leaf minor-level-threshold {
         type uint32;
       }
       leaf minor-level-action-taken {
         type uint32;
       }
       leaf minor-level-action {
         type string;
       }
       leaf major-level-occured {
         type uint32;
       }
       leaf major-level-cleared {
         type uint32;
       }
       leaf major-level-threshold {
         type uint32;
       }
       leaf major-level-action-taken {
         type uint32;
       }
       leaf major-level-action {
         type string;
       }
       leaf fatal-level-occured {
         type uint32;
       }
       leaf fatal-level-cleared {
         type uint32;
       }
       leaf fatal-level-threshold {
         type uint32;
       }
       leaf fatal-level-action-taken {
         type uint32;
       }
       leaf fatal-level-action {
         type string;
       }
       leaf fpc-pfe-state {
         type string;
       }
       container pic-detail {
         container port-information {
         }
         container package-information {
           container package {
           }
         }
         container port-speed-information {
         }
       }
     }
   }
 }
 grouping fm-fpc-state-information-block {
   container brief1 {
     list fm-fpc-ln {
       list fm-pfe-ln {
         list fm-sib-ln {
         }
       }
     }
     list fm-fpc-ln1 {
       leaf fpc-slot1 {
         type int32;
       }
       list fm-pfe-ln1 {
         list fm-pfe-core-ln {
         }
       }
     }
   }
   container brief {
     list fm-fpc-ln {
       leaf slot {
         type int32;
       }
       list fm-pfe-ln {
         list fm-sib-ln {
         }
       }
     }
     list fm-fpc-ln1 {
       list fm-pfe-ln1 {
         list fm-pfe-core-ln {
         }
       }
     }
   }
   container terse {
     leaf comment {
       type string;
     }
     list fm-fpc-ln {
       leaf slot {
         type int32;
       }
       list fm-pfe-ln {
         container fm-plane-ln {
         }
       }
     }
     list fm-fpc-ln1 {
       list fm-pfe-ln1 {
         list fm-pfe-core-ln {
         }
       }
     }
   }
   container link {
     list fm-fpc-ln {
       leaf slot {
         type int32;
       }
       list fm-pfe-ln {
         container fm-link-ln {
         }
       }
     }
     list fm-fpc-ln1 {
       list fm-pfe-ln1 {
         list fm-pfe-core-ln {
         }
       }
     }
   }
 }
 grouping fm-fabric-destinations-state-block {
   container terse {
     description "Fabric destinations state information";
     list fm-dest-fpc-ln {
       description "Fabric destinations state for fpc";
       leaf fm-slot {
         type uint32;
         description "FPC slot";
       }
       list fm-dest-pfe-ln {
         description "Fabric destinations state for pfe";
         list fm-dest-plane-ln {
           description "Fabric destinations state for plane";
           container fm-dest-fabric-destinations-ln {
           }
         }
       }
     }
   }
 }
 grouping fm-plane-location-information-block {
   container fm-plane-location {
     leaf plane {
       type string;
       description "Plane information";
     }
     leaf sib-f13-slot {
       type string;
       description "F13 SIB information";
     }
     leaf sib-f2-slot {
       type string;
       description "F2 SIB information";
     }
     leaf sib-l-slot {
       type string;
       description "LCC SIB information";
     }
     leaf plane-slot {
       type uint32;
     }
     leaf cb-slot {
       type uint32;
     }
     leaf sfb-plane {
       type uint32;
     }
     leaf sfb-slot {
       type uint32;
     }
     leaf sib-slot {
       type int32;
       description "SIB slot number";
     }
     leaf planes {
       type string;
       description "Planes associated with the SIB";
     }
     leaf plane-number {
       type uint32;
       description "Planes number";
     }
     list fab-fru-slot-ln {
     }
   }
 }
 grouping fm-topology-block {
   container fm-topo-link-src-des {
     leaf fm-topo-link-msg {
       type string;
     }
     container fm-topo-link-src {
       leaf fm-topo-link-src-in {
         type string;
       }
       leaf fm-topo-link-src-out {
         type string;
       }
       leaf hsl2-state-src {
         type string;
       }
     }
     container fm-topo-link-des {
       leaf fm-topo-link-des-in {
         type string;
       }
       leaf fm-topo-link-des-out {
         type string;
       }
       leaf hsl2-state-des {
         type string;
       }
     }
   }
   container fm-topo-link-io {
     leaf fm-topo-link-header-message {
       type string;
       description "Header messages for this command";
     }
     container fm-topo-link-sib {
       leaf fm-topo-link-sibnum {
         type int32;
         description "SIB number";
       }
       leaf fm-topo-link-sib-message {
         type string;
         description "SIB messages";
       }
       container fm-topo-link-fchip {
         container fm-topo-link-fcore {
           container fm-topo-link-source {
           }
           container fm-topo-link-destination {
           }
         }
       }
     }
   }
   container fm-topo-link {
     container detail {
       container fm-topo-link-details {
         container fm-topo-link-in-out {
           leaf fm-topo-link-type {
             type string;
             description "Type of the link";
           }
         }
         container fm-topo-link-details-head-lcc {
           leaf fm-topo-sib-source {
             type string;
             description "Source sib";
           }
           leaf fm-topo-sib-dest {
             type string;
             description "Destination sib";
           }
         }
         container fm-topo-link-details-lcc {
           leaf source-pfe-xc-link {
             type string;
             description "Source pfe link";
           }
           leaf dest-pfe-xc-link {
             type string;
             description "Destination pfe link";
           }
           leaf vcsel-status {
             type string;
             description "VCSEL status";
           }
           leaf hsl2-channel {
             type string;
             description "HSL2 channel number";
           }
           leaf hsl2-status {
             type string;
             description "HSL2 channel status";
           }
         }
         container fm-topo-link-details-head-sfc {
           leaf fm-topo-sib-source {
             type string;
             description "Source sib";
           }
           leaf fm-topo-sib-dest {
             type string;
             description "Destination sib";
           }
         }
         container fm-topo-link-details-sfc {
           leaf source-pfe-xc-link {
             type string;
             description "Source pfe link";
           }
           leaf dest-pfe-xc-link {
             type string;
             description "Destination pfe link";
           }
           leaf vcsel-status {
             type string;
             description "VCSEL status";
           }
           leaf hsl2-channel {
             type string;
             description "HSL2 channel number";
           }
           leaf hsl2-status {
             type string;
             description "HSL2 channel status";
           }
         }
       }
       container fm-topo-link-information {
         leaf fm-topo-sib {
           type string;
           description "SIB information";
         }
         leaf fm-topo-dbl-line {
           type string;
           description "Under line of the header";
         }
         container fm-topo-link-fail {
           leaf fm-topo-fail-msg {
             type string;
             description "Details of the failure";
           }
         }
         container fm-topo-link-details {
           container fm-topo-link-in-out {
             leaf fm-topo-link-type {
               type string;
               description "Type of the link";
             }
           }
           container fm-topo-link-details-head-lcc {
             leaf fm-topo-sib-source {
               type string;
               description "Source sib";
             }
             leaf fm-topo-sib-dest {
               type string;
               description "Destination sib";
             }
           }
           container fm-topo-link-details-lcc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
           container fm-topo-link-details-head-sfc {
             leaf fm-topo-sib-source {
               type string;
               description "Source sib";
             }
             leaf fm-topo-sib-dest {
               type string;
               description "Destination sib";
             }
           }
           container fm-topo-link-details-sfc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
         }
       }
       container fm-topo-link-information-sgl {
         container fm-topo-link-fail-sgl {
           leaf fm-topo-sib {
             type string;
             description "SIB information";
           }
           leaf fm-topo-fail-msg {
             type string;
             description "Details of the failure";
           }
         }
         container fm-topo-link-details {
           container fm-topo-link-in-out {
             leaf fm-topo-link-type {
               type string;
               description "Type of the link";
             }
           }
           container fm-topo-link-details-head-lcc {
             leaf fm-topo-sib-source {
               type string;
               description "Source sib";
             }
             leaf fm-topo-sib-dest {
               type string;
               description "Destination sib";
             }
           }
           container fm-topo-link-details-lcc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
           container fm-topo-link-details-head-sfc {
             leaf fm-topo-sib-source {
               type string;
               description "Source sib";
             }
             leaf fm-topo-sib-dest {
               type string;
               description "Destination sib";
             }
           }
           container fm-topo-link-details-sfc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
         }
       }
     }
   }
   container fm-topo-map {
     container fm-topo-map-ln {
       leaf fm-fpc-slot {
         type uint32;
       }
       leaf fm-pfe-slot {
         type uint32;
         description "PFE slot";
       }
       leaf fm-cb-slot {
         type uint32;
       }
       leaf port {
         type uint32;
       }
       leaf link-state {
         type string;
       }
     }
   }
 }
 grouping fm-plane-state-information-block {
   container terse {
     leaf comment {
       type string;
     }
     container fmp-plane {
       leaf slot {
         type int32;
       }
       leaf state {
         type string;
         description "Status of the component";
       }
       leaf fru-name {
         type string;
       }
       leaf fru-slot {
         type int32;
         description "FRU slot number";
       }
       leaf pfe-slot {
         type int32;
       }
       leaf pfe-link-status {
         type string;
         description "PFE link status information";
       }
     }
   }
   container brief {
     leaf fabric-header {
       type string;
       description "Fabric header";
     }
     leaf comment {
       type string;
     }
     container fmp-plane {
       leaf slot {
         type int32;
       }
       leaf state {
         type string;
         description "Status of the component";
       }
       leaf link-error {
         type string;
         description "Link error count";
       }
       leaf destination-error {
         type string;
         description "Destination error count";
       }
       leaf up-time {
         type string;
         description "Length of time this component has been operational";
       }
     }
   }
   container brief_cable_error {
     leaf fabric-header {
       type string;
       description "Fabric header";
     }
     leaf comment {
       type string;
     }
     container fmp-plane {
       leaf slot {
         type int32;
       }
       leaf state {
         type string;
         description "Status of the component";
       }
       leaf plane-cable-errors {
         type string;
         description "Number of cable errors in the plane";
       }
       leaf link-error {
         type string;
         description "Link error count";
       }
       leaf destination-error {
         type string;
         description "Destination error count";
       }
       leaf up-time {
         type string;
         description "Length of time this component has been operational";
       }
     }
   }
   container detail {
     leaf fabric-header {
       type string;
       description "Fabric header";
     }
     leaf comment {
       type string;
     }
     container fmp-plane {
       leaf slot {
         type int32;
       }
       leaf plane-state {
         type string;
         description "Plane state information";
       }
       leaf sib-name {
         type string;
         description "SIB name";
       }
       leaf sibs-slot {
         type string;
         description "Chassis SIB slot number";
       }
       leaf state {
         type string;
         description "Status of the component";
       }
     }
   }
   container extensive {
     leaf fabric-header {
       type string;
       description "Fabric header";
     }
     leaf comment {
       type string;
     }
     container fmp-plane {
       leaf slot {
         type int32;
       }
       leaf plane-state {
         type string;
         description "Plane state information";
       }
       leaf sib-name {
         type string;
         description "SIB name";
       }
       leaf sibs-slot {
         type string;
         description "Chassis SIB slot number";
       }
       leaf state {
         type string;
         description "Status of the component";
       }
       leaf sib-f13-name {
         type string;
         description "F13 SIB name";
       }
       leaf f13-slot {
         type int32;
         description "F13 slot number";
       }
       leaf even-odd {
         type string;
         description "Even or Odd part of SIB F13";
       }
       leaf lcc-slot {
         type int32;
         description "LCC slot number";
       }
       leaf sibl-slot {
         type int32;
         description "LCC SIB slot number";
       }
       leaf sibl-link-state {
         type string;
         description "LCC SIB link state information";
       }
       leaf sgasic-number {
         type int32;
         description "SG number on SFC";
       }
       leaf sgasic-port-number {
         type int32;
         description "SG port number on SFC";
       }
       leaf sgasic-port-link-state {
         type string;
         description "SG port link status on SFC";
       }
       leaf sibs-lcc-pfe-slot {
         type int32;
         description "SFC PFE slot number";
       }
       leaf sibs-lcc-pfe-link-state {
         type string;
         description "SFC PFE link state information";
       }
       leaf sib-f2-name {
         type string;
         description "F2 SIB name";
       }
       leaf sibs2-slot {
         type string;
         description "Chassis F2 SIB slot number";
       }
       leaf f2-link-state {
         type string;
         description "F2 link state information";
       }
       leaf lcc-sib-link-state {
         type string;
         description "LCC SIB link state information";
       }
       leaf lcc-sgasic-number {
         type int32;
         description "SG number on LCC";
       }
       leaf lcc-sgasic-port-number {
         type int32;
         description "SG port number on LCC";
       }
       leaf lcc-sgasic-port-link-state {
         type string;
         description "SG port link status on LCC";
       }
       leaf sibl-lcc-pfe-slot {
         type int32;
         description "LCC PFE slot number";
       }
       leaf sibl-lcc-pfe-link-state {
         type string;
         description "LCC PFE link state information";
       }
       leaf lcc-fpc-slot {
         type int32;
         description "FPC slot number";
       }
       leaf lcc-pfe-slot {
         type int32;
         description "PFE slot number";
       }
       leaf lcc-pfe-link-state {
         type string;
         description "PFE link state information";
       }
     }
   }
 }
 grouping fm-state-information-block {
   leaf comment {
     type string;
   }
   container fm-state-item {
     leaf plane-slot {
       type uint32;
     }
     leaf state {
       type string;
       description "Status of the component";
     }
     leaf up-time {
       type string;
       description "Length of time this component has been operational";
     }
   }
 }
 grouping fm-ext-state-information-block {
   leaf comment {
     type string;
   }
   container fm-ext-state-item {
     leaf plane-slot {
       type uint32;
     }
     leaf state {
       type string;
       description "Status of the component";
     }
     leaf link-error {
       type string;
       description "Link error count";
     }
     leaf link-tf {
       type string;
       description "Count of training failure links";
     }
     leaf destination-error {
       type string;
       description "Destination error count";
     }
     leaf up-time {
       type string;
       description "Length of time this component has been operational";
     }
   }
 }
 grouping fm-fabric-reachability-information-block {
   leaf fab-reach-status {
     type string;
   }
   leaf fab-reach-resolute {
     type string;
   }
   container fab-reachability-detect {
     leaf unreach-dests {
       type string;
     }
     leaf detect-time {
       type string;
       description "Time of unreachability detection";
     }
     leaf unreachability-reason {
       type string;
     }
   }
   container fab-reachability-action {
     leaf current-act {
       type string;
     }
     leaf act-reason {
       type string;
     }
     leaf init-phase {
       type string;
     }
     leaf current-phase {
       type string;
     }
     leaf current-phase-status {
       type string;
     }
     leaf act-start-time {
       type string;
       description "Fabric reachability action started";
     }
     leaf act-end-time {
       type string;
       description "Time fabric reachability action completed";
     }
     container plane-restart-phase {
       leaf plane-restart-phase-status {
         type string;
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
     }
     container sib-restart-phase {
       leaf plane-restart-phase-status {
         type string;
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
     }
     container plane-fpc-restart-phase {
       leaf plane-fpc-restart-phase-status {
         type string;
       }
       leaf plane-fpc-restart-start-time {
         type string;
         description "Plane and FPC restart phase start time";
       }
       leaf fpc-offline-start-time {
         type string;
         description "Offline FPC stage start time";
       }
       leaf fpc-action-list {
         type string;
       }
       leaf fpc-offline-timeout-list {
         type string;
         description "FPCs timed out on offline event";
       }
       leaf fpc-offline-current {
         type int32;
       }
       leaf fpc-offline-time {
         type string;
         description "Time FPC made offline";
       }
       leaf fpc-offline-end-time {
         type string;
         description "Offline FPC stage end time";
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
       leaf fpc-online-start-time {
         type string;
         description "FPC online stage start time";
       }
       leaf fpc-online-list {
         type string;
       }
       leaf fpc-online-timeout-list {
         type string;
         description "FPCs timed out on online event";
       }
       leaf fpc-online-current {
         type int32;
       }
       leaf fpc-online-time {
         type string;
         description "Time FPC made online";
       }
       leaf fpc-online-end-time {
         type string;
         description "FPC online stage end time";
       }
       leaf fpc-restart-list {
         type string;
         description "FPCs restart list";
       }
       leaf fpc-restart-time {
         type string;
         description "FPC restart time";
       }
       leaf plane-fpc-restart-phase-end-time {
         type string;
         description "Plane and FPC restart phase end time";
       }
     }
     container sib-fpc-restart-phase {
       leaf plane-fpc-restart-phase-status {
         type string;
       }
       leaf plane-fpc-restart-start-time {
         type string;
         description "Plane and FPC restart phase start time";
       }
       leaf fpc-offline-start-time {
         type string;
         description "Offline FPC stage start time";
       }
       leaf fpc-offline-list {
         type string;
       }
       leaf fpc-offline-timeout-list {
         type string;
         description "FPCs timed out on offline event";
       }
       leaf fpc-offline-current {
         type int32;
       }
       leaf fpc-offline-time {
         type string;
         description "Time FPC made offline";
       }
       leaf fpc-offline-end-time {
         type string;
         description "Offline FPC stage end time";
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
       leaf fpc-online-start-time {
         type string;
         description "FPC online stage start time";
       }
       leaf fpc-online-list {
         type string;
       }
       leaf fpc-online-timeout-list {
         type string;
         description "FPCs timed out on online event";
       }
       leaf fpc-online-current {
         type int32;
       }
       leaf fpc-online-time {
         type string;
         description "Time FPC made online";
       }
       leaf fpc-online-end-time {
         type string;
         description "FPC online stage end time";
       }
       leaf fpc-restart-list {
         type string;
         description "FPCs restart list";
       }
       leaf fpc-restart-time {
         type string;
         description "FPC restart time";
       }
       leaf plane-fpc-restart-phase-end-time {
         type string;
         description "Plane and FPC restart phase end time";
       }
     }
     container fpc-offline-phase {
       leaf fpc-offline-phase-status {
         type string;
       }
       leaf fpc-offline-phase-start-time {
         type string;
         description "FPC offline phase start time";
       }
       leaf fpc-offline-start-time {
         type string;
         description "Offline FPC stage start time";
       }
       leaf fpc-action-list {
         type string;
       }
       leaf fpc-offline-timeout-list {
         type string;
         description "FPCs timed out on offline event";
       }
       leaf fpc-offline-current {
         type int32;
       }
       leaf fpc-offline-time {
         type string;
         description "Time FPC made offline";
       }
       leaf fpc-offline-end-time {
         type string;
         description "Offline FPC stage end time";
       }
       leaf fpc-offline-phase-end-time {
         type string;
         description "FPC offline phase end time";
       }
     }
   }
 }
 grouping chassis-inventory-block {
   container chassis {
     description "Hardware inventory of this chassis";
     container inventory {
       description "Hardware inventory of this chassis";
       leaf name {
         type string;
         description "Name of this component";
       }
       leaf version {
         type string;
         description "Version of this component";
       }
       leaf part-number {
         type string;
         description "Part number of this component";
       }
       leaf serial-number {
         type string;
         description "Serial number of this component";
       }
       leaf description {
         type string;
         description "Description of this component";
       }
       leaf hardware-incomplete {
         type empty;
       }
       container i2c-information {
         leaf jedec-code {
           type string;
         }
         leaf eeprom-version {
           type string;
         }
         leaf assembly-identifier {
           type string;
         }
         leaf assembly-version {
           type string;
         }
         leaf manufacture-date {
           type string;
           description "Date this component was manufactured";
         }
         leaf assembly-flags {
           type string;
         }
         leaf i2c-version {
           type string;
         }
         leaf clei-code {
           type string;
           description "Common Language Equipment Identifier code of this component";
         }
         leaf i2c-identifier {
           type string;
         }
         leaf model-number {
           type string;
           description "Model number of this component";
         }
         leaf board-information-record {
           type string;
           description "Hex dump of board information record";
         }
         leaf i2c-data {
           type string;
           description "Hex dump of I2C data";
         }
       }
       list chassis-module {
         leaf name {
           type string;
           description "Name of this component";
         }
         leaf version {
           type string;
           description "Version of this component";
         }
         leaf part-number {
           type string;
           description "Part number of this component";
         }
         leaf serial-number {
           type string;
           description "Serial number of this component";
         }
         leaf description {
           type string;
           description "Description of this component";
         }
         leaf ir-mode {
           type string;
           description "R/IR mode configured";
         }
         leaf license-mode {
           type string;
           description "PTX R/IR mode configured";
         }
         container i2c-information {
           leaf jedec-code {
             type string;
           }
           leaf eeprom-version {
             type string;
           }
           leaf assembly-identifier {
             type string;
           }
           leaf assembly-version {
             type string;
           }
           leaf manufacture-date {
             type string;
             description "Date this component was manufactured";
           }
           leaf assembly-flags {
             type string;
           }
           leaf i2c-version {
             type string;
           }
           leaf clei-code {
             type string;
             description "Common Language Equipment Identifier code of this component";
           }
           leaf i2c-identifier {
             type string;
           }
           leaf model-number {
             type string;
             description "Model number of this component";
           }
           leaf board-information-record {
             type string;
             description "Hex dump of board information record";
           }
           leaf i2c-data {
             type string;
             description "Hex dump of I2C data";
           }
         }
         list chassis-sub-module {
           leaf name {
             type string;
             description "Name of this component";
           }
           leaf version {
             type string;
             description "Version of this component";
           }
           leaf part-number {
             type string;
             description "Part number of this component";
           }
           leaf serial-number {
             type string;
             description "Serial number of this component";
           }
           leaf description {
             type string;
             description "Description of this component";
           }
           container i2c-information {
             leaf jedec-code {
               type string;
             }
             leaf eeprom-version {
               type string;
             }
             leaf assembly-identifier {
               type string;
             }
             leaf assembly-version {
               type string;
             }
             leaf manufacture-date {
               type string;
               description "Date this component was manufactured";
             }
             leaf assembly-flags {
               type string;
             }
             leaf i2c-version {
               type string;
             }
             leaf clei-code {
               type string;
               description "Common Language Equipment Identifier code of this component";
             }
             leaf i2c-identifier {
               type string;
             }
             leaf model-number {
               type string;
               description "Model number of this component";
             }
             leaf board-information-record {
               type string;
               description "Hex dump of board information record";
             }
             leaf i2c-data {
               type string;
               description "Hex dump of I2C data";
             }
           }
           list chassis-sub-sub-module {
             leaf name {
               type string;
               description "Name of this component";
             }
             leaf version {
               type string;
               description "Version of this component";
             }
             leaf part-number {
               type string;
               description "Part number of this component";
             }
             leaf serial-number {
               type string;
               description "Serial number of this component";
             }
             leaf description {
               type string;
               description "Description of this component";
             }
             list chassis-sub-sub-sub-module {
             }
           }
         }
         list chassis-re-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
         list chassis-re-usb-module {
           leaf name {
             type string;
             description "Name of this component";
           }
           leaf product {
             type string;
           }
           leaf product-number {
             type int32;
           }
           leaf vendor {
             type string;
           }
           leaf description {
             type string;
             description "Description of this component";
           }
         }
         list chassis-re-dimm-module {
           leaf name {
             type string;
             description "Name of this component";
           }
           leaf part-number {
             type string;
             description "Part number of this component";
           }
           leaf die-rev {
             type string;
             description " DIE revision of the DIMM";
           }
           leaf pcb-rev {
             type string;
             description "PCB revision ";
           }
           leaf mfr-id {
             type string;
             description "Manufacture Id of the DIMM";
           }
         }
         list chassis-compute-node-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
       }
     }
     container model-inventory {
       description "Hardware inventory of this chassis";
       list chassis-module {
         leaf name {
           type string;
           description "Name of this component";
         }
         leaf version {
           type string;
           description "Version of this component";
         }
         leaf part-number {
           type string;
           description "Part number of this component";
         }
         leaf serial-number {
           type string;
           description "Serial number of this component";
         }
         leaf model-number {
           type string;
           description "Model number of this component";
         }
         list chassis-sub-module {
           list chassis-sub-sub-module {
             list chassis-sub-sub-sub-module {
             }
           }
         }
       }
     }
     container clei-model-inventory {
       description "Hardware inventory of this chassis";
       list chassis-module {
         leaf name {
           type string;
           description "Name of this component";
         }
         leaf version {
           type string;
           description "Version of this component";
         }
         leaf part-number {
           type string;
           description "Part number of this component";
         }
         leaf clei-code {
           type string;
           description "Common Language Equipment Identifier code of this component";
         }
         leaf model-number {
           type string;
           description "Model number of this component";
         }
         list chassis-sub-module {
           list chassis-sub-sub-module {
             list chassis-sub-sub-sub-module {
             }
           }
         }
       }
     }
     container firmware {
       description "Hardware inventory of this chassis";
       list chassis-module {
         leaf name {
           type string;
           description "Name of this component";
         }
         list chassis-sub-module {
           list chassis-sub-sub-module {
             list chassis-sub-sub-sub-module {
             }
           }
         }
       }
     }
   }
 }
 grouping chassis-mac-addresses-block {
   list chassis-mac-addresses-edge-info {
     container re-mac-address {
       leaf re-fc-mac-base {
         type string;
       }
       leaf re-fc-mac-count {
         type string;
       }
       leaf re-vlan-mac {
         type string;
       }
     }
     list fpc-mac-address {
       leaf name {
         type string;
         description "Name of this component";
       }
       leaf fpc-mac-base {
         type string;
       }
       leaf fpc-mac-count {
         type string;
       }
     }
   }
   list mac-address-information {
     leaf public-base-address {
       type string;
     }
     leaf public-count {
       type string;
     }
     leaf private-base-address {
       type string;
     }
     leaf private-count {
       type string;
     }
   }
   container external-mac-address-information {
     leaf external-base-address {
       type string;
     }
     leaf external-count {
       type string;
     }
     leaf external-available {
       type string;
     }
   }
 }
 grouping route-engine-information-block {
   list route-engine {
     leaf slot {
       type int32;
     }
     leaf physical-slot {
       type int32;
     }
     leaf mastership-state {
       type string;
       description "Current state of mastership on this Routing Engine";
     }
     leaf mastership-priority {
       type string;
       description "Configured priority for mastership on this Routing Engine";
     }
     leaf temperature {
       type string;
       description "Temperature of the item";
     }
     leaf cpu-temperature {
       type string;
     }
     leaf memory-dram-size {
       type int32;
       description "DRAM";
     }
     leaf memory-installed-size {
       type string;
       description "Installed RAM";
     }
     leaf memory-buffer-utilization {
       type int32;
       description "Percentage of buffer memory utilized";
     }
     leaf memory-system-total {
       type int32;
       description "Display the total system memory";
     }
     leaf memory-system-total-used {
       type int32;
       description "Display overall utilization of system memory";
     }
     leaf memory-system-total-util {
       type int32;
       description "Display overall %utilization of system memory";
     }
     leaf memory-control-plane {
       type int32;
       description "Display the total memory with control plane";
     }
     leaf memory-control-plane-used {
       type int32;
       description "Display the memory utilization of control plane mem";
     }
     leaf memory-control-plane-util {
       type int32;
       description "Display the %memory utilization of control plane mem";
     }
     leaf memory-data-plane {
       type int32;
       description "Display the total memory preallocated for data plane";
     }
     leaf memory-data-plane-used {
       type int32;
       description "Display the memory utilization of data plane mem";
     }
     leaf memory-data-plane-util {
       type int32;
       description "Display the %memory utilization of data plane mem";
     }
     leaf control-plane-cpu-count {
       type int32;
       description "Display the number of CPUS dedicated for control-plane";
     }
     leaf data-plane-cpu-count {
       type int32;
       description "Display the number of CPUS dedicated for data-plane";
     }
     leaf cpu-user {
       type int32;
       description "Percentage of CPU utilized by user processes";
     }
     leaf cpu-real-time {
       type int32;
       description "Percentage of CPU utilized by real-time threads";
     }
     leaf cpu-background {
       type int32;
       description "Percentage of CPU utilized by background processes";
     }
     leaf cpu-system {
       type int32;
       description "Percentage of CPU utilized by the kernel";
     }
     leaf cpu-interrupt {
       type int32;
       description "Percentage of CPU utilized by interrupt processing";
     }
     leaf cpu-idle {
       type int32;
       description "Percentage of CPU idle time";
     }
     leaf cpu-user1 {
       type int32;
       description "Percentage of CPU utilized by user processes";
     }
     leaf cpu-background1 {
       type int32;
       description "Percentage of CPU utilized by background processes";
     }
     leaf cpu-system1 {
       type int32;
       description "Percentage of CPU utilized by the kernel";
     }
     leaf cpu-interrupt1 {
       type int32;
       description "Percentage of CPU utilized by the Interrupt";
     }
     leaf cpu-idle1 {
       type int32;
       description "Percentage of CPU idle time";
     }
     leaf cpu-user2 {
       type int32;
       description "Percentage of CPU utilized by user processes";
     }
     leaf cpu-background2 {
       type int32;
       description "Percentage of CPU utilized by background processes";
     }
     leaf cpu-system2 {
       type int32;
       description "Percentage of CPU utilized by the kernel";
     }
     leaf cpu-interrupt2 {
       type int32;
       description "Percentage of CPU utilized by the Interrupt";
     }
     leaf cpu-idle2 {
       type int32;
       description "Percentage of CPU idle time";
     }
     leaf cpu-user3 {
       type int32;
       description "Percentage of CPU utilized by user processes";
     }
     leaf cpu-background3 {
       type int32;
       description "Percentage of CPU utilized by background processes";
     }
     leaf cpu-system3 {
       type int32;
       description "Percentage of CPU utilized by the kernel";
     }
     leaf cpu-interrupt3 {
       type int32;
       description "Percentage of CPU utilized by the Interrupt";
     }
     leaf cpu-idle3 {
       type int32;
       description "Percentage of CPU idle time";
     }
     leaf model {
       type string;
     }
     leaf serial-number {
       type string;
       description "Serial number of this component";
     }
     leaf start-time {
       type string;
       description "Time this component was started";
     }
     leaf up-time {
       type string;
       description "Length of time this component has been operational";
     }
     leaf last-reboot-reason {
       type string;
       description "Last reboot reason of routinge engine";
     }
     leaf load-average-one {
       type string;
     }
     leaf load-average-five {
       type string;
     }
     leaf load-average-fifteen {
       type string;
     }
     leaf bios-version {
       type string;
       description "Routing engine BIOS version";
     }
     leaf bios-date {
       type string;
       description "Routing engine BIOS date";
     }
     leaf bios-id {
       type string;
       description "Routing engine BIOS ID";
     }
     leaf loader-name {
       type string;
       description "Routing engine Loader name";
     }
     leaf loader-version {
       type string;
       description "Routing engine Loader version";
     }
     leaf icrt-version {
       type string;
       description "Routing engine iCRT version";
     }
   }
 }
 grouping scb-information-block {
   container brief {
     leaf cross-connect {
       type string;
     }
     leaf packet-scheduling {
       type string;
       description "Packet scheduling knob status";
     }
     list scb {
       leaf slot {
         type int32;
       }
       leaf state {
         type string;
         description "Status of the component";
       }
       leaf comment {
         type string;
       }
       leaf temperature {
         type string;
         description "Temperature of the item";
       }
       leaf cpu-total {
         type int32;
         description "Percentage of CPU utilized";
       }
       leaf cpu-interrupt {
         type int32;
         description "Percentage of CPU utilized by interrupt processing";
       }
       leaf memory-dram-size {
         type int32;
         description "DRAM";
       }
       leaf memory-heap-utilization {
         type int32;
         description "Percentage of heap memory utilized";
       }
       leaf memory-buffer-utilization {
         type int32;
         description "Percentage of buffer memory utilized";
       }
     }
   }
   container verbose {
     leaf cross-connect {
       type string;
     }
     leaf packet-scheduling {
       type string;
       description "Packet scheduling knob status";
     }
     leaf scb-type {
       type string;
     }
     list scb {
       leaf slot {
         type int32;
       }
       leaf state {
         type string;
         description "Status of the component";
       }
       leaf failover-count {
         type int32;
       }
       leaf temperature {
         type string;
         description "Temperature of the item";
       }
       leaf intake-temperature {
         type string;
       }
       leaf exhaust-temperature {
         type string;
       }
       leaf exhaust-a-temperature {
         type string;
         description "Exhaust A temperature";
       }
       leaf exhaust-b-temperature {
         type string;
         description "Exhaust B temperature";
       }
       leaf spp-temperature {
         type string;
       }
       leaf spr-temperature {
         type string;
       }
       leaf cpu-total {
         type int32;
         description "Percentage of CPU utilized";
       }
       leaf cpu-total-ukern {
         type int32;
       }
       leaf cpu-total-rt {
         type int32;
       }
       leaf cpu-interrupt {
         type int32;
         description "Percentage of CPU utilized by interrupt processing";
       }
       leaf memory-heap-utilization {
         type int32;
         description "Percentage of heap memory utilized";
       }
       leaf memory-buffer-utilization {
         type int32;
         description "Percentage of buffer memory utilized";
       }
       leaf memory-dram-size {
         type int32;
         description "DRAM";
       }
       leaf memory-sram-size {
         type int32;
         description "SRAM";
       }
       leaf memory-rldram-size {
         type int32;
         description "RLDRAM";
       }
       leaf memory-xr2-size {
         type int32;
         description "XR2";
       }
       leaf memory-ddr-dram-size {
         type int32;
         description "DDR DRAM";
       }
       leaf asic-name {
         type string;
       }
       leaf asic-information {
         type string;
       }
       leaf start-time {
         type string;
         description "Time this component was started";
       }
       leaf up-time {
         type string;
         description "Length of time this component has been operational";
       }
       leaf comment {
         type string;
       }
       leaf activate-count {
         type int32;
       }
       leaf reset-count {
         type int32;
       }
       leaf max-power-consumption {
         type int32;
       }
       leaf configured-bandwidth {
         type int32;
       }
       leaf operating-bandwidth {
         type int32;
       }
     }
   }
 }
 grouping chassis-location-block {
   list chassis-location-information {
     leaf country-code {
       type string;
       description "Country code";
     }
     leaf postal-code {
       type string;
       description "Postal code";
     }
     leaf npa-nxx {
       type string;
       description "Six digits of the phone number";
     }
     leaf altitude {
       type int32;
       description "Feet above (or below) sea level";
     }
     leaf lata {
       type string;
       description "Long distance service area";
     }
     leaf latitude {
       type string;
       description "Latitude";
     }
     leaf longitude {
       type string;
       description "Longitude";
     }
     leaf vcoord {
       type string;
       description "Bellcore vertical coordinate";
     }
     leaf hcoord {
       type string;
       description "Bellcore horizontal coordinate";
     }
     leaf building {
       type string;
       description "Building information";
     }
     leaf floor {
       type uint32;
       description "Floor in building";
     }
     leaf rack {
       type uint32;
       description "Rack";
     }
   }
 }
 grouping temperature-threshold-information-block {
   list temperature-threshold {
     description "Temperature threshold information for a component on the routing platform.";
   }
 }
 grouping power-management-information-block {
   list power-management {
     description "Information about JSeries Power Management";
     leaf power-mgmt-device {
       type string;
       description "Type of device";
     }
     leaf power-mgmt-low-power {
       type int32;
       description "Low power Rating tokens";
     }
     leaf power-mgmt-high-power {
       type int32;
       description "High power Rating tokens";
     }
     leaf power-mgmt-heat {
       type int32;
       description "Heat Rating tokens";
     }
     leaf power-mgmt-state {
       type string;
       description "Ratings exceed Chassis limits or not";
     }
   }
 }
 grouping chassis-oss-map-block {
   leaf chassis-model {
     type string;
     description "Actual chassis model";
   }
   leaf oss-map {
     type string;
     description "Configured OSS chassis model";
   }
 }
 }
