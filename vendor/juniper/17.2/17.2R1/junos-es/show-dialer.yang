/*
 * Copyright (c) 2017 Juniper Networks, Inc.
 * All rights reserved.
 */
 module show-dialer {
  namespace "http://yang.juniper.net/yang/1.1/jrpc/show-dialer/junos-es/17.2R1.13";
  prefix show-dialer;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-dialer-interface-information {
     description "Show interface information";
     input {
       leaf level {
         type enumeration {
           enum "brief" {
             description "Display brief output";
           }
           enum "detail" {
             description "Display detailed output";
           }
         }
       }
       leaf interface-name {
         description "Name of dialer logical interface";
         type string;
       }
     }
     output {
       container dialer-interface-information {
         uses dialer-interface-information-block;
       }
     }
   }
   rpc get-dialer-pool-information {
     description "Show pool information";
     input {
       leaf level {
         type enumeration {
           enum "brief" {
             description "Display brief output";
           }
           enum "detail" {
             description "Display detailed output";
           }
         }
       }
       leaf pool-name {
         description "Dialer pool identifier";
         type string;
       }
     }
     output {
       container dialer-pool-information {
         uses dialer-pool-information-block;
       }
     }
   }
   rpc get-dialer-defaults-information {
     description "Show dialer services software defaults";
     output {
       container dialer-defaults-information {
         uses dialer-defaults-information-block;
       }
     }
   }
 grouping dialer-interface-information-block {
   container brief {
     container dialer-interface {
       leaf dialer-interface-name {
         type string;
         description "Interface name";
       }
       leaf dialer-interface-state {
         type string;
         description "Dialer interface state";
       }
       leaf pool-id {
         type string;
         description "Pool identifier";
       }
       leaf primary-interface {
         type string;
         description "Primary interface";
       }
       container dialer-interface-flags {
         description "Flags indicating interface configuration";
       }
       list dial-string-list {
         list detail {
           leaf dial-string {
             type string;
             description "Dial string";
           }
         }
         list ifinfo {
           leaf dial-string {
             type string;
             description "Dial string";
           }
         }
       }
       list sub-interface-list {
         list brief {
           leaf sub-interface-name {
             type string;
             description "Subordinate interface name";
           }
         }
         list detail {
           leaf sub-interface-name {
             type string;
             description "Subordinate interface name";
           }
         }
         list ifinfo {
           leaf sub-interface-name {
             type string;
             description "Subordinate interface name";
           }
         }
       }
       list watch-list {
         list brief {
           leaf watch-route {
             type string;
             description "Watch route";
           }
         }
         list detail {
           leaf watch-route {
             type string;
             description "Watch route";
           }
         }
         list ifinfo {
           leaf watch-route {
             type string;
             description "Watch route";
           }
         }
       }
     }
   }
   container detail {
     container dialer-interface {
       leaf dialer-interface-name {
         type string;
         description "Interface name";
       }
       leaf dialer-interface-state {
         type string;
         description "Dialer interface state";
       }
       leaf pool-id {
         type string;
         description "Pool identifier";
       }
       leaf primary-interface {
         type string;
         description "Primary interface";
       }
       leaf activation-delay {
         type string;
         description "Activation delay";
       }
       leaf deactivation-delay {
         type string;
         description "Deactivation delay";
       }
       leaf activation-delay-elapsed {
         type string;
         description "Activation delay elapsed";
       }
       leaf deactivation-delay-elapsed {
         type string;
         description "Deactivation delay elapsed";
       }
       leaf call-idle-timeout {
         type string;
         description "Call idle timeout";
       }
       leaf initial-route-check {
         type string;
         description "Initial route check delay";
       }
       leaf redial-delay {
         type string;
         description "Delay before dialer dials out again (seconds)";
       }
       leaf callback-wait-period {
         type string;
         description "Delay before dialer attempts callback (seconds)";
       }
       leaf callback-wait-period-elapsed {
         type string;
         description "Number of seconds in callback wait period that have elapsed";
       }
       leaf load-threshold {
         type string;
         description "Load threshold that determines when interfaces are added to bundle";
       }
       leaf load-interval {
         type string;
         description "Interval over which average load is calculated";
       }
       container dialer-interface-flags {
         description "Flags indicating interface configuration";
       }
       list dial-string-list {
         list detail {
           leaf dial-string {
             type string;
             description "Dial string";
           }
         }
         list ifinfo {
           leaf dial-string {
             type string;
             description "Dial string";
           }
         }
       }
       list sub-interface-list {
         list brief {
           leaf sub-interface-name {
             type string;
             description "Subordinate interface name";
           }
         }
         list detail {
           leaf sub-interface-name {
             type string;
             description "Subordinate interface name";
           }
         }
         list ifinfo {
           leaf sub-interface-name {
             type string;
             description "Subordinate interface name";
           }
         }
       }
       list watch-list {
         list brief {
           leaf watch-route {
             type string;
             description "Watch route";
           }
         }
         list detail {
           leaf watch-route {
             type string;
             description "Watch route";
           }
         }
         list ifinfo {
           leaf watch-route {
             type string;
             description "Watch route";
           }
         }
       }
     }
   }
   container ifinfo {
     container dialer-interface {
       leaf dialer-interface-state {
         type string;
         description "Dialer interface state";
       }
       leaf pool-id {
         type string;
         description "Pool identifier";
       }
       leaf primary-interface {
         type string;
         description "Primary interface";
       }
       leaf activation-delay {
         type string;
         description "Activation delay";
       }
       leaf deactivation-delay {
         type string;
         description "Deactivation delay";
       }
       leaf activation-delay-elapsed {
         type string;
         description "Activation delay elapsed";
       }
       leaf deactivation-delay-elapsed {
         type string;
         description "Deactivation delay elapsed";
       }
       leaf call-idle-timeout {
         type string;
         description "Call idle timeout";
       }
       leaf initial-route-check {
         type string;
         description "Initial route check delay";
       }
       leaf redial-delay {
         type string;
         description "Delay before dialer dials out again (seconds)";
       }
       leaf callback-wait-period {
         type string;
         description "Delay before dialer attempts callback (seconds)";
       }
       leaf callback-wait-period-elapsed {
         type string;
         description "Number of seconds in callback wait period that have elapsed";
       }
       leaf load-threshold {
         type string;
         description "Load threshold that determines when interfaces are added to bundle";
       }
       leaf load-interval {
         type string;
         description "Interval over which average load is calculated";
       }
       list dial-string-list {
         list detail {
           leaf dial-string {
             type string;
             description "Dial string";
           }
         }
         list ifinfo {
           leaf dial-string {
             type string;
             description "Dial string";
           }
         }
       }
       list sub-interface-list {
         list brief {
           leaf sub-interface-name {
             type string;
             description "Subordinate interface name";
           }
         }
         list detail {
           leaf sub-interface-name {
             type string;
             description "Subordinate interface name";
           }
         }
         list ifinfo {
           leaf sub-interface-name {
             type string;
             description "Subordinate interface name";
           }
         }
       }
       list watch-list {
         list brief {
           leaf watch-route {
             type string;
             description "Watch route";
           }
         }
         list detail {
           leaf watch-route {
             type string;
             description "Watch route";
           }
         }
         list ifinfo {
           leaf watch-route {
             type string;
             description "Watch route";
           }
         }
       }
     }
   }
 }
 grouping dialer-pool-information-block {
   container brief {
     container dialer-pool {
       leaf pool-id {
         type string;
         description "Pool identifier";
       }
       list pool-member-list {
         container dialer-info {
         }
         container sub-info {
         }
       }
     }
   }
   container detail {
     container dialer-pool {
       leaf pool-id {
         type string;
         description "Pool identifier";
       }
       list pool-member-list {
         container dialer-info {
         }
         container sub-info {
         }
       }
     }
   }
 }
 grouping dialer-defaults-information-block {
   leaf default-idle-timeout {
     type int32;
     description "Default value of dialer idle timeout";
   }
   leaf default-activation-delay {
     type int32;
     description "Default value of dialer activation delay";
   }
   leaf default-deactivation-delay {
     type int32;
     description "Default value of dialer deactivation delay";
   }
   leaf default-initial-route-check {
     type int32;
     description "Default value of dialer watch initial route check time";
   }
   leaf default-pool-priority {
     type int32;
     description "Default value of dialer pool priority";
   }
   leaf default-load-threshold {
     type int32;
     description "Default value of dialer load threshold";
   }
   leaf default-load-interval {
     type int32;
     description "Default value of dialer load interval";
   }
   leaf default-redial-delay {
     type int32;
     description "Default value for dialer redial delay which determines how long to wait before dialer attempts to redial";
   }
   leaf default-callback-wait-period {
     type int32;
     description "Default value of dialer callback wait period which determines how long to wait before dialer attempts a callback";
   }
 }
 }
