/*
 * Copyright (c) 2017 Juniper Networks, Inc.
 * All rights reserved.
 */
 module show-dvmrp {
  namespace "http://yang.juniper.net/yang/1.1/jrpc/show-dvmrp/junos-es/17.2R1.13";
  prefix show-dvmrp;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-dvmrp-neighbors-information {
     description "Show DVMRP neighbors";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container dvmrp-neighbors-information {
         uses dvmrp-neighbors-information-block;
       }
     }
   }
   rpc get-dvmrp-interfaces-information {
     description "Show DVMRP interfaces";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container dvmrp-interfaces-information {
         uses dvmrp-interfaces-information-block;
       }
     }
   }
   rpc get-dvmrp-prunes-information {
     description "Show DVMRP prunes";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf type {
         default "all";
         type enumeration {
           enum "all" {
             description "Display both received and transmitted prunes";
           }
           enum "rx" {
             description "Display received prunes";
           }
           enum "tx" {
             description "Display transmitted prunes";
           }
         }
       }
     }
     output {
       container dvmrp-prunes-information {
         uses dvmrp-prunes-information-block;
       }
     }
   }
   rpc get-dvmrp-prefix-information {
     description "Show DVMRP prefixes";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf prefix {
         description "DVMRP prefix";
         type string;
       }
     }
     output {
       container dvmrp-prefix-information {
         uses dvmrp-prefix-information-block;
       }
     }
   }
 grouping dvmrp-neighbors-information-block {
   list dvmrp-instance {
     leaf instance-name {
       type string;
     }
     list dvmrp-interface {
       leaf interface-name {
         type string;
         description "Name of interface";
       }
       leaf dvmrp-interface-state {
         type string;
       }
       leaf dvmrp-interface-leaf {
         type string;
       }
       leaf dvmrp-interface-metric {
         type int32;
       }
       leaf dvmrp-interface-announcements {
         type int32;
       }
       leaf dvmrp-interface-mode {
         type string;
       }
       leaf dvmrp-interface-holdtime {
         type int32;
       }
     }
     list dvmrp-graft {
       leaf multicast-group-address {
         type ipaddr;
         description "Group address";
       }
       leaf multicast-source-address {
         type ipaddr;
         description "Source address";
       }
       leaf dvmrp-graft-expire-time {
         type int32;
       }
       leaf dvmrp-neighbor-address {
         type ipaddr;
       }
     }
     list dvmrp-neighbor {
       leaf dvmrp-neighbor-address {
         type ipaddr;
       }
       leaf interface-name {
         type string;
         description "Name of interface";
       }
       leaf dvmrp-major-version {
         type int32;
       }
       leaf dvmrp-minor-version {
         type int32;
       }
       leaf dvmrp-neighbor-routes {
         type int32;
       }
       leaf dvmrp-neighbor-timeout {
         type int32;
       }
       leaf dvmrp-neighbor-transitions {
         type int32;
       }
       container dvmrp-capability-flags {
         leaf dvmrp-neighbor-one-way {
           type empty;
         }
         leaf dvmrp-neighbor-prune {
           type empty;
         }
         leaf dvmrp-neighbor-generation-id {
           type empty;
         }
         leaf dvmrp-neighbor-mtrace {
           type empty;
         }
         leaf dvmrp-neighbor-leave {
           type empty;
         }
         leaf dvmrp-neighbor-snmp {
           type empty;
         }
         leaf dvmrp-neighbor-netmask {
           type empty;
         }
       }
     }
     list dvmrp-prefix-entry {
       leaf dvmrp-prefix {
         type ipaddr;
       }
       leaf dvmrp-prefix-length {
         type int32;
       }
       leaf dvmrp-next-hop {
         type ipaddr;
       }
       leaf dvmrp-prefix-age {
         type string;
       }
       list dvmrp-group {
         leaf multicast-group-address {
           type ipaddr;
           description "Group address";
         }
         leaf dvmrp-prunes-sent {
           type int32;
         }
         leaf dvmrp-grafts-sent {
           type int32;
         }
         leaf dvmrp-cache-lifetime {
           type int32;
         }
         leaf dvmrp-prune-time {
           type int32;
         }
         leaf dvmrp-prune-lifetime {
           type int32;
         }
         list dvmrp-prune {
           leaf dvmrp-neighbor-address {
             type ipaddr;
           }
         }
       }
     }
     list dvmrp-prune {
       leaf multicast-group-address {
         type ipaddr;
         description "Group address";
       }
       leaf multicast-source-address {
         type ipaddr;
         description "Source address";
       }
       leaf multicast-source-prefix-length {
         type uint32;
         description "Source prefix length";
       }
       leaf dvmrp-prune-timeout {
         type int32;
       }
       leaf dvmrp-neighbor-address {
         type ipaddr;
       }
     }
   }
 }
 grouping dvmrp-interfaces-information-block {
   list dvmrp-instance {
     leaf instance-name {
       type string;
     }
     list dvmrp-interface {
       leaf interface-name {
         type string;
         description "Name of interface";
       }
       leaf dvmrp-interface-state {
         type string;
       }
       leaf dvmrp-interface-leaf {
         type string;
       }
       leaf dvmrp-interface-metric {
         type int32;
       }
       leaf dvmrp-interface-announcements {
         type int32;
       }
       leaf dvmrp-interface-mode {
         type string;
       }
       leaf dvmrp-interface-holdtime {
         type int32;
       }
     }
     list dvmrp-graft {
       leaf multicast-group-address {
         type ipaddr;
         description "Group address";
       }
       leaf multicast-source-address {
         type ipaddr;
         description "Source address";
       }
       leaf dvmrp-graft-expire-time {
         type int32;
       }
       leaf dvmrp-neighbor-address {
         type ipaddr;
       }
     }
     list dvmrp-neighbor {
       leaf dvmrp-neighbor-address {
         type ipaddr;
       }
       leaf interface-name {
         type string;
         description "Name of interface";
       }
       leaf dvmrp-major-version {
         type int32;
       }
       leaf dvmrp-minor-version {
         type int32;
       }
       leaf dvmrp-neighbor-routes {
         type int32;
       }
       leaf dvmrp-neighbor-timeout {
         type int32;
       }
       leaf dvmrp-neighbor-transitions {
         type int32;
       }
       container dvmrp-capability-flags {
         leaf dvmrp-neighbor-one-way {
           type empty;
         }
         leaf dvmrp-neighbor-prune {
           type empty;
         }
         leaf dvmrp-neighbor-generation-id {
           type empty;
         }
         leaf dvmrp-neighbor-mtrace {
           type empty;
         }
         leaf dvmrp-neighbor-leave {
           type empty;
         }
         leaf dvmrp-neighbor-snmp {
           type empty;
         }
         leaf dvmrp-neighbor-netmask {
           type empty;
         }
       }
     }
     list dvmrp-prefix-entry {
       leaf dvmrp-prefix {
         type ipaddr;
       }
       leaf dvmrp-prefix-length {
         type int32;
       }
       leaf dvmrp-next-hop {
         type ipaddr;
       }
       leaf dvmrp-prefix-age {
         type string;
       }
       list dvmrp-group {
         leaf multicast-group-address {
           type ipaddr;
           description "Group address";
         }
         leaf dvmrp-prunes-sent {
           type int32;
         }
         leaf dvmrp-grafts-sent {
           type int32;
         }
         leaf dvmrp-cache-lifetime {
           type int32;
         }
         leaf dvmrp-prune-time {
           type int32;
         }
         leaf dvmrp-prune-lifetime {
           type int32;
         }
         list dvmrp-prune {
           leaf dvmrp-neighbor-address {
             type ipaddr;
           }
         }
       }
     }
     list dvmrp-prune {
       leaf multicast-group-address {
         type ipaddr;
         description "Group address";
       }
       leaf multicast-source-address {
         type ipaddr;
         description "Source address";
       }
       leaf multicast-source-prefix-length {
         type uint32;
         description "Source prefix length";
       }
       leaf dvmrp-prune-timeout {
         type int32;
       }
       leaf dvmrp-neighbor-address {
         type ipaddr;
       }
     }
   }
 }
 grouping dvmrp-prunes-information-block {
   list dvmrp-instance {
     leaf instance-name {
       type string;
     }
     list dvmrp-interface {
       leaf interface-name {
         type string;
         description "Name of interface";
       }
       leaf dvmrp-interface-state {
         type string;
       }
       leaf dvmrp-interface-leaf {
         type string;
       }
       leaf dvmrp-interface-metric {
         type int32;
       }
       leaf dvmrp-interface-announcements {
         type int32;
       }
       leaf dvmrp-interface-mode {
         type string;
       }
       leaf dvmrp-interface-holdtime {
         type int32;
       }
     }
     list dvmrp-graft {
       leaf multicast-group-address {
         type ipaddr;
         description "Group address";
       }
       leaf multicast-source-address {
         type ipaddr;
         description "Source address";
       }
       leaf dvmrp-graft-expire-time {
         type int32;
       }
       leaf dvmrp-neighbor-address {
         type ipaddr;
       }
     }
     list dvmrp-neighbor {
       leaf dvmrp-neighbor-address {
         type ipaddr;
       }
       leaf interface-name {
         type string;
         description "Name of interface";
       }
       leaf dvmrp-major-version {
         type int32;
       }
       leaf dvmrp-minor-version {
         type int32;
       }
       leaf dvmrp-neighbor-routes {
         type int32;
       }
       leaf dvmrp-neighbor-timeout {
         type int32;
       }
       leaf dvmrp-neighbor-transitions {
         type int32;
       }
       container dvmrp-capability-flags {
         leaf dvmrp-neighbor-one-way {
           type empty;
         }
         leaf dvmrp-neighbor-prune {
           type empty;
         }
         leaf dvmrp-neighbor-generation-id {
           type empty;
         }
         leaf dvmrp-neighbor-mtrace {
           type empty;
         }
         leaf dvmrp-neighbor-leave {
           type empty;
         }
         leaf dvmrp-neighbor-snmp {
           type empty;
         }
         leaf dvmrp-neighbor-netmask {
           type empty;
         }
       }
     }
     list dvmrp-prefix-entry {
       leaf dvmrp-prefix {
         type ipaddr;
       }
       leaf dvmrp-prefix-length {
         type int32;
       }
       leaf dvmrp-next-hop {
         type ipaddr;
       }
       leaf dvmrp-prefix-age {
         type string;
       }
       list dvmrp-group {
         leaf multicast-group-address {
           type ipaddr;
           description "Group address";
         }
         leaf dvmrp-prunes-sent {
           type int32;
         }
         leaf dvmrp-grafts-sent {
           type int32;
         }
         leaf dvmrp-cache-lifetime {
           type int32;
         }
         leaf dvmrp-prune-time {
           type int32;
         }
         leaf dvmrp-prune-lifetime {
           type int32;
         }
         list dvmrp-prune {
           leaf dvmrp-neighbor-address {
             type ipaddr;
           }
         }
       }
     }
     list dvmrp-prune {
       leaf multicast-group-address {
         type ipaddr;
         description "Group address";
       }
       leaf multicast-source-address {
         type ipaddr;
         description "Source address";
       }
       leaf multicast-source-prefix-length {
         type uint32;
         description "Source prefix length";
       }
       leaf dvmrp-prune-timeout {
         type int32;
       }
       leaf dvmrp-neighbor-address {
         type ipaddr;
       }
     }
   }
 }
 grouping dvmrp-prefix-information-block {
   list dvmrp-instance {
     leaf instance-name {
       type string;
     }
     list dvmrp-interface {
       leaf interface-name {
         type string;
         description "Name of interface";
       }
       leaf dvmrp-interface-state {
         type string;
       }
       leaf dvmrp-interface-leaf {
         type string;
       }
       leaf dvmrp-interface-metric {
         type int32;
       }
       leaf dvmrp-interface-announcements {
         type int32;
       }
       leaf dvmrp-interface-mode {
         type string;
       }
       leaf dvmrp-interface-holdtime {
         type int32;
       }
     }
     list dvmrp-graft {
       leaf multicast-group-address {
         type ipaddr;
         description "Group address";
       }
       leaf multicast-source-address {
         type ipaddr;
         description "Source address";
       }
       leaf dvmrp-graft-expire-time {
         type int32;
       }
       leaf dvmrp-neighbor-address {
         type ipaddr;
       }
     }
     list dvmrp-neighbor {
       leaf dvmrp-neighbor-address {
         type ipaddr;
       }
       leaf interface-name {
         type string;
         description "Name of interface";
       }
       leaf dvmrp-major-version {
         type int32;
       }
       leaf dvmrp-minor-version {
         type int32;
       }
       leaf dvmrp-neighbor-routes {
         type int32;
       }
       leaf dvmrp-neighbor-timeout {
         type int32;
       }
       leaf dvmrp-neighbor-transitions {
         type int32;
       }
       container dvmrp-capability-flags {
         leaf dvmrp-neighbor-one-way {
           type empty;
         }
         leaf dvmrp-neighbor-prune {
           type empty;
         }
         leaf dvmrp-neighbor-generation-id {
           type empty;
         }
         leaf dvmrp-neighbor-mtrace {
           type empty;
         }
         leaf dvmrp-neighbor-leave {
           type empty;
         }
         leaf dvmrp-neighbor-snmp {
           type empty;
         }
         leaf dvmrp-neighbor-netmask {
           type empty;
         }
       }
     }
     list dvmrp-prefix-entry {
       leaf dvmrp-prefix {
         type ipaddr;
       }
       leaf dvmrp-prefix-length {
         type int32;
       }
       leaf dvmrp-next-hop {
         type ipaddr;
       }
       leaf dvmrp-prefix-age {
         type string;
       }
       list dvmrp-group {
         leaf multicast-group-address {
           type ipaddr;
           description "Group address";
         }
         leaf dvmrp-prunes-sent {
           type int32;
         }
         leaf dvmrp-grafts-sent {
           type int32;
         }
         leaf dvmrp-cache-lifetime {
           type int32;
         }
         leaf dvmrp-prune-time {
           type int32;
         }
         leaf dvmrp-prune-lifetime {
           type int32;
         }
         list dvmrp-prune {
           leaf dvmrp-neighbor-address {
             type ipaddr;
           }
         }
       }
     }
     list dvmrp-prune {
       leaf multicast-group-address {
         type ipaddr;
         description "Group address";
       }
       leaf multicast-source-address {
         type ipaddr;
         description "Source address";
       }
       leaf multicast-source-prefix-length {
         type uint32;
         description "Source prefix length";
       }
       leaf dvmrp-prune-timeout {
         type int32;
       }
       leaf dvmrp-neighbor-address {
         type ipaddr;
       }
     }
   }
 }
 }
