/*
 * Copyright (c) 2017 Juniper Networks, Inc.
 * All rights reserved.
 */
 module show-system {
  namespace "http://yang.juniper.net/yang/1.1/jrpc/show-system/junos-es/17.2R1.13";
  prefix show-system;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-system-alarm-information {
     description "Show system alarm status";
     output {
       container alarm-information {
         uses alarm-information-block;
       }
     }
   }
   rpc get-commit-information {
     description "Show pending commit requests (if any) and commit history";
     output {
       container commit-information {
         uses commit-information-block;
       }
     }
   }
   rpc get-commit-revision-information {
     description "Show latest commit revision number for shared database";
     input {
       leaf level {
         default "brief";
         type enumeration {
           enum "brief" {
             description "Display brief output";
           }
           enum "detail" {
             description "Display detailed output";
           }
         }
       }
     }
     output {
       container commit-revision-information {
         uses commit-revision-information-block;
       }
     }
   }
   rpc get-commit-server-information {
     description "Show commit server detail";
     input {
       leaf status {
         description "Display commit server status";
         type empty;
       }
     }
     output {
       container commit-server-information {
         uses commit-server-information-block;
       }
     }
   }
   rpc get-commit-server-queue-information {
     description "Show transaction ids in the commit queue";
     input {
       container job-status-or-id {
         choice job-status-or-id_c {
           case id {
             leaf id {
               description "Show commit queue id";
               type uint32;
             }
           }
           case job-status {
             leaf job-status {
               description "Restrict display by job status";
               default "all";
               type enumeration {
                 enum "all" {
                   description "Display all jobs";
                 }
                 enum "error" {
                   description "Display jobs that had errors";
                 }
                 enum "success" {
                   description "Display jobs that succeeded";
                 }
                 enum "pending" {
                   description "Display jobs that are pending";
                 }
               }
             }
           }
         }
       }
       leaf patch {
         description "Display commit queue patch";
         type empty;
       }
     }
     output {
       container commit-server-queue-information {
         uses commit-server-queue-information-block;
       }
     }
   }
   rpc get-rescue-information {
     description "Show rescue configuration";
     input {
       leaf format {
         description "Output format of configuration (XML or text or JSON)";
         type enumeration {
           enum "text" {
             description "Output text configuration";
           }
           enum "xml" {
             description "Output XML configuration";
           }
           enum "json" {
             description "Output JSON configuration";
           }
         }
       }
     }
     output {
       container rescue-information {
         uses rescue-information-block;
       }
     }
   }
   rpc get-system-archival {
     description "List files queued up for archive transfer";
     output {
       container directory-list {
         uses directory-list-block;
       }
     }
   }
   rpc get-database-usage {
     description "Show configuration database usage";
     output {
       container database-usage {
         uses database-usage-block;
       }
     }
   }
   rpc get-rollback-information {
     description "Show rolled back configuration";
     input {
       leaf rollback {
         description "Rollback number to display";
         type uint32 {
           range "0 .. 49";
         }
         mandatory true;
       }
       leaf compare {
         description "Rollback number to compare";
         type uint32 {
           range "0 .. 49";
         }
       }
       leaf format {
         description "Output format of configuration (XML or text or JSON)";
         type enumeration {
           enum "text" {
             description "Output text configuration";
           }
           enum "xml" {
             description "Output XML configuration";
           }
           enum "json" {
             description "Output JSON configuration";
           }
         }
       }
     }
     output {
       container rollback-information {
         uses rollback-information-block;
       }
     }
   }
   rpc get-system-uptime-information {
     description "Show time since system and processes started";
     input {
       container dcf-role {
         description "Device type";
         choice dcf-role_c {
           case interconnect-device {
           }
           case node-group {
           }
           case infrastructure {
           }
           case director-group {
           }
         }
       }
     }
     output {
       container system-uptime-information {
         uses system-uptime-information-block;
       }
     }
   }
   rpc get-license-summary-information {
     description "Show feature licenses information";
     output {
       container license-summary-information {
         uses license-summary-information-block;
       }
     }
   }
   rpc get-license-information {
     description "Show installed feature licenses";
     output {
       container license-information {
         uses license-information-block;
       }
     }
   }
   rpc get-license-key-information {
     description "Show license keys";
     output {
       container license-key-information {
         uses license-key-information-block;
       }
     }
   }
   rpc get-license-usage-summary {
     description "Show licensed features";
     output {
       container license-usage-summary {
         uses license-usage-summary-block;
       }
     }
   }
   rpc get-license-revoked-info {
     description "Show revoked licenses information";
     status deprecated;
     output {
       container license-revoked-information {
         uses license-revoked-information-block;
       }
     }
   }
   rpc get-lsys-license-status {
     description "Show logical system status";
     input {
       container lsys {
         choice lsys_c {
           case logical-system {
             leaf logical-system {
               description "Logical-system name";
               type string;
             }
           }
           case root-logical-system {
             leaf root-logical-system {
               description "Root logical-system (default)";
               type empty;
             }
           }
         }
       }
     }
   }
   rpc get-system-information {
     description "Show system information";
     output {
       container system-information {
         uses system-information-block;
       }
     }
   }
   rpc get-system-login-lockout-information {
     description "Show user accounts not permitted logins";
     input {
       leaf user {
         description "Name of user";
         type string;
       }
     }
     output {
       container system-login-lockout-information {
         uses system-login-lockout-information-block;
       }
     }
   }
   rpc get-yang-schema {
     description "Show system schema in various formats";
     input {
       leaf format {
         description "The data modeling language of the schema";
         default "yang";
         type enumeration {
           enum "yang" {
             description "YANG (default)";
           }
         }
       }
       leaf identifier {
         description "Module to be shown";
         type enumeration {
           enum "configuration" {
             description "Junos configuration module";
           }
           enum "junos-extension" {
             description "Junos extension module";
           }
           enum "juniper-command" {
             description "Juniper command module";
           }
           enum "junos-extension-odl" {
             description "Junos ODL extension module";
           }
         }
         mandatory true;
       }
       leaf version {
         description "Version of the schema requested";
         type string;
       }
       leaf output-file-name {
         description "Filename to save generated YANG module";
         status deprecated;
         type string;
       }
       leaf output-directory {
         description "Directory to save generated YANG module";
         type string;
       }
       leaf-list filter {
         description "Apply filter for yang module";
         type string;
       }
       leaf module-name {
         description "Name of module";
         type string {
           junos:posix-pattern "^[a-zA-Z_][[:alnum:]_.-]{0,63}$";
           junos:pattern-message "Upto 64 characters beginning with ASCII letters/underscore, followed by ASCII letters, digits, underscores, hyphens, dots";
         }
       }
     }
   }
   rpc get-system-yang-packages {
     description "Show YANG package(s) installed on system";
     input {
       leaf id {
         description "Show YANG package with ID";
         type string;
       }
     }
     output {
       container yang-pkgs-info {
         uses yang-pkgs-info-block;
       }
     }
   }
   rpc get-service-deployment-service-information {
     description "Show service deployment service information";
   }
   rpc get-system-services-reverse-information {
     description "Show reverse telnet/SSH connection information";
     output {
       container system-services-reverse-information {
         uses system-services-reverse-information-block;
       }
     }
   }
   rpc get-dhcp-binding-information {
     description "Show DHCP client binding information";
     input {
       leaf detail {
         description "Display detailed information";
         type empty;
       }
       leaf address {
         description "Address of DHCP client binding";
         type ipaddr;
       }
     }
     output {
       container dhcp-binding-information {
         uses dhcp-binding-information-block;
       }
     }
   }
   rpc get-dhcp-conflict-information {
     description "Show DHCP address conflict";
     output {
       container dhcp-conflict-information {
         uses dhcp-conflict-information-block;
       }
     }
   }
   rpc get-dhcp-global-information {
     description "Show DHCP global scope information";
     output {
       container dhcp-global-information {
         uses dhcp-global-information-block;
       }
     }
   }
   rpc get-dhcp-pool-information {
     description "Show DHCP address pool information";
     input {
       leaf detail {
         description "Display detailed information";
         type empty;
       }
       leaf subnet-address {
         description "Logical subnet of address pool";
         type ipprefix;
       }
     }
     output {
       container dhcp-pool-information {
         uses dhcp-pool-information-block;
       }
     }
   }
   rpc get-dhcp-statistics-information {
     description "Show DHCP statistics";
     output {
       container dhcp-statistics-information {
         uses dhcp-statistics-information-block;
       }
     }
   }
   rpc get-dhcp-client-information {
     description "Show DHCP client information";
     input {
       leaf statistics {
         description "Show DHCP client statistics";
         type empty;
       }
       leaf interface-name {
         description "Interface name of DHCP client";
         type string;
       }
     }
     output {
       container dhcp-client-information {
         uses dhcp-client-information-block;
       }
     }
   }
   rpc get-dhcp-helper-statistics {
     description "Show DHCP relay statistics information";
     output {
       container dhcp-helper-statistics {
         uses dhcp-helper-statistics-block;
       }
     }
   }
   rpc get-dns-proxy-information {
     description "Show DNS proxy statistic information";
   }
   rpc get-dns-proxy-cache-information {
     description "Show DNS proxy nameserver cache";
     input {
       leaf view-name {
         description "Show DNS proxy nameserver view cache";
         type string;
       }
     }
   }
   rpc get-dns-proxy-propogate-setting {
     description "Show DNS proxy dhcp/pppoe propogated name-server";
   }
   rpc get-dynamic-dns-client-information {
     description "Show Dynamic DNS client information";
     input {
       leaf level {
         default "brief";
         type enumeration {
           enum "detail" {
             description "Display detailed output";
           }
           enum "brief" {
             description "Display brief output";
           }
         }
       }
       leaf hostname {
         description "Dynamic DNS hostname";
         type string;
       }
     }
   }
   rpc get-system-core-dumps {
     description "Show system core files";
     output {
       container directory-list {
         uses directory-list-block;
       }
     }
   }
   rpc get-core-file-information {
     description "Display the stack trace of core file";
     status deprecated;
     input {
       leaf display-style {
         description "Option for viewing brief/detailed info about core file";
         default "brief";
         type enumeration {
           enum "detail" {
             description "View stack trace with details of binary";
           }
           enum "brief" {
             description "View details of binary";
           }
         }
       }
       leaf core-filename {
         description "Name of core file";
         type filename;
         mandatory true;
       }
     }
     output {
       container core-information {
         uses core-information-block;
       }
     }
   }
   rpc get-directory-usage-information {
     description "Show local directory information";
     input {
       leaf path {
         description "Path of root directory to traverse";
         type string;
       }
       leaf depth {
         description "Depth of directories to traverse";
         type uint32;
       }
     }
     output {
       container directory-usage-information {
         uses directory-usage-information-block;
       }
     }
   }
   rpc get-auto-snapshot-information {
     description "Show auto-snapshot status when system booted from alternate slice";
     output {
       container auto-snapshot-information {
         uses auto-snapshot-information-block;
       }
     }
   }
   rpc get-snapshot-information {
     description "Show snapshot information";
     input {
       leaf slice {
         description "Show snapshot information from specified partition";
         type enumeration {
           enum "1" {
             description "Show snapshot information from first partition";
           }
           enum "2" {
             description "Show snapshot information from second partition";
           }
           enum "alternate" {
             description "Show snapshot information from alternate partition";
           }
         }
       }
       leaf media {
         description "Media to show snapshot information from";
         type enumeration {
           enum "removable-compact-flash" {
             description "Show snapshot information from removable compact flash";
           }
           enum "compact-flash" {
             description "Show snapshot information from compact flash";
           }
           enum "usb" {
             description "Show snapshot information from device connected to USB port";
           }
           enum "usb0" {
             description "Show snapshot information from device connected to USB0";
           }
           enum "usb1" {
             description "Show snapshot information from device connected to USB1";
           }
           enum "hard-disk" {
             description "Show snapshot information from hard disk";
           }
           enum "internal" {
             description "Show snapshot information from internal flash";
           }
           enum "external" {
             description "Show snapshot information from external flash";
           }
         }
       }
     }
     output {
       container snapshot-information {
         uses snapshot-information-block;
       }
     }
   }
   rpc get-software-installation-status {
     description "Show status of software installation";
     output {
       container software-installation-status {
         uses software-installation-status-block;
       }
     }
   }
   rpc get-package-backup-information {
     description "Show status of old system software packages";
     output {
       container package-backup-information {
         uses package-backup-information-block;
       }
     }
   }
   rpc get-process-health-information {
     description "Show process health information";
     input {
       container name_pid_choice {
         choice name_pid_choice_c {
           case process-name {
             leaf process-name {
               description "Process name";
               type string;
             }
           }
           case pid {
             leaf pid {
               description "Process identifier";
               type uint32 {
                 range "1 .. 99999";
               }
             }
           }
         }
       }
     }
     output {
       container system-processes-health-information {
         uses system-processes-health-information-block;
       }
     }
   }
   rpc get-system-process-resource-limits {
     description "Show process resource limits";
     input {
       leaf process-name {
         description "Process name";
         type string;
       }
       leaf verbosity_level {
         default "brief";
         type enumeration {
           enum "brief" {
             description "Display brief output (default)";
           }
           enum "detail" {
             description "Display detailed output";
           }
         }
       }
     }
     output {
       container secpolinfo-policy-information {
         uses secpolinfo-policy-information-block;
       }
     }
   }
   rpc get-statistics-information {
     description "Show statistics for protocol";
     input {
       leaf protocol {
         type enumeration {
           enum "ip" {
             description "IP version 4 (IPv4)";
           }
           enum "ip6" {
             description "IP version 6 (IPv6)";
           }
           enum "icmp" {
             description "Internet Control Message Protocol";
           }
           enum "nd6" {
             description "Internet Control Message Protocol for IPv6";
           }
           enum "icmp6" {
             description "Internet Control Message Protocol for IPv6";
           }
           enum "tcp" {
             description "Transmission Control Protocol";
           }
           enum "udp" {
             description "User Datagram Protocol";
           }
           enum "igmp" {
             description "Internet Gateway Management Protocol";
           }
           enum "arp" {
             description "Address Resolution Protocol";
           }
           enum "clns" {
             description "Connectionless Network Service";
           }
           enum "esis" {
             description "End System-to-Intermediate System";
           }
           enum "tnp" {
             description "Trivial Network Protocol";
           }
           enum "rdp" {
             description "Reliable Datagram Protocol";
           }
           enum "ttp" {
             description "TNP Tunneling Protocol";
           }
           enum "tudp" {
             description "Trivial User Datagram Protocol";
           }
           enum "mpls" {
             description "Multiprotocol Label Switching";
           }
           enum "ethoamcfm" {
             description "Ethernet OAM protocol for connectivity fault management";
           }
           enum "ethoamlfm" {
             description "Ethernet OAM protocol for link fault management";
           }
           enum "jsr" {
             description "Juniper Socket Replication";
           }
         }
       }
     }
     output {
       container statistics {
         uses statistics-block;
       }
     }
   }
   rpc get-system-vpls-statistics {
     description "Virtual private LAN service";
     output {
       container statistics {
         uses statistics-block;
       }
     }
   }
   rpc get-system-bridge-statistics {
     description "IEEE 802.1 Bridging";
     output {
       container statistics {
         uses statistics-block;
       }
     }
   }
   rpc get-system-stats-extended {
     description "System wide statistics";
     input {
       leaf protocol {
         description "Show sysstem statistics extended protocol";
         type enumeration {
           enum "ipv4" {
             description "Display ipv4 sysstem statistics";
           }
           enum "ipv6" {
             description "Display ipv6 sysstem statistics";
           }
         }
       }
     }
     output {
       container extended-system-stats {
         uses extended-system-stats-block;
       }
     }
   }
   rpc get-system-storage {
     description "Show local storage data";
     input {
       leaf detail {
         type empty;
       }
     }
     output {
       container system-storage-information {
         uses system-storage-information-block;
       }
     }
   }
   rpc get-system-storage-partitions {
     description "Show partitions information for the boot media";
     output {
       container system-storage-information {
         uses system-storage-information-block;
       }
     }
   }
   rpc get-switchover-information {
     description "Show Routing Engine graceful switchover information";
     output {
       container switchover-information {
         uses switchover-information-block;
       }
     }
   }
   rpc get-system-memory-information {
     description "Show system memory usage";
     output {
       container system-memory-information {
         uses system-memory-information-block;
       }
     }
   }
   rpc get-system-virtual-memory-information {
     description "Show kernel dynamic memory usage";
     output {
       container system-virtual-memory-information {
         uses system-virtual-memory-information-block;
       }
     }
   }
   rpc get-system-users-information {
     description "Show users who are currently logged in";
     input {
       leaf no-resolve {
         description "Don't attempt to print addresses symbolically";
         type empty;
       }
     }
     output {
       container system-users-information {
         uses system-users-information-block;
       }
     }
   }
   rpc get-syslog-events {
     description "Show system log messages";
     input {
       leaf stream {
         description "Name of stream (log file) containing messages to filter";
         type string {
           junos:posix-pattern "![/ %]";
           junos:pattern-message "Must not contain '/', % or a space";
         }
         mandatory true;
       }
       leaf event {
         description "Event ID of messages to include in output";
         type string {
           length "1 .. 256";
         }
       }
       leaf process {
         description "Name of process generating messages to include in output";
         type string {
           length "1 .. 256";
         }
       }
       leaf-list priority {
         description "Facility and severity of messages to include in output";
         type string;
       }
       leaf host {
         description "Name of host generating messages to include in output";
         type string {
           length "1 .. 256";
         }
       }
       leaf start-time {
         description "Earliest timestamp of messages to include in output";
         type time;
       }
       leaf stop-time {
         description "Latest timestamp of messages to include in output";
         type time;
       }
       leaf-list parameter {
         description "Parameter (key=value) of messages to include in output";
         type regular-expression;
       }
       leaf text-pattern {
         description "Pattern in messages to include in output";
         type regular-expression;
       }
       leaf count {
         description "Number of messages to include in output";
         type uint32;
       }
       leaf recorded {
         description "Match only the recorded messages";
         type empty;
       }
       leaf connection-id {
         description "Connection ID";
         type string;
       }
     }
     output {
       container syslog-events {
         uses syslog-events-block;
       }
     }
   }
   rpc get-system-resource-cleanup-processes-information {
     description "Show process resource cleanup information";
     input {
       leaf detail {
         description "Display detailed information";
         type empty;
       }
       container name_pid_choice {
         choice name_pid_choice_c {
           case process-name {
             leaf process-name {
               description "Process name";
               type string;
             }
           }
           case pid {
             leaf pid {
               description "Process identifier";
               type uint32 {
                 range "1 .. 99999";
               }
             }
           }
         }
       }
     }
     output {
       container system-resource-cleanup-processes-information {
         uses system-resource-cleanup-processes-information-block;
       }
     }
   }
   rpc get-subscriber-management-summary-information {
     description "Show Subscriber management summary";
     output {
       container subscriber-management-summary-information {
         uses subscriber-management-summary-information-block;
       }
     }
   }
   rpc get-subscriber-management-statistics {
     description "Show subscriber management statistics";
     input {
       leaf all {
         description "Display all statistics";
         type empty;
       }
       leaf dhcp {
         description "Display dhcp statistics";
         type empty;
       }
       leaf dvlan {
         description "Display dvlan statistics";
         type empty;
       }
       leaf ppp {
         description "Display ppp statistics";
         type empty;
       }
       leaf pppoe {
         description "Display pppoe statistics";
         type empty;
       }
       leaf l2tp {
         description "Display l2tp statistics";
         type empty;
       }
     }
   }
   rpc get-subscriber-management-route-information {
     description "Show subscriber management route information";
     input {
       leaf family {
         description "Name of family";
         type enumeration {
           enum "inet" {
             description "IP version 4 (IPv4)";
           }
           enum "inet6" {
             description "IP version 6 (IPv6)";
           }
         }
       }
       leaf route-type {
         description "Type of route";
         type enumeration {
           enum "local" {
             description "Local route";
           }
           enum "access" {
             description "Access route";
           }
           enum "access-internal" {
             description "Access-internal route";
           }
           enum "kernel" {
             description "Kernel route";
           }
         }
       }
       leaf routing-instance {
         description "Name of routing instance";
         type string;
       }
       leaf level {
         default "brief";
         type enumeration {
           enum "brief" {
             description "Display brief information";
           }
           enum "detail" {
             description "Display detailed information";
           }
         }
       }
       leaf incomplete {
         description "Display only incomplete routes";
         type empty;
       }
     }
     output {
       container subscriber-management-route-information {
         uses subscriber-management-route-information-block;
       }
     }
   }
   rpc get-subscriber-management-route-summary {
     description "Show subscriber management route summary";
   }
   rpc get-subscriber-management-route-nh {
     description "Show subscriber management route next-hop information";
     input {
       leaf index {
         description "Next-hop index";
         type uint16 {
           range "1 .. 65535";
         }
       }
     }
   }
   rpc get-subscriber-management-arp {
     description "Show subscriber management arp information";
   }
   rpc get-subscriber-management-arp-interface {
     description "Name of interface";
     input {
       leaf interface-name {
         description "Name of interface";
         type string;
         mandatory true;
       }
     }
   }
   rpc get-subscriber-management-arp-address {
     description "Ipv4 address";
     input {
       leaf ip-address {
         description "Ipv4 address";
         type ipv4addr;
         mandatory true;
       }
     }
   }
   rpc get-subscriber-management-ipv6-neighbors {
     description "Show subscriber management ipv6 neighbors information";
   }
   rpc get-subscriber-management-ipv6-neighbor-interface {
     description "Name of interface";
     input {
       leaf interface-name {
         description "Name of interface";
         type string;
         mandatory true;
       }
     }
   }
   rpc get-subscriber-management-ipv6-neighbor-address {
     description "Ipv6 address";
     input {
       leaf interface-name {
         description "Ipv6 address";
         type ipv6addr;
         mandatory true;
       }
     }
   }
   rpc get-autoinstallation-status-information {
     description "Show autoinstallation status";
     output {
       container autoinstallation-status-information {
         uses autoinstallation-status-information-block;
       }
     }
   }
   rpc get-system-firmware-information {
     description "Show all firmware version information";
     input {
       leaf compatibility {
         description "Show all firmware compatibility information";
         type empty;
       }
     }
     output {
       container system-firmware-information {
         uses system-firmware-information-block;
       }
     }
   }
   rpc get-system-crypto-information {
     description "Show system security crypto level";
     output {
       container system-crypto-information {
         uses system-crypto-information-block;
       }
     }
   }
   rpc get-system-autorecovery {
     description "Show autorecovery information";
   }
   rpc get-system-autorecovery-state {
     description "Show saved autorecovery information";
   }
   rpc get-download-information {
     description "Show status of downloads";
     input {
       leaf download-id {
         description "ID of the download whose status is to be shown";
         type uint16;
       }
     }
   }
   rpc get-security-profile-all-resource-information {
     description "Show all resources information per logical system";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-auth-entry-information {
     description "Show authentication resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-zone-information {
     description "Show zone resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-policy-information {
     description "Show policy resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-policy-with-count-information {
     description "Show resource information of policy with count";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-appfw-rule-set-information {
     description "Show appfw rule-set resource information";
     input {
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
       leaf level {
         default "terse";
         type enumeration {
           enum "terse" {
             description "Display terse output (default)";
           }
           enum "detail" {
             description "Display detailed output";
           }
         }
       }
     }
   }
   rpc get-security-profile-appfw-rule-information {
     description "Show appfw rule resource information";
     input {
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
       leaf level {
         default "terse";
         type enumeration {
           enum "terse" {
             description "Display terse output (default)";
           }
           enum "detail" {
             description "Display detailed output";
           }
         }
       }
     }
   }
   rpc get-security-profile-appfw-profile-information {
     description "Show appfw profile resource information";
     input {
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
       leaf level {
         default "terse";
         type enumeration {
           enum "terse" {
             description "Display terse output (default)";
           }
           enum "detail" {
             description "Display detailed output";
           }
         }
       }
     }
   }
   rpc get-security-profile-scheduler-information {
     description "Show scheduler resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-source-pool-information {
     description "Show nat source pool resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-destination-pool-information {
     description "Show nat destination pool resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-pat-address-information {
     description "Show nat source pat address resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-nopat-address-information {
     description "Show nat source nopat address resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-pat-portnum-information {
     description "Show nat source pat port number resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-source-rule-information {
     description "Show nat source rule resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-destination-rule-information {
     description "Show nat destination rule resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-static-rule-information {
     description "Show nat static rule resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-rule-referenced-prefix-information {
     description "Show nat rule referenced IP-prefix information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-cone-binding-information {
     description "Show nat cone binding resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-port-ol-ipnumber-information {
     description "Show nat port overloading resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-nat-interface-po-information {
     description "Show nat interface port overloading resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-flow-session-information {
     description "Show flow session resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-flow-gate-information {
     description "Show flow gate resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-cpu-information {
     description "Show CPU utilization information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-dslite-softwire-initiator-information {
     description "Show security dslite softwire initiator resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
   rpc get-security-profile-address-book-information {
     description "Show address-book resource information";
     input {
       leaf level {
         default "terse";
         type enumeration {
           enum "terse" {
             description "Display terse output (default)";
           }
           enum "detail" {
             description "Display detailed output";
           }
         }
       }
       container lsys {
         choice lsys_c {
           case logical-system {
             leaf logical-system {
               description "Logical-system name";
               default "all";
               type string;
             }
           }
           case root-logical-system {
             leaf root-logical-system {
               description "Root logical-system";
               type empty;
             }
           }
           case summary {
             leaf summary {
               description "Display summary output";
               type empty;
             }
           }
         }
       }
     }
   }
 grouping alarm-information-block {
   container alarm-summary {
     description "Number of alarms currently active";
     leaf active-alarm-count {
       type int32;
       description "Number of active alarms";
     }
     leaf no-active-alarms {
       type empty;
       description "No active alarms";
     }
     container satellite {
       description "Number of alarms currently active";
       leaf active-fpc-slot {
         type int32;
         description "FPC slot with active alarms";
       }
     }
   }
   list alarm-detail {
     description "Detailed information about an active alarm";
     leaf alarm-time {
       type string;
       description "Time of the alarm";
     }
     leaf alarm-class {
       type string;
       description "Class of the alarm";
     }
     leaf alarm-description {
       type string;
       description "Description of the alarm";
     }
   }
 }
 grouping commit-information-block {
   container pending-commit {
     leaf user {
       type string;
       description "User name executing this script";
     }
     leaf client {
       type string;
       description "This client application performed the commit";
     }
     leaf date-time {
       type string;
     }
   }
   list commit-history {
     leaf sequence-number {
       type int32;
       description "Commit sequence number, 0 being the most recent";
     }
     leaf date-time {
       type string;
     }
     leaf user {
       type string;
       description "User name executing this script";
     }
     leaf client {
       type string;
       description "This client application performed the commit";
     }
     leaf comment {
       type string;
     }
     leaf log {
       type string;
       description "Log message for this commit";
     }
   }
   container rescue-configuration {
     leaf date-time {
       type string;
     }
     leaf user {
       type string;
       description "User name executing this script";
     }
     leaf client {
       type string;
       description "This client application performed the commit";
     }
     leaf comment {
       type string;
     }
     leaf log {
       type string;
       description "Log message for this commit";
     }
   }
 }
 grouping commit-revision-information-block {
   leaf revision {
     type uint32;
   }
   leaf date-time {
     type string;
   }
   leaf user {
     type string;
     description "User name executing this script";
   }
   leaf client {
     type string;
     description "This client application performed the commit";
   }
   leaf comment {
     type string;
   }
   leaf log {
     type string;
     description "Log message for this commit";
   }
 }
 grouping commit-server-information-block {
   leaf server-status {
     type string;
     description "Commit server status";
   }
   container jobs-detail {
     description "Jobs processed by commit server";
     list job {
       leaf job-id {
         type uint32;
         description "Job id";
       }
     }
   }
   container pause-status {
     description "Commit server pause status";
   }
   container start-status {
     description "Commit server start status";
   }
 }
 grouping commit-server-queue-information-block {
   list commit-server-queue {
     leaf queue-name {
       type string;
       description "Commit queue name";
     }
     list job {
       leaf job-id {
         type uint32;
         description "Job id";
       }
       leaf job-date {
         type string;
         description "Commit job modify date";
       }
       leaf job-status {
         type string;
         description "Commit job status";
       }
       leaf jobs-none {
         type empty;
       }
       leaf job-patch {
         type string;
         description "Job patch";
       }
     }
   }
 }
 grouping rescue-information-block {
   container load-configuration-results {
     leaf load-success {
       type empty;
       description "Load completed with no errors";
     }
     leaf load-error-count {
       type int32;
       description "Number of errors during load";
     }
     leaf diff-error-count {
       type int32;
       description "Number of errors";
     }
   }
   container configuration-information {
     leaf configuration-output {
       type string;
     }
     leaf json-output {
       type string;
     }
     container file-destination {
       leaf source-filename {
         type string;
       }
       leaf alias-filename {
         type string;
       }
       leaf export-data-type {
         type string;
         description "Type of data being exported";
       }
     }
     container configuration-detail {
       leaf indent {
         type int32;
       }
       container configuration-detail-line {
         leaf detail-name {
           type string;
         }
         leaf detail-value {
           type string;
         }
         leaf detail-message {
           type string;
         }
       }
     }
   }
 }
 grouping directory-list-block {
   container brief {
     description "Show directory contents";
     container directory {
       description "Information about system directory usage";
       leaf directory-name {
         type string;
         description "Directory name";
       }
       container file-information {
       }
     }
   }
   container verbose {
     description "Show directory contents";
     container directory {
       description "Information about system directory usage";
       leaf directory-name {
         type string;
         description "Directory name";
       }
       leaf total-file-blocks {
         type int32;
         description "Total number of blocks used by files in this directory";
       }
       leaf total-files {
         type int32;
         description "Total number of files in this directory";
       }
       container file-information {
       }
     }
   }
   container host {
     description "Show directory contents";
     container directory {
       description "Information about system directory usage";
       container file-information {
       }
     }
   }
 }
 grouping database-usage-block {
   leaf maximum-size {
     type int32;
     description "Show maximum size of database";
   }
   leaf current-size {
     type int32;
     description "Show current database size on disk";
   }
   leaf actual-usage {
     type int32;
     description "Show actual database usage";
   }
   leaf available-space {
     type int32;
     description "Show available database space";
   }
 }
 grouping rollback-information-block {
   container load-configuration-results {
     leaf load-success {
       type empty;
       description "Load completed with no errors";
     }
     leaf load-error-count {
       type int32;
       description "Number of errors during load";
     }
     leaf diff-error-count {
       type int32;
       description "Number of errors";
     }
   }
   container configuration-information {
     leaf configuration-output {
       type string;
     }
     leaf json-output {
       type string;
     }
     container file-destination {
       leaf source-filename {
         type string;
       }
       leaf alias-filename {
         type string;
       }
       leaf export-data-type {
         type string;
         description "Type of data being exported";
       }
     }
     container configuration-detail {
       leaf indent {
         type int32;
       }
       container configuration-detail-line {
         leaf detail-name {
           type string;
         }
         leaf detail-value {
           type string;
         }
         leaf detail-message {
           type string;
         }
       }
     }
   }
 }
 grouping system-uptime-information-block {
   leaf time-source {
     type string;
     description "Time Source";
   }
   container last-configured-time {
     description "Last configured time";
     leaf date-time {
       type string;
     }
     leaf time-length {
       type string;
     }
     leaf user {
       type string;
       description "User name executing this script";
     }
   }
   container current-time {
     description "Current time";
     leaf date-time {
       type string;
     }
   }
   container system-booted-time {
     description "System booted time";
     leaf date-time {
       type string;
     }
     leaf time-length {
       type string;
     }
   }
   container protocols-started-time {
     description "Protocols started time";
     leaf date-time {
       type string;
     }
     leaf time-length {
       type string;
     }
   }
   container uptime-information {
     description "System uptime details";
     leaf date-time {
       type string;
     }
     leaf up-time {
       type string;
       description "Uptime in ascii format";
     }
     leaf active-user-count {
       type int32;
       description "Number of users currently logged in";
     }
     leaf load-average-1 {
       type string;
       description "Load average for last 1 minute";
     }
     leaf load-average-5 {
       type string;
       description "Load average for last 5 minutes";
     }
     leaf load-average-15 {
       type string;
       description "Load average for last 15 minutes";
     }
     container user-table {
       list user-entry {
         leaf user {
           type string;
           description "User name executing this script";
         }
         leaf tty {
           type string;
           description "Name of the terminal the user is on";
         }
         leaf from {
           type string;
           description "Host from which the user is logged on";
         }
         leaf login-time {
           type string;
           description "Time the user logged on";
         }
         leaf idle-time {
           type string;
           description "Time since the user last typed anything";
         }
         leaf command {
           type string;
         }
       }
       container process-table {
         list process-entry {
         }
       }
     }
   }
 }
 grouping license-summary-information-block {
   container license-usage-summary {
     description "Information about features licensed on this device";
     leaf features-used {
       type empty;
       description "Licensed features are being used";
     }
     leaf no-feature-used {
       type empty;
       description "No licensed feature is being used";
     }
     list feature-summary {
       leaf name {
         type string;
         description "Identifier for this object";
       }
       leaf used-licensed {
         type int32;
         description "Number used that require a license";
       }
       leaf licensed {
         type int32;
         description "Number available in valid licenses";
       }
       leaf needed {
         type int32;
         description "Number used that require a license above licensed count";
       }
       leaf validity-type {
         type string;
         description "Type of validity of the license";
       }
       leaf end-date {
         type string;
       }
       container remaining-time {
       }
     }
   }
   container license-information {
     description "Information about feature licenses installed on device";
     leaf licenses-installed {
       type empty;
       description "Feature licenses are installed";
     }
     leaf no-licenses-installed {
       type empty;
       description "No feature licenses are installed";
     }
     list license {
       leaf name {
         type string;
         description "Identifier for this object";
       }
       leaf license-version {
         type int32;
         description "Version of license";
       }
       leaf license-type {
         type string;
         description "Type of license";
       }
       leaf device-reference {
         type string;
         description "License is tied to this device";
       }
       leaf num-units {
         type int32;
         description "Number of units of the license";
       }
       leaf software-sn {
         type string;
         description "License is tied to this Software Serial Number";
       }
       leaf customer-reference {
         type string;
         description "Customer id of the license";
       }
       leaf release-version {
         type string;
         description "License defines the JUNOS release version it is tied to.";
       }
       leaf upgrade-license {
         type string;
         description "License defines if this is a software upgrade license tied to JUNOS release";
       }
       leaf group-reference {
         type string;
         description "License is tied to this group";
       }
       leaf group-define {
         type string;
         description "License defines device to be part of this license group";
       }
       leaf unsupported-attribute {
         type int32;
         description "An attribute that is not recognized by this implementation";
       }
       list feature-block {
         list feature {
           description "A single feature instance";
           list permanent-feature {
             description "A single feature instance";
             leaf description {
               type string;
               description "Description of feature";
             }
             container validity-information {
               leaf validity-type {
                 type string;
                 description "Type of validity of the license";
               }
             }
           }
           list countdown-feature {
             description "A single feature instance";
             leaf description {
               type string;
               description "Description of feature";
             }
             container validity-information {
               leaf validity-type {
                 type string;
                 description "Type of validity of the license";
               }
               container original-validity {
               }
               container remaining-time {
               }
             }
           }
           list datebased-feature {
             description "A single feature instance";
             leaf name {
               type string;
               description "Identifier for this object";
             }
             leaf description {
               type string;
               description "Description of feature";
             }
             container validity-information {
               leaf validity-type {
                 type string;
                 description "Type of validity of the license";
               }
               leaf start-date {
                 type string;
               }
               leaf end-date {
                 type string;
               }
             }
           }
         }
       }
     }
   }
 }
 grouping license-information-block {
   leaf no-licenses-installed {
     type empty;
     description "No feature licenses are installed";
   }
   list license {
     leaf name {
       type string;
       description "Identifier for this object";
     }
     leaf license-version {
       type int32;
       description "Version of license";
     }
     leaf license-type {
       type string;
       description "Type of license";
     }
     leaf device-reference {
       type string;
       description "License is tied to this device";
     }
     leaf num-units {
       type int32;
       description "Number of units of the license";
     }
     leaf software-sn {
       type string;
       description "License is tied to this Software Serial Number";
     }
     leaf customer-reference {
       type string;
       description "Customer id of the license";
     }
     leaf release-version {
       type string;
       description "License defines the JUNOS release version it is tied to.";
     }
     leaf upgrade-license {
       type string;
       description "License defines if this is a software upgrade license tied to JUNOS release";
     }
     leaf group-reference {
       type string;
       description "License is tied to this group";
     }
     leaf group-define {
       type string;
       description "License defines device to be part of this license group";
     }
     leaf unsupported-attribute {
       type int32;
       description "An attribute that is not recognized by this implementation";
     }
     list feature-block {
       list feature {
         description "A single feature instance";
         list permanent-feature {
           description "A single feature instance";
           leaf description {
             type string;
             description "Description of feature";
           }
           container validity-information {
             leaf validity-type {
               type string;
               description "Type of validity of the license";
             }
           }
         }
         list countdown-feature {
           description "A single feature instance";
           leaf description {
             type string;
             description "Description of feature";
           }
           container validity-information {
             leaf validity-type {
               type string;
               description "Type of validity of the license";
             }
             container original-validity {
             }
             container remaining-time {
             }
           }
         }
         list datebased-feature {
           description "A single feature instance";
           leaf name {
             type string;
             description "Identifier for this object";
           }
           leaf description {
             type string;
             description "Description of feature";
           }
           container validity-information {
             leaf validity-type {
               type string;
               description "Type of validity of the license";
             }
             leaf start-date {
               type string;
             }
             leaf end-date {
               type string;
             }
           }
         }
       }
     }
   }
 }
 grouping license-key-information-block {
   list license-key {
     leaf name {
       type string;
       description "Identifier for this object";
     }
     leaf key-data {
       type string;
       description "Textual license key";
     }
   }
 }
 grouping license-usage-summary-block {
   leaf no-feature-used {
     type empty;
     description "No licensed feature is being used";
   }
   list feature-summary {
     leaf name {
       type string;
       description "Identifier for this object";
     }
     leaf used-licensed {
       type int32;
       description "Number used that require a license";
     }
     leaf licensed {
       type int32;
       description "Number available in valid licenses";
     }
     leaf needed {
       type int32;
       description "Number used that require a license above licensed count";
     }
     leaf validity-type {
       type string;
       description "Type of validity of the license";
     }
     leaf end-date {
       type string;
     }
     container remaining-time {
     }
   }
 }
 grouping license-revoked-information-block {
   leaf no-license-revoked {
     type empty;
     description "No license revoked";
   }
   list license-revoke-summary {
     leaf license-revoke-time {
       type string;
     }
     leaf auth-id {
       type string;
       description "Authorization ID";
     }
     leaf confirm-code {
       type string;
       description "Confirmation Code";
     }
     leaf confirmcode-expiry-time {
       type string;
     }
     leaf license-id-list {
       type string;
       description "License IDs list";
     }
   }
 }
 grouping system-information-block {
   leaf system-hardware-cpu-architecture {
     type string;
     description "CPU architecture";
   }
   leaf system-hardware-cpu-model {
     type string;
     description "CPU model";
   }
   leaf system-hardware-cpu-count {
     type int32;
     description "Number of active CPUs";
   }
   leaf system-boot-device {
     type string;
     description "Device the system booted from";
   }
   leaf system-boot-next-device {
     type string;
     description "Device the system booted from";
   }
   leaf system-hardware-physical-memory {
     type int32;
     description "Physical memory in system, in bytes";
   }
   leaf system-hardware-page-available {
     type int32;
     description "Pages of memory available";
   }
   leaf system-hardware-user-memory {
     type int32;
     description "Physical memory available to user processes, in bytes";
   }
   leaf system-hardware-page-size {
     type int32;
     description "System memory page size, in bytes";
   }
   leaf system-virtual-memory-page-size {
     type int32;
     description "Size of page, in bytes";
   }
   leaf system-hardware-routing-engine-name {
     type string;
     description "Routing Engine name";
   }
   leaf system-hardware-routing-engine-model {
     type string;
     description "Routing Engine model";
   }
   leaf system-hardware-routing-engine-serial-number {
     type string;
     description "Routing Engine serial number";
   }
   leaf system-hardware-routing-engine-other-present {
     type empty;
     description "Other Routing Engine is present";
   }
   leaf system-hardware-routing-engine-other-alive {
     type empty;
     description "Other Routing Engine is operational";
   }
   leaf system-virtual-memory-page-count {
     type int32;
     description "Total page count";
   }
   leaf system-virtual-memory-swap-enabled {
     type empty;
     description "Swapping is enabled";
   }
   leaf system-virtual-memory-context-switches {
     type int32;
     description "Number of context switches";
   }
   leaf system-virtual-memory-trap {
     type int32;
     description "Number of traps";
   }
   leaf system-virtual-memory-syscall {
     type int32;
     description "Number of system calls";
   }
   leaf system-virtual-memory-hard-interrupts {
     type int32;
     description "Number of hardware interrupts";
   }
   leaf system-virtual-memory-soft-interrupts {
     type int32;
     description "Number of software interrupts";
   }
   leaf system-virtual-memory-faults {
     type int32;
     description "Virtual memory page faults";
   }
   leaf system-virtual-memory-copy-on-write-faults {
     type int32;
     description "Copy on write page faults";
   }
   leaf system-virtual-memory-copy-on-write-optimized {
     type int32;
     description "Optimized copy on write page faults";
   }
   leaf system-virtual-memory-zeroed-pages {
     type int32;
     description "Zero filled pages";
   }
   leaf system-virtual-memory-zeroed-pages-optimized {
     type int32;
     description "Optimized zero filled pages";
   }
   leaf system-virtual-memory-swapin {
     type int32;
     description "Swap-in operations";
   }
   leaf system-virtual-memory-swapout {
     type int32;
     description "Swap-out operations";
   }
   leaf system-virtual-memory-swapped-in-pages {
     type int32;
     description "Swapped in pages";
   }
   leaf system-virtual-memory-swapped-out-pages {
     type int32;
     description "Swapped out pages";
   }
   leaf system-virtual-memory-reactivated-pages {
     type int32;
     description "Re-activated pages";
   }
   leaf system-virtual-memory-vnode-in {
     type int32;
     description "Vnodein operations";
   }
   leaf system-virtual-memory-vnode-out {
     type int32;
     description "Vnodeout operations";
   }
   leaf system-virtual-memory-vnode-page-ins {
     type int32;
     description "Vnode page-ins";
   }
   leaf system-virtual-memory-vnode-page-outs {
     type int32;
     description "Vnode page-outs";
   }
   leaf system-virtual-memory-pager-wakes {
     type int32;
     description "Pager wakeup events";
   }
   leaf system-virtual-memory-pager-scans {
     type int32;
     description "Pager page scans";
   }
   leaf system-virtual-memory-free-reserved {
     type int32;
     description "Reserved free pages";
   }
   leaf system-virtual-memory-free-minimum {
     type int32;
     description "Minimum free pages";
   }
   leaf system-virtual-memory-free-pages {
     type int32;
     description "Free pages";
   }
   leaf system-virtual-memory-wired-pages {
     type int32;
     description "Pages fixed in memory";
   }
   leaf system-virtual-memory-active-pages {
     type int32;
     description "Pages recently statistically used by user processes";
   }
   leaf system-virtual-memory-cache-pages {
     type int32;
     description "Pages ready for use or clean";
   }
   leaf system-virtual-memory-cache-pages-minimum {
     type int32;
     description "Minimum cache pages";
   }
   leaf system-virtual-memory-cache-pages-maximum {
     type int32;
     description "Maximum cache pages";
   }
   leaf system-last-pid {
     type int32;
     description "Last PID assigned";
   }
   container system-virtual-memory-load-averages {
     description "Load averages";
     leaf load-average-one-minute {
       type string;
       description "One minute run queue average length";
     }
     leaf load-average-five-minute {
       type string;
       description "Five minute run queue average length";
     }
     leaf load-average-fifteen-minute {
       type string;
       description "Fifteen minute run queue average length";
     }
   }
   container system-process-counts {
     description "Number of processes on system";
     leaf process-total {
       type int32;
       description "Total number of processes";
     }
     leaf process-run {
       type int32;
       description "Running processes";
     }
     leaf process-sleep {
       type int32;
       description "Sleeping processes";
     }
     leaf process-stop {
       type int32;
       description "Stopped processes";
     }
     leaf process-start {
       type int32;
       description "Starting processes";
     }
     leaf process-zombie {
       type int32;
       description "Zombie processes";
     }
   }
   container system-cpu-states {
     description "Process state information";
     leaf cpu-user-time-percent {
       type string;
       description "CPU time spent in user state";
     }
     leaf cpu-nice-time-percent {
       type string;
       description "CPU time spent in nice state";
     }
     leaf cpu-system-time-percent {
       type string;
       description "CPU time spent in system state";
     }
     leaf cpu-interrupts-time-percent {
       type string;
       description "CPU time spent in interrupts state";
     }
     leaf cpu-idle-time-percent {
       type string;
       description "CPU time spent in idle state";
     }
   }
   list package-information {
   }
 }
 grouping system-login-lockout-information-block {
   leaf no-login-lockout {
     type empty;
     description "No users locked out from logins";
   }
   leaf no-login-lockout-user {
     type empty;
     description "User not locked out from logins";
   }
   container login-lockout-users-table {
     list login-lockout-user-entry {
       description "Login lockout information for a user";
       leaf login-lockout-user {
         type string;
         description "Name of user being locked out";
       }
       leaf login-lockout-start-time {
         type string;
         description "The time the lockout started";
       }
       leaf login-lockout-end-time {
         type string;
         description "The time the lockout ends";
       }
     }
   }
 }
 grouping yang-pkgs-info-block {
   leaf yang-pkg-id {
     type string;
     description "Package ID";
   }
   leaf yang-modules {
     type string;
     description "YANG modules(s)";
   }
   leaf action-scripts {
     type string;
     description "Action script(s)";
   }
   leaf trans-scripts {
     type string;
     description "Translation script(s)";
   }
   leaf trans-scripts-status {
     type string;
     description "Translation script(s) status";
   }
 }
 grouping system-services-reverse-information-block {
   container reverse-connection {
     leaf reverse-since {
       type string;
       description "Connected since";
     }
     leaf reverse-method {
       type string;
       description "Connection method";
     }
   }
 }
 grouping dhcp-binding-information-block {
   container tabular-summary {
     description "Information about the address assigned to each of one or more Dynamic Host Configuration Protocol clients";
     list dhcp-binding {
       description "Information about the address assigned to a Dynamic Host Configuration Protocol client";
       leaf allocated-address {
         type ipaddr;
         description "IPv4 address assigned to the DHCP client";
       }
       leaf mac-address {
         type mac-addr;
         description "Media access control (hardware) address of the DHCP client";
       }
       leaf dhcp-lease-binding-type {
         type string;
         description "Type of the address assignment";
       }
       leaf lease-end-time {
         type string;
         description "Time when the address assignment will expire, in the format YYYY-MM-DD hh:mm:ss TZ (year, month, date, hour in 24-hour format, minute, second, time zone). The value 'never' indicates that the lease does not expire.";
       }
       container dhcp-option-table {
         description "Information about one or more Dynamic Host Configuration Protocol options that are associated with the address assignment";
         list dhcp-option {
           description "Information about a Dynamic Host Configuration Protocol option that is associated with the address assignment";
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
       container dhcp-lease-information {
         description "Information about an address assignment";
       }
       container client-identifier {
         description "Identifier that the DHCP client provided for itself when it requested an address assignment";
         leaf hex-data-line {
           type string;
           description "Line of data in hexadecimal format";
         }
         leaf printable-data-line {
           type string;
           description "Line of data in printable format";
         }
       }
     }
   }
   container tabular-detail {
     description "Information about the address assigned to each of one or more Dynamic Host Configuration Protocol clients";
     list dhcp-binding {
       description "Information about the address assigned to a Dynamic Host Configuration Protocol client";
       leaf allocated-address {
         type ipaddr;
         description "IPv4 address assigned to the DHCP client";
       }
       leaf mac-address {
         type mac-addr;
         description "Media access control (hardware) address of the DHCP client";
       }
       leaf dhcp-lease-binding-type {
         type string;
         description "Type of the address assignment";
       }
       leaf lease-end-time {
         type string;
         description "Time when the address assignment will expire, in the format YYYY-MM-DD hh:mm:ss TZ (year, month, date, hour in 24-hour format, minute, second, time zone). The value 'never' indicates that the lease does not expire.";
       }
       leaf lease-state {
         type string;
         description "Status of the address assignment";
       }
       container dhcp-option-table {
         description "Information about one or more Dynamic Host Configuration Protocol options that are associated with the address assignment";
         list dhcp-option {
           description "Information about a Dynamic Host Configuration Protocol option that is associated with the address assignment";
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
       container dhcp-lease-information {
         description "Information about an address assignment";
       }
       container client-identifier {
         description "Identifier that the DHCP client provided for itself when it requested an address assignment";
         leaf hex-data-line {
           type string;
           description "Line of data in hexadecimal format";
         }
         leaf printable-data-line {
           type string;
           description "Line of data in printable format";
         }
       }
     }
   }
   container summary {
     description "Information about the address assigned to each of one or more Dynamic Host Configuration Protocol clients";
     list dhcp-binding {
       description "Information about the address assigned to a Dynamic Host Configuration Protocol client";
       leaf dhcp-lease-binding-type {
         type string;
         description "Type of the address assignment";
       }
       leaf allocated-address {
         type ipaddr;
         description "IPv4 address assigned to the DHCP client";
       }
       leaf mac-address {
         type mac-addr;
         description "Media access control (hardware) address of the DHCP client";
       }
       leaf lease-end-time {
         type string;
         description "Time when the address assignment will expire, in the format YYYY-MM-DD hh:mm:ss TZ (year, month, date, hour in 24-hour format, minute, second, time zone). The value 'never' indicates that the lease does not expire.";
       }
       container dhcp-option-table {
         description "Information about one or more Dynamic Host Configuration Protocol options that are associated with the address assignment";
         list dhcp-option {
           description "Information about a Dynamic Host Configuration Protocol option that is associated with the address assignment";
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
       container dhcp-lease-information {
         description "Information about an address assignment";
         container dhcp-option-table {
           description "Information about one or more Dynamic Host Configuration Protocol options that are associated with the address assignment";
           list dhcp-option {
             description "Information about a Dynamic Host Configuration Protocol option that is associated with the address assignment";
             leaf dhcp-option-code {
               type int32;
               description "Numeric code assigned to the DHCP option";
             }
             leaf dhcp-option-name {
               type string;
               description "Name of the DHCP option";
             }
             leaf dhcp-option-type {
               type string;
               description "Type of value for the DHCP option (for example, string [word], integer, IP address)";
             }
             leaf dhcp-option-value {
               type string;
               description "Value of the DHCP option";
             }
           }
         }
         container dhcp-lease-information {
           description "Information about an address assignment";
           container dhcp-option-table {
             description "Information about one or more Dynamic Host Configuration Protocol options that are associated with the address assignment";
             list dhcp-option {
               description "Information about a Dynamic Host Configuration Protocol option that is associated with the address assignment";
               leaf dhcp-option-code {
                 type int32;
                 description "Numeric code assigned to the DHCP option";
               }
               leaf dhcp-option-name {
                 type string;
                 description "Name of the DHCP option";
               }
               leaf dhcp-option-type {
                 type string;
                 description "Type of value for the DHCP option (for example, string [word], integer, IP address)";
               }
               leaf dhcp-option-value {
                 type string;
                 description "Value of the DHCP option";
               }
             }
           }
           container dhcp-lease-information {
             description "Information about an address assignment";
             container dhcp-option-table {
               description "Information about one or more Dynamic Host Configuration Protocol options that are associated with the address assignment";
               list dhcp-option {
                 description "Information about a Dynamic Host Configuration Protocol option that is associated with the address assignment";
                 leaf dhcp-option-code {
                   type int32;
                   description "Numeric code assigned to the DHCP option";
                 }
                 leaf dhcp-option-name {
                   type string;
                   description "Name of the DHCP option";
                 }
                 leaf dhcp-option-type {
                   type string;
                   description "Type of value for the DHCP option (for example, string [word], integer, IP address)";
                 }
                 leaf dhcp-option-value {
                   type string;
                   description "Value of the DHCP option";
                 }
               }
             }
             container dhcp-lease-information {
               description "Information about an address assignment";
               container dhcp-option-table {
                 description "Information about one or more Dynamic Host Configuration Protocol options that are associated with the address assignment";
                 list dhcp-option {
                   description "Information about a Dynamic Host Configuration Protocol option that is associated with the address assignment";
                   leaf dhcp-option-code {
                     type int32;
                     description "Numeric code assigned to the DHCP option";
                   }
                   leaf dhcp-option-name {
                     type string;
                     description "Name of the DHCP option";
                   }
                   leaf dhcp-option-type {
                     type string;
                     description "Type of value for the DHCP option (for example, string [word], integer, IP address)";
                   }
                   leaf dhcp-option-value {
                     type string;
                     description "Value of the DHCP option";
                   }
                 }
               }
               container dhcp-lease-information {
                 description "Information about an address assignment";
                 container dhcp-option-table {
                   description "Information about one or more Dynamic Host Configuration Protocol options that are associated with the address assignment";
                   list dhcp-option {
                     description "Information about a Dynamic Host Configuration Protocol option that is associated with the address assignment";
                     leaf dhcp-option-code {
                       type int32;
                       description "Numeric code assigned to the DHCP option";
                     }
                     leaf dhcp-option-name {
                       type string;
                       description "Name of the DHCP option";
                     }
                     leaf dhcp-option-type {
                       type string;
                       description "Type of value for the DHCP option (for example, string [word], integer, IP address)";
                     }
                     leaf dhcp-option-value {
                       type string;
                       description "Value of the DHCP option";
                     }
                   }
                 }
                 container dhcp-lease-information {
                   description "Information about an address assignment";
                   container dhcp-option-table {
                     description "Information about one or more Dynamic Host Configuration Protocol options that are associated with the address assignment";
                     list dhcp-option {
                       description "Information about a Dynamic Host Configuration Protocol option that is associated with the address assignment";
                       leaf dhcp-option-code {
                         type int32;
                         description "Numeric code assigned to the DHCP option";
                       }
                       leaf dhcp-option-name {
                         type string;
                         description "Name of the DHCP option";
                       }
                       leaf dhcp-option-type {
                         type string;
                         description "Type of value for the DHCP option (for example, string [word], integer, IP address)";
                       }
                       leaf dhcp-option-value {
                         type string;
                         description "Value of the DHCP option";
                       }
                     }
                   }
                   container dhcp-lease-information {
                     description "Information about an address assignment";
                     container dhcp-option-table {
                       description "Information about one or more Dynamic Host Configuration Protocol options that are associated with the address assignment";
                       list dhcp-option {
                         description "Information about a Dynamic Host Configuration Protocol option that is associated with the address assignment";
                         leaf dhcp-option-code {
                           type int32;
                           description "Numeric code assigned to the DHCP option";
                         }
                         leaf dhcp-option-name {
                           type string;
                           description "Name of the DHCP option";
                         }
                         leaf dhcp-option-type {
                           type string;
                           description "Type of value for the DHCP option (for example, string [word], integer, IP address)";
                         }
                         leaf dhcp-option-value {
                           type string;
                           description "Value of the DHCP option";
                         }
                       }
                     }
                     container dhcp-lease-information {
                       description "Information about an address assignment";
                       container dhcp-option-table {
                         description "Information about one or more Dynamic Host Configuration Protocol options that are associated with the address assignment";
                         list dhcp-option {
                           description "Information about a Dynamic Host Configuration Protocol option that is associated with the address assignment";
                           leaf dhcp-option-code {
                             type int32;
                             description "Numeric code assigned to the DHCP option";
                           }
                           leaf dhcp-option-name {
                             type string;
                             description "Name of the DHCP option";
                           }
                           leaf dhcp-option-type {
                             type string;
                             description "Type of value for the DHCP option (for example, string [word], integer, IP address)";
                           }
                           leaf dhcp-option-value {
                             type string;
                             description "Value of the DHCP option";
                           }
                         }
                       }
                       container dhcp-lease-information {
                         description "Information about an address assignment";
                         container dhcp-option-table {
                           description "Information about one or more Dynamic Host Configuration Protocol options that are associated with the address assignment";
                           list dhcp-option {
                             description "Information about a Dynamic Host Configuration Protocol option that is associated with the address assignment";
                             leaf dhcp-option-code {
                               type int32;
                               description "Numeric code assigned to the DHCP option";
                             }
                             leaf dhcp-option-name {
                               type string;
                               description "Name of the DHCP option";
                             }
                             leaf dhcp-option-type {
                               type string;
                               description "Type of value for the DHCP option (for example, string [word], integer, IP address)";
                             }
                             leaf dhcp-option-value {
                               type string;
                               description "Value of the DHCP option";
                             }
                           }
                         }
                         container dhcp-lease-information {
                           description "Information about an address assignment";
                           container dhcp-option-table {
                             description "Information about one or more Dynamic Host Configuration Protocol options that are associated with the address assignment";
                             list dhcp-option {
                               description "Information about a Dynamic Host Configuration Protocol option that is associated with the address assignment";
                               leaf dhcp-option-code {
                                 type int32;
                                 description "Numeric code assigned to the DHCP option";
                               }
                               leaf dhcp-option-name {
                                 type string;
                                 description "Name of the DHCP option";
                               }
                               leaf dhcp-option-type {
                                 type string;
                                 description "Type of value for the DHCP option (for example, string [word], integer, IP address)";
                               }
                               leaf dhcp-option-value {
                                 type string;
                                 description "Value of the DHCP option";
                               }
                             }
                           }
                           container dhcp-lease-information {
                             description "Information about an address assignment";
                             container dhcp-option-table {
                               description "Information about one or more Dynamic Host Configuration Protocol options that are associated with the address assignment";
                               list dhcp-option {
                                 description "Information about a Dynamic Host Configuration Protocol option that is associated with the address assignment";
                                 leaf dhcp-option-code {
                                   type int32;
                                   description "Numeric code assigned to the DHCP option";
                                 }
                                 leaf dhcp-option-name {
                                   type string;
                                   description "Name of the DHCP option";
                                 }
                                 leaf dhcp-option-type {
                                   type string;
                                   description "Type of value for the DHCP option (for example, string [word], integer, IP address)";
                                 }
                                 leaf dhcp-option-value {
                                   type string;
                                   description "Value of the DHCP option";
                                 }
                               }
                             }
                             container dhcp-lease-information {
                               description "Information about an address assignment";
                               container dhcp-option-table {
                                 description "Information about one or more Dynamic Host Configuration Protocol options that are associated with the address assignment";
                                 list dhcp-option {
                                   description "Information about a Dynamic Host Configuration Protocol option that is associated with the address assignment";
                                   leaf dhcp-option-code {
                                     type int32;
                                     description "Numeric code assigned to the DHCP option";
                                   }
                                   leaf dhcp-option-name {
                                     type string;
                                     description "Name of the DHCP option";
                                   }
                                   leaf dhcp-option-type {
                                     type string;
                                     description "Type of value for the DHCP option (for example, string [word], integer, IP address)";
                                   }
                                   leaf dhcp-option-value {
                                     type string;
                                     description "Value of the DHCP option";
                                   }
                                 }
                               }
                               container dhcp-lease-information {
                                 description "Information about an address assignment";
                                 container dhcp-option-table {
                                   description "Information about one or more Dynamic Host Configuration Protocol options that are associated with the address assignment";
                                   list dhcp-option {
                                     description "Information about a Dynamic Host Configuration Protocol option that is associated with the address assignment";
                                     leaf dhcp-option-code {
                                       type int32;
                                       description "Numeric code assigned to the DHCP option";
                                     }
                                     leaf dhcp-option-name {
                                       type string;
                                       description "Name of the DHCP option";
                                     }
                                     leaf dhcp-option-type {
                                       type string;
                                       description "Type of value for the DHCP option (for example, string [word], integer, IP address)";
                                     }
                                     leaf dhcp-option-value {
                                       type string;
                                       description "Value of the DHCP option";
                                     }
                                   }
                                 }
                                 container dhcp-lease-information {
                                   description "Information about an address assignment";
                                   container dhcp-option-table {
                                     description "Information about one or more Dynamic Host Configuration Protocol options that are associated with the address assignment";
                                     list dhcp-option {
                                       description "Information about a Dynamic Host Configuration Protocol option that is associated with the address assignment";
                                       leaf dhcp-option-code {
                                         type int32;
                                         description "Numeric code assigned to the DHCP option";
                                       }
                                       leaf dhcp-option-name {
                                         type string;
                                         description "Name of the DHCP option";
                                       }
                                       leaf dhcp-option-type {
                                         type string;
                                         description "Type of value for the DHCP option (for example, string [word], integer, IP address)";
                                       }
                                       leaf dhcp-option-value {
                                         type string;
                                         description "Value of the DHCP option";
                                       }
                                     }
                                   }
                                   container dhcp-lease-information {
                                     description "Information about an address assignment";
                                     container dhcp-option-table {
                                       description "Information about one or more Dynamic Host Configuration Protocol options that are associated with the address assignment";
                                       list dhcp-option {
                                         description "Information about a Dynamic Host Configuration Protocol option that is associated with the address assignment";
                                         leaf dhcp-option-code {
                                           type int32;
                                           description "Numeric code assigned to the DHCP option";
                                         }
                                         leaf dhcp-option-name {
                                           type string;
                                           description "Name of the DHCP option";
                                         }
                                         leaf dhcp-option-type {
                                           type string;
                                           description "Type of value for the DHCP option (for example, string [word], integer, IP address)";
                                         }
                                         leaf dhcp-option-value {
                                           type string;
                                           description "Value of the DHCP option";
                                         }
                                       }
                                     }
                                     container dhcp-lease-information {
                                       description "Information about an address assignment";
                                       container dhcp-option-table {
                                         description "Information about one or more Dynamic Host Configuration Protocol options that are associated with the address assignment";
                                         list dhcp-option {
                                           description "Information about a Dynamic Host Configuration Protocol option that is associated with the address assignment";
                                           leaf dhcp-option-code {
                                             type int32;
                                             description "Numeric code assigned to the DHCP option";
                                           }
                                           leaf dhcp-option-name {
                                             type string;
                                             description "Name of the DHCP option";
                                           }
                                           leaf dhcp-option-type {
                                             type string;
                                             description "Type of value for the DHCP option (for example, string [word], integer, IP address)";
                                           }
                                           leaf dhcp-option-value {
                                             type string;
                                             description "Value of the DHCP option";
                                           }
                                         }
                                       }
                                       container dhcp-lease-information {
                                         description "Information about an address assignment";
                                         container dhcp-option-table {
                                           description "Information about one or more Dynamic Host Configuration Protocol options that are associated with the address assignment";
                                           list dhcp-option {
                                             description "Information about a Dynamic Host Configuration Protocol option that is associated with the address assignment";
                                             leaf dhcp-option-code {
                                               type int32;
                                               description "Numeric code assigned to the DHCP option";
                                             }
                                             leaf dhcp-option-name {
                                               type string;
                                               description "Name of the DHCP option";
                                             }
                                             leaf dhcp-option-type {
                                               type string;
                                               description "Type of value for the DHCP option (for example, string [word], integer, IP address)";
                                             }
                                             leaf dhcp-option-value {
                                               type string;
                                               description "Value of the DHCP option";
                                             }
                                           }
                                         }
                                         container dhcp-lease-information {
                                           description "Information about an address assignment";
                                           container dhcp-option-table {
                                             description "Information about one or more Dynamic Host Configuration Protocol options that are associated with the address assignment";
                                             list dhcp-option {
                                               description "Information about a Dynamic Host Configuration Protocol option that is associated with the address assignment";
                                               leaf dhcp-option-code {
                                                 type int32;
                                                 description "Numeric code assigned to the DHCP option";
                                               }
                                               leaf dhcp-option-name {
                                                 type string;
                                                 description "Name of the DHCP option";
                                               }
                                               leaf dhcp-option-type {
                                                 type string;
                                                 description "Type of value for the DHCP option (for example, string [word], integer, IP address)";
                                               }
                                               leaf dhcp-option-value {
                                                 type string;
                                                 description "Value of the DHCP option";
                                               }
                                             }
                                           }
                                           container dhcp-lease-information {
                                             description "Information about an address assignment";
                                             container dhcp-option-table {
                                               description "Information about one or more Dynamic Host Configuration Protocol options that are associated with the address assignment";
                                               list dhcp-option {
                                                 description "Information about a Dynamic Host Configuration Protocol option that is associated with the address assignment";
                                                 leaf dhcp-option-code {
                                                   type int32;
                                                   description "Numeric code assigned to the DHCP option";
                                                 }
                                                 leaf dhcp-option-name {
                                                   type string;
                                                   description "Name of the DHCP option";
                                                 }
                                                 leaf dhcp-option-type {
                                                   type string;
                                                   description "Type of value for the DHCP option (for example, string [word], integer, IP address)";
                                                 }
                                                 leaf dhcp-option-value {
                                                   type string;
                                                   description "Value of the DHCP option";
                                                 }
                                               }
                                             }
                                             container dhcp-lease-information {
                                               description "Information about an address assignment";
                                               container dhcp-option-table {
                                                 description "Information about one or more Dynamic Host Configuration Protocol options that are associated with the address assignment";
                                                 list dhcp-option {
                                                   description "Information about a Dynamic Host Configuration Protocol option that is associated with the address assignment";
                                                   leaf dhcp-option-code {
                                                     type int32;
                                                     description "Numeric code assigned to the DHCP option";
                                                   }
                                                   leaf dhcp-option-name {
                                                     type string;
                                                     description "Name of the DHCP option";
                                                   }
                                                   leaf dhcp-option-type {
                                                     type string;
                                                     description "Type of value for the DHCP option (for example, string [word], integer, IP address)";
                                                   }
                                                   leaf dhcp-option-value {
                                                     type string;
                                                     description "Value of the DHCP option";
                                                   }
                                                 }
                                               }
                                               container dhcp-lease-information {
                                                 description "Information about an address assignment";
                                                 container dhcp-option-table {
                                                   description "Information about one or more Dynamic Host Configuration Protocol options that are associated with the address assignment";
                                                   list dhcp-option {
                                                     description "Information about a Dynamic Host Configuration Protocol option that is associated with the address assignment";
                                                     leaf dhcp-option-code {
                                                       type int32;
                                                       description "Numeric code assigned to the DHCP option";
                                                     }
                                                     leaf dhcp-option-name {
                                                       type string;
                                                       description "Name of the DHCP option";
                                                     }
                                                     leaf dhcp-option-type {
                                                       type string;
                                                       description "Type of value for the DHCP option (for example, string [word], integer, IP address)";
                                                     }
                                                     leaf dhcp-option-value {
                                                       type string;
                                                       description "Value of the DHCP option";
                                                     }
                                                   }
                                                 }
                                                 container dhcp-lease-information {
                                                   description "Information about an address assignment";
                                                   container dhcp-option-table {
                                                     description "Information about one or more Dynamic Host Configuration Protocol options that are associated with the address assignment";
                                                     list dhcp-option {
                                                       description "Information about a Dynamic Host Configuration Protocol option that is associated with the address assignment";
                                                       leaf dhcp-option-code {
                                                         type int32;
                                                         description "Numeric code assigned to the DHCP option";
                                                       }
                                                       leaf dhcp-option-name {
                                                         type string;
                                                         description "Name of the DHCP option";
                                                       }
                                                       leaf dhcp-option-type {
                                                         type string;
                                                         description "Type of value for the DHCP option (for example, string [word], integer, IP address)";
                                                       }
                                                       leaf dhcp-option-value {
                                                         type string;
                                                         description "Value of the DHCP option";
                                                       }
                                                     }
                                                   }
                                                   container dhcp-lease-information {
                                                     description "Information about an address assignment";
                                                     container dhcp-option-table {
                                                       description "Information about one or more Dynamic Host Configuration Protocol options that are associated with the address assignment";
                                                       list dhcp-option {
                                                         description "Information about a Dynamic Host Configuration Protocol option that is associated with the address assignment";
                                                         leaf dhcp-option-code {
                                                           type int32;
                                                           description "Numeric code assigned to the DHCP option";
                                                         }
                                                         leaf dhcp-option-name {
                                                           type string;
                                                           description "Name of the DHCP option";
                                                         }
                                                         leaf dhcp-option-type {
                                                           type string;
                                                           description "Type of value for the DHCP option (for example, string [word], integer, IP address)";
                                                         }
                                                         leaf dhcp-option-value {
                                                           type string;
                                                           description "Value of the DHCP option";
                                                         }
                                                       }
                                                     }
                                                     container dhcp-lease-information {
                                                       description "Information about an address assignment";
                                                       container dhcp-option-table {
                                                         description "Information about one or more Dynamic Host Configuration Protocol options that are associated with the address assignment";
                                                         list dhcp-option {
                                                           description "Information about a Dynamic Host Configuration Protocol option that is associated with the address assignment";
                                                           leaf dhcp-option-code {
                                                             type int32;
                                                             description "Numeric code assigned to the DHCP option";
                                                           }
                                                           leaf dhcp-option-name {
                                                             type string;
                                                             description "Name of the DHCP option";
                                                           }
                                                           leaf dhcp-option-type {
                                                             type string;
                                                             description "Type of value for the DHCP option (for example, string [word], integer, IP address)";
                                                           }
                                                           leaf dhcp-option-value {
                                                             type string;
                                                             description "Value of the DHCP option";
                                                           }
                                                         }
                                                       }
                                                       container dhcp-lease-information {
                                                         description "Information about an address assignment";
                                                         container dhcp-option-table {
                                                           description "Information about one or more Dynamic Host Configuration Protocol options that are associated with the address assignment";
                                                           list dhcp-option {
                                                             description "Information about a Dynamic Host Configuration Protocol option that is associated with the address assignment";
                                                             leaf dhcp-option-code {
                                                               type int32;
                                                               description "Numeric code assigned to the DHCP option";
                                                             }
                                                             leaf dhcp-option-name {
                                                               type string;
                                                               description "Name of the DHCP option";
                                                             }
                                                             leaf dhcp-option-type {
                                                               type string;
                                                               description "Type of value for the DHCP option (for example, string [word], integer, IP address)";
                                                             }
                                                             leaf dhcp-option-value {
                                                               type string;
                                                               description "Value of the DHCP option";
                                                             }
                                                           }
                                                         }
                                                         container dhcp-lease-information {
                                                           description "Information about an address assignment";
                                                           container dhcp-option-table {
                                                             description "Information about one or more Dynamic Host Configuration Protocol options that are associated with the address assignment";
                                                             list dhcp-option {
                                                               description "Information about a Dynamic Host Configuration Protocol option that is associated with the address assignment";
                                                               leaf dhcp-option-code {
                                                                 type int32;
                                                                 description "Numeric code assigned to the DHCP option";
                                                               }
                                                               leaf dhcp-option-name {
                                                                 type string;
                                                                 description "Name of the DHCP option";
                                                               }
                                                               leaf dhcp-option-type {
                                                                 type string;
                                                                 description "Type of value for the DHCP option (for example, string [word], integer, IP address)";
                                                               }
                                                               leaf dhcp-option-value {
                                                                 type string;
                                                                 description "Value of the DHCP option";
                                                               }
                                                             }
                                                           }
                                                           container dhcp-lease-information {
                                                             description "Information about an address assignment";
                                                             container dhcp-option-table {
                                                               description "Information about one or more Dynamic Host Configuration Protocol options that are associated with the address assignment";
                                                               list dhcp-option {
                                                                 description "Information about a Dynamic Host Configuration Protocol option that is associated with the address assignment";
                                                                 leaf dhcp-option-code {
                                                                   type int32;
                                                                   description "Numeric code assigned to the DHCP option";
                                                                 }
                                                                 leaf dhcp-option-name {
                                                                   type string;
                                                                   description "Name of the DHCP option";
                                                                 }
                                                                 leaf dhcp-option-type {
                                                                   type string;
                                                                   description "Type of value for the DHCP option (for example, string [word], integer, IP address)";
                                                                 }
                                                                 leaf dhcp-option-value {
                                                                   type string;
                                                                   description "Value of the DHCP option";
                                                                 }
                                                               }
                                                             }
                                                             container dhcp-lease-information {
                                                               description "Information about an address assignment";
                                                               container dhcp-option-table {
                                                                 description "Information about one or more Dynamic Host Configuration Protocol options that are associated with the address assignment";
                                                                 list dhcp-option {
                                                                   description "Information about a Dynamic Host Configuration Protocol option that is associated with the address assignment";
                                                                   leaf dhcp-option-code {
                                                                     type int32;
                                                                     description "Numeric code assigned to the DHCP option";
                                                                   }
                                                                   leaf dhcp-option-name {
                                                                     type string;
                                                                     description "Name of the DHCP option";
                                                                   }
                                                                   leaf dhcp-option-type {
                                                                     type string;
                                                                     description "Type of value for the DHCP option (for example, string [word], integer, IP address)";
                                                                   }
                                                                   leaf dhcp-option-value {
                                                                     type string;
                                                                     description "Value of the DHCP option";
                                                                   }
                                                                 }
                                                               }
                                                               container dhcp-lease-information {
                                                                 description "Information about an address assignment";
                                                                 container dhcp-option-table {
                                                                   description "Information about one or more Dynamic Host Configuration Protocol options that are associated with the address assignment";
                                                                   list dhcp-option {
                                                                     description "Information about a Dynamic Host Configuration Protocol option that is associated with the address assignment";
                                                                     leaf dhcp-option-code {
                                                                       type int32;
                                                                       description "Numeric code assigned to the DHCP option";
                                                                     }
                                                                     leaf dhcp-option-name {
                                                                       type string;
                                                                       description "Name of the DHCP option";
                                                                     }
                                                                     leaf dhcp-option-type {
                                                                       type string;
                                                                       description "Type of value for the DHCP option (for example, string [word], integer, IP address)";
                                                                     }
                                                                     leaf dhcp-option-value {
                                                                       type string;
                                                                       description "Value of the DHCP option";
                                                                     }
                                                                   }
                                                                 }
                                                                 container dhcp-lease-information {
                                                                   description "Information about an address assignment";
                                                                   container dhcp-option-table {
                                                                     description "Information about one or more Dynamic Host Configuration Protocol options that are associated with the address assignment";
                                                                     list dhcp-option {
                                                                       description "Information about a Dynamic Host Configuration Protocol option that is associated with the address assignment";
                                                                       leaf dhcp-option-code {
                                                                         type int32;
                                                                         description "Numeric code assigned to the DHCP option";
                                                                       }
                                                                       leaf dhcp-option-name {
                                                                         type string;
                                                                         description "Name of the DHCP option";
                                                                       }
                                                                       leaf dhcp-option-type {
                                                                         type string;
                                                                         description "Type of value for the DHCP option (for example, string [word], integer, IP address)";
                                                                       }
                                                                       leaf dhcp-option-value {
                                                                         type string;
                                                                         description "Value of the DHCP option";
                                                                       }
                                                                     }
                                                                   }
                                                                   container dhcp-lease-information {
                                                                     description "Information about an address assignment";
                                                                     container dhcp-option-table {
                                                                       description "Information about one or more Dynamic Host Configuration Protocol options that are associated with the address assignment";
                                                                       list dhcp-option {
                                                                         description "Information about a Dynamic Host Configuration Protocol option that is associated with the address assignment";
                                                                         leaf dhcp-option-code {
                                                                           type int32;
                                                                           description "Numeric code assigned to the DHCP option";
                                                                         }
                                                                         leaf dhcp-option-name {
                                                                           type string;
                                                                           description "Name of the DHCP option";
                                                                         }
                                                                         leaf dhcp-option-type {
                                                                           type string;
                                                                           description "Type of value for the DHCP option (for example, string [word], integer, IP address)";
                                                                         }
                                                                         leaf dhcp-option-value {
                                                                           type string;
                                                                           description "Value of the DHCP option";
                                                                         }
                                                                       }
                                                                     }
                                                                     container dhcp-lease-information {
                                                                       description "Information about an address assignment";
                                                                       container dhcp-option-table {
                                                                         description "Information about one or more Dynamic Host Configuration Protocol options that are associated with the address assignment";
                                                                         list dhcp-option {
                                                                           description "Information about a Dynamic Host Configuration Protocol option that is associated with the address assignment";
                                                                           leaf dhcp-option-code {
                                                                             type int32;
                                                                             description "Numeric code assigned to the DHCP option";
                                                                           }
                                                                           leaf dhcp-option-name {
                                                                             type string;
                                                                             description "Name of the DHCP option";
                                                                           }
                                                                           leaf dhcp-option-type {
                                                                             type string;
                                                                             description "Type of value for the DHCP option (for example, string [word], integer, IP address)";
                                                                           }
                                                                           leaf dhcp-option-value {
                                                                             type string;
                                                                             description "Value of the DHCP option";
                                                                           }
                                                                         }
                                                                       }
                                                                       container dhcp-lease-information {
                                                                         description "Information about an address assignment";
                                                                         container dhcp-option-table {
                                                                           description "Information about one or more Dynamic Host Configuration Protocol options that are associated with the address assignment";
                                                                           list dhcp-option {
                                                                             description "Information about a Dynamic Host Configuration Protocol option that is associated with the address assignment";
                                                                             leaf dhcp-option-code {
                                                                               type int32;
                                                                               description "Numeric code assigned to the DHCP option";
                                                                             }
                                                                             leaf dhcp-option-name {
                                                                               type string;
                                                                               description "Name of the DHCP option";
                                                                             }
                                                                             leaf dhcp-option-type {
                                                                               type string;
                                                                               description "Type of value for the DHCP option (for example, string [word], integer, IP address)";
                                                                             }
                                                                             leaf dhcp-option-value {
                                                                               type string;
                                                                               description "Value of the DHCP option";
                                                                             }
                                                                           }
                                                                         }
                                                                         container dhcp-lease-information {
                                                                           description "Information about an address assignment";
                                                                           container dhcp-option-table {
                                                                             description "Information about one or more Dynamic Host Configuration Protocol options that are associated with the address assignment";
                                                                             list dhcp-option {
                                                                               description "Information about a Dynamic Host Configuration Protocol option that is associated with the address assignment";
                                                                               leaf dhcp-option-code {
                                                                                 type int32;
                                                                                 description "Numeric code assigned to the DHCP option";
                                                                               }
                                                                               leaf dhcp-option-name {
                                                                                 type string;
                                                                                 description "Name of the DHCP option";
                                                                               }
                                                                               leaf dhcp-option-type {
                                                                                 type string;
                                                                                 description "Type of value for the DHCP option (for example, string [word], integer, IP address)";
                                                                               }
                                                                               leaf dhcp-option-value {
                                                                                 type string;
                                                                                 description "Value of the DHCP option";
                                                                               }
                                                                             }
                                                                           }
                                                                           container dhcp-lease-information {
                                                                             description "Information about an address assignment";
                                                                             container dhcp-option-table {
                                                                               description "Information about one or more Dynamic Host Configuration Protocol options that are associated with the address assignment";
                                                                               list dhcp-option {
                                                                                 description "Information about a Dynamic Host Configuration Protocol option that is associated with the address assignment";
                                                                                 leaf dhcp-option-code {
                                                                                   type int32;
                                                                                   description "Numeric code assigned to the DHCP option";
                                                                                 }
                                                                                 leaf dhcp-option-name {
                                                                                   type string;
                                                                                   description "Name of the DHCP option";
                                                                                 }
                                                                                 leaf dhcp-option-type {
                                                                                   type string;
                                                                                   description "Type of value for the DHCP option (for example, string [word], integer, IP address)";
                                                                                 }
                                                                                 leaf dhcp-option-value {
                                                                                   type string;
                                                                                   description "Value of the DHCP option";
                                                                                 }
                                                                               }
                                                                             }
                                                                             container dhcp-lease-information {
                                                                               description "Information about an address assignment";
                                                                               container dhcp-option-table {
                                                                                 description "Information about one or more Dynamic Host Configuration Protocol options that are associated with the address assignment";
                                                                                 list dhcp-option {
                                                                                   description "Information about a Dynamic Host Configuration Protocol option that is associated with the address assignment";
                                                                                   leaf dhcp-option-code {
                                                                                     type int32;
                                                                                     description "Numeric code assigned to the DHCP option";
                                                                                   }
                                                                                   leaf dhcp-option-name {
                                                                                     type string;
                                                                                     description "Name of the DHCP option";
                                                                                   }
                                                                                   leaf dhcp-option-type {
                                                                                     type string;
                                                                                     description "Type of value for the DHCP option (for example, string [word], integer, IP address)";
                                                                                   }
                                                                                   leaf dhcp-option-value {
                                                                                     type string;
                                                                                     description "Value of the DHCP option";
                                                                                   }
                                                                                 }
                                                                               }
                                                                               container dhcp-lease-information {
                                                                                 description "Information about an address assignment";
                                                                                 container dhcp-option-table {
                                                                                   description "Information about one or more Dynamic Host Configuration Protocol options that are associated with the address assignment";
                                                                                   list dhcp-option {
                                                                                     description "Information about a Dynamic Host Configuration Protocol option that is associated with the address assignment";
                                                                                     leaf dhcp-option-code {
                                                                                       type int32;
                                                                                       description "Numeric code assigned to the DHCP option";
                                                                                     }
                                                                                     leaf dhcp-option-name {
                                                                                       type string;
                                                                                       description "Name of the DHCP option";
                                                                                     }
                                                                                     leaf dhcp-option-type {
                                                                                       type string;
                                                                                       description "Type of value for the DHCP option (for example, string [word], integer, IP address)";
                                                                                     }
                                                                                     leaf dhcp-option-value {
                                                                                       type string;
                                                                                       description "Value of the DHCP option";
                                                                                     }
                                                                                   }
                                                                                 }
                                                                                 container dhcp-lease-information {
                                                                                   description "Information about an address assignment";
                                                                                   container dhcp-option-table {
                                                                                     description "Information about one or more Dynamic Host Configuration Protocol options that are associated with the address assignment";
                                                                                     list dhcp-option {
                                                                                       description "Information about a Dynamic Host Configuration Protocol option that is associated with the address assignment";
                                                                                       leaf dhcp-option-code {
                                                                                         type int32;
                                                                                         description "Numeric code assigned to the DHCP option";
                                                                                       }
                                                                                       leaf dhcp-option-name {
                                                                                         type string;
                                                                                         description "Name of the DHCP option";
                                                                                       }
                                                                                       leaf dhcp-option-type {
                                                                                         type string;
                                                                                         description "Type of value for the DHCP option (for example, string [word], integer, IP address)";
                                                                                       }
                                                                                       leaf dhcp-option-value {
                                                                                         type string;
                                                                                         description "Value of the DHCP option";
                                                                                       }
                                                                                     }
                                                                                   }
                                                                                   container dhcp-lease-information {
                                                                                     description "Information about an address assignment";
                                                                                     container dhcp-option-table {
                                                                                       description "Information about one or more Dynamic Host Configuration Protocol options that are associated with the address assignment";
                                                                                       list dhcp-option {
                                                                                         description "Information about a Dynamic Host Configuration Protocol option that is associated with the address assignment";
                                                                                         leaf dhcp-option-code {
                                                                                           type int32;
                                                                                           description "Numeric code assigned to the DHCP option";
                                                                                         }
                                                                                         leaf dhcp-option-name {
                                                                                           type string;
                                                                                           description "Name of the DHCP option";
                                                                                         }
                                                                                         leaf dhcp-option-type {
                                                                                           type string;
                                                                                           description "Type of value for the DHCP option (for example, string [word], integer, IP address)";
                                                                                         }
                                                                                         leaf dhcp-option-value {
                                                                                           type string;
                                                                                           description "Value of the DHCP option";
                                                                                         }
                                                                                       }
                                                                                     }
                                                                                     container dhcp-lease-information {
                                                                                       description "Information about an address assignment";
                                                                                       container dhcp-option-table {
                                                                                         description "Information about one or more Dynamic Host Configuration Protocol options that are associated with the address assignment";
                                                                                         list dhcp-option {
                                                                                           description "Information about a Dynamic Host Configuration Protocol option that is associated with the address assignment";
                                                                                           leaf dhcp-option-code {
                                                                                             type int32;
                                                                                             description "Numeric code assigned to the DHCP option";
                                                                                           }
                                                                                           leaf dhcp-option-name {
                                                                                             type string;
                                                                                             description "Name of the DHCP option";
                                                                                           }
                                                                                           leaf dhcp-option-type {
                                                                                             type string;
                                                                                             description "Type of value for the DHCP option (for example, string [word], integer, IP address)";
                                                                                           }
                                                                                           leaf dhcp-option-value {
                                                                                             type string;
                                                                                             description "Value of the DHCP option";
                                                                                           }
                                                                                         }
                                                                                       }
                                                                                       container dhcp-lease-information {
                                                                                         description "Information about an address assignment";
                                                                                         container dhcp-option-table {
                                                                                           description "Information about one or more Dynamic Host Configuration Protocol options that are associated with the address assignment";
                                                                                           list dhcp-option {
                                                                                             description "Information about a Dynamic Host Configuration Protocol option that is associated with the address assignment";
                                                                                             leaf dhcp-option-code {
                                                                                               type int32;
                                                                                               description "Numeric code assigned to the DHCP option";
                                                                                             }
                                                                                             leaf dhcp-option-name {
                                                                                               type string;
                                                                                               description "Name of the DHCP option";
                                                                                             }
                                                                                             leaf dhcp-option-type {
                                                                                               type string;
                                                                                               description "Type of value for the DHCP option (for example, string [word], integer, IP address)";
                                                                                             }
                                                                                             leaf dhcp-option-value {
                                                                                               type string;
                                                                                               description "Value of the DHCP option";
                                                                                             }
                                                                                           }
                                                                                         }
                                                                                         container dhcp-lease-information {
                                                                                           description "Information about an address assignment";
                                                                                           container dhcp-option-table {
                                                                                             description "Information about one or more Dynamic Host Configuration Protocol options that are associated with the address assignment";
                                                                                             list dhcp-option {
                                                                                               description "Information about a Dynamic Host Configuration Protocol option that is associated with the address assignment";
                                                                                               leaf dhcp-option-code {
                                                                                                 type int32;
                                                                                                 description "Numeric code assigned to the DHCP option";
                                                                                               }
                                                                                               leaf dhcp-option-name {
                                                                                                 type string;
                                                                                                 description "Name of the DHCP option";
                                                                                               }
                                                                                               leaf dhcp-option-type {
                                                                                                 type string;
                                                                                                 description "Type of value for the DHCP option (for example, string [word], integer, IP address)";
                                                                                               }
                                                                                               leaf dhcp-option-value {
                                                                                                 type string;
                                                                                                 description "Value of the DHCP option";
                                                                                               }
                                                                                             }
                                                                                           }
                                                                                           container dhcp-lease-information {
                                                                                             description "Information about an address assignment";
                                                                                             container dhcp-option-table {
                                                                                               description "Information about one or more Dynamic Host Configuration Protocol options that are associated with the address assignment";
                                                                                               list dhcp-option {
                                                                                                 description "Information about a Dynamic Host Configuration Protocol option that is associated with the address assignment";
                                                                                                 leaf dhcp-option-code {
                                                                                                   type int32;
                                                                                                   description "Numeric code assigned to the DHCP option";
                                                                                                 }
                                                                                                 leaf dhcp-option-name {
                                                                                                   type string;
                                                                                                   description "Name of the DHCP option";
                                                                                                 }
                                                                                                 leaf dhcp-option-type {
                                                                                                   type string;
                                                                                                   description "Type of value for the DHCP option (for example, string [word], integer, IP address)";
                                                                                                 }
                                                                                                 leaf dhcp-option-value {
                                                                                                   type string;
                                                                                                   description "Value of the DHCP option";
                                                                                                 }
                                                                                               }
                                                                                             }
                                                                                             container dhcp-lease-information {
                                                                                               description "Information about an address assignment";
                                                                                               container dhcp-option-table {
                                                                                                 description "Information about one or more Dynamic Host Configuration Protocol options that are associated with the address assignment";
                                                                                                 list dhcp-option {
                                                                                                   description "Information about a Dynamic Host Configuration Protocol option that is associated with the address assignment";
                                                                                                   leaf dhcp-option-code {
                                                                                                     type int32;
                                                                                                     description "Numeric code assigned to the DHCP option";
                                                                                                   }
                                                                                                   leaf dhcp-option-name {
                                                                                                     type string;
                                                                                                     description "Name of the DHCP option";
                                                                                                   }
                                                                                                   leaf dhcp-option-type {
                                                                                                     type string;
                                                                                                     description "Type of value for the DHCP option (for example, string [word], integer, IP address)";
                                                                                                   }
                                                                                                   leaf dhcp-option-value {
                                                                                                     type string;
                                                                                                     description "Value of the DHCP option";
                                                                                                   }
                                                                                                 }
                                                                                               }
                                                                                               container dhcp-lease-information {
                                                                                                 description "Information about an address assignment";
                                                                                                 container dhcp-option-table {
                                                                                                   description "Information about one or more Dynamic Host Configuration Protocol options that are associated with the address assignment";
                                                                                                   list dhcp-option {
                                                                                                     description "Information about a Dynamic Host Configuration Protocol option that is associated with the address assignment";
                                                                                                     leaf dhcp-option-code {
                                                                                                       type int32;
                                                                                                       description "Numeric code assigned to the DHCP option";
                                                                                                     }
                                                                                                     leaf dhcp-option-name {
                                                                                                       type string;
                                                                                                       description "Name of the DHCP option";
                                                                                                     }
                                                                                                     leaf dhcp-option-type {
                                                                                                       type string;
                                                                                                       description "Type of value for the DHCP option (for example, string [word], integer, IP address)";
                                                                                                     }
                                                                                                     leaf dhcp-option-value {
                                                                                                       type string;
                                                                                                       description "Value of the DHCP option";
                                                                                                     }
                                                                                                   }
                                                                                                 }
                                                                                                 container dhcp-lease-information {
                                                                                                   description "Information about an address assignment";
                                                                                                   container dhcp-option-table {
                                                                                                     description "Information about one or more Dynamic Host Configuration Protocol options that are associated with the address assignment";
                                                                                                     list dhcp-option {
                                                                                                       description "Information about a Dynamic Host Configuration Protocol option that is associated with the address assignment";
                                                                                                       leaf dhcp-option-code {
                                                                                                         type int32;
                                                                                                         description "Numeric code assigned to the DHCP option";
                                                                                                       }
                                                                                                       leaf dhcp-option-name {
                                                                                                         type string;
                                                                                                         description "Name of the DHCP option";
                                                                                                       }
                                                                                                       leaf dhcp-option-type {
                                                                                                         type string;
                                                                                                         description "Type of value for the DHCP option (for example, string [word], integer, IP address)";
                                                                                                       }
                                                                                                       leaf dhcp-option-value {
                                                                                                         type string;
                                                                                                         description "Value of the DHCP option";
                                                                                                       }
                                                                                                     }
                                                                                                   }
                                                                                                   container dhcp-lease-information {
                                                                                                     description "Information about an address assignment";
                                                                                                     container dhcp-option-table {
                                                                                                       description "Information about one or more Dynamic Host Configuration Protocol options that are associated with the address assignment";
                                                                                                       list dhcp-option {
                                                                                                         description "Information about a Dynamic Host Configuration Protocol option that is associated with the address assignment";
                                                                                                         leaf dhcp-option-code {
                                                                                                           type int32;
                                                                                                           description "Numeric code assigned to the DHCP option";
                                                                                                         }
                                                                                                         leaf dhcp-option-name {
                                                                                                           type string;
                                                                                                           description "Name of the DHCP option";
                                                                                                         }
                                                                                                         leaf dhcp-option-type {
                                                                                                           type string;
                                                                                                           description "Type of value for the DHCP option (for example, string [word], integer, IP address)";
                                                                                                         }
                                                                                                         leaf dhcp-option-value {
                                                                                                           type string;
                                                                                                           description "Value of the DHCP option";
                                                                                                         }
                                                                                                       }
                                                                                                     }
                                                                                                     container dhcp-lease-information {
                                                                                                       description "Information about an address assignment";
                                                                                                       container dhcp-option-table {
                                                                                                         description "Information about one or more Dynamic Host Configuration Protocol options that are associated with the address assignment";
                                                                                                         list dhcp-option {
                                                                                                           description "Information about a Dynamic Host Configuration Protocol option that is associated with the address assignment";
                                                                                                           leaf dhcp-option-code {
                                                                                                             type int32;
                                                                                                             description "Numeric code assigned to the DHCP option";
                                                                                                           }
                                                                                                           leaf dhcp-option-name {
                                                                                                             type string;
                                                                                                             description "Name of the DHCP option";
                                                                                                           }
                                                                                                           leaf dhcp-option-type {
                                                                                                             type string;
                                                                                                             description "Type of value for the DHCP option (for example, string [word], integer, IP address)";
                                                                                                           }
                                                                                                           leaf dhcp-option-value {
                                                                                                             type string;
                                                                                                             description "Value of the DHCP option";
                                                                                                           }
                                                                                                         }
                                                                                                       }
                                                                                                       container dhcp-lease-information {
                                                                                                         description "Information about an address assignment";
                                                                                                         container dhcp-option-table {
                                                                                                           description "Information about one or more Dynamic Host Configuration Protocol options that are associated with the address assignment";
                                                                                                           list dhcp-option {
                                                                                                             description "Information about a Dynamic Host Configuration Protocol option that is associated with the address assignment";
                                                                                                             leaf dhcp-option-code {
                                                                                                               type int32;
                                                                                                               description "Numeric code assigned to the DHCP option";
                                                                                                             }
                                                                                                             leaf dhcp-option-name {
                                                                                                               type string;
                                                                                                               description "Name of the DHCP option";
                                                                                                             }
                                                                                                             leaf dhcp-option-type {
                                                                                                               type string;
                                                                                                               description "Type of value for the DHCP option (for example, string [word], integer, IP address)";
                                                                                                             }
                                                                                                             leaf dhcp-option-value {
                                                                                                               type string;
                                                                                                               description "Value of the DHCP option";
                                                                                                             }
                                                                                                           }
                                                                                                         }
                                                                                                         container dhcp-lease-information {
                                                                                                           description "Information about an address assignment";
                                                                                                           container dhcp-option-table {
                                                                                                             description "Information about one or more Dynamic Host Configuration Protocol options that are associated with the address assignment";
                                                                                                             list dhcp-option {
                                                                                                               description "Information about a Dynamic Host Configuration Protocol option that is associated with the address assignment";
                                                                                                               leaf dhcp-option-code {
                                                                                                                 type int32;
                                                                                                                 description "Numeric code assigned to the DHCP option";
                                                                                                               }
                                                                                                               leaf dhcp-option-name {
                                                                                                                 type string;
                                                                                                                 description "Name of the DHCP option";
                                                                                                               }
                                                                                                               leaf dhcp-option-type {
                                                                                                                 type string;
                                                                                                                 description "Type of value for the DHCP option (for example, string [word], integer, IP address)";
                                                                                                               }
                                                                                                               leaf dhcp-option-value {
                                                                                                                 type string;
                                                                                                                 description "Value of the DHCP option";
                                                                                                               }
                                                                                                             }
                                                                                                           }
                                                                                                           container dhcp-lease-information {
                                                                                                             description "Information about an address assignment";
                                                                                                             container dhcp-option-table {
                                                                                                               description "Information about one or more Dynamic Host Configuration Protocol options that are associated with the address assignment";
                                                                                                               list dhcp-option {
                                                                                                                 description "Information about a Dynamic Host Configuration Protocol option that is associated with the address assignment";
                                                                                                                 leaf dhcp-option-code {
                                                                                                                   type int32;
                                                                                                                   description "Numeric code assigned to the DHCP option";
                                                                                                                 }
                                                                                                                 leaf dhcp-option-name {
                                                                                                                   type string;
                                                                                                                   description "Name of the DHCP option";
                                                                                                                 }
                                                                                                                 leaf dhcp-option-type {
                                                                                                                   type string;
                                                                                                                   description "Type of value for the DHCP option (for example, string [word], integer, IP address)";
                                                                                                                 }
                                                                                                                 leaf dhcp-option-value {
                                                                                                                   type string;
                                                                                                                   description "Value of the DHCP option";
                                                                                                                 }
                                                                                                               }
                                                                                                             }
                                                                                                             container dhcp-lease-information {
                                                                                                               description "Information about an address assignment";
                                                                                                               container dhcp-option-table {
                                                                                                                 description "Information about one or more Dynamic Host Configuration Protocol options that are associated with the address assignment";
                                                                                                                 list dhcp-option {
                                                                                                                   description "Information about a Dynamic Host Configuration Protocol option that is associated with the address assignment";
                                                                                                                   leaf dhcp-option-code {
                                                                                                                     type int32;
                                                                                                                     description "Numeric code assigned to the DHCP option";
                                                                                                                   }
                                                                                                                   leaf dhcp-option-name {
                                                                                                                     type string;
                                                                                                                     description "Name of the DHCP option";
                                                                                                                   }
                                                                                                                   leaf dhcp-option-type {
                                                                                                                     type string;
                                                                                                                     description "Type of value for the DHCP option (for example, string [word], integer, IP address)";
                                                                                                                   }
                                                                                                                   leaf dhcp-option-value {
                                                                                                                     type string;
                                                                                                                     description "Value of the DHCP option";
                                                                                                                   }
                                                                                                                 }
                                                                                                               }
                                                                                                               container dhcp-lease-information {
                                                                                                                 description "Information about an address assignment";
                                                                                                                 container dhcp-option-table {
                                                                                                                   description "Information about one or more Dynamic Host Configuration Protocol options that are associated with the address assignment";
                                                                                                                   list dhcp-option {
                                                                                                                     description "Information about a Dynamic Host Configuration Protocol option that is associated with the address assignment";
                                                                                                                     leaf dhcp-option-code {
                                                                                                                       type int32;
                                                                                                                       description "Numeric code assigned to the DHCP option";
                                                                                                                     }
                                                                                                                     leaf dhcp-option-name {
                                                                                                                       type string;
                                                                                                                       description "Name of the DHCP option";
                                                                                                                     }
                                                                                                                     leaf dhcp-option-type {
                                                                                                                       type string;
                                                                                                                       description "Type of value for the DHCP option (for example, string [word], integer, IP address)";
                                                                                                                     }
                                                                                                                     leaf dhcp-option-value {
                                                                                                                       type string;
                                                                                                                       description "Value of the DHCP option";
                                                                                                                     }
                                                                                                                   }
                                                                                                                 }
                                                                                                                 container dhcp-lease-information {
                                                                                                                   description "Information about an address assignment";
                                                                                                                   container dhcp-option-table {
                                                                                                                     description "Information about one or more Dynamic Host Configuration Protocol options that are associated with the address assignment";
                                                                                                                     list dhcp-option {
                                                                                                                       description "Information about a Dynamic Host Configuration Protocol option that is associated with the address assignment";
                                                                                                                       leaf dhcp-option-code {
                                                                                                                         type int32;
                                                                                                                         description "Numeric code assigned to the DHCP option";
                                                                                                                       }
                                                                                                                       leaf dhcp-option-name {
                                                                                                                         type string;
                                                                                                                         description "Name of the DHCP option";
                                                                                                                       }
                                                                                                                       leaf dhcp-option-type {
                                                                                                                         type string;
                                                                                                                         description "Type of value for the DHCP option (for example, string [word], integer, IP address)";
                                                                                                                       }
                                                                                                                       leaf dhcp-option-value {
                                                                                                                         type string;
                                                                                                                         description "Value of the DHCP option";
                                                                                                                       }
                                                                                                                     }
                                                                                                                   }
                                                                                                                   container dhcp-lease-information {
                                                                                                                     description "Information about an address assignment";
                                                                                                                     container dhcp-option-table {
                                                                                                                       description "Information about one or more Dynamic Host Configuration Protocol options that are associated with the address assignment";
                                                                                                                       list dhcp-option {
                                                                                                                         description "Information about a Dynamic Host Configuration Protocol option that is associated with the address assignment";
                                                                                                                         leaf dhcp-option-code {
                                                                                                                           type int32;
                                                                                                                           description "Numeric code assigned to the DHCP option";
                                                                                                                         }
                                                                                                                         leaf dhcp-option-name {
                                                                                                                           type string;
                                                                                                                           description "Name of the DHCP option";
                                                                                                                         }
                                                                                                                         leaf dhcp-option-type {
                                                                                                                           type string;
                                                                                                                           description "Type of value for the DHCP option (for example, string [word], integer, IP address)";
                                                                                                                         }
                                                                                                                         leaf dhcp-option-value {
                                                                                                                           type string;
                                                                                                                           description "Value of the DHCP option";
                                                                                                                         }
                                                                                                                       }
                                                                                                                     }
                                                                                                                     container dhcp-lease-information {
                                                                                                                       description "Information about an address assignment";
                                                                                                                       container dhcp-option-table {
                                                                                                                         description "Information about one or more Dynamic Host Configuration Protocol options that are associated with the address assignment";
                                                                                                                         list dhcp-option {
                                                                                                                           description "Information about a Dynamic Host Configuration Protocol option that is associated with the address assignment";
                                                                                                                           leaf dhcp-option-code {
                                                                                                                             type int32;
                                                                                                                             description "Numeric code assigned to the DHCP option";
                                                                                                                           }
                                                                                                                           leaf dhcp-option-name {
                                                                                                                             type string;
                                                                                                                             description "Name of the DHCP option";
                                                                                                                           }
                                                                                                                           leaf dhcp-option-type {
                                                                                                                             type string;
                                                                                                                             description "Type of value for the DHCP option (for example, string [word], integer, IP address)";
                                                                                                                           }
                                                                                                                           leaf dhcp-option-value {
                                                                                                                             type string;
                                                                                                                             description "Value of the DHCP option";
                                                                                                                           }
                                                                                                                         }
                                                                                                                       }
                                                                                                                       container dhcp-lease-information {
                                                                                                                         description "Information about an address assignment";
                                                                                                                         container dhcp-option-table {
                                                                                                                           description "Information about one or more Dynamic Host Configuration Protocol options that are associated with the address assignment";
                                                                                                                           list dhcp-option {
                                                                                                                             description "Information about a Dynamic Host Configuration Protocol option that is associated with the address assignment";
                                                                                                                             leaf dhcp-option-code {
                                                                                                                               type int32;
                                                                                                                               description "Numeric code assigned to the DHCP option";
                                                                                                                             }
                                                                                                                             leaf dhcp-option-name {
                                                                                                                               type string;
                                                                                                                               description "Name of the DHCP option";
                                                                                                                             }
                                                                                                                             leaf dhcp-option-type {
                                                                                                                               type string;
                                                                                                                               description "Type of value for the DHCP option (for example, string [word], integer, IP address)";
                                                                                                                             }
                                                                                                                             leaf dhcp-option-value {
                                                                                                                               type string;
                                                                                                                               description "Value of the DHCP option";
                                                                                                                             }
                                                                                                                           }
                                                                                                                         }
                                                                                                                         container dhcp-lease-information {
                                                                                                                           description "Information about an address assignment";
                                                                                                                           container dhcp-option-table {
                                                                                                                             description "Information about one or more Dynamic Host Configuration Protocol options that are associated with the address assignment";
                                                                                                                             list dhcp-option {
                                                                                                                               description "Information about a Dynamic Host Configuration Protocol option that is associated with the address assignment";
                                                                                                                               leaf dhcp-option-code {
                                                                                                                                 type int32;
                                                                                                                                 description "Numeric code assigned to the DHCP option";
                                                                                                                               }
                                                                                                                               leaf dhcp-option-name {
                                                                                                                                 type string;
                                                                                                                                 description "Name of the DHCP option";
                                                                                                                               }
                                                                                                                               leaf dhcp-option-type {
                                                                                                                                 type string;
                                                                                                                                 description "Type of value for the DHCP option (for example, string [word], integer, IP address)";
                                                                                                                               }
                                                                                                                               leaf dhcp-option-value {
                                                                                                                                 type string;
                                                                                                                                 description "Value of the DHCP option";
                                                                                                                               }
                                                                                                                             }
                                                                                                                           }
                                                                                                                           container dhcp-lease-information {
                                                                                                                             description "Information about an address assignment";
                                                                                                                             container dhcp-option-table {
                                                                                                                               description "Information about one or more Dynamic Host Configuration Protocol options that are associated with the address assignment";
                                                                                                                               list dhcp-option {
                                                                                                                                 description "Information about a Dynamic Host Configuration Protocol option that is associated with the address assignment";
                                                                                                                                 leaf dhcp-option-code {
                                                                                                                                   type int32;
                                                                                                                                   description "Numeric code assigned to the DHCP option";
                                                                                                                                 }
                                                                                                                                 leaf dhcp-option-name {
                                                                                                                                   type string;
                                                                                                                                   description "Name of the DHCP option";
                                                                                                                                 }
                                                                                                                                 leaf dhcp-option-type {
                                                                                                                                   type string;
                                                                                                                                   description "Type of value for the DHCP option (for example, string [word], integer, IP address)";
                                                                                                                                 }
                                                                                                                                 leaf dhcp-option-value {
                                                                                                                                   type string;
                                                                                                                                   description "Value of the DHCP option";
                                                                                                                                 }
                                                                                                                               }
                                                                                                                             }
                                                                                                                             container dhcp-lease-information {
                                                                                                                               description "Information about an address assignment";
                                                                                                                               container dhcp-option-table {
                                                                                                                                 description "Information about one or more Dynamic Host Configuration Protocol options that are associated with the address assignment";
                                                                                                                                 list dhcp-option {
                                                                                                                                   description "Information about a Dynamic Host Configuration Protocol option that is associated with the address assignment";
                                                                                                                                   leaf dhcp-option-code {
                                                                                                                                     type int32;
                                                                                                                                     description "Numeric code assigned to the DHCP option";
                                                                                                                                   }
                                                                                                                                   leaf dhcp-option-name {
                                                                                                                                     type string;
                                                                                                                                     description "Name of the DHCP option";
                                                                                                                                   }
                                                                                                                                   leaf dhcp-option-type {
                                                                                                                                     type string;
                                                                                                                                     description "Type of value for the DHCP option (for example, string [word], integer, IP address)";
                                                                                                                                   }
                                                                                                                                   leaf dhcp-option-value {
                                                                                                                                     type string;
                                                                                                                                     description "Value of the DHCP option";
                                                                                                                                   }
                                                                                                                                 }
                                                                                                                               }
                                                                                                                               container dhcp-lease-information {
                                                                                                                                 description "Information about an address assignment";
                                                                                                                                 container dhcp-option-table {
                                                                                                                                   description "Information about one or more Dynamic Host Configuration Protocol options that are associated with the address assignment";
                                                                                                                                   list dhcp-option {
                                                                                                                                     description "Information about a Dynamic Host Configuration Protocol option that is associated with the address assignment";
                                                                                                                                     leaf dhcp-option-code {
                                                                                                                                       type int32;
                                                                                                                                       description "Numeric code assigned to the DHCP option";
                                                                                                                                     }
                                                                                                                                     leaf dhcp-option-name {
                                                                                                                                       type string;
                                                                                                                                       description "Name of the DHCP option";
                                                                                                                                     }
                                                                                                                                     leaf dhcp-option-type {
                                                                                                                                       type string;
                                                                                                                                       description "Type of value for the DHCP option (for example, string [word], integer, IP address)";
                                                                                                                                     }
                                                                                                                                     leaf dhcp-option-value {
                                                                                                                                       type string;
                                                                                                                                       description "Value of the DHCP option";
                                                                                                                                     }
                                                                                                                                   }
                                                                                                                                 }
                                                                                                                                 container dhcp-lease-information {
                                                                                                                                   description "Information about an address assignment";
                                                                                                                                   container dhcp-option-table {
                                                                                                                                     description "Information about one or more Dynamic Host Configuration Protocol options that are associated with the address assignment";
                                                                                                                                     list dhcp-option {
                                                                                                                                       description "Information about a Dynamic Host Configuration Protocol option that is associated with the address assignment";
                                                                                                                                       leaf dhcp-option-code {
                                                                                                                                         type int32;
                                                                                                                                         description "Numeric code assigned to the DHCP option";
                                                                                                                                       }
                                                                                                                                       leaf dhcp-option-name {
                                                                                                                                         type string;
                                                                                                                                         description "Name of the DHCP option";
                                                                                                                                       }
                                                                                                                                       leaf dhcp-option-type {
                                                                                                                                         type string;
                                                                                                                                         description "Type of value for the DHCP option (for example, string [word], integer, IP address)";
                                                                                                                                       }
                                                                                                                                       leaf dhcp-option-value {
                                                                                                                                         type string;
                                                                                                                                         description "Value of the DHCP option";
                                                                                                                                       }
                                                                                                                                     }
                                                                                                                                   }
                                                                                                                                   container dhcp-lease-information {
                                                                                                                                     description "Information about an address assignment";
                                                                                                                                     container dhcp-option-table {
                                                                                                                                       description "Information about one or more Dynamic Host Configuration Protocol options that are associated with the address assignment";
                                                                                                                                       list dhcp-option {
                                                                                                                                         description "Information about a Dynamic Host Configuration Protocol option that is associated with the address assignment";
                                                                                                                                         leaf dhcp-option-code {
                                                                                                                                           type int32;
                                                                                                                                           description "Numeric code assigned to the DHCP option";
                                                                                                                                         }
                                                                                                                                         leaf dhcp-option-name {
                                                                                                                                           type string;
                                                                                                                                           description "Name of the DHCP option";
                                                                                                                                         }
                                                                                                                                         leaf dhcp-option-type {
                                                                                                                                           type string;
                                                                                                                                           description "Type of value for the DHCP option (for example, string [word], integer, IP address)";
                                                                                                                                         }
                                                                                                                                         leaf dhcp-option-value {
                                                                                                                                           type string;
                                                                                                                                           description "Value of the DHCP option";
                                                                                                                                         }
                                                                                                                                       }
                                                                                                                                     }
                                                                                                                                     container dhcp-lease-information {
                                                                                                                                       description "Information about an address assignment";
                                                                                                                                       container dhcp-option-table {
                                                                                                                                         description "Information about one or more Dynamic Host Configuration Protocol options that are associated with the address assignment";
                                                                                                                                         list dhcp-option {
                                                                                                                                           description "Information about a Dynamic Host Configuration Protocol option that is associated with the address assignment";
                                                                                                                                           leaf dhcp-option-code {
                                                                                                                                             type int32;
                                                                                                                                             description "Numeric code assigned to the DHCP option";
                                                                                                                                           }
                                                                                                                                           leaf dhcp-option-name {
                                                                                                                                             type string;
                                                                                                                                             description "Name of the DHCP option";
                                                                                                                                           }
                                                                                                                                           leaf dhcp-option-type {
                                                                                                                                             type string;
                                                                                                                                             description "Type of value for the DHCP option (for example, string [word], integer, IP address)";
                                                                                                                                           }
                                                                                                                                           leaf dhcp-option-value {
                                                                                                                                             type string;
                                                                                                                                             description "Value of the DHCP option";
                                                                                                                                           }
                                                                                                                                         }
                                                                                                                                       }
                                                                                                                                       container dhcp-lease-information {
                                                                                                                                         description "Information about an address assignment";
                                                                                                                                         container dhcp-option-table {
                                                                                                                                           description "Information about one or more Dynamic Host Configuration Protocol options that are associated with the address assignment";
                                                                                                                                           list dhcp-option {
                                                                                                                                             description "Information about a Dynamic Host Configuration Protocol option that is associated with the address assignment";
                                                                                                                                             leaf dhcp-option-code {
                                                                                                                                               type int32;
                                                                                                                                               description "Numeric code assigned to the DHCP option";
                                                                                                                                             }
                                                                                                                                             leaf dhcp-option-name {
                                                                                                                                               type string;
                                                                                                                                               description "Name of the DHCP option";
                                                                                                                                             }
                                                                                                                                             leaf dhcp-option-type {
                                                                                                                                               type string;
                                                                                                                                               description "Type of value for the DHCP option (for example, string [word], integer, IP address)";
                                                                                                                                             }
                                                                                                                                             leaf dhcp-option-value {
                                                                                                                                               type string;
                                                                                                                                               description "Value of the DHCP option";
                                                                                                                                             }
                                                                                                                                           }
                                                                                                                                         }
                                                                                                                                         container dhcp-lease-information {
                                                                                                                                           description "Information about an address assignment";
                                                                                                                                           container dhcp-option-table {
                                                                                                                                             description "Information about one or more Dynamic Host Configuration Protocol options that are associated with the address assignment";
                                                                                                                                             list dhcp-option {
                                                                                                                                               description "Information about a Dynamic Host Configuration Protocol option that is associated with the address assignment";
                                                                                                                                               leaf dhcp-option-code {
                                                                                                                                                 type int32;
                                                                                                                                                 description "Numeric code assigned to the DHCP option";
                                                                                                                                               }
                                                                                                                                               leaf dhcp-option-name {
                                                                                                                                                 type string;
                                                                                                                                                 description "Name of the DHCP option";
                                                                                                                                               }
                                                                                                                                               leaf dhcp-option-type {
                                                                                                                                                 type string;
                                                                                                                                                 description "Type of value for the DHCP option (for example, string [word], integer, IP address)";
                                                                                                                                               }
                                                                                                                                               leaf dhcp-option-value {
                                                                                                                                                 type string;
                                                                                                                                                 description "Value of the DHCP option";
                                                                                                                                               }
                                                                                                                                             }
                                                                                                                                           }
                                                                                                                                           container dhcp-lease-information {
                                                                                                                                             description "Information about an address assignment";
                                                                                                                                             container dhcp-option-table {
                                                                                                                                               description "Information about one or more Dynamic Host Configuration Protocol options that are associated with the address assignment";
                                                                                                                                               list dhcp-option {
                                                                                                                                                 description "Information about a Dynamic Host Configuration Protocol option that is associated with the address assignment";
                                                                                                                                                 leaf dhcp-option-code {
                                                                                                                                                   type int32;
                                                                                                                                                   description "Numeric code assigned to the DHCP option";
                                                                                                                                                 }
                                                                                                                                                 leaf dhcp-option-name {
                                                                                                                                                   type string;
                                                                                                                                                   description "Name of the DHCP option";
                                                                                                                                                 }
                                                                                                                                                 leaf dhcp-option-type {
                                                                                                                                                   type string;
                                                                                                                                                   description "Type of value for the DHCP option (for example, string [word], integer, IP address)";
                                                                                                                                                 }
                                                                                                                                                 leaf dhcp-option-value {
                                                                                                                                                   type string;
                                                                                                                                                   description "Value of the DHCP option";
                                                                                                                                                 }
                                                                                                                                               }
                                                                                                                                             }
                                                                                                                                             container dhcp-lease-information {
                                                                                                                                               description "Information about an address assignment";
                                                                                                                                               container dhcp-option-table {
                                                                                                                                                 description "Information about one or more Dynamic Host Configuration Protocol options that are associated with the address assignment";
                                                                                                                                                 list dhcp-option {
                                                                                                                                                   description "Information about a Dynamic Host Configuration Protocol option that is associated with the address assignment";
                                                                                                                                                   leaf dhcp-option-code {
                                                                                                                                                     type int32;
                                                                                                                                                     description "Numeric code assigned to the DHCP option";
                                                                                                                                                   }
                                                                                                                                                   leaf dhcp-option-name {
                                                                                                                                                     type string;
                                                                                                                                                     description "Name of the DHCP option";
                                                                                                                                                   }
                                                                                                                                                   leaf dhcp-option-type {
                                                                                                                                                     type string;
                                                                                                                                                     description "Type of value for the DHCP option (for example, string [word], integer, IP address)";
                                                                                                                                                   }
                                                                                                                                                   leaf dhcp-option-value {
                                                                                                                                                     type string;
                                                                                                                                                     description "Value of the DHCP option";
                                                                                                                                                   }
                                                                                                                                                 }
                                                                                                                                               }
                                                                                                                                               container dhcp-lease-information {
                                                                                                                                                 description "Information about an address assignment";
                                                                                                                                                 container dhcp-option-table {
                                                                                                                                                   description "Information about one or more Dynamic Host Configuration Protocol options that are associated with the address assignment";
                                                                                                                                                   list dhcp-option {
                                                                                                                                                     description "Information about a Dynamic Host Configuration Protocol option that is associated with the address assignment";
                                                                                                                                                     leaf dhcp-option-code {
                                                                                                                                                       type int32;
                                                                                                                                                       description "Numeric code assigned to the DHCP option";
                                                                                                                                                     }
                                                                                                                                                     leaf dhcp-option-name {
                                                                                                                                                       type string;
                                                                                                                                                       description "Name of the DHCP option";
                                                                                                                                                     }
                                                                                                                                                     leaf dhcp-option-type {
                                                                                                                                                       type string;
                                                                                                                                                       description "Type of value for the DHCP option (for example, string [word], integer, IP address)";
                                                                                                                                                     }
                                                                                                                                                     leaf dhcp-option-value {
                                                                                                                                                       type string;
                                                                                                                                                       description "Value of the DHCP option";
                                                                                                                                                     }
                                                                                                                                                   }
                                                                                                                                                 }
                                                                                                                                                 container dhcp-lease-information {
                                                                                                                                                   description "Information about an address assignment";
                                                                                                                                                   container dhcp-option-table {
                                                                                                                                                     description "Information about one or more Dynamic Host Configuration Protocol options that are associated with the address assignment";
                                                                                                                                                     list dhcp-option {
                                                                                                                                                       description "Information about a Dynamic Host Configuration Protocol option that is associated with the address assignment";
                                                                                                                                                       leaf dhcp-option-code {
                                                                                                                                                         type int32;
                                                                                                                                                         description "Numeric code assigned to the DHCP option";
                                                                                                                                                       }
                                                                                                                                                       leaf dhcp-option-name {
                                                                                                                                                         type string;
                                                                                                                                                         description "Name of the DHCP option";
                                                                                                                                                       }
                                                                                                                                                       leaf dhcp-option-type {
                                                                                                                                                         type string;
                                                                                                                                                         description "Type of value for the DHCP option (for example, string [word], integer, IP address)";
                                                                                                                                                       }
                                                                                                                                                       leaf dhcp-option-value {
                                                                                                                                                         type string;
                                                                                                                                                         description "Value of the DHCP option";
                                                                                                                                                       }
                                                                                                                                                     }
                                                                                                                                                   }
                                                                                                                                                   container dhcp-lease-information {
                                                                                                                                                     description "Information about an address assignment";
                                                                                                                                                     container dhcp-option-table {
                                                                                                                                                       description "Information about one or more Dynamic Host Configuration Protocol options that are associated with the address assignment";
                                                                                                                                                       list dhcp-option {
                                                                                                                                                         description "Information about a Dynamic Host Configuration Protocol option that is associated with the address assignment";
                                                                                                                                                         leaf dhcp-option-code {
                                                                                                                                                           type int32;
                                                                                                                                                           description "Numeric code assigned to the DHCP option";
                                                                                                                                                         }
                                                                                                                                                         leaf dhcp-option-name {
                                                                                                                                                           type string;
                                                                                                                                                           description "Name of the DHCP option";
                                                                                                                                                         }
                                                                                                                                                         leaf dhcp-option-type {
                                                                                                                                                           type string;
                                                                                                                                                           description "Type of value for the DHCP option (for example, string [word], integer, IP address)";
                                                                                                                                                         }
                                                                                                                                                         leaf dhcp-option-value {
                                                                                                                                                           type string;
                                                                                                                                                           description "Value of the DHCP option";
                                                                                                                                                         }
                                                                                                                                                       }
                                                                                                                                                     }
                                                                                                                                                     container dhcp-lease-information {
                                                                                                                                                       description "Information about an address assignment";
                                                                                                                                                       container dhcp-option-table {
                                                                                                                                                         description "Information about one or more Dynamic Host Configuration Protocol options that are associated with the address assignment";
                                                                                                                                                         list dhcp-option {
                                                                                                                                                           description "Information about a Dynamic Host Configuration Protocol option that is associated with the address assignment";
                                                                                                                                                           leaf dhcp-option-code {
                                                                                                                                                             type int32;
                                                                                                                                                             description "Numeric code assigned to the DHCP option";
                                                                                                                                                           }
                                                                                                                                                           leaf dhcp-option-name {
                                                                                                                                                             type string;
                                                                                                                                                             description "Name of the DHCP option";
                                                                                                                                                           }
                                                                                                                                                           leaf dhcp-option-type {
                                                                                                                                                             type string;
                                                                                                                                                             description "Type of value for the DHCP option (for example, string [word], integer, IP address)";
                                                                                                                                                           }
                                                                                                                                                           leaf dhcp-option-value {
                                                                                                                                                             type string;
                                                                                                                                                             description "Value of the DHCP option";
                                                                                                                                                           }
                                                                                                                                                         }
                                                                                                                                                       }
                                                                                                                                                       container dhcp-lease-information {
                                                                                                                                                         description "Information about an address assignment";
                                                                                                                                                         container dhcp-option-table {
                                                                                                                                                           description "Information about one or more Dynamic Host Configuration Protocol options that are associated with the address assignment";
                                                                                                                                                           list dhcp-option {
                                                                                                                                                             description "Information about a Dynamic Host Configuration Protocol option that is associated with the address assignment";
                                                                                                                                                             leaf dhcp-option-code {
                                                                                                                                                               type int32;
                                                                                                                                                               description "Numeric code assigned to the DHCP option";
                                                                                                                                                             }
                                                                                                                                                             leaf dhcp-option-name {
                                                                                                                                                               type string;
                                                                                                                                                               description "Name of the DHCP option";
                                                                                                                                                             }
                                                                                                                                                             leaf dhcp-option-type {
                                                                                                                                                               type string;
                                                                                                                                                               description "Type of value for the DHCP option (for example, string [word], integer, IP address)";
                                                                                                                                                             }
                                                                                                                                                             leaf dhcp-option-value {
                                                                                                                                                               type string;
                                                                                                                                                               description "Value of the DHCP option";
                                                                                                                                                             }
                                                                                                                                                           }
                                                                                                                                                         }
                                                                                                                                                         container dhcp-lease-information {
                                                                                                                                                           description "Information about an address assignment";
                                                                                                                                                           container dhcp-option-table {
                                                                                                                                                             description "Information about one or more Dynamic Host Configuration Protocol options that are associated with the address assignment";
                                                                                                                                                             list dhcp-option {
                                                                                                                                                               description "Information about a Dynamic Host Configuration Protocol option that is associated with the address assignment";
                                                                                                                                                               leaf dhcp-option-code {
                                                                                                                                                                 type int32;
                                                                                                                                                                 description "Numeric code assigned to the DHCP option";
                                                                                                                                                               }
                                                                                                                                                               leaf dhcp-option-name {
                                                                                                                                                                 type string;
                                                                                                                                                                 description "Name of the DHCP option";
                                                                                                                                                               }
                                                                                                                                                               leaf dhcp-option-type {
                                                                                                                                                                 type string;
                                                                                                                                                                 description "Type of value for the DHCP option (for example, string [word], integer, IP address)";
                                                                                                                                                               }
                                                                                                                                                               leaf dhcp-option-value {
                                                                                                                                                                 type string;
                                                                                                                                                                 description "Value of the DHCP option";
                                                                                                                                                               }
                                                                                                                                                             }
                                                                                                                                                           }
                                                                                                                                                           container dhcp-lease-information {
                                                                                                                                                             description "Information about an address assignment";
                                                                                                                                                             container dhcp-option-table {
                                                                                                                                                               description "Information about one or more Dynamic Host Configuration Protocol options that are associated with the address assignment";
                                                                                                                                                               list dhcp-option {
                                                                                                                                                                 description "Information about a Dynamic Host Configuration Protocol option that is associated with the address assignment";
                                                                                                                                                                 leaf dhcp-option-code {
                                                                                                                                                                   type int32;
                                                                                                                                                                   description "Numeric code assigned to the DHCP option";
                                                                                                                                                                 }
                                                                                                                                                                 leaf dhcp-option-name {
                                                                                                                                                                   type string;
                                                                                                                                                                   description "Name of the DHCP option";
                                                                                                                                                                 }
                                                                                                                                                                 leaf dhcp-option-type {
                                                                                                                                                                   type string;
                                                                                                                                                                   description "Type of value for the DHCP option (for example, string [word], integer, IP address)";
                                                                                                                                                                 }
                                                                                                                                                                 leaf dhcp-option-value {
                                                                                                                                                                   type string;
                                                                                                                                                                   description "Value of the DHCP option";
                                                                                                                                                                 }
                                                                                                                                                               }
                                                                                                                                                             }
                                                                                                                                                             container dhcp-lease-information {
                                                                                                                                                               description "Information about an address assignment";
                                                                                                                                                               container dhcp-option-table {
                                                                                                                                                                 description "Information about one or more Dynamic Host Configuration Protocol options that are associated with the address assignment";
                                                                                                                                                                 list dhcp-option {
                                                                                                                                                                   description "Information about a Dynamic Host Configuration Protocol option that is associated with the address assignment";
                                                                                                                                                                   leaf dhcp-option-code {
                                                                                                                                                                     type int32;
                                                                                                                                                                     description "Numeric code assigned to the DHCP option";
                                                                                                                                                                   }
                                                                                                                                                                   leaf dhcp-option-name {
                                                                                                                                                                     type string;
                                                                                                                                                                     description "Name of the DHCP option";
                                                                                                                                                                   }
                                                                                                                                                                   leaf dhcp-option-type {
                                                                                                                                                                     type string;
                                                                                                                                                                     description "Type of value for the DHCP option (for example, string [word], integer, IP address)";
                                                                                                                                                                   }
                                                                                                                                                                   leaf dhcp-option-value {
                                                                                                                                                                     type string;
                                                                                                                                                                     description "Value of the DHCP option";
                                                                                                                                                                   }
                                                                                                                                                                 }
                                                                                                                                                               }
                                                                                                                                                               container dhcp-lease-information {
                                                                                                                                                                 description "Information about an address assignment";
                                                                                                                                                                 container dhcp-option-table {
                                                                                                                                                                   description "Information about one or more Dynamic Host Configuration Protocol options that are associated with the address assignment";
                                                                                                                                                                   list dhcp-option {
                                                                                                                                                                     description "Information about a Dynamic Host Configuration Protocol option that is associated with the address assignment";
                                                                                                                                                                     leaf dhcp-option-code {
                                                                                                                                                                       type int32;
                                                                                                                                                                       description "Numeric code assigned to the DHCP option";
                                                                                                                                                                     }
                                                                                                                                                                     leaf dhcp-option-name {
                                                                                                                                                                       type string;
                                                                                                                                                                       description "Name of the DHCP option";
                                                                                                                                                                     }
                                                                                                                                                                     leaf dhcp-option-type {
                                                                                                                                                                       type string;
                                                                                                                                                                       description "Type of value for the DHCP option (for example, string [word], integer, IP address)";
                                                                                                                                                                     }
                                                                                                                                                                     leaf dhcp-option-value {
                                                                                                                                                                       type string;
                                                                                                                                                                       description "Value of the DHCP option";
                                                                                                                                                                     }
                                                                                                                                                                   }
                                                                                                                                                                 }
                                                                                                                                                                 container dhcp-lease-information {
                                                                                                                                                                   description "Information about an address assignment";
                                                                                                                                                                   container dhcp-option-table {
                                                                                                                                                                     description "Information about one or more Dynamic Host Configuration Protocol options that are associated with the address assignment";
                                                                                                                                                                     list dhcp-option {
                                                                                                                                                                       description "Information about a Dynamic Host Configuration Protocol option that is associated with the address assignment";
                                                                                                                                                                       leaf dhcp-option-code {
                                                                                                                                                                         type int32;
                                                                                                                                                                         description "Numeric code assigned to the DHCP option";
                                                                                                                                                                       }
                                                                                                                                                                       leaf dhcp-option-name {
                                                                                                                                                                         type string;
                                                                                                                                                                         description "Name of the DHCP option";
                                                                                                                                                                       }
                                                                                                                                                                       leaf dhcp-option-type {
                                                                                                                                                                         type string;
                                                                                                                                                                         description "Type of value for the DHCP option (for example, string [word], integer, IP address)";
                                                                                                                                                                       }
                                                                                                                                                                       leaf dhcp-option-value {
                                                                                                                                                                         type string;
                                                                                                                                                                         description "Value of the DHCP option";
                                                                                                                                                                       }
                                                                                                                                                                     }
                                                                                                                                                                   }
                                                                                                                                                                   container dhcp-lease-information {
                                                                                                                                                                     description "Information about an address assignment";
                                                                                                                                                                     container dhcp-option-table {
                                                                                                                                                                       description "Information about one or more Dynamic Host Configuration Protocol options that are associated with the address assignment";
                                                                                                                                                                       list dhcp-option {
                                                                                                                                                                         description "Information about a Dynamic Host Configuration Protocol option that is associated with the address assignment";
                                                                                                                                                                         leaf dhcp-option-code {
                                                                                                                                                                           type int32;
                                                                                                                                                                           description "Numeric code assigned to the DHCP option";
                                                                                                                                                                         }
                                                                                                                                                                         leaf dhcp-option-name {
                                                                                                                                                                           type string;
                                                                                                                                                                           description "Name of the DHCP option";
                                                                                                                                                                         }
                                                                                                                                                                         leaf dhcp-option-type {
                                                                                                                                                                           type string;
                                                                                                                                                                           description "Type of value for the DHCP option (for example, string [word], integer, IP address)";
                                                                                                                                                                         }
                                                                                                                                                                         leaf dhcp-option-value {
                                                                                                                                                                           type string;
                                                                                                                                                                           description "Value of the DHCP option";
                                                                                                                                                                         }
                                                                                                                                                                       }
                                                                                                                                                                     }
                                                                                                                                                                     container dhcp-lease-information {
                                                                                                                                                                       description "Information about an address assignment";
                                                                                                                                                                       container dhcp-option-table {
                                                                                                                                                                         description "Information about one or more Dynamic Host Configuration Protocol options that are associated with the address assignment";
                                                                                                                                                                         list dhcp-option {
                                                                                                                                                                           description "Information about a Dynamic Host Configuration Protocol option that is associated with the address assignment";
                                                                                                                                                                           leaf dhcp-option-code {
                                                                                                                                                                             type int32;
                                                                                                                                                                             description "Numeric code assigned to the DHCP option";
                                                                                                                                                                           }
                                                                                                                                                                           leaf dhcp-option-name {
                                                                                                                                                                             type string;
                                                                                                                                                                             description "Name of the DHCP option";
                                                                                                                                                                           }
                                                                                                                                                                           leaf dhcp-option-type {
                                                                                                                                                                             type string;
                                                                                                                                                                             description "Type of value for the DHCP option (for example, string [word], integer, IP address)";
                                                                                                                                                                           }
                                                                                                                                                                           leaf dhcp-option-value {
                                                                                                                                                                             type string;
                                                                                                                                                                             description "Value of the DHCP option";
                                                                                                                                                                           }
                                                                                                                                                                         }
                                                                                                                                                                       }
                                                                                                                                                                       container dhcp-lease-information {
                                                                                                                                                                         description "Information about an address assignment";
                                                                                                                                                                         container dhcp-option-table {
                                                                                                                                                                           description "Information about one or more Dynamic Host Configuration Protocol options that are associated with the address assignment";
                                                                                                                                                                           list dhcp-option {
                                                                                                                                                                             description "Information about a Dynamic Host Configuration Protocol option that is associated with the address assignment";
                                                                                                                                                                             leaf dhcp-option-code {
                                                                                                                                                                               type int32;
                                                                                                                                                                               description "Numeric code assigned to the DHCP option";
                                                                                                                                                                             }
                                                                                                                                                                             leaf dhcp-option-name {
                                                                                                                                                                               type string;
                                                                                                                                                                               description "Name of the DHCP option";
                                                                                                                                                                             }
                                                                                                                                                                             leaf dhcp-option-type {
                                                                                                                                                                               type string;
                                                                                                                                                                               description "Type of value for the DHCP option (for example, string [word], integer, IP address)";
                                                                                                                                                                             }
                                                                                                                                                                             leaf dhcp-option-value {
                                                                                                                                                                               type string;
                                                                                                                                                                               description "Value of the DHCP option";
                                                                                                                                                                             }
                                                                                                                                                                           }
                                                                                                                                                                         }
                                                                                                                                                                         container dhcp-lease-information {
                                                                                                                                                                           description "Information about an address assignment";
                                                                                                                                                                           container dhcp-option-table {
                                                                                                                                                                             description "Information about one or more Dynamic Host Configuration Protocol options that are associated with the address assignment";
                                                                                                                                                                             list dhcp-option {
                                                                                                                                                                               description "Information about a Dynamic Host Configuration Protocol option that is associated with the address assignment";
                                                                                                                                                                               leaf dhcp-option-code {
                                                                                                                                                                                 type int32;
                                                                                                                                                                                 description "Numeric code assigned to the DHCP option";
                                                                                                                                                                               }
                                                                                                                                                                               leaf dhcp-option-name {
                                                                                                                                                                                 type string;
                                                                                                                                                                                 description "Name of the DHCP option";
                                                                                                                                                                               }
                                                                                                                                                                               leaf dhcp-option-type {
                                                                                                                                                                                 type string;
                                                                                                                                                                                 description "Type of value for the DHCP option (for example, string [word], integer, IP address)";
                                                                                                                                                                               }
                                                                                                                                                                               leaf dhcp-option-value {
                                                                                                                                                                                 type string;
                                                                                                                                                                                 description "Value of the DHCP option";
                                                                                                                                                                               }
                                                                                                                                                                             }
                                                                                                                                                                           }
                                                                                                                                                                           container dhcp-lease-information {
                                                                                                                                                                             description "Information about an address assignment";
                                                                                                                                                                             container dhcp-option-table {
                                                                                                                                                                               description "Information about one or more Dynamic Host Configuration Protocol options that are associated with the address assignment";
                                                                                                                                                                               list dhcp-option {
                                                                                                                                                                                 description "Information about a Dynamic Host Configuration Protocol option that is associated with the address assignment";
                                                                                                                                                                                 leaf dhcp-option-code {
                                                                                                                                                                                   type int32;
                                                                                                                                                                                   description "Numeric code assigned to the DHCP option";
                                                                                                                                                                                 }
                                                                                                                                                                                 leaf dhcp-option-name {
                                                                                                                                                                                   type string;
                                                                                                                                                                                   description "Name of the DHCP option";
                                                                                                                                                                                 }
                                                                                                                                                                                 leaf dhcp-option-type {
                                                                                                                                                                                   type string;
                                                                                                                                                                                   description "Type of value for the DHCP option (for example, string [word], integer, IP address)";
                                                                                                                                                                                 }
                                                                                                                                                                                 leaf dhcp-option-value {
                                                                                                                                                                                   type string;
                                                                                                                                                                                   description "Value of the DHCP option";
                                                                                                                                                                                 }
                                                                                                                                                                               }
                                                                                                                                                                             }
                                                                                                                                                                             container dhcp-lease-information {
                                                                                                                                                                               description "Information about an address assignment";
                                                                                                                                                                               container dhcp-option-table {
                                                                                                                                                                                 description "Information about one or more Dynamic Host Configuration Protocol options that are associated with the address assignment";
                                                                                                                                                                                 list dhcp-option {
                                                                                                                                                                                   description "Information about a Dynamic Host Configuration Protocol option that is associated with the address assignment";
                                                                                                                                                                                   leaf dhcp-option-code {
                                                                                                                                                                                     type int32;
                                                                                                                                                                                     description "Numeric code assigned to the DHCP option";
                                                                                                                                                                                   }
                                                                                                                                                                                   leaf dhcp-option-name {
                                                                                                                                                                                     type string;
                                                                                                                                                                                     description "Name of the DHCP option";
                                                                                                                                                                                   }
                                                                                                                                                                                   leaf dhcp-option-type {
                                                                                                                                                                                     type string;
                                                                                                                                                                                     description "Type of value for the DHCP option (for example, string [word], integer, IP address)";
                                                                                                                                                                                   }
                                                                                                                                                                                   leaf dhcp-option-value {
                                                                                                                                                                                     type string;
                                                                                                                                                                                     description "Value of the DHCP option";
                                                                                                                                                                                   }
                                                                                                                                                                                 }
                                                                                                                                                                               }
                                                                                                                                                                               container dhcp-lease-information {
                                                                                                                                                                                 description "Information about an address assignment";
                                                                                                                                                                                 container dhcp-option-table {
                                                                                                                                                                                   description "Information about one or more Dynamic Host Configuration Protocol options that are associated with the address assignment";
                                                                                                                                                                                   list dhcp-option {
                                                                                                                                                                                     description "Information about a Dynamic Host Configuration Protocol option that is associated with the address assignment";
                                                                                                                                                                                     leaf dhcp-option-code {
                                                                                                                                                                                       type int32;
                                                                                                                                                                                       description "Numeric code assigned to the DHCP option";
                                                                                                                                                                                     }
                                                                                                                                                                                     leaf dhcp-option-name {
                                                                                                                                                                                       type string;
                                                                                                                                                                                       description "Name of the DHCP option";
                                                                                                                                                                                     }
                                                                                                                                                                                     leaf dhcp-option-type {
                                                                                                                                                                                       type string;
                                                                                                                                                                                       description "Type of value for the DHCP option (for example, string [word], integer, IP address)";
                                                                                                                                                                                     }
                                                                                                                                                                                     leaf dhcp-option-value {
                                                                                                                                                                                       type string;
                                                                                                                                                                                       description "Value of the DHCP option";
                                                                                                                                                                                     }
                                                                                                                                                                                   }
                                                                                                                                                                                 }
                                                                                                                                                                                 container dhcp-lease-information {
                                                                                                                                                                                   description "Information about an address assignment";
                                                                                                                                                                                   container dhcp-option-table {
                                                                                                                                                                                     description "Information about one or more Dynamic Host Configuration Protocol options that are associated with the address assignment";
                                                                                                                                                                                     list dhcp-option {
                                                                                                                                                                                       description "Information about a Dynamic Host Configuration Protocol option that is associated with the address assignment";
                                                                                                                                                                                       leaf dhcp-option-code {
                                                                                                                                                                                         type int32;
                                                                                                                                                                                         description "Numeric code assigned to the DHCP option";
                                                                                                                                                                                       }
                                                                                                                                                                                       leaf dhcp-option-name {
                                                                                                                                                                                         type string;
                                                                                                                                                                                         description "Name of the DHCP option";
                                                                                                                                                                                       }
                                                                                                                                                                                       leaf dhcp-option-type {
                                                                                                                                                                                         type string;
                                                                                                                                                                                         description "Type of value for the DHCP option (for example, string [word], integer, IP address)";
                                                                                                                                                                                       }
                                                                                                                                                                                       leaf dhcp-option-value {
                                                                                                                                                                                         type string;
                                                                                                                                                                                         description "Value of the DHCP option";
                                                                                                                                                                                       }
                                                                                                                                                                                     }
                                                                                                                                                                                   }
                                                                                                                                                                                   container dhcp-lease-information {
                                                                                                                                                                                     description "Information about an address assignment";
                                                                                                                                                                                     container dhcp-option-table {
                                                                                                                                                                                       description "Information about one or more Dynamic Host Configuration Protocol options that are associated with the address assignment";
                                                                                                                                                                                       list dhcp-option {
                                                                                                                                                                                         description "Information about a Dynamic Host Configuration Protocol option that is associated with the address assignment";
                                                                                                                                                                                         leaf dhcp-option-code {
                                                                                                                                                                                           type int32;
                                                                                                                                                                                           description "Numeric code assigned to the DHCP option";
                                                                                                                                                                                         }
                                                                                                                                                                                         leaf dhcp-option-name {
                                                                                                                                                                                           type string;
                                                                                                                                                                                           description "Name of the DHCP option";
                                                                                                                                                                                         }
                                                                                                                                                                                         leaf dhcp-option-type {
                                                                                                                                                                                           type string;
                                                                                                                                                                                           description "Type of value for the DHCP option (for example, string [word], integer, IP address)";
                                                                                                                                                                                         }
                                                                                                                                                                                         leaf dhcp-option-value {
                                                                                                                                                                                           type string;
                                                                                                                                                                                           description "Value of the DHCP option";
                                                                                                                                                                                         }
                                                                                                                                                                                       }
                                                                                                                                                                                     }
                                                                                                                                                                                     container dhcp-lease-information {
                                                                                                                                                                                       description "Information about an address assignment";
                                                                                                                                                                                       container dhcp-option-table {
                                                                                                                                                                                         description "Information about one or more Dynamic Host Configuration Protocol options that are associated with the address assignment";
                                                                                                                                                                                         list dhcp-option {
                                                                                                                                                                                           description "Information about a Dynamic Host Configuration Protocol option that is associated with the address assignment";
                                                                                                                                                                                           leaf dhcp-option-code {
                                                                                                                                                                                             type int32;
                                                                                                                                                                                             description "Numeric code assigned to the DHCP option";
                                                                                                                                                                                           }
                                                                                                                                                                                           leaf dhcp-option-name {
                                                                                                                                                                                             type string;
                                                                                                                                                                                             description "Name of the DHCP option";
                                                                                                                                                                                           }
                                                                                                                                                                                           leaf dhcp-option-type {
                                                                                                                                                                                             type string;
                                                                                                                                                                                             description "Type of value for the DHCP option (for example, string [word], integer, IP address)";
                                                                                                                                                                                           }
                                                                                                                                                                                           leaf dhcp-option-value {
                                                                                                                                                                                             type string;
                                                                                                                                                                                             description "Value of the DHCP option";
                                                                                                                                                                                           }
                                                                                                                                                                                         }
                                                                                                                                                                                       }
                                                                                                                                                                                       container dhcp-lease-information {
                                                                                                                                                                                         description "Information about an address assignment";
                                                                                                                                                                                         container dhcp-option-table {
                                                                                                                                                                                           description "Information about one or more Dynamic Host Configuration Protocol options that are associated with the address assignment";
                                                                                                                                                                                           list dhcp-option {
                                                                                                                                                                                             description "Information about a Dynamic Host Configuration Protocol option that is associated with the address assignment";
                                                                                                                                                                                             leaf dhcp-option-code {
                                                                                                                                                                                               type int32;
                                                                                                                                                                                               description "Numeric code assigned to the DHCP option";
                                                                                                                                                                                             }
                                                                                                                                                                                             leaf dhcp-option-name {
                                                                                                                                                                                               type string;
                                                                                                                                                                                               description "Name of the DHCP option";
                                                                                                                                                                                             }
                                                                                                                                                                                             leaf dhcp-option-type {
                                                                                                                                                                                               type string;
                                                                                                                                                                                               description "Type of value for the DHCP option (for example, string [word], integer, IP address)";
                                                                                                                                                                                             }
                                                                                                                                                                                             leaf dhcp-option-value {
                                                                                                                                                                                               type string;
                                                                                                                                                                                               description "Value of the DHCP option";
                                                                                                                                                                                             }
                                                                                                                                                                                           }
                                                                                                                                                                                         }
                                                                                                                                                                                         container dhcp-lease-information {
                                                                                                                                                                                           description "Information about an address assignment";
                                                                                                                                                                                           container dhcp-option-table {
                                                                                                                                                                                             description "Information about one or more Dynamic Host Configuration Protocol options that are associated with the address assignment";
                                                                                                                                                                                             list dhcp-option {
                                                                                                                                                                                               description "Information about a Dynamic Host Configuration Protocol option that is associated with the address assignment";
                                                                                                                                                                                               leaf dhcp-option-code {
                                                                                                                                                                                                 type int32;
                                                                                                                                                                                                 description "Numeric code assigned to the DHCP option";
                                                                                                                                                                                               }
                                                                                                                                                                                               leaf dhcp-option-name {
                                                                                                                                                                                                 type string;
                                                                                                                                                                                                 description "Name of the DHCP option";
                                                                                                                                                                                               }
                                                                                                                                                                                               leaf dhcp-option-type {
                                                                                                                                                                                                 type string;
                                                                                                                                                                                                 description "Type of value for the DHCP option (for example, string [word], integer, IP address)";
                                                                                                                                                                                               }
                                                                                                                                                                                               leaf dhcp-option-value {
                                                                                                                                                                                                 type string;
                                                                                                                                                                                                 description "Value of the DHCP option";
                                                                                                                                                                                               }
                                                                                                                                                                                             }
                                                                                                                                                                                           }
                                                                                                                                                                                           container dhcp-lease-information {
                                                                                                                                                                                             description "Information about an address assignment";
                                                                                                                                                                                             container dhcp-option-table {
                                                                                                                                                                                               description "Information about one or more Dynamic Host Configuration Protocol options that are associated with the address assignment";
                                                                                                                                                                                               list dhcp-option {
                                                                                                                                                                                                 description "Information about a Dynamic Host Configuration Protocol option that is associated with the address assignment";
                                                                                                                                                                                                 leaf dhcp-option-code {
                                                                                                                                                                                                   type int32;
                                                                                                                                                                                                   description "Numeric code assigned to the DHCP option";
                                                                                                                                                                                                 }
                                                                                                                                                                                                 leaf dhcp-option-name {
                                                                                                                                                                                                   type string;
                                                                                                                                                                                                   description "Name of the DHCP option";
                                                                                                                                                                                                 }
                                                                                                                                                                                                 leaf dhcp-option-type {
                                                                                                                                                                                                   type string;
                                                                                                                                                                                                   description "Type of value for the DHCP option (for example, string [word], integer, IP address)";
                                                                                                                                                                                                 }
                                                                                                                                                                                                 leaf dhcp-option-value {
                                                                                                                                                                                                   type string;
                                                                                                                                                                                                   description "Value of the DHCP option";
                                                                                                                                                                                                 }
                                                                                                                                                                                               }
                                                                                                                                                                                             }
                                                                                                                                                                                             container dhcp-lease-information {
                                                                                                                                                                                               description "Information about an address assignment";
                                                                                                                                                                                               container dhcp-option-table {
                                                                                                                                                                                                 description "Information about one or more Dynamic Host Configuration Protocol options that are associated with the address assignment";
                                                                                                                                                                                                 list dhcp-option {
                                                                                                                                                                                                   description "Information about a Dynamic Host Configuration Protocol option that is associated with the address assignment";
                                                                                                                                                                                                   leaf dhcp-option-code {
                                                                                                                                                                                                     type int32;
                                                                                                                                                                                                     description "Numeric code assigned to the DHCP option";
                                                                                                                                                                                                   }
                                                                                                                                                                                                   leaf dhcp-option-name {
                                                                                                                                                                                                     type string;
                                                                                                                                                                                                     description "Name of the DHCP option";
                                                                                                                                                                                                   }
                                                                                                                                                                                                   leaf dhcp-option-type {
                                                                                                                                                                                                     type string;
                                                                                                                                                                                                     description "Type of value for the DHCP option (for example, string [word], integer, IP address)";
                                                                                                                                                                                                   }
                                                                                                                                                                                                   leaf dhcp-option-value {
                                                                                                                                                                                                     type string;
                                                                                                                                                                                                     description "Value of the DHCP option";
                                                                                                                                                                                                   }
                                                                                                                                                                                                 }
                                                                                                                                                                                               }
                                                                                                                                                                                               container dhcp-lease-information {
                                                                                                                                                                                                 description "Information about an address assignment";
                                                                                                                                                                                                 container dhcp-option-table {
                                                                                                                                                                                                   description "Information about one or more Dynamic Host Configuration Protocol options that are associated with the address assignment";
                                                                                                                                                                                                   list dhcp-option {
                                                                                                                                                                                                     description "Information about a Dynamic Host Configuration Protocol option that is associated with the address assignment";
                                                                                                                                                                                                     leaf dhcp-option-code {
                                                                                                                                                                                                       type int32;
                                                                                                                                                                                                       description "Numeric code assigned to the DHCP option";
                                                                                                                                                                                                     }
                                                                                                                                                                                                     leaf dhcp-option-name {
                                                                                                                                                                                                       type string;
                                                                                                                                                                                                       description "Name of the DHCP option";
                                                                                                                                                                                                     }
                                                                                                                                                                                                     leaf dhcp-option-type {
                                                                                                                                                                                                       type string;
                                                                                                                                                                                                       description "Type of value for the DHCP option (for example, string [word], integer, IP address)";
                                                                                                                                                                                                     }
                                                                                                                                                                                                     leaf dhcp-option-value {
                                                                                                                                                                                                       type string;
                                                                                                                                                                                                       description "Value of the DHCP option";
                                                                                                                                                                                                     }
                                                                                                                                                                                                   }
                                                                                                                                                                                                 }
                                                                                                                                                                                                 container dhcp-lease-information {
                                                                                                                                                                                                   description "Information about an address assignment";
                                                                                                                                                                                                   container dhcp-option-table {
                                                                                                                                                                                                     description "Information about one or more Dynamic Host Configuration Protocol options that are associated with the address assignment";
                                                                                                                                                                                                     list dhcp-option {
                                                                                                                                                                                                       description "Information about a Dynamic Host Configuration Protocol option that is associated with the address assignment";
                                                                                                                                                                                                       leaf dhcp-option-code {
                                                                                                                                                                                                         type int32;
                                                                                                                                                                                                         description "Numeric code assigned to the DHCP option";
                                                                                                                                                                                                       }
                                                                                                                                                                                                       leaf dhcp-option-name {
                                                                                                                                                                                                         type string;
                                                                                                                                                                                                         description "Name of the DHCP option";
                                                                                                                                                                                                       }
                                                                                                                                                                                                       leaf dhcp-option-type {
                                                                                                                                                                                                         type string;
                                                                                                                                                                                                         description "Type of value for the DHCP option (for example, string [word], integer, IP address)";
                                                                                                                                                                                                       }
                                                                                                                                                                                                       leaf dhcp-option-value {
                                                                                                                                                                                                         type string;
                                                                                                                                                                                                         description "Value of the DHCP option";
                                                                                                                                                                                                       }
                                                                                                                                                                                                     }
                                                                                                                                                                                                   }
                                                                                                                                                                                                   container dhcp-lease-information {
                                                                                                                                                                                                     description "Information about an address assignment";
                                                                                                                                                                                                     container dhcp-option-table {
                                                                                                                                                                                                       description "Information about one or more Dynamic Host Configuration Protocol options that are associated with the address assignment";
                                                                                                                                                                                                       list dhcp-option {
                                                                                                                                                                                                         description "Information about a Dynamic Host Configuration Protocol option that is associated with the address assignment";
                                                                                                                                                                                                         leaf dhcp-option-code {
                                                                                                                                                                                                           type int32;
                                                                                                                                                                                                           description "Numeric code assigned to the DHCP option";
                                                                                                                                                                                                         }
                                                                                                                                                                                                         leaf dhcp-option-name {
                                                                                                                                                                                                           type string;
                                                                                                                                                                                                           description "Name of the DHCP option";
                                                                                                                                                                                                         }
                                                                                                                                                                                                         leaf dhcp-option-type {
                                                                                                                                                                                                           type string;
                                                                                                                                                                                                           description "Type of value for the DHCP option (for example, string [word], integer, IP address)";
                                                                                                                                                                                                         }
                                                                                                                                                                                                         leaf dhcp-option-value {
                                                                                                                                                                                                           type string;
                                                                                                                                                                                                           description "Value of the DHCP option";
                                                                                                                                                                                                         }
                                                                                                                                                                                                       }
                                                                                                                                                                                                     }
                                                                                                                                                                                                     container dhcp-lease-information {
                                                                                                                                                                                                       description "Information about an address assignment";
                                                                                                                                                                                                       container dhcp-option-table {
                                                                                                                                                                                                         description "Information about one or more Dynamic Host Configuration Protocol options that are associated with the address assignment";
                                                                                                                                                                                                         list dhcp-option {
                                                                                                                                                                                                           description "Information about a Dynamic Host Configuration Protocol option that is associated with the address assignment";
                                                                                                                                                                                                           leaf dhcp-option-code {
                                                                                                                                                                                                             type int32;
                                                                                                                                                                                                             description "Numeric code assigned to the DHCP option";
                                                                                                                                                                                                           }
                                                                                                                                                                                                           leaf dhcp-option-name {
                                                                                                                                                                                                             type string;
                                                                                                                                                                                                             description "Name of the DHCP option";
                                                                                                                                                                                                           }
                                                                                                                                                                                                           leaf dhcp-option-type {
                                                                                                                                                                                                             type string;
                                                                                                                                                                                                             description "Type of value for the DHCP option (for example, string [word], integer, IP address)";
                                                                                                                                                                                                           }
                                                                                                                                                                                                           leaf dhcp-option-value {
                                                                                                                                                                                                             type string;
                                                                                                                                                                                                             description "Value of the DHCP option";
                                                                                                                                                                                                           }
                                                                                                                                                                                                         }
                                                                                                                                                                                                       }
                                                                                                                                                                                                       container dhcp-lease-information {
                                                                                                                                                                                                         description "Information about an address assignment";
                                                                                                                                                                                                         container dhcp-option-table {
                                                                                                                                                                                                           description "Information about one or more Dynamic Host Configuration Protocol options that are associated with the address assignment";
                                                                                                                                                                                                           list dhcp-option {
                                                                                                                                                                                                             description "Information about a Dynamic Host Configuration Protocol option that is associated with the address assignment";
                                                                                                                                                                                                             leaf dhcp-option-code {
                                                                                                                                                                                                               type int32;
                                                                                                                                                                                                               description "Numeric code assigned to the DHCP option";
                                                                                                                                                                                                             }
                                                                                                                                                                                                             leaf dhcp-option-name {
                                                                                                                                                                                                               type string;
                                                                                                                                                                                                               description "Name of the DHCP option";
                                                                                                                                                                                                             }
                                                                                                                                                                                                             leaf dhcp-option-type {
                                                                                                                                                                                                               type string;
                                                                                                                                                                                                               description "Type of value for the DHCP option (for example, string [word], integer, IP address)";
                                                                                                                                                                                                             }
                                                                                                                                                                                                             leaf dhcp-option-value {
                                                                                                                                                                                                               type string;
                                                                                                                                                                                                               description "Value of the DHCP option";
                                                                                                                                                                                                             }
                                                                                                                                                                                                           }
                                                                                                                                                                                                         }
                                                                                                                                                                                                         container dhcp-lease-information {
                                                                                                                                                                                                           description "Information about an address assignment";
                                                                                                                                                                                                           container dhcp-option-table {
                                                                                                                                                                                                             description "Information about one or more Dynamic Host Configuration Protocol options that are associated with the address assignment";
                                                                                                                                                                                                             list dhcp-option {
                                                                                                                                                                                                               description "Information about a Dynamic Host Configuration Protocol option that is associated with the address assignment";
                                                                                                                                                                                                               leaf dhcp-option-code {
                                                                                                                                                                                                                 type int32;
                                                                                                                                                                                                                 description "Numeric code assigned to the DHCP option";
                                                                                                                                                                                                               }
                                                                                                                                                                                                               leaf dhcp-option-name {
                                                                                                                                                                                                                 type string;
                                                                                                                                                                                                                 description "Name of the DHCP option";
                                                                                                                                                                                                               }
                                                                                                                                                                                                               leaf dhcp-option-type {
                                                                                                                                                                                                                 type string;
                                                                                                                                                                                                                 description "Type of value for the DHCP option (for example, string [word], integer, IP address)";
                                                                                                                                                                                                               }
                                                                                                                                                                                                               leaf dhcp-option-value {
                                                                                                                                                                                                                 type string;
                                                                                                                                                                                                                 description "Value of the DHCP option";
                                                                                                                                                                                                               }
                                                                                                                                                                                                             }
                                                                                                                                                                                                           }
                                                                                                                                                                                                           container dhcp-lease-information {
                                                                                                                                                                                                             description "Information about an address assignment";
                                                                                                                                                                                                             container dhcp-option-table {
                                                                                                                                                                                                               description "Information about one or more Dynamic Host Configuration Protocol options that are associated with the address assignment";
                                                                                                                                                                                                               list dhcp-option {
                                                                                                                                                                                                                 description "Information about a Dynamic Host Configuration Protocol option that is associated with the address assignment";
                                                                                                                                                                                                                 leaf dhcp-option-code {
                                                                                                                                                                                                                   type int32;
                                                                                                                                                                                                                   description "Numeric code assigned to the DHCP option";
                                                                                                                                                                                                                 }
                                                                                                                                                                                                                 leaf dhcp-option-name {
                                                                                                                                                                                                                   type string;
                                                                                                                                                                                                                   description "Name of the DHCP option";
                                                                                                                                                                                                                 }
                                                                                                                                                                                                                 leaf dhcp-option-type {
                                                                                                                                                                                                                   type string;
                                                                                                                                                                                                                   description "Type of value for the DHCP option (for example, string [word], integer, IP address)";
                                                                                                                                                                                                                 }
                                                                                                                                                                                                                 leaf dhcp-option-value {
                                                                                                                                                                                                                   type string;
                                                                                                                                                                                                                   description "Value of the DHCP option";
                                                                                                                                                                                                                 }
                                                                                                                                                                                                               }
                                                                                                                                                                                                             }
                                                                                                                                                                                                             container dhcp-lease-information {
                                                                                                                                                                                                               description "Information about an address assignment";
                                                                                                                                                                                                               container dhcp-option-table {
                                                                                                                                                                                                                 description "Information about one or more Dynamic Host Configuration Protocol options that are associated with the address assignment";
                                                                                                                                                                                                                 list dhcp-option {
                                                                                                                                                                                                                   description "Information about a Dynamic Host Configuration Protocol option that is associated with the address assignment";
                                                                                                                                                                                                                   leaf dhcp-option-code {
                                                                                                                                                                                                                     type int32;
                                                                                                                                                                                                                     description "Numeric code assigned to the DHCP option";
                                                                                                                                                                                                                   }
                                                                                                                                                                                                                   leaf dhcp-option-name {
                                                                                                                                                                                                                     type string;
                                                                                                                                                                                                                     description "Name of the DHCP option";
                                                                                                                                                                                                                   }
                                                                                                                                                                                                                   leaf dhcp-option-type {
                                                                                                                                                                                                                     type string;
                                                                                                                                                                                                                     description "Type of value for the DHCP option (for example, string [word], integer, IP address)";
                                                                                                                                                                                                                   }
                                                                                                                                                                                                                   leaf dhcp-option-value {
                                                                                                                                                                                                                     type string;
                                                                                                                                                                                                                     description "Value of the DHCP option";
                                                                                                                                                                                                                   }
                                                                                                                                                                                                                 }
                                                                                                                                                                                                               }
                                                                                                                                                                                                               container dhcp-lease-information {
                                                                                                                                                                                                                 description "Information about an address assignment";
                                                                                                                                                                                                                 container dhcp-option-table {
                                                                                                                                                                                                                   description "Information about one or more Dynamic Host Configuration Protocol options that are associated with the address assignment";
                                                                                                                                                                                                                   list dhcp-option {
                                                                                                                                                                                                                     description "Information about a Dynamic Host Configuration Protocol option that is associated with the address assignment";
                                                                                                                                                                                                                     leaf dhcp-option-code {
                                                                                                                                                                                                                       type int32;
                                                                                                                                                                                                                       description "Numeric code assigned to the DHCP option";
                                                                                                                                                                                                                     }
                                                                                                                                                                                                                     leaf dhcp-option-name {
                                                                                                                                                                                                                       type string;
                                                                                                                                                                                                                       description "Name of the DHCP option";
                                                                                                                                                                                                                     }
                                                                                                                                                                                                                     leaf dhcp-option-type {
                                                                                                                                                                                                                       type string;
                                                                                                                                                                                                                       description "Type of value for the DHCP option (for example, string [word], integer, IP address)";
                                                                                                                                                                                                                     }
                                                                                                                                                                                                                     leaf dhcp-option-value {
                                                                                                                                                                                                                       type string;
                                                                                                                                                                                                                       description "Value of the DHCP option";
                                                                                                                                                                                                                     }
                                                                                                                                                                                                                   }
                                                                                                                                                                                                                 }
                                                                                                                                                                                                                 container dhcp-lease-information {
                                                                                                                                                                                                                   description "Information about an address assignment";
                                                                                                                                                                                                                   container dhcp-option-table {
                                                                                                                                                                                                                     description "Information about one or more Dynamic Host Configuration Protocol options that are associated with the address assignment";
                                                                                                                                                                                                                     list dhcp-option {
                                                                                                                                                                                                                       description "Information about a Dynamic Host Configuration Protocol option that is associated with the address assignment";
                                                                                                                                                                                                                       leaf dhcp-option-code {
                                                                                                                                                                                                                         type int32;
                                                                                                                                                                                                                         description "Numeric code assigned to the DHCP option";
                                                                                                                                                                                                                       }
                                                                                                                                                                                                                       leaf dhcp-option-name {
                                                                                                                                                                                                                         type string;
                                                                                                                                                                                                                         description "Name of the DHCP option";
                                                                                                                                                                                                                       }
                                                                                                                                                                                                                       leaf dhcp-option-type {
                                                                                                                                                                                                                         type string;
                                                                                                                                                                                                                         description "Type of value for the DHCP option (for example, string [word], integer, IP address)";
                                                                                                                                                                                                                       }
                                                                                                                                                                                                                       leaf dhcp-option-value {
                                                                                                                                                                                                                         type string;
                                                                                                                                                                                                                         description "Value of the DHCP option";
                                                                                                                                                                                                                       }
                                                                                                                                                                                                                     }
                                                                                                                                                                                                                   }
                                                                                                                                                                                                                   container dhcp-lease-information {
                                                                                                                                                                                                                     description "Information about an address assignment";
                                                                                                                                                                                                                     container dhcp-option-table {
                                                                                                                                                                                                                       description "Information about one or more Dynamic Host Configuration Protocol options that are associated with the address assignment";
                                                                                                                                                                                                                       list dhcp-option {
                                                                                                                                                                                                                         description "Information about a Dynamic Host Configuration Protocol option that is associated with the address assignment";
                                                                                                                                                                                                                         leaf dhcp-option-code {
                                                                                                                                                                                                                           type int32;
                                                                                                                                                                                                                           description "Numeric code assigned to the DHCP option";
                                                                                                                                                                                                                         }
                                                                                                                                                                                                                         leaf dhcp-option-name {
                                                                                                                                                                                                                           type string;
                                                                                                                                                                                                                           description "Name of the DHCP option";
                                                                                                                                                                                                                         }
                                                                                                                                                                                                                         leaf dhcp-option-type {
                                                                                                                                                                                                                           type string;
                                                                                                                                                                                                                           description "Type of value for the DHCP option (for example, string [word], integer, IP address)";
                                                                                                                                                                                                                         }
                                                                                                                                                                                                                         leaf dhcp-option-value {
                                                                                                                                                                                                                           type string;
                                                                                                                                                                                                                           description "Value of the DHCP option";
                                                                                                                                                                                                                         }
                                                                                                                                                                                                                       }
                                                                                                                                                                                                                     }
                                                                                                                                                                                                                     container dhcp-lease-information {
                                                                                                                                                                                                                       description "Information about an address assignment";
                                                                                                                                                                                                                       container dhcp-option-table {
                                                                                                                                                                                                                         description "Information about one or more Dynamic Host Configuration Protocol options that are associated with the address assignment";
                                                                                                                                                                                                                         list dhcp-option {
                                                                                                                                                                                                                           description "Information about a Dynamic Host Configuration Protocol option that is associated with the address assignment";
                                                                                                                                                                                                                           leaf dhcp-option-code {
                                                                                                                                                                                                                             type int32;
                                                                                                                                                                                                                             description "Numeric code assigned to the DHCP option";
                                                                                                                                                                                                                           }
                                                                                                                                                                                                                           leaf dhcp-option-name {
                                                                                                                                                                                                                             type string;
                                                                                                                                                                                                                             description "Name of the DHCP option";
                                                                                                                                                                                                                           }
                                                                                                                                                                                                                           leaf dhcp-option-type {
                                                                                                                                                                                                                             type string;
                                                                                                                                                                                                                             description "Type of value for the DHCP option (for example, string [word], integer, IP address)";
                                                                                                                                                                                                                           }
                                                                                                                                                                                                                           leaf dhcp-option-value {
                                                                                                                                                                                                                             type string;
                                                                                                                                                                                                                             description "Value of the DHCP option";
                                                                                                                                                                                                                           }
                                                                                                                                                                                                                         }
                                                                                                                                                                                                                       }
                                                                                                                                                                                                                       container dhcp-lease-information {
                                                                                                                                                                                                                         description "Information about an address assignment";
                                                                                                                                                                                                                         container dhcp-option-table {
                                                                                                                                                                                                                           description "Information about one or more Dynamic Host Configuration Protocol options that are associated with the address assignment";
                                                                                                                                                                                                                           list dhcp-option {
                                                                                                                                                                                                                             description "Information about a Dynamic Host Configuration Protocol option that is associated with the address assignment";
                                                                                                                                                                                                                             leaf dhcp-option-code {
                                                                                                                                                                                                                               type int32;
                                                                                                                                                                                                                               description "Numeric code assigned to the DHCP option";
                                                                                                                                                                                                                             }
                                                                                                                                                                                                                             leaf dhcp-option-name {
                                                                                                                                                                                                                               type string;
                                                                                                                                                                                                                               description "Name of the DHCP option";
                                                                                                                                                                                                                             }
                                                                                                                                                                                                                             leaf dhcp-option-type {
                                                                                                                                                                                                                               type string;
                                                                                                                                                                                                                               description "Type of value for the DHCP option (for example, string [word], integer, IP address)";
                                                                                                                                                                                                                             }
                                                                                                                                                                                                                             leaf dhcp-option-value {
                                                                                                                                                                                                                               type string;
                                                                                                                                                                                                                               description "Value of the DHCP option";
                                                                                                                                                                                                                             }
                                                                                                                                                                                                                           }
                                                                                                                                                                                                                         }
                                                                                                                                                                                                                         container dhcp-lease-information {
                                                                                                                                                                                                                           description "Information about an address assignment";
                                                                                                                                                                                                                           container dhcp-option-table {
                                                                                                                                                                                                                             description "Information about one or more Dynamic Host Configuration Protocol options that are associated with the address assignment";
                                                                                                                                                                                                                             list dhcp-option {
                                                                                                                                                                                                                               description "Information about a Dynamic Host Configuration Protocol option that is associated with the address assignment";
                                                                                                                                                                                                                               leaf dhcp-option-code {
                                                                                                                                                                                                                                 type int32;
                                                                                                                                                                                                                                 description "Numeric code assigned to the DHCP option";
                                                                                                                                                                                                                               }
                                                                                                                                                                                                                               leaf dhcp-option-name {
                                                                                                                                                                                                                                 type string;
                                                                                                                                                                                                                                 description "Name of the DHCP option";
                                                                                                                                                                                                                               }
                                                                                                                                                                                                                               leaf dhcp-option-type {
                                                                                                                                                                                                                                 type string;
                                                                                                                                                                                                                                 description "Type of value for the DHCP option (for example, string [word], integer, IP address)";
                                                                                                                                                                                                                               }
                                                                                                                                                                                                                               leaf dhcp-option-value {
                                                                                                                                                                                                                                 type string;
                                                                                                                                                                                                                                 description "Value of the DHCP option";
                                                                                                                                                                                                                               }
                                                                                                                                                                                                                             }
                                                                                                                                                                                                                           }
                                                                                                                                                                                                                           container dhcp-lease-information {
                                                                                                                                                                                                                             description "Information about an address assignment";
                                                                                                                                                                                                                             container dhcp-option-table {
                                                                                                                                                                                                                               description "Information about one or more Dynamic Host Configuration Protocol options that are associated with the address assignment";
                                                                                                                                                                                                                               list dhcp-option {
                                                                                                                                                                                                                                 description "Information about a Dynamic Host Configuration Protocol option that is associated with the address assignment";
                                                                                                                                                                                                                                 leaf dhcp-option-code {
                                                                                                                                                                                                                                   type int32;
                                                                                                                                                                                                                                   description "Numeric code assigned to the DHCP option";
                                                                                                                                                                                                                                 }
                                                                                                                                                                                                                                 leaf dhcp-option-name {
                                                                                                                                                                                                                                   type string;
                                                                                                                                                                                                                                   description "Name of the DHCP option";
                                                                                                                                                                                                                                 }
                                                                                                                                                                                                                                 leaf dhcp-option-type {
                                                                                                                                                                                                                                   type string;
                                                                                                                                                                                                                                   description "Type of value for the DHCP option (for example, string [word], integer, IP address)";
                                                                                                                                                                                                                                 }
                                                                                                                                                                                                                                 leaf dhcp-option-value {
                                                                                                                                                                                                                                   type string;
                                                                                                                                                                                                                                   description "Value of the DHCP option";
                                                                                                                                                                                                                                 }
                                                                                                                                                                                                                               }
                                                                                                                                                                                                                             }
                                                                                                                                                                                                                             container dhcp-lease-information {
                                                                                                                                                                                                                               description "Information about an address assignment";
                                                                                                                                                                                                                               container dhcp-option-table {
                                                                                                                                                                                                                                 description "Information about one or more Dynamic Host Configuration Protocol options that are associated with the address assignment";
                                                                                                                                                                                                                                 list dhcp-option {
                                                                                                                                                                                                                                   description "Information about a Dynamic Host Configuration Protocol option that is associated with the address assignment";
                                                                                                                                                                                                                                   leaf dhcp-option-code {
                                                                                                                                                                                                                                     type int32;
                                                                                                                                                                                                                                     description "Numeric code assigned to the DHCP option";
                                                                                                                                                                                                                                   }
                                                                                                                                                                                                                                   leaf dhcp-option-name {
                                                                                                                                                                                                                                     type string;
                                                                                                                                                                                                                                     description "Name of the DHCP option";
                                                                                                                                                                                                                                   }
                                                                                                                                                                                                                                   leaf dhcp-option-type {
                                                                                                                                                                                                                                     type string;
                                                                                                                                                                                                                                     description "Type of value for the DHCP option (for example, string [word], integer, IP address)";
                                                                                                                                                                                                                                   }
                                                                                                                                                                                                                                   leaf dhcp-option-value {
                                                                                                                                                                                                                                     type string;
                                                                                                                                                                                                                                     description "Value of the DHCP option";
                                                                                                                                                                                                                                   }
                                                                                                                                                                                                                                 }
                                                                                                                                                                                                                               }
                                                                                                                                                                                                                               container dhcp-lease-information {
                                                                                                                                                                                                                                 description "Information about an address assignment";
                                                                                                                                                                                                                                 container dhcp-option-table {
                                                                                                                                                                                                                                   description "Information about one or more Dynamic Host Configuration Protocol options that are associated with the address assignment";
                                                                                                                                                                                                                                   list dhcp-option {
                                                                                                                                                                                                                                     description "Information about a Dynamic Host Configuration Protocol option that is associated with the address assignment";
                                                                                                                                                                                                                                     leaf dhcp-option-code {
                                                                                                                                                                                                                                       type int32;
                                                                                                                                                                                                                                       description "Numeric code assigned to the DHCP option";
                                                                                                                                                                                                                                     }
                                                                                                                                                                                                                                     leaf dhcp-option-name {
                                                                                                                                                                                                                                       type string;
                                                                                                                                                                                                                                       description "Name of the DHCP option";
                                                                                                                                                                                                                                     }
                                                                                                                                                                                                                                     leaf dhcp-option-type {
                                                                                                                                                                                                                                       type string;
                                                                                                                                                                                                                                       description "Type of value for the DHCP option (for example, string [word], integer, IP address)";
                                                                                                                                                                                                                                     }
                                                                                                                                                                                                                                     leaf dhcp-option-value {
                                                                                                                                                                                                                                       type string;
                                                                                                                                                                                                                                       description "Value of the DHCP option";
                                                                                                                                                                                                                                     }
                                                                                                                                                                                                                                   }
                                                                                                                                                                                                                                 }
                                                                                                                                                                                                                                 container dhcp-lease-information {
                                                                                                                                                                                                                                   description "Information about an address assignment";
                                                                                                                                                                                                                                   container dhcp-option-table {
                                                                                                                                                                                                                                     description "Information about one or more Dynamic Host Configuration Protocol options that are associated with the address assignment";
                                                                                                                                                                                                                                     list dhcp-option {
                                                                                                                                                                                                                                       description "Information about a Dynamic Host Configuration Protocol option that is associated with the address assignment";
                                                                                                                                                                                                                                       leaf dhcp-option-code {
                                                                                                                                                                                                                                         type int32;
                                                                                                                                                                                                                                         description "Numeric code assigned to the DHCP option";
                                                                                                                                                                                                                                       }
                                                                                                                                                                                                                                       leaf dhcp-option-name {
                                                                                                                                                                                                                                         type string;
                                                                                                                                                                                                                                         description "Name of the DHCP option";
                                                                                                                                                                                                                                       }
                                                                                                                                                                                                                                       leaf dhcp-option-type {
                                                                                                                                                                                                                                         type string;
                                                                                                                                                                                                                                         description "Type of value for the DHCP option (for example, string [word], integer, IP address)";
                                                                                                                                                                                                                                       }
                                                                                                                                                                                                                                       leaf dhcp-option-value {
                                                                                                                                                                                                                                         type string;
                                                                                                                                                                                                                                         description "Value of the DHCP option";
                                                                                                                                                                                                                                       }
                                                                                                                                                                                                                                     }
                                                                                                                                                                                                                                   }
                                                                                                                                                                                                                                   container dhcp-lease-information {
                                                                                                                                                                                                                                     description "Information about an address assignment";
                                                                                                                                                                                                                                     container dhcp-option-table {
                                                                                                                                                                                                                                       description "Information about one or more Dynamic Host Configuration Protocol options that are associated with the address assignment";
                                                                                                                                                                                                                                       list dhcp-option {
                                                                                                                                                                                                                                         description "Information about a Dynamic Host Configuration Protocol option that is associated with the address assignment";
                                                                                                                                                                                                                                         leaf dhcp-option-code {
                                                                                                                                                                                                                                           type int32;
                                                                                                                                                                                                                                           description "Numeric code assigned to the DHCP option";
                                                                                                                                                                                                                                         }
                                                                                                                                                                                                                                         leaf dhcp-option-name {
                                                                                                                                                                                                                                           type string;
                                                                                                                                                                                                                                           description "Name of the DHCP option";
                                                                                                                                                                                                                                         }
                                                                                                                                                                                                                                         leaf dhcp-option-type {
                                                                                                                                                                                                                                           type string;
                                                                                                                                                                                                                                           description "Type of value for the DHCP option (for example, string [word], integer, IP address)";
                                                                                                                                                                                                                                         }
                                                                                                                                                                                                                                         leaf dhcp-option-value {
                                                                                                                                                                                                                                           type string;
                                                                                                                                                                                                                                           description "Value of the DHCP option";
                                                                                                                                                                                                                                         }
                                                                                                                                                                                                                                       }
                                                                                                                                                                                                                                     }
                                                                                                                                                                                                                                     container dhcp-lease-information {
                                                                                                                                                                                                                                       description "Information about an address assignment";
                                                                                                                                                                                                                                       container dhcp-option-table {
                                                                                                                                                                                                                                         description "Information about one or more Dynamic Host Configuration Protocol options that are associated with the address assignment";
                                                                                                                                                                                                                                         list dhcp-option {
                                                                                                                                                                                                                                           description "Information about a Dynamic Host Configuration Protocol option that is associated with the address assignment";
                                                                                                                                                                                                                                           leaf dhcp-option-code {
                                                                                                                                                                                                                                             type int32;
                                                                                                                                                                                                                                             description "Numeric code assigned to the DHCP option";
                                                                                                                                                                                                                                           }
                                                                                                                                                                                                                                           leaf dhcp-option-name {
                                                                                                                                                                                                                                             type string;
                                                                                                                                                                                                                                             description "Name of the DHCP option";
                                                                                                                                                                                                                                           }
                                                                                                                                                                                                                                           leaf dhcp-option-type {
                                                                                                                                                                                                                                             type string;
                                                                                                                                                                                                                                             description "Type of value for the DHCP option (for example, string [word], integer, IP address)";
                                                                                                                                                                                                                                           }
                                                                                                                                                                                                                                           leaf dhcp-option-value {
                                                                                                                                                                                                                                             type string;
                                                                                                                                                                                                                                             description "Value of the DHCP option";
                                                                                                                                                                                                                                           }
                                                                                                                                                                                                                                         }
                                                                                                                                                                                                                                       }
                                                                                                                                                                                                                                       container dhcp-lease-information {
                                                                                                                                                                                                                                         description "Information about an address assignment";
                                                                                                                                                                                                                                         container dhcp-option-table {
                                                                                                                                                                                                                                           description "Information about one or more Dynamic Host Configuration Protocol options that are associated with the address assignment";
                                                                                                                                                                                                                                           list dhcp-option {
                                                                                                                                                                                                                                             description "Information about a Dynamic Host Configuration Protocol option that is associated with the address assignment";
                                                                                                                                                                                                                                             leaf dhcp-option-code {
                                                                                                                                                                                                                                               type int32;
                                                                                                                                                                                                                                               description "Numeric code assigned to the DHCP option";
                                                                                                                                                                                                                                             }
                                                                                                                                                                                                                                             leaf dhcp-option-name {
                                                                                                                                                                                                                                               type string;
                                                                                                                                                                                                                                               description "Name of the DHCP option";
                                                                                                                                                                                                                                             }
                                                                                                                                                                                                                                             leaf dhcp-option-type {
                                                                                                                                                                                                                                               type string;
                                                                                                                                                                                                                                               description "Type of value for the DHCP option (for example, string [word], integer, IP address)";
                                                                                                                                                                                                                                             }
                                                                                                                                                                                                                                             leaf dhcp-option-value {
                                                                                                                                                                                                                                               type string;
                                                                                                                                                                                                                                               description "Value of the DHCP option";
                                                                                                                                                                                                                                             }
                                                                                                                                                                                                                                           }
                                                                                                                                                                                                                                         }
                                                                                                                                                                                                                                         container dhcp-lease-information {
                                                                                                                                                                                                                                           description "Information about an address assignment";
                                                                                                                                                                                                                                           container dhcp-option-table {
                                                                                                                                                                                                                                             description "Information about one or more Dynamic Host Configuration Protocol options that are associated with the address assignment";
                                                                                                                                                                                                                                             list dhcp-option {
                                                                                                                                                                                                                                               description "Information about a Dynamic Host Configuration Protocol option that is associated with the address assignment";
                                                                                                                                                                                                                                               leaf dhcp-option-code {
                                                                                                                                                                                                                                                 type int32;
                                                                                                                                                                                                                                                 description "Numeric code assigned to the DHCP option";
                                                                                                                                                                                                                                               }
                                                                                                                                                                                                                                               leaf dhcp-option-name {
                                                                                                                                                                                                                                                 type string;
                                                                                                                                                                                                                                                 description "Name of the DHCP option";
                                                                                                                                                                                                                                               }
                                                                                                                                                                                                                                               leaf dhcp-option-type {
                                                                                                                                                                                                                                                 type string;
                                                                                                                                                                                                                                                 description "Type of value for the DHCP option (for example, string [word], integer, IP address)";
                                                                                                                                                                                                                                               }
                                                                                                                                                                                                                                               leaf dhcp-option-value {
                                                                                                                                                                                                                                                 type string;
                                                                                                                                                                                                                                                 description "Value of the DHCP option";
                                                                                                                                                                                                                                               }
                                                                                                                                                                                                                                             }
                                                                                                                                                                                                                                           }
                                                                                                                                                                                                                                           container dhcp-lease-information {
                                                                                                                                                                                                                                             description "Information about an address assignment";
                                                                                                                                                                                                                                             container dhcp-option-table {
                                                                                                                                                                                                                                               description "Information about one or more Dynamic Host Configuration Protocol options that are associated with the address assignment";
                                                                                                                                                                                                                                               list dhcp-option {
                                                                                                                                                                                                                                                 description "Information about a Dynamic Host Configuration Protocol option that is associated with the address assignment";
                                                                                                                                                                                                                                                 leaf dhcp-option-code {
                                                                                                                                                                                                                                                   type int32;
                                                                                                                                                                                                                                                   description "Numeric code assigned to the DHCP option";
                                                                                                                                                                                                                                                 }
                                                                                                                                                                                                                                                 leaf dhcp-option-name {
                                                                                                                                                                                                                                                   type string;
                                                                                                                                                                                                                                                   description "Name of the DHCP option";
                                                                                                                                                                                                                                                 }
                                                                                                                                                                                                                                                 leaf dhcp-option-type {
                                                                                                                                                                                                                                                   type string;
                                                                                                                                                                                                                                                   description "Type of value for the DHCP option (for example, string [word], integer, IP address)";
                                                                                                                                                                                                                                                 }
                                                                                                                                                                                                                                                 leaf dhcp-option-value {
                                                                                                                                                                                                                                                   type string;
                                                                                                                                                                                                                                                   description "Value of the DHCP option";
                                                                                                                                                                                                                                                 }
                                                                                                                                                                                                                                               }
                                                                                                                                                                                                                                             }
                                                                                                                                                                                                                                             container dhcp-lease-information {
                                                                                                                                                                                                                                               description "Information about an address assignment";
                                                                                                                                                                                                                                               container dhcp-option-table {
                                                                                                                                                                                                                                                 description "Information about one or more Dynamic Host Configuration Protocol options that are associated with the address assignment";
                                                                                                                                                                                                                                                 list dhcp-option {
                                                                                                                                                                                                                                                   description "Information about a Dynamic Host Configuration Protocol option that is associated with the address assignment";
                                                                                                                                                                                                                                                   leaf dhcp-option-code {
                                                                                                                                                                                                                                                     type int32;
                                                                                                                                                                                                                                                     description "Numeric code assigned to the DHCP option";
                                                                                                                                                                                                                                                   }
                                                                                                                                                                                                                                                   leaf dhcp-option-name {
                                                                                                                                                                                                                                                     type string;
                                                                                                                                                                                                                                                     description "Name of the DHCP option";
                                                                                                                                                                                                                                                   }
                                                                                                                                                                                                                                                   leaf dhcp-option-type {
                                                                                                                                                                                                                                                     type string;
                                                                                                                                                                                                                                                     description "Type of value for the DHCP option (for example, string [word], integer, IP address)";
                                                                                                                                                                                                                                                   }
                                                                                                                                                                                                                                                   leaf dhcp-option-value {
                                                                                                                                                                                                                                                     type string;
                                                                                                                                                                                                                                                     description "Value of the DHCP option";
                                                                                                                                                                                                                                                   }
                                                                                                                                                                                                                                                 }
                                                                                                                                                                                                                                               }
                                                                                                                                                                                                                                               container dhcp-lease-information {
                                                                                                                                                                                                                                                 description "Information about an address assignment";
                                                                                                                                                                                                                                                 container dhcp-option-table {
                                                                                                                                                                                                                                                   description "Information about one or more Dynamic Host Configuration Protocol options that are associated with the address assignment";
                                                                                                                                                                                                                                                   list dhcp-option {
                                                                                                                                                                                                                                                     description "Information about a Dynamic Host Configuration Protocol option that is associated with the address assignment";
                                                                                                                                                                                                                                                     leaf dhcp-option-code {
                                                                                                                                                                                                                                                       type int32;
                                                                                                                                                                                                                                                       description "Numeric code assigned to the DHCP option";
                                                                                                                                                                                                                                                     }
                                                                                                                                                                                                                                                     leaf dhcp-option-name {
                                                                                                                                                                                                                                                       type string;
                                                                                                                                                                                                                                                       description "Name of the DHCP option";
                                                                                                                                                                                                                                                     }
                                                                                                                                                                                                                                                     leaf dhcp-option-type {
                                                                                                                                                                                                                                                       type string;
                                                                                                                                                                                                                                                       description "Type of value for the DHCP option (for example, string [word], integer, IP address)";
                                                                                                                                                                                                                                                     }
                                                                                                                                                                                                                                                     leaf dhcp-option-value {
                                                                                                                                                                                                                                                       type string;
                                                                                                                                                                                                                                                       description "Value of the DHCP option";
                                                                                                                                                                                                                                                     }
                                                                                                                                                                                                                                                   }
                                                                                                                                                                                                                                                 }
                                                                                                                                                                                                                                                 container dhcp-lease-information {
                                                                                                                                                                                                                                                   description "Information about an address assignment";
                                                                                                                                                                                                                                                   container dhcp-option-table {
                                                                                                                                                                                                                                                     description "Information about one or more Dynamic Host Configuration Protocol options that are associated with the address assignment";
                                                                                                                                                                                                                                                     list dhcp-option {
                                                                                                                                                                                                                                                       description "Information about a Dynamic Host Configuration Protocol option that is associated with the address assignment";
                                                                                                                                                                                                                                                       leaf dhcp-option-code {
                                                                                                                                                                                                                                                         type int32;
                                                                                                                                                                                                                                                         description "Numeric code assigned to the DHCP option";
                                                                                                                                                                                                                                                       }
                                                                                                                                                                                                                                                       leaf dhcp-option-name {
                                                                                                                                                                                                                                                         type string;
                                                                                                                                                                                                                                                         description "Name of the DHCP option";
                                                                                                                                                                                                                                                       }
                                                                                                                                                                                                                                                       leaf dhcp-option-type {
                                                                                                                                                                                                                                                         type string;
                                                                                                                                                                                                                                                         description "Type of value for the DHCP option (for example, string [word], integer, IP address)";
                                                                                                                                                                                                                                                       }
                                                                                                                                                                                                                                                       leaf dhcp-option-value {
                                                                                                                                                                                                                                                         type string;
                                                                                                                                                                                                                                                         description "Value of the DHCP option";
                                                                                                                                                                                                                                                       }
                                                                                                                                                                                                                                                     }
                                                                                                                                                                                                                                                   }
                                                                                                                                                                                                                                                   container dhcp-lease-information {
                                                                                                                                                                                                                                                     description "Information about an address assignment";
                                                                                                                                                                                                                                                     container dhcp-option-table {
                                                                                                                                                                                                                                                       description "Information about one or more Dynamic Host Configuration Protocol options that are associated with the address assignment";
                                                                                                                                                                                                                                                       list dhcp-option {
                                                                                                                                                                                                                                                         description "Information about a Dynamic Host Configuration Protocol option that is associated with the address assignment";
                                                                                                                                                                                                                                                         leaf dhcp-option-code {
                                                                                                                                                                                                                                                           type int32;
                                                                                                                                                                                                                                                           description "Numeric code assigned to the DHCP option";
                                                                                                                                                                                                                                                         }
                                                                                                                                                                                                                                                         leaf dhcp-option-name {
                                                                                                                                                                                                                                                           type string;
                                                                                                                                                                                                                                                           description "Name of the DHCP option";
                                                                                                                                                                                                                                                         }
                                                                                                                                                                                                                                                         leaf dhcp-option-type {
                                                                                                                                                                                                                                                           type string;
                                                                                                                                                                                                                                                           description "Type of value for the DHCP option (for example, string [word], integer, IP address)";
                                                                                                                                                                                                                                                         }
                                                                                                                                                                                                                                                         leaf dhcp-option-value {
                                                                                                                                                                                                                                                           type string;
                                                                                                                                                                                                                                                           description "Value of the DHCP option";
                                                                                                                                                                                                                                                         }
                                                                                                                                                                                                                                                       }
                                                                                                                                                                                                                                                     }
                                                                                                                                                                                                                                                     container dhcp-lease-information {
                                                                                                                                                                                                                                                       description "Information about an address assignment";
                                                                                                                                                                                                                                                       container dhcp-option-table {
                                                                                                                                                                                                                                                         description "Information about one or more Dynamic Host Configuration Protocol options that are associated with the address assignment";
                                                                                                                                                                                                                                                         list dhcp-option {
                                                                                                                                                                                                                                                           description "Information about a Dynamic Host Configuration Protocol option that is associated with the address assignment";
                                                                                                                                                                                                                                                           leaf dhcp-option-code {
                                                                                                                                                                                                                                                             type int32;
                                                                                                                                                                                                                                                             description "Numeric code assigned to the DHCP option";
                                                                                                                                                                                                                                                           }
                                                                                                                                                                                                                                                           leaf dhcp-option-name {
                                                                                                                                                                                                                                                             type string;
                                                                                                                                                                                                                                                             description "Name of the DHCP option";
                                                                                                                                                                                                                                                           }
                                                                                                                                                                                                                                                           leaf dhcp-option-type {
                                                                                                                                                                                                                                                             type string;
                                                                                                                                                                                                                                                             description "Type of value for the DHCP option (for example, string [word], integer, IP address)";
                                                                                                                                                                                                                                                           }
                                                                                                                                                                                                                                                           leaf dhcp-option-value {
                                                                                                                                                                                                                                                             type string;
                                                                                                                                                                                                                                                             description "Value of the DHCP option";
                                                                                                                                                                                                                                                           }
                                                                                                                                                                                                                                                         }
                                                                                                                                                                                                                                                       }
                                                                                                                                                                                                                                                       container dhcp-lease-information {
                                                                                                                                                                                                                                                         description "Information about an address assignment";
                                                                                                                                                                                                                                                         container dhcp-option-table {
                                                                                                                                                                                                                                                           description "Information about one or more Dynamic Host Configuration Protocol options that are associated with the address assignment";
                                                                                                                                                                                                                                                           list dhcp-option {
                                                                                                                                                                                                                                                             description "Information about a Dynamic Host Configuration Protocol option that is associated with the address assignment";
                                                                                                                                                                                                                                                             leaf dhcp-option-code {
                                                                                                                                                                                                                                                               type int32;
                                                                                                                                                                                                                                                               description "Numeric code assigned to the DHCP option";
                                                                                                                                                                                                                                                             }
                                                                                                                                                                                                                                                             leaf dhcp-option-name {
                                                                                                                                                                                                                                                               type string;
                                                                                                                                                                                                                                                               description "Name of the DHCP option";
                                                                                                                                                                                                                                                             }
                                                                                                                                                                                                                                                             leaf dhcp-option-type {
                                                                                                                                                                                                                                                               type string;
                                                                                                                                                                                                                                                               description "Type of value for the DHCP option (for example, string [word], integer, IP address)";
                                                                                                                                                                                                                                                             }
                                                                                                                                                                                                                                                             leaf dhcp-option-value {
                                                                                                                                                                                                                                                               type string;
                                                                                                                                                                                                                                                               description "Value of the DHCP option";
                                                                                                                                                                                                                                                             }
                                                                                                                                                                                                                                                           }
                                                                                                                                                                                                                                                         }
                                                                                                                                                                                                                                                         container dhcp-lease-information {
                                                                                                                                                                                                                                                           description "Information about an address assignment";
                                                                                                                                                                                                                                                           container dhcp-option-table {
                                                                                                                                                                                                                                                             description "Information about one or more Dynamic Host Configuration Protocol options that are associated with the address assignment";
                                                                                                                                                                                                                                                             list dhcp-option {
                                                                                                                                                                                                                                                               description "Information about a Dynamic Host Configuration Protocol option that is associated with the address assignment";
                                                                                                                                                                                                                                                               leaf dhcp-option-code {
                                                                                                                                                                                                                                                                 type int32;
                                                                                                                                                                                                                                                                 description "Numeric code assigned to the DHCP option";
                                                                                                                                                                                                                                                               }
                                                                                                                                                                                                                                                               leaf dhcp-option-name {
                                                                                                                                                                                                                                                                 type string;
                                                                                                                                                                                                                                                                 description "Name of the DHCP option";
                                                                                                                                                                                                                                                               }
                                                                                                                                                                                                                                                               leaf dhcp-option-type {
                                                                                                                                                                                                                                                                 type string;
                                                                                                                                                                                                                                                                 description "Type of value for the DHCP option (for example, string [word], integer, IP address)";
                                                                                                                                                                                                                                                               }
                                                                                                                                                                                                                                                               leaf dhcp-option-value {
                                                                                                                                                                                                                                                                 type string;
                                                                                                                                                                                                                                                                 description "Value of the DHCP option";
                                                                                                                                                                                                                                                               }
                                                                                                                                                                                                                                                             }
                                                                                                                                                                                                                                                           }
                                                                                                                                                                                                                                                           container dhcp-lease-information {
                                                                                                                                                                                                                                                             description "Information about an address assignment";
                                                                                                                                                                                                                                                             container dhcp-option-table {
                                                                                                                                                                                                                                                               description "Information about one or more Dynamic Host Configuration Protocol options that are associated with the address assignment";
                                                                                                                                                                                                                                                               list dhcp-option {
                                                                                                                                                                                                                                                                 description "Information about a Dynamic Host Configuration Protocol option that is associated with the address assignment";
                                                                                                                                                                                                                                                                 leaf dhcp-option-code {
                                                                                                                                                                                                                                                                   type int32;
                                                                                                                                                                                                                                                                   description "Numeric code assigned to the DHCP option";
                                                                                                                                                                                                                                                                 }
                                                                                                                                                                                                                                                                 leaf dhcp-option-name {
                                                                                                                                                                                                                                                                   type string;
                                                                                                                                                                                                                                                                   description "Name of the DHCP option";
                                                                                                                                                                                                                                                                 }
                                                                                                                                                                                                                                                                 leaf dhcp-option-type {
                                                                                                                                                                                                                                                                   type string;
                                                                                                                                                                                                                                                                   description "Type of value for the DHCP option (for example, string [word], integer, IP address)";
                                                                                                                                                                                                                                                                 }
                                                                                                                                                                                                                                                                 leaf dhcp-option-value {
                                                                                                                                                                                                                                                                   type string;
                                                                                                                                                                                                                                                                   description "Value of the DHCP option";
                                                                                                                                                                                                                                                                 }
                                                                                                                                                                                                                                                               }
                                                                                                                                                                                                                                                             }
                                                                                                                                                                                                                                                             container dhcp-lease-information {
                                                                                                                                                                                                                                                               description "Information about an address assignment";
                                                                                                                                                                                                                                                               container dhcp-option-table {
                                                                                                                                                                                                                                                                 description "Information about one or more Dynamic Host Configuration Protocol options that are associated with the address assignment";
                                                                                                                                                                                                                                                                 list dhcp-option {
                                                                                                                                                                                                                                                                   description "Information about a Dynamic Host Configuration Protocol option that is associated with the address assignment";
                                                                                                                                                                                                                                                                   leaf dhcp-option-code {
                                                                                                                                                                                                                                                                     type int32;
                                                                                                                                                                                                                                                                     description "Numeric code assigned to the DHCP option";
                                                                                                                                                                                                                                                                   }
                                                                                                                                                                                                                                                                   leaf dhcp-option-name {
                                                                                                                                                                                                                                                                     type string;
                                                                                                                                                                                                                                                                     description "Name of the DHCP option";
                                                                                                                                                                                                                                                                   }
                                                                                                                                                                                                                                                                   leaf dhcp-option-type {
                                                                                                                                                                                                                                                                     type string;
                                                                                                                                                                                                                                                                     description "Type of value for the DHCP option (for example, string [word], integer, IP address)";
                                                                                                                                                                                                                                                                   }
                                                                                                                                                                                                                                                                   leaf dhcp-option-value {
                                                                                                                                                                                                                                                                     type string;
                                                                                                                                                                                                                                                                     description "Value of the DHCP option";
                                                                                                                                                                                                                                                                   }
                                                                                                                                                                                                                                                                 }
                                                                                                                                                                                                                                                               }
                                                                                                                                                                                                                                                               container dhcp-lease-information {
                                                                                                                                                                                                                                                                 description "Information about an address assignment";
                                                                                                                                                                                                                                                                 container dhcp-option-table {
                                                                                                                                                                                                                                                                   description "Information about one or more Dynamic Host Configuration Protocol options that are associated with the address assignment";
                                                                                                                                                                                                                                                                   list dhcp-option {
                                                                                                                                                                                                                                                                     description "Information about a Dynamic Host Configuration Protocol option that is associated with the address assignment";
                                                                                                                                                                                                                                                                     leaf dhcp-option-code {
                                                                                                                                                                                                                                                                       type int32;
                                                                                                                                                                                                                                                                       description "Numeric code assigned to the DHCP option";
                                                                                                                                                                                                                                                                     }
                                                                                                                                                                                                                                                                     leaf dhcp-option-name {
                                                                                                                                                                                                                                                                       type string;
                                                                                                                                                                                                                                                                       description "Name of the DHCP option";
                                                                                                                                                                                                                                                                     }
                                                                                                                                                                                                                                                                     leaf dhcp-option-type {
                                                                                                                                                                                                                                                                       type string;
                                                                                                                                                                                                                                                                       description "Type of value for the DHCP option (for example, string [word], integer, IP address)";
                                                                                                                                                                                                                                                                     }
                                                                                                                                                                                                                                                                     leaf dhcp-option-value {
                                                                                                                                                                                                                                                                       type string;
                                                                                                                                                                                                                                                                       description "Value of the DHCP option";
                                                                                                                                                                                                                                                                     }
                                                                                                                                                                                                                                                                   }
                                                                                                                                                                                                                                                                 }
                                                                                                                                                                                                                                                                 container client-identifier {
                                                                                                                                                                                                                                                                   description "Identifier that the DHCP client provided for itself when it requested an address assignment";
                                                                                                                                                                                                                                                                   leaf hex-data-line {
                                                                                                                                                                                                                                                                     type string;
                                                                                                                                                                                                                                                                     description "Line of data in hexadecimal format";
                                                                                                                                                                                                                                                                   }
                                                                                                                                                                                                                                                                   leaf printable-data-line {
                                                                                                                                                                                                                                                                     type string;
                                                                                                                                                                                                                                                                     description "Line of data in printable format";
                                                                                                                                                                                                                                                                   }
                                                                                                                                                                                                                                                                 }
                                                                                                                                                                                                                                                               }
                                                                                                                                                                                                                                                             }
                                                                                                                                                                                                                                                             container client-identifier {
                                                                                                                                                                                                                                                               description "Identifier that the DHCP client provided for itself when it requested an address assignment";
                                                                                                                                                                                                                                                               leaf hex-data-line {
                                                                                                                                                                                                                                                                 type string;
                                                                                                                                                                                                                                                                 description "Line of data in hexadecimal format";
                                                                                                                                                                                                                                                               }
                                                                                                                                                                                                                                                               leaf printable-data-line {
                                                                                                                                                                                                                                                                 type string;
                                                                                                                                                                                                                                                                 description "Line of data in printable format";
                                                                                                                                                                                                                                                               }
                                                                                                                                                                                                                                                             }
                                                                                                                                                                                                                                                           }
                                                                                                                                                                                                                                                         }
                                                                                                                                                                                                                                                         container client-identifier {
                                                                                                                                                                                                                                                           description "Identifier that the DHCP client provided for itself when it requested an address assignment";
                                                                                                                                                                                                                                                           leaf hex-data-line {
                                                                                                                                                                                                                                                             type string;
                                                                                                                                                                                                                                                             description "Line of data in hexadecimal format";
                                                                                                                                                                                                                                                           }
                                                                                                                                                                                                                                                           leaf printable-data-line {
                                                                                                                                                                                                                                                             type string;
                                                                                                                                                                                                                                                             description "Line of data in printable format";
                                                                                                                                                                                                                                                           }
                                                                                                                                                                                                                                                         }
                                                                                                                                                                                                                                                       }
                                                                                                                                                                                                                                                     }
                                                                                                                                                                                                                                                     container client-identifier {
                                                                                                                                                                                                                                                       description "Identifier that the DHCP client provided for itself when it requested an address assignment";
                                                                                                                                                                                                                                                       leaf hex-data-line {
                                                                                                                                                                                                                                                         type string;
                                                                                                                                                                                                                                                         description "Line of data in hexadecimal format";
                                                                                                                                                                                                                                                       }
                                                                                                                                                                                                                                                       leaf printable-data-line {
                                                                                                                                                                                                                                                         type string;
                                                                                                                                                                                                                                                         description "Line of data in printable format";
                                                                                                                                                                                                                                                       }
                                                                                                                                                                                                                                                     }
                                                                                                                                                                                                                                                   }
                                                                                                                                                                                                                                                 }
                                                                                                                                                                                                                                                 container client-identifier {
                                                                                                                                                                                                                                                   description "Identifier that the DHCP client provided for itself when it requested an address assignment";
                                                                                                                                                                                                                                                   leaf hex-data-line {
                                                                                                                                                                                                                                                     type string;
                                                                                                                                                                                                                                                     description "Line of data in hexadecimal format";
                                                                                                                                                                                                                                                   }
                                                                                                                                                                                                                                                   leaf printable-data-line {
                                                                                                                                                                                                                                                     type string;
                                                                                                                                                                                                                                                     description "Line of data in printable format";
                                                                                                                                                                                                                                                   }
                                                                                                                                                                                                                                                 }
                                                                                                                                                                                                                                               }
                                                                                                                                                                                                                                             }
                                                                                                                                                                                                                                             container client-identifier {
                                                                                                                                                                                                                                               description "Identifier that the DHCP client provided for itself when it requested an address assignment";
                                                                                                                                                                                                                                               leaf hex-data-line {
                                                                                                                                                                                                                                                 type string;
                                                                                                                                                                                                                                                 description "Line of data in hexadecimal format";
                                                                                                                                                                                                                                               }
                                                                                                                                                                                                                                               leaf printable-data-line {
                                                                                                                                                                                                                                                 type string;
                                                                                                                                                                                                                                                 description "Line of data in printable format";
                                                                                                                                                                                                                                               }
                                                                                                                                                                                                                                             }
                                                                                                                                                                                                                                           }
                                                                                                                                                                                                                                         }
                                                                                                                                                                                                                                         container client-identifier {
                                                                                                                                                                                                                                           description "Identifier that the DHCP client provided for itself when it requested an address assignment";
                                                                                                                                                                                                                                           leaf hex-data-line {
                                                                                                                                                                                                                                             type string;
                                                                                                                                                                                                                                             description "Line of data in hexadecimal format";
                                                                                                                                                                                                                                           }
                                                                                                                                                                                                                                           leaf printable-data-line {
                                                                                                                                                                                                                                             type string;
                                                                                                                                                                                                                                             description "Line of data in printable format";
                                                                                                                                                                                                                                           }
                                                                                                                                                                                                                                         }
                                                                                                                                                                                                                                       }
                                                                                                                                                                                                                                     }
                                                                                                                                                                                                                                     container client-identifier {
                                                                                                                                                                                                                                       description "Identifier that the DHCP client provided for itself when it requested an address assignment";
                                                                                                                                                                                                                                       leaf hex-data-line {
                                                                                                                                                                                                                                         type string;
                                                                                                                                                                                                                                         description "Line of data in hexadecimal format";
                                                                                                                                                                                                                                       }
                                                                                                                                                                                                                                       leaf printable-data-line {
                                                                                                                                                                                                                                         type string;
                                                                                                                                                                                                                                         description "Line of data in printable format";
                                                                                                                                                                                                                                       }
                                                                                                                                                                                                                                     }
                                                                                                                                                                                                                                   }
                                                                                                                                                                                                                                 }
                                                                                                                                                                                                                                 container client-identifier {
                                                                                                                                                                                                                                   description "Identifier that the DHCP client provided for itself when it requested an address assignment";
                                                                                                                                                                                                                                   leaf hex-data-line {
                                                                                                                                                                                                                                     type string;
                                                                                                                                                                                                                                     description "Line of data in hexadecimal format";
                                                                                                                                                                                                                                   }
                                                                                                                                                                                                                                   leaf printable-data-line {
                                                                                                                                                                                                                                     type string;
                                                                                                                                                                                                                                     description "Line of data in printable format";
                                                                                                                                                                                                                                   }
                                                                                                                                                                                                                                 }
                                                                                                                                                                                                                               }
                                                                                                                                                                                                                             }
                                                                                                                                                                                                                             container client-identifier {
                                                                                                                                                                                                                               description "Identifier that the DHCP client provided for itself when it requested an address assignment";
                                                                                                                                                                                                                               leaf hex-data-line {
                                                                                                                                                                                                                                 type string;
                                                                                                                                                                                                                                 description "Line of data in hexadecimal format";
                                                                                                                                                                                                                               }
                                                                                                                                                                                                                               leaf printable-data-line {
                                                                                                                                                                                                                                 type string;
                                                                                                                                                                                                                                 description "Line of data in printable format";
                                                                                                                                                                                                                               }
                                                                                                                                                                                                                             }
                                                                                                                                                                                                                           }
                                                                                                                                                                                                                         }
                                                                                                                                                                                                                         container client-identifier {
                                                                                                                                                                                                                           description "Identifier that the DHCP client provided for itself when it requested an address assignment";
                                                                                                                                                                                                                           leaf hex-data-line {
                                                                                                                                                                                                                             type string;
                                                                                                                                                                                                                             description "Line of data in hexadecimal format";
                                                                                                                                                                                                                           }
                                                                                                                                                                                                                           leaf printable-data-line {
                                                                                                                                                                                                                             type string;
                                                                                                                                                                                                                             description "Line of data in printable format";
                                                                                                                                                                                                                           }
                                                                                                                                                                                                                         }
                                                                                                                                                                                                                       }
                                                                                                                                                                                                                     }
                                                                                                                                                                                                                     container client-identifier {
                                                                                                                                                                                                                       description "Identifier that the DHCP client provided for itself when it requested an address assignment";
                                                                                                                                                                                                                       leaf hex-data-line {
                                                                                                                                                                                                                         type string;
                                                                                                                                                                                                                         description "Line of data in hexadecimal format";
                                                                                                                                                                                                                       }
                                                                                                                                                                                                                       leaf printable-data-line {
                                                                                                                                                                                                                         type string;
                                                                                                                                                                                                                         description "Line of data in printable format";
                                                                                                                                                                                                                       }
                                                                                                                                                                                                                     }
                                                                                                                                                                                                                   }
                                                                                                                                                                                                                 }
                                                                                                                                                                                                                 container client-identifier {
                                                                                                                                                                                                                   description "Identifier that the DHCP client provided for itself when it requested an address assignment";
                                                                                                                                                                                                                   leaf hex-data-line {
                                                                                                                                                                                                                     type string;
                                                                                                                                                                                                                     description "Line of data in hexadecimal format";
                                                                                                                                                                                                                   }
                                                                                                                                                                                                                   leaf printable-data-line {
                                                                                                                                                                                                                     type string;
                                                                                                                                                                                                                     description "Line of data in printable format";
                                                                                                                                                                                                                   }
                                                                                                                                                                                                                 }
                                                                                                                                                                                                               }
                                                                                                                                                                                                             }
                                                                                                                                                                                                             container client-identifier {
                                                                                                                                                                                                               description "Identifier that the DHCP client provided for itself when it requested an address assignment";
                                                                                                                                                                                                               leaf hex-data-line {
                                                                                                                                                                                                                 type string;
                                                                                                                                                                                                                 description "Line of data in hexadecimal format";
                                                                                                                                                                                                               }
                                                                                                                                                                                                               leaf printable-data-line {
                                                                                                                                                                                                                 type string;
                                                                                                                                                                                                                 description "Line of data in printable format";
                                                                                                                                                                                                               }
                                                                                                                                                                                                             }
                                                                                                                                                                                                           }
                                                                                                                                                                                                         }
                                                                                                                                                                                                         container client-identifier {
                                                                                                                                                                                                           description "Identifier that the DHCP client provided for itself when it requested an address assignment";
                                                                                                                                                                                                           leaf hex-data-line {
                                                                                                                                                                                                             type string;
                                                                                                                                                                                                             description "Line of data in hexadecimal format";
                                                                                                                                                                                                           }
                                                                                                                                                                                                           leaf printable-data-line {
                                                                                                                                                                                                             type string;
                                                                                                                                                                                                             description "Line of data in printable format";
                                                                                                                                                                                                           }
                                                                                                                                                                                                         }
                                                                                                                                                                                                       }
                                                                                                                                                                                                     }
                                                                                                                                                                                                     container client-identifier {
                                                                                                                                                                                                       description "Identifier that the DHCP client provided for itself when it requested an address assignment";
                                                                                                                                                                                                       leaf hex-data-line {
                                                                                                                                                                                                         type string;
                                                                                                                                                                                                         description "Line of data in hexadecimal format";
                                                                                                                                                                                                       }
                                                                                                                                                                                                       leaf printable-data-line {
                                                                                                                                                                                                         type string;
                                                                                                                                                                                                         description "Line of data in printable format";
                                                                                                                                                                                                       }
                                                                                                                                                                                                     }
                                                                                                                                                                                                   }
                                                                                                                                                                                                 }
                                                                                                                                                                                                 container client-identifier {
                                                                                                                                                                                                   description "Identifier that the DHCP client provided for itself when it requested an address assignment";
                                                                                                                                                                                                   leaf hex-data-line {
                                                                                                                                                                                                     type string;
                                                                                                                                                                                                     description "Line of data in hexadecimal format";
                                                                                                                                                                                                   }
                                                                                                                                                                                                   leaf printable-data-line {
                                                                                                                                                                                                     type string;
                                                                                                                                                                                                     description "Line of data in printable format";
                                                                                                                                                                                                   }
                                                                                                                                                                                                 }
                                                                                                                                                                                               }
                                                                                                                                                                                             }
                                                                                                                                                                                             container client-identifier {
                                                                                                                                                                                               description "Identifier that the DHCP client provided for itself when it requested an address assignment";
                                                                                                                                                                                               leaf hex-data-line {
                                                                                                                                                                                                 type string;
                                                                                                                                                                                                 description "Line of data in hexadecimal format";
                                                                                                                                                                                               }
                                                                                                                                                                                               leaf printable-data-line {
                                                                                                                                                                                                 type string;
                                                                                                                                                                                                 description "Line of data in printable format";
                                                                                                                                                                                               }
                                                                                                                                                                                             }
                                                                                                                                                                                           }
                                                                                                                                                                                         }
                                                                                                                                                                                         container client-identifier {
                                                                                                                                                                                           description "Identifier that the DHCP client provided for itself when it requested an address assignment";
                                                                                                                                                                                           leaf hex-data-line {
                                                                                                                                                                                             type string;
                                                                                                                                                                                             description "Line of data in hexadecimal format";
                                                                                                                                                                                           }
                                                                                                                                                                                           leaf printable-data-line {
                                                                                                                                                                                             type string;
                                                                                                                                                                                             description "Line of data in printable format";
                                                                                                                                                                                           }
                                                                                                                                                                                         }
                                                                                                                                                                                       }
                                                                                                                                                                                     }
                                                                                                                                                                                     container client-identifier {
                                                                                                                                                                                       description "Identifier that the DHCP client provided for itself when it requested an address assignment";
                                                                                                                                                                                       leaf hex-data-line {
                                                                                                                                                                                         type string;
                                                                                                                                                                                         description "Line of data in hexadecimal format";
                                                                                                                                                                                       }
                                                                                                                                                                                       leaf printable-data-line {
                                                                                                                                                                                         type string;
                                                                                                                                                                                         description "Line of data in printable format";
                                                                                                                                                                                       }
                                                                                                                                                                                     }
                                                                                                                                                                                   }
                                                                                                                                                                                 }
                                                                                                                                                                                 container client-identifier {
                                                                                                                                                                                   description "Identifier that the DHCP client provided for itself when it requested an address assignment";
                                                                                                                                                                                   leaf hex-data-line {
                                                                                                                                                                                     type string;
                                                                                                                                                                                     description "Line of data in hexadecimal format";
                                                                                                                                                                                   }
                                                                                                                                                                                   leaf printable-data-line {
                                                                                                                                                                                     type string;
                                                                                                                                                                                     description "Line of data in printable format";
                                                                                                                                                                                   }
                                                                                                                                                                                 }
                                                                                                                                                                               }
                                                                                                                                                                             }
                                                                                                                                                                             container client-identifier {
                                                                                                                                                                               description "Identifier that the DHCP client provided for itself when it requested an address assignment";
                                                                                                                                                                               leaf hex-data-line {
                                                                                                                                                                                 type string;
                                                                                                                                                                                 description "Line of data in hexadecimal format";
                                                                                                                                                                               }
                                                                                                                                                                               leaf printable-data-line {
                                                                                                                                                                                 type string;
                                                                                                                                                                                 description "Line of data in printable format";
                                                                                                                                                                               }
                                                                                                                                                                             }
                                                                                                                                                                           }
                                                                                                                                                                         }
                                                                                                                                                                         container client-identifier {
                                                                                                                                                                           description "Identifier that the DHCP client provided for itself when it requested an address assignment";
                                                                                                                                                                           leaf hex-data-line {
                                                                                                                                                                             type string;
                                                                                                                                                                             description "Line of data in hexadecimal format";
                                                                                                                                                                           }
                                                                                                                                                                           leaf printable-data-line {
                                                                                                                                                                             type string;
                                                                                                                                                                             description "Line of data in printable format";
                                                                                                                                                                           }
                                                                                                                                                                         }
                                                                                                                                                                       }
                                                                                                                                                                     }
                                                                                                                                                                     container client-identifier {
                                                                                                                                                                       description "Identifier that the DHCP client provided for itself when it requested an address assignment";
                                                                                                                                                                       leaf hex-data-line {
                                                                                                                                                                         type string;
                                                                                                                                                                         description "Line of data in hexadecimal format";
                                                                                                                                                                       }
                                                                                                                                                                       leaf printable-data-line {
                                                                                                                                                                         type string;
                                                                                                                                                                         description "Line of data in printable format";
                                                                                                                                                                       }
                                                                                                                                                                     }
                                                                                                                                                                   }
                                                                                                                                                                 }
                                                                                                                                                                 container client-identifier {
                                                                                                                                                                   description "Identifier that the DHCP client provided for itself when it requested an address assignment";
                                                                                                                                                                   leaf hex-data-line {
                                                                                                                                                                     type string;
                                                                                                                                                                     description "Line of data in hexadecimal format";
                                                                                                                                                                   }
                                                                                                                                                                   leaf printable-data-line {
                                                                                                                                                                     type string;
                                                                                                                                                                     description "Line of data in printable format";
                                                                                                                                                                   }
                                                                                                                                                                 }
                                                                                                                                                               }
                                                                                                                                                             }
                                                                                                                                                             container client-identifier {
                                                                                                                                                               description "Identifier that the DHCP client provided for itself when it requested an address assignment";
                                                                                                                                                               leaf hex-data-line {
                                                                                                                                                                 type string;
                                                                                                                                                                 description "Line of data in hexadecimal format";
                                                                                                                                                               }
                                                                                                                                                               leaf printable-data-line {
                                                                                                                                                                 type string;
                                                                                                                                                                 description "Line of data in printable format";
                                                                                                                                                               }
                                                                                                                                                             }
                                                                                                                                                           }
                                                                                                                                                         }
                                                                                                                                                         container client-identifier {
                                                                                                                                                           description "Identifier that the DHCP client provided for itself when it requested an address assignment";
                                                                                                                                                           leaf hex-data-line {
                                                                                                                                                             type string;
                                                                                                                                                             description "Line of data in hexadecimal format";
                                                                                                                                                           }
                                                                                                                                                           leaf printable-data-line {
                                                                                                                                                             type string;
                                                                                                                                                             description "Line of data in printable format";
                                                                                                                                                           }
                                                                                                                                                         }
                                                                                                                                                       }
                                                                                                                                                     }
                                                                                                                                                     container client-identifier {
                                                                                                                                                       description "Identifier that the DHCP client provided for itself when it requested an address assignment";
                                                                                                                                                       leaf hex-data-line {
                                                                                                                                                         type string;
                                                                                                                                                         description "Line of data in hexadecimal format";
                                                                                                                                                       }
                                                                                                                                                       leaf printable-data-line {
                                                                                                                                                         type string;
                                                                                                                                                         description "Line of data in printable format";
                                                                                                                                                       }
                                                                                                                                                     }
                                                                                                                                                   }
                                                                                                                                                 }
                                                                                                                                                 container client-identifier {
                                                                                                                                                   description "Identifier that the DHCP client provided for itself when it requested an address assignment";
                                                                                                                                                   leaf hex-data-line {
                                                                                                                                                     type string;
                                                                                                                                                     description "Line of data in hexadecimal format";
                                                                                                                                                   }
                                                                                                                                                   leaf printable-data-line {
                                                                                                                                                     type string;
                                                                                                                                                     description "Line of data in printable format";
                                                                                                                                                   }
                                                                                                                                                 }
                                                                                                                                               }
                                                                                                                                             }
                                                                                                                                             container client-identifier {
                                                                                                                                               description "Identifier that the DHCP client provided for itself when it requested an address assignment";
                                                                                                                                               leaf hex-data-line {
                                                                                                                                                 type string;
                                                                                                                                                 description "Line of data in hexadecimal format";
                                                                                                                                               }
                                                                                                                                               leaf printable-data-line {
                                                                                                                                                 type string;
                                                                                                                                                 description "Line of data in printable format";
                                                                                                                                               }
                                                                                                                                             }
                                                                                                                                           }
                                                                                                                                         }
                                                                                                                                         container client-identifier {
                                                                                                                                           description "Identifier that the DHCP client provided for itself when it requested an address assignment";
                                                                                                                                           leaf hex-data-line {
                                                                                                                                             type string;
                                                                                                                                             description "Line of data in hexadecimal format";
                                                                                                                                           }
                                                                                                                                           leaf printable-data-line {
                                                                                                                                             type string;
                                                                                                                                             description "Line of data in printable format";
                                                                                                                                           }
                                                                                                                                         }
                                                                                                                                       }
                                                                                                                                     }
                                                                                                                                     container client-identifier {
                                                                                                                                       description "Identifier that the DHCP client provided for itself when it requested an address assignment";
                                                                                                                                       leaf hex-data-line {
                                                                                                                                         type string;
                                                                                                                                         description "Line of data in hexadecimal format";
                                                                                                                                       }
                                                                                                                                       leaf printable-data-line {
                                                                                                                                         type string;
                                                                                                                                         description "Line of data in printable format";
                                                                                                                                       }
                                                                                                                                     }
                                                                                                                                   }
                                                                                                                                 }
                                                                                                                                 container client-identifier {
                                                                                                                                   description "Identifier that the DHCP client provided for itself when it requested an address assignment";
                                                                                                                                   leaf hex-data-line {
                                                                                                                                     type string;
                                                                                                                                     description "Line of data in hexadecimal format";
                                                                                                                                   }
                                                                                                                                   leaf printable-data-line {
                                                                                                                                     type string;
                                                                                                                                     description "Line of data in printable format";
                                                                                                                                   }
                                                                                                                                 }
                                                                                                                               }
                                                                                                                             }
                                                                                                                             container client-identifier {
                                                                                                                               description "Identifier that the DHCP client provided for itself when it requested an address assignment";
                                                                                                                               leaf hex-data-line {
                                                                                                                                 type string;
                                                                                                                                 description "Line of data in hexadecimal format";
                                                                                                                               }
                                                                                                                               leaf printable-data-line {
                                                                                                                                 type string;
                                                                                                                                 description "Line of data in printable format";
                                                                                                                               }
                                                                                                                             }
                                                                                                                           }
                                                                                                                         }
                                                                                                                         container client-identifier {
                                                                                                                           description "Identifier that the DHCP client provided for itself when it requested an address assignment";
                                                                                                                           leaf hex-data-line {
                                                                                                                             type string;
                                                                                                                             description "Line of data in hexadecimal format";
                                                                                                                           }
                                                                                                                           leaf printable-data-line {
                                                                                                                             type string;
                                                                                                                             description "Line of data in printable format";
                                                                                                                           }
                                                                                                                         }
                                                                                                                       }
                                                                                                                     }
                                                                                                                     container client-identifier {
                                                                                                                       description "Identifier that the DHCP client provided for itself when it requested an address assignment";
                                                                                                                       leaf hex-data-line {
                                                                                                                         type string;
                                                                                                                         description "Line of data in hexadecimal format";
                                                                                                                       }
                                                                                                                       leaf printable-data-line {
                                                                                                                         type string;
                                                                                                                         description "Line of data in printable format";
                                                                                                                       }
                                                                                                                     }
                                                                                                                   }
                                                                                                                 }
                                                                                                                 container client-identifier {
                                                                                                                   description "Identifier that the DHCP client provided for itself when it requested an address assignment";
                                                                                                                   leaf hex-data-line {
                                                                                                                     type string;
                                                                                                                     description "Line of data in hexadecimal format";
                                                                                                                   }
                                                                                                                   leaf printable-data-line {
                                                                                                                     type string;
                                                                                                                     description "Line of data in printable format";
                                                                                                                   }
                                                                                                                 }
                                                                                                               }
                                                                                                             }
                                                                                                             container client-identifier {
                                                                                                               description "Identifier that the DHCP client provided for itself when it requested an address assignment";
                                                                                                               leaf hex-data-line {
                                                                                                                 type string;
                                                                                                                 description "Line of data in hexadecimal format";
                                                                                                               }
                                                                                                               leaf printable-data-line {
                                                                                                                 type string;
                                                                                                                 description "Line of data in printable format";
                                                                                                               }
                                                                                                             }
                                                                                                           }
                                                                                                         }
                                                                                                         container client-identifier {
                                                                                                           description "Identifier that the DHCP client provided for itself when it requested an address assignment";
                                                                                                           leaf hex-data-line {
                                                                                                             type string;
                                                                                                             description "Line of data in hexadecimal format";
                                                                                                           }
                                                                                                           leaf printable-data-line {
                                                                                                             type string;
                                                                                                             description "Line of data in printable format";
                                                                                                           }
                                                                                                         }
                                                                                                       }
                                                                                                     }
                                                                                                     container client-identifier {
                                                                                                       description "Identifier that the DHCP client provided for itself when it requested an address assignment";
                                                                                                       leaf hex-data-line {
                                                                                                         type string;
                                                                                                         description "Line of data in hexadecimal format";
                                                                                                       }
                                                                                                       leaf printable-data-line {
                                                                                                         type string;
                                                                                                         description "Line of data in printable format";
                                                                                                       }
                                                                                                     }
                                                                                                   }
                                                                                                 }
                                                                                                 container client-identifier {
                                                                                                   description "Identifier that the DHCP client provided for itself when it requested an address assignment";
                                                                                                   leaf hex-data-line {
                                                                                                     type string;
                                                                                                     description "Line of data in hexadecimal format";
                                                                                                   }
                                                                                                   leaf printable-data-line {
                                                                                                     type string;
                                                                                                     description "Line of data in printable format";
                                                                                                   }
                                                                                                 }
                                                                                               }
                                                                                             }
                                                                                             container client-identifier {
                                                                                               description "Identifier that the DHCP client provided for itself when it requested an address assignment";
                                                                                               leaf hex-data-line {
                                                                                                 type string;
                                                                                                 description "Line of data in hexadecimal format";
                                                                                               }
                                                                                               leaf printable-data-line {
                                                                                                 type string;
                                                                                                 description "Line of data in printable format";
                                                                                               }
                                                                                             }
                                                                                           }
                                                                                         }
                                                                                         container client-identifier {
                                                                                           description "Identifier that the DHCP client provided for itself when it requested an address assignment";
                                                                                           leaf hex-data-line {
                                                                                             type string;
                                                                                             description "Line of data in hexadecimal format";
                                                                                           }
                                                                                           leaf printable-data-line {
                                                                                             type string;
                                                                                             description "Line of data in printable format";
                                                                                           }
                                                                                         }
                                                                                       }
                                                                                     }
                                                                                     container client-identifier {
                                                                                       description "Identifier that the DHCP client provided for itself when it requested an address assignment";
                                                                                       leaf hex-data-line {
                                                                                         type string;
                                                                                         description "Line of data in hexadecimal format";
                                                                                       }
                                                                                       leaf printable-data-line {
                                                                                         type string;
                                                                                         description "Line of data in printable format";
                                                                                       }
                                                                                     }
                                                                                   }
                                                                                 }
                                                                                 container client-identifier {
                                                                                   description "Identifier that the DHCP client provided for itself when it requested an address assignment";
                                                                                   leaf hex-data-line {
                                                                                     type string;
                                                                                     description "Line of data in hexadecimal format";
                                                                                   }
                                                                                   leaf printable-data-line {
                                                                                     type string;
                                                                                     description "Line of data in printable format";
                                                                                   }
                                                                                 }
                                                                               }
                                                                             }
                                                                             container client-identifier {
                                                                               description "Identifier that the DHCP client provided for itself when it requested an address assignment";
                                                                               leaf hex-data-line {
                                                                                 type string;
                                                                                 description "Line of data in hexadecimal format";
                                                                               }
                                                                               leaf printable-data-line {
                                                                                 type string;
                                                                                 description "Line of data in printable format";
                                                                               }
                                                                             }
                                                                           }
                                                                         }
                                                                         container client-identifier {
                                                                           description "Identifier that the DHCP client provided for itself when it requested an address assignment";
                                                                           leaf hex-data-line {
                                                                             type string;
                                                                             description "Line of data in hexadecimal format";
                                                                           }
                                                                           leaf printable-data-line {
                                                                             type string;
                                                                             description "Line of data in printable format";
                                                                           }
                                                                         }
                                                                       }
                                                                     }
                                                                     container client-identifier {
                                                                       description "Identifier that the DHCP client provided for itself when it requested an address assignment";
                                                                       leaf hex-data-line {
                                                                         type string;
                                                                         description "Line of data in hexadecimal format";
                                                                       }
                                                                       leaf printable-data-line {
                                                                         type string;
                                                                         description "Line of data in printable format";
                                                                       }
                                                                     }
                                                                   }
                                                                 }
                                                                 container client-identifier {
                                                                   description "Identifier that the DHCP client provided for itself when it requested an address assignment";
                                                                   leaf hex-data-line {
                                                                     type string;
                                                                     description "Line of data in hexadecimal format";
                                                                   }
                                                                   leaf printable-data-line {
                                                                     type string;
                                                                     description "Line of data in printable format";
                                                                   }
                                                                 }
                                                               }
                                                             }
                                                             container client-identifier {
                                                               description "Identifier that the DHCP client provided for itself when it requested an address assignment";
                                                               leaf hex-data-line {
                                                                 type string;
                                                                 description "Line of data in hexadecimal format";
                                                               }
                                                               leaf printable-data-line {
                                                                 type string;
                                                                 description "Line of data in printable format";
                                                               }
                                                             }
                                                           }
                                                         }
                                                         container client-identifier {
                                                           description "Identifier that the DHCP client provided for itself when it requested an address assignment";
                                                           leaf hex-data-line {
                                                             type string;
                                                             description "Line of data in hexadecimal format";
                                                           }
                                                           leaf printable-data-line {
                                                             type string;
                                                             description "Line of data in printable format";
                                                           }
                                                         }
                                                       }
                                                     }
                                                     container client-identifier {
                                                       description "Identifier that the DHCP client provided for itself when it requested an address assignment";
                                                       leaf hex-data-line {
                                                         type string;
                                                         description "Line of data in hexadecimal format";
                                                       }
                                                       leaf printable-data-line {
                                                         type string;
                                                         description "Line of data in printable format";
                                                       }
                                                     }
                                                   }
                                                 }
                                                 container client-identifier {
                                                   description "Identifier that the DHCP client provided for itself when it requested an address assignment";
                                                   leaf hex-data-line {
                                                     type string;
                                                     description "Line of data in hexadecimal format";
                                                   }
                                                   leaf printable-data-line {
                                                     type string;
                                                     description "Line of data in printable format";
                                                   }
                                                 }
                                               }
                                             }
                                             container client-identifier {
                                               description "Identifier that the DHCP client provided for itself when it requested an address assignment";
                                               leaf hex-data-line {
                                                 type string;
                                                 description "Line of data in hexadecimal format";
                                               }
                                               leaf printable-data-line {
                                                 type string;
                                                 description "Line of data in printable format";
                                               }
                                             }
                                           }
                                         }
                                         container client-identifier {
                                           description "Identifier that the DHCP client provided for itself when it requested an address assignment";
                                           leaf hex-data-line {
                                             type string;
                                             description "Line of data in hexadecimal format";
                                           }
                                           leaf printable-data-line {
                                             type string;
                                             description "Line of data in printable format";
                                           }
                                         }
                                       }
                                     }
                                     container client-identifier {
                                       description "Identifier that the DHCP client provided for itself when it requested an address assignment";
                                       leaf hex-data-line {
                                         type string;
                                         description "Line of data in hexadecimal format";
                                       }
                                       leaf printable-data-line {
                                         type string;
                                         description "Line of data in printable format";
                                       }
                                     }
                                   }
                                 }
                                 container client-identifier {
                                   description "Identifier that the DHCP client provided for itself when it requested an address assignment";
                                   leaf hex-data-line {
                                     type string;
                                     description "Line of data in hexadecimal format";
                                   }
                                   leaf printable-data-line {
                                     type string;
                                     description "Line of data in printable format";
                                   }
                                 }
                               }
                             }
                             container client-identifier {
                               description "Identifier that the DHCP client provided for itself when it requested an address assignment";
                               leaf hex-data-line {
                                 type string;
                                 description "Line of data in hexadecimal format";
                               }
                               leaf printable-data-line {
                                 type string;
                                 description "Line of data in printable format";
                               }
                             }
                           }
                         }
                         container client-identifier {
                           description "Identifier that the DHCP client provided for itself when it requested an address assignment";
                           leaf hex-data-line {
                             type string;
                             description "Line of data in hexadecimal format";
                           }
                           leaf printable-data-line {
                             type string;
                             description "Line of data in printable format";
                           }
                         }
                       }
                     }
                     container client-identifier {
                       description "Identifier that the DHCP client provided for itself when it requested an address assignment";
                       leaf hex-data-line {
                         type string;
                         description "Line of data in hexadecimal format";
                       }
                       leaf printable-data-line {
                         type string;
                         description "Line of data in printable format";
                       }
                     }
                   }
                 }
                 container client-identifier {
                   description "Identifier that the DHCP client provided for itself when it requested an address assignment";
                   leaf hex-data-line {
                     type string;
                     description "Line of data in hexadecimal format";
                   }
                   leaf printable-data-line {
                     type string;
                     description "Line of data in printable format";
                   }
                 }
               }
             }
             container client-identifier {
               description "Identifier that the DHCP client provided for itself when it requested an address assignment";
               leaf hex-data-line {
                 type string;
                 description "Line of data in hexadecimal format";
               }
               leaf printable-data-line {
                 type string;
                 description "Line of data in printable format";
               }
             }
           }
         }
         container client-identifier {
           description "Identifier that the DHCP client provided for itself when it requested an address assignment";
           leaf hex-data-line {
             type string;
             description "Line of data in hexadecimal format";
           }
           leaf printable-data-line {
             type string;
             description "Line of data in printable format";
           }
         }
       }
     }
   }
   container detail {
     description "Information about the address assigned to each of one or more Dynamic Host Configuration Protocol clients";
     list dhcp-binding {
       description "Information about the address assigned to a Dynamic Host Configuration Protocol client";
       leaf dhcp-lease-binding-type {
         type string;
         description "Type of the address assignment";
       }
       leaf allocated-address {
         type ipaddr;
         description "IPv4 address assigned to the DHCP client";
       }
       leaf mac-address {
         type mac-addr;
         description "Media access control (hardware) address of the DHCP client";
       }
       leaf address-pool-name {
         type string;
         description "Name of the address pool";
       }
       leaf interface-name {
         type string;
         description "Name of the interface via which the DHCP relay process transmitted the address assignment";
       }
       leaf bootp-relay-address {
         type ipaddr;
         description "IP address of the bootstrap protocol server that relayed the address assigned by the DHCP server";
       }
       leaf lease-end-time {
         type string;
         description "Time when the address assignment will expire, in the format YYYY-MM-DD hh:mm:ss TZ (year, month, date, hour in 24-hour format, minute, second, time zone). The value 'never' indicates that the lease does not expire.";
       }
       leaf lease-state {
         type string;
         description "Status of the address assignment";
       }
       container dhcp-option-table {
         description "Information about one or more Dynamic Host Configuration Protocol options that are associated with the address assignment";
         list dhcp-option {
           description "Information about a Dynamic Host Configuration Protocol option that is associated with the address assignment";
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
       container dhcp-lease-information {
         description "Information about an address assignment";
         container dhcp-option-table {
           description "Information about one or more Dynamic Host Configuration Protocol options that are associated with the address assignment";
           list dhcp-option {
             description "Information about a Dynamic Host Configuration Protocol option that is associated with the address assignment";
             leaf dhcp-option-code {
               type int32;
               description "Numeric code assigned to the DHCP option";
             }
             leaf dhcp-option-name {
               type string;
               description "Name of the DHCP option";
             }
             leaf dhcp-option-type {
               type string;
               description "Type of value for the DHCP option (for example, string [word], integer, IP address)";
             }
             leaf dhcp-option-value {
               type string;
               description "Value of the DHCP option";
             }
           }
         }
         container dhcp-lease-information {
           description "Information about an address assignment";
           container dhcp-option-table {
             description "Information about one or more Dynamic Host Configuration Protocol options that are associated with the address assignment";
             list dhcp-option {
               description "Information about a Dynamic Host Configuration Protocol option that is associated with the address assignment";
               leaf dhcp-option-code {
                 type int32;
                 description "Numeric code assigned to the DHCP option";
               }
               leaf dhcp-option-name {
                 type string;
                 description "Name of the DHCP option";
               }
               leaf dhcp-option-type {
                 type string;
                 description "Type of value for the DHCP option (for example, string [word], integer, IP address)";
               }
               leaf dhcp-option-value {
                 type string;
                 description "Value of the DHCP option";
               }
             }
           }
           container dhcp-lease-information {
             description "Information about an address assignment";
             container dhcp-option-table {
               description "Information about one or more Dynamic Host Configuration Protocol options that are associated with the address assignment";
               list dhcp-option {
                 description "Information about a Dynamic Host Configuration Protocol option that is associated with the address assignment";
                 leaf dhcp-option-code {
                   type int32;
                   description "Numeric code assigned to the DHCP option";
                 }
                 leaf dhcp-option-name {
                   type string;
                   description "Name of the DHCP option";
                 }
                 leaf dhcp-option-type {
                   type string;
                   description "Type of value for the DHCP option (for example, string [word], integer, IP address)";
                 }
                 leaf dhcp-option-value {
                   type string;
                   description "Value of the DHCP option";
                 }
               }
             }
             container dhcp-lease-information {
               description "Information about an address assignment";
               container dhcp-option-table {
                 description "Information about one or more Dynamic Host Configuration Protocol options that are associated with the address assignment";
                 list dhcp-option {
                   description "Information about a Dynamic Host Configuration Protocol option that is associated with the address assignment";
                   leaf dhcp-option-code {
                     type int32;
                     description "Numeric code assigned to the DHCP option";
                   }
                   leaf dhcp-option-name {
                     type string;
                     description "Name of the DHCP option";
                   }
                   leaf dhcp-option-type {
                     type string;
                     description "Type of value for the DHCP option (for example, string [word], integer, IP address)";
                   }
                   leaf dhcp-option-value {
                     type string;
                     description "Value of the DHCP option";
                   }
                 }
               }
               container dhcp-lease-information {
                 description "Information about an address assignment";
                 container dhcp-option-table {
                   description "Information about one or more Dynamic Host Configuration Protocol options that are associated with the address assignment";
                   list dhcp-option {
                     description "Information about a Dynamic Host Configuration Protocol option that is associated with the address assignment";
                     leaf dhcp-option-code {
                       type int32;
                       description "Numeric code assigned to the DHCP option";
                     }
                     leaf dhcp-option-name {
                       type string;
                       description "Name of the DHCP option";
                     }
                     leaf dhcp-option-type {
                       type string;
                       description "Type of value for the DHCP option (for example, string [word], integer, IP address)";
                     }
                     leaf dhcp-option-value {
                       type string;
                       description "Value of the DHCP option";
                     }
                   }
                 }
                 container dhcp-lease-information {
                   description "Information about an address assignment";
                   container dhcp-option-table {
                     description "Information about one or more Dynamic Host Configuration Protocol options that are associated with the address assignment";
                     list dhcp-option {
                       description "Information about a Dynamic Host Configuration Protocol option that is associated with the address assignment";
                       leaf dhcp-option-code {
                         type int32;
                         description "Numeric code assigned to the DHCP option";
                       }
                       leaf dhcp-option-name {
                         type string;
                         description "Name of the DHCP option";
                       }
                       leaf dhcp-option-type {
                         type string;
                         description "Type of value for the DHCP option (for example, string [word], integer, IP address)";
                       }
                       leaf dhcp-option-value {
                         type string;
                         description "Value of the DHCP option";
                       }
                     }
                   }
                   container dhcp-lease-information {
                     description "Information about an address assignment";
                     container dhcp-option-table {
                       description "Information about one or more Dynamic Host Configuration Protocol options that are associated with the address assignment";
                       list dhcp-option {
                         description "Information about a Dynamic Host Configuration Protocol option that is associated with the address assignment";
                         leaf dhcp-option-code {
                           type int32;
                           description "Numeric code assigned to the DHCP option";
                         }
                         leaf dhcp-option-name {
                           type string;
                           description "Name of the DHCP option";
                         }
                         leaf dhcp-option-type {
                           type string;
                           description "Type of value for the DHCP option (for example, string [word], integer, IP address)";
                         }
                         leaf dhcp-option-value {
                           type string;
                           description "Value of the DHCP option";
                         }
                       }
                     }
                     container dhcp-lease-information {
                       description "Information about an address assignment";
                       container dhcp-option-table {
                         description "Information about one or more Dynamic Host Configuration Protocol options that are associated with the address assignment";
                         list dhcp-option {
                           description "Information about a Dynamic Host Configuration Protocol option that is associated with the address assignment";
                           leaf dhcp-option-code {
                             type int32;
                             description "Numeric code assigned to the DHCP option";
                           }
                           leaf dhcp-option-name {
                             type string;
                             description "Name of the DHCP option";
                           }
                           leaf dhcp-option-type {
                             type string;
                             description "Type of value for the DHCP option (for example, string [word], integer, IP address)";
                           }
                           leaf dhcp-option-value {
                             type string;
                             description "Value of the DHCP option";
                           }
                         }
                       }
                       container dhcp-lease-information {
                         description "Information about an address assignment";
                         container dhcp-option-table {
                           description "Information about one or more Dynamic Host Configuration Protocol options that are associated with the address assignment";
                           list dhcp-option {
                             description "Information about a Dynamic Host Configuration Protocol option that is associated with the address assignment";
                             leaf dhcp-option-code {
                               type int32;
                               description "Numeric code assigned to the DHCP option";
                             }
                             leaf dhcp-option-name {
                               type string;
                               description "Name of the DHCP option";
                             }
                             leaf dhcp-option-type {
                               type string;
                               description "Type of value for the DHCP option (for example, string [word], integer, IP address)";
                             }
                             leaf dhcp-option-value {
                               type string;
                               description "Value of the DHCP option";
                             }
                           }
                         }
                         container dhcp-lease-information {
                           description "Information about an address assignment";
                           container dhcp-option-table {
                             description "Information about one or more Dynamic Host Configuration Protocol options that are associated with the address assignment";
                             list dhcp-option {
                               description "Information about a Dynamic Host Configuration Protocol option that is associated with the address assignment";
                               leaf dhcp-option-code {
                                 type int32;
                                 description "Numeric code assigned to the DHCP option";
                               }
                               leaf dhcp-option-name {
                                 type string;
                                 description "Name of the DHCP option";
                               }
                               leaf dhcp-option-type {
                                 type string;
                                 description "Type of value for the DHCP option (for example, string [word], integer, IP address)";
                               }
                               leaf dhcp-option-value {
                                 type string;
                                 description "Value of the DHCP option";
                               }
                             }
                           }
                           container dhcp-lease-information {
                             description "Information about an address assignment";
                             container dhcp-option-table {
                               description "Information about one or more Dynamic Host Configuration Protocol options that are associated with the address assignment";
                               list dhcp-option {
                                 description "Information about a Dynamic Host Configuration Protocol option that is associated with the address assignment";
                                 leaf dhcp-option-code {
                                   type int32;
                                   description "Numeric code assigned to the DHCP option";
                                 }
                                 leaf dhcp-option-name {
                                   type string;
                                   description "Name of the DHCP option";
                                 }
                                 leaf dhcp-option-type {
                                   type string;
                                   description "Type of value for the DHCP option (for example, string [word], integer, IP address)";
                                 }
                                 leaf dhcp-option-value {
                                   type string;
                                   description "Value of the DHCP option";
                                 }
                               }
                             }
                             container dhcp-lease-information {
                               description "Information about an address assignment";
                               container dhcp-option-table {
                                 description "Information about one or more Dynamic Host Configuration Protocol options that are associated with the address assignment";
                                 list dhcp-option {
                                   description "Information about a Dynamic Host Configuration Protocol option that is associated with the address assignment";
                                   leaf dhcp-option-code {
                                     type int32;
                                     description "Numeric code assigned to the DHCP option";
                                   }
                                   leaf dhcp-option-name {
                                     type string;
                                     description "Name of the DHCP option";
                                   }
                                   leaf dhcp-option-type {
                                     type string;
                                     description "Type of value for the DHCP option (for example, string [word], integer, IP address)";
                                   }
                                   leaf dhcp-option-value {
                                     type string;
                                     description "Value of the DHCP option";
                                   }
                                 }
                               }
                               container dhcp-lease-information {
                                 description "Information about an address assignment";
                                 container dhcp-option-table {
                                   description "Information about one or more Dynamic Host Configuration Protocol options that are associated with the address assignment";
                                   list dhcp-option {
                                     description "Information about a Dynamic Host Configuration Protocol option that is associated with the address assignment";
                                     leaf dhcp-option-code {
                                       type int32;
                                       description "Numeric code assigned to the DHCP option";
                                     }
                                     leaf dhcp-option-name {
                                       type string;
                                       description "Name of the DHCP option";
                                     }
                                     leaf dhcp-option-type {
                                       type string;
                                       description "Type of value for the DHCP option (for example, string [word], integer, IP address)";
                                     }
                                     leaf dhcp-option-value {
                                       type string;
                                       description "Value of the DHCP option";
                                     }
                                   }
                                 }
                                 container dhcp-lease-information {
                                   description "Information about an address assignment";
                                   container dhcp-option-table {
                                     description "Information about one or more Dynamic Host Configuration Protocol options that are associated with the address assignment";
                                     list dhcp-option {
                                       description "Information about a Dynamic Host Configuration Protocol option that is associated with the address assignment";
                                       leaf dhcp-option-code {
                                         type int32;
                                         description "Numeric code assigned to the DHCP option";
                                       }
                                       leaf dhcp-option-name {
                                         type string;
                                         description "Name of the DHCP option";
                                       }
                                       leaf dhcp-option-type {
                                         type string;
                                         description "Type of value for the DHCP option (for example, string [word], integer, IP address)";
                                       }
                                       leaf dhcp-option-value {
                                         type string;
                                         description "Value of the DHCP option";
                                       }
                                     }
                                   }
                                   container dhcp-lease-information {
                                     description "Information about an address assignment";
                                     container dhcp-option-table {
                                       description "Information about one or more Dynamic Host Configuration Protocol options that are associated with the address assignment";
                                       list dhcp-option {
                                         description "Information about a Dynamic Host Configuration Protocol option that is associated with the address assignment";
                                         leaf dhcp-option-code {
                                           type int32;
                                           description "Numeric code assigned to the DHCP option";
                                         }
                                         leaf dhcp-option-name {
                                           type string;
                                           description "Name of the DHCP option";
                                         }
                                         leaf dhcp-option-type {
                                           type string;
                                           description "Type of value for the DHCP option (for example, string [word], integer, IP address)";
                                         }
                                         leaf dhcp-option-value {
                                           type string;
                                           description "Value of the DHCP option";
                                         }
                                       }
                                     }
                                     container dhcp-lease-information {
                                       description "Information about an address assignment";
                                       container dhcp-option-table {
                                         description "Information about one or more Dynamic Host Configuration Protocol options that are associated with the address assignment";
                                         list dhcp-option {
                                           description "Information about a Dynamic Host Configuration Protocol option that is associated with the address assignment";
                                           leaf dhcp-option-code {
                                             type int32;
                                             description "Numeric code assigned to the DHCP option";
                                           }
                                           leaf dhcp-option-name {
                                             type string;
                                             description "Name of the DHCP option";
                                           }
                                           leaf dhcp-option-type {
                                             type string;
                                             description "Type of value for the DHCP option (for example, string [word], integer, IP address)";
                                           }
                                           leaf dhcp-option-value {
                                             type string;
                                             description "Value of the DHCP option";
                                           }
                                         }
                                       }
                                       container dhcp-lease-information {
                                         description "Information about an address assignment";
                                         container dhcp-option-table {
                                           description "Information about one or more Dynamic Host Configuration Protocol options that are associated with the address assignment";
                                           list dhcp-option {
                                             description "Information about a Dynamic Host Configuration Protocol option that is associated with the address assignment";
                                             leaf dhcp-option-code {
                                               type int32;
                                               description "Numeric code assigned to the DHCP option";
                                             }
                                             leaf dhcp-option-name {
                                               type string;
                                               description "Name of the DHCP option";
                                             }
                                             leaf dhcp-option-type {
                                               type string;
                                               description "Type of value for the DHCP option (for example, string [word], integer, IP address)";
                                             }
                                             leaf dhcp-option-value {
                                               type string;
                                               description "Value of the DHCP option";
                                             }
                                           }
                                         }
                                         container dhcp-lease-information {
                                           description "Information about an address assignment";
                                           container dhcp-option-table {
                                             description "Information about one or more Dynamic Host Configuration Protocol options that are associated with the address assignment";
                                             list dhcp-option {
                                               description "Information about a Dynamic Host Configuration Protocol option that is associated with the address assignment";
                                               leaf dhcp-option-code {
                                                 type int32;
                                                 description "Numeric code assigned to the DHCP option";
                                               }
                                               leaf dhcp-option-name {
                                                 type string;
                                                 description "Name of the DHCP option";
                                               }
                                               leaf dhcp-option-type {
                                                 type string;
                                                 description "Type of value for the DHCP option (for example, string [word], integer, IP address)";
                                               }
                                               leaf dhcp-option-value {
                                                 type string;
                                                 description "Value of the DHCP option";
                                               }
                                             }
                                           }
                                           container dhcp-lease-information {
                                             description "Information about an address assignment";
                                             container dhcp-option-table {
                                               description "Information about one or more Dynamic Host Configuration Protocol options that are associated with the address assignment";
                                               list dhcp-option {
                                                 description "Information about a Dynamic Host Configuration Protocol option that is associated with the address assignment";
                                                 leaf dhcp-option-code {
                                                   type int32;
                                                   description "Numeric code assigned to the DHCP option";
                                                 }
                                                 leaf dhcp-option-name {
                                                   type string;
                                                   description "Name of the DHCP option";
                                                 }
                                                 leaf dhcp-option-type {
                                                   type string;
                                                   description "Type of value for the DHCP option (for example, string [word], integer, IP address)";
                                                 }
                                                 leaf dhcp-option-value {
                                                   type string;
                                                   description "Value of the DHCP option";
                                                 }
                                               }
                                             }
                                             container dhcp-lease-information {
                                               description "Information about an address assignment";
                                               container dhcp-option-table {
                                                 description "Information about one or more Dynamic Host Configuration Protocol options that are associated with the address assignment";
                                                 list dhcp-option {
                                                   description "Information about a Dynamic Host Configuration Protocol option that is associated with the address assignment";
                                                   leaf dhcp-option-code {
                                                     type int32;
                                                     description "Numeric code assigned to the DHCP option";
                                                   }
                                                   leaf dhcp-option-name {
                                                     type string;
                                                     description "Name of the DHCP option";
                                                   }
                                                   leaf dhcp-option-type {
                                                     type string;
                                                     description "Type of value for the DHCP option (for example, string [word], integer, IP address)";
                                                   }
                                                   leaf dhcp-option-value {
                                                     type string;
                                                     description "Value of the DHCP option";
                                                   }
                                                 }
                                               }
                                               container dhcp-lease-information {
                                                 description "Information about an address assignment";
                                                 container dhcp-option-table {
                                                   description "Information about one or more Dynamic Host Configuration Protocol options that are associated with the address assignment";
                                                   list dhcp-option {
                                                     description "Information about a Dynamic Host Configuration Protocol option that is associated with the address assignment";
                                                     leaf dhcp-option-code {
                                                       type int32;
                                                       description "Numeric code assigned to the DHCP option";
                                                     }
                                                     leaf dhcp-option-name {
                                                       type string;
                                                       description "Name of the DHCP option";
                                                     }
                                                     leaf dhcp-option-type {
                                                       type string;
                                                       description "Type of value for the DHCP option (for example, string [word], integer, IP address)";
                                                     }
                                                     leaf dhcp-option-value {
                                                       type string;
                                                       description "Value of the DHCP option";
                                                     }
                                                   }
                                                 }
                                                 container dhcp-lease-information {
                                                   description "Information about an address assignment";
                                                   container dhcp-option-table {
                                                     description "Information about one or more Dynamic Host Configuration Protocol options that are associated with the address assignment";
                                                     list dhcp-option {
                                                       description "Information about a Dynamic Host Configuration Protocol option that is associated with the address assignment";
                                                       leaf dhcp-option-code {
                                                         type int32;
                                                         description "Numeric code assigned to the DHCP option";
                                                       }
                                                       leaf dhcp-option-name {
                                                         type string;
                                                         description "Name of the DHCP option";
                                                       }
                                                       leaf dhcp-option-type {
                                                         type string;
                                                         description "Type of value for the DHCP option (for example, string [word], integer, IP address)";
                                                       }
                                                       leaf dhcp-option-value {
                                                         type string;
                                                         description "Value of the DHCP option";
                                                       }
                                                     }
                                                   }
                                                   container dhcp-lease-information {
                                                     description "Information about an address assignment";
                                                     container dhcp-option-table {
                                                       description "Information about one or more Dynamic Host Configuration Protocol options that are associated with the address assignment";
                                                       list dhcp-option {
                                                         description "Information about a Dynamic Host Configuration Protocol option that is associated with the address assignment";
                                                         leaf dhcp-option-code {
                                                           type int32;
                                                           description "Numeric code assigned to the DHCP option";
                                                         }
                                                         leaf dhcp-option-name {
                                                           type string;
                                                           description "Name of the DHCP option";
                                                         }
                                                         leaf dhcp-option-type {
                                                           type string;
                                                           description "Type of value for the DHCP option (for example, string [word], integer, IP address)";
                                                         }
                                                         leaf dhcp-option-value {
                                                           type string;
                                                           description "Value of the DHCP option";
                                                         }
                                                       }
                                                     }
                                                     container dhcp-lease-information {
                                                       description "Information about an address assignment";
                                                       container dhcp-option-table {
                                                         description "Information about one or more Dynamic Host Configuration Protocol options that are associated with the address assignment";
                                                         list dhcp-option {
                                                           description "Information about a Dynamic Host Configuration Protocol option that is associated with the address assignment";
                                                           leaf dhcp-option-code {
                                                             type int32;
                                                             description "Numeric code assigned to the DHCP option";
                                                           }
                                                           leaf dhcp-option-name {
                                                             type string;
                                                             description "Name of the DHCP option";
                                                           }
                                                           leaf dhcp-option-type {
                                                             type string;
                                                             description "Type of value for the DHCP option (for example, string [word], integer, IP address)";
                                                           }
                                                           leaf dhcp-option-value {
                                                             type string;
                                                             description "Value of the DHCP option";
                                                           }
                                                         }
                                                       }
                                                       container dhcp-lease-information {
                                                         description "Information about an address assignment";
                                                         container dhcp-option-table {
                                                           description "Information about one or more Dynamic Host Configuration Protocol options that are associated with the address assignment";
                                                           list dhcp-option {
                                                             description "Information about a Dynamic Host Configuration Protocol option that is associated with the address assignment";
                                                             leaf dhcp-option-code {
                                                               type int32;
                                                               description "Numeric code assigned to the DHCP option";
                                                             }
                                                             leaf dhcp-option-name {
                                                               type string;
                                                               description "Name of the DHCP option";
                                                             }
                                                             leaf dhcp-option-type {
                                                               type string;
                                                               description "Type of value for the DHCP option (for example, string [word], integer, IP address)";
                                                             }
                                                             leaf dhcp-option-value {
                                                               type string;
                                                               description "Value of the DHCP option";
                                                             }
                                                           }
                                                         }
                                                         container dhcp-lease-information {
                                                           description "Information about an address assignment";
                                                           container dhcp-option-table {
                                                             description "Information about one or more Dynamic Host Configuration Protocol options that are associated with the address assignment";
                                                             list dhcp-option {
                                                               description "Information about a Dynamic Host Configuration Protocol option that is associated with the address assignment";
                                                               leaf dhcp-option-code {
                                                                 type int32;
                                                                 description "Numeric code assigned to the DHCP option";
                                                               }
                                                               leaf dhcp-option-name {
                                                                 type string;
                                                                 description "Name of the DHCP option";
                                                               }
                                                               leaf dhcp-option-type {
                                                                 type string;
                                                                 description "Type of value for the DHCP option (for example, string [word], integer, IP address)";
                                                               }
                                                               leaf dhcp-option-value {
                                                                 type string;
                                                                 description "Value of the DHCP option";
                                                               }
                                                             }
                                                           }
                                                           container dhcp-lease-information {
                                                             description "Information about an address assignment";
                                                             container dhcp-option-table {
                                                               description "Information about one or more Dynamic Host Configuration Protocol options that are associated with the address assignment";
                                                               list dhcp-option {
                                                                 description "Information about a Dynamic Host Configuration Protocol option that is associated with the address assignment";
                                                                 leaf dhcp-option-code {
                                                                   type int32;
                                                                   description "Numeric code assigned to the DHCP option";
                                                                 }
                                                                 leaf dhcp-option-name {
                                                                   type string;
                                                                   description "Name of the DHCP option";
                                                                 }
                                                                 leaf dhcp-option-type {
                                                                   type string;
                                                                   description "Type of value for the DHCP option (for example, string [word], integer, IP address)";
                                                                 }
                                                                 leaf dhcp-option-value {
                                                                   type string;
                                                                   description "Value of the DHCP option";
                                                                 }
                                                               }
                                                             }
                                                             container dhcp-lease-information {
                                                               description "Information about an address assignment";
                                                               container dhcp-option-table {
                                                                 description "Information about one or more Dynamic Host Configuration Protocol options that are associated with the address assignment";
                                                                 list dhcp-option {
                                                                   description "Information about a Dynamic Host Configuration Protocol option that is associated with the address assignment";
                                                                   leaf dhcp-option-code {
                                                                     type int32;
                                                                     description "Numeric code assigned to the DHCP option";
                                                                   }
                                                                   leaf dhcp-option-name {
                                                                     type string;
                                                                     description "Name of the DHCP option";
                                                                   }
                                                                   leaf dhcp-option-type {
                                                                     type string;
                                                                     description "Type of value for the DHCP option (for example, string [word], integer, IP address)";
                                                                   }
                                                                   leaf dhcp-option-value {
                                                                     type string;
                                                                     description "Value of the DHCP option";
                                                                   }
                                                                 }
                                                               }
                                                               container dhcp-lease-information {
                                                                 description "Information about an address assignment";
                                                                 container dhcp-option-table {
                                                                   description "Information about one or more Dynamic Host Configuration Protocol options that are associated with the address assignment";
                                                                   list dhcp-option {
                                                                     description "Information about a Dynamic Host Configuration Protocol option that is associated with the address assignment";
                                                                     leaf dhcp-option-code {
                                                                       type int32;
                                                                       description "Numeric code assigned to the DHCP option";
                                                                     }
                                                                     leaf dhcp-option-name {
                                                                       type string;
                                                                       description "Name of the DHCP option";
                                                                     }
                                                                     leaf dhcp-option-type {
                                                                       type string;
                                                                       description "Type of value for the DHCP option (for example, string [word], integer, IP address)";
                                                                     }
                                                                     leaf dhcp-option-value {
                                                                       type string;
                                                                       description "Value of the DHCP option";
                                                                     }
                                                                   }
                                                                 }
                                                                 container dhcp-lease-information {
                                                                   description "Information about an address assignment";
                                                                   container dhcp-option-table {
                                                                     description "Information about one or more Dynamic Host Configuration Protocol options that are associated with the address assignment";
                                                                     list dhcp-option {
                                                                       description "Information about a Dynamic Host Configuration Protocol option that is associated with the address assignment";
                                                                       leaf dhcp-option-code {
                                                                         type int32;
                                                                         description "Numeric code assigned to the DHCP option";
                                                                       }
                                                                       leaf dhcp-option-name {
                                                                         type string;
                                                                         description "Name of the DHCP option";
                                                                       }
                                                                       leaf dhcp-option-type {
                                                                         type string;
                                                                         description "Type of value for the DHCP option (for example, string [word], integer, IP address)";
                                                                       }
                                                                       leaf dhcp-option-value {
                                                                         type string;
                                                                         description "Value of the DHCP option";
                                                                       }
                                                                     }
                                                                   }
                                                                   container dhcp-lease-information {
                                                                     description "Information about an address assignment";
                                                                     container dhcp-option-table {
                                                                       description "Information about one or more Dynamic Host Configuration Protocol options that are associated with the address assignment";
                                                                       list dhcp-option {
                                                                         description "Information about a Dynamic Host Configuration Protocol option that is associated with the address assignment";
                                                                         leaf dhcp-option-code {
                                                                           type int32;
                                                                           description "Numeric code assigned to the DHCP option";
                                                                         }
                                                                         leaf dhcp-option-name {
                                                                           type string;
                                                                           description "Name of the DHCP option";
                                                                         }
                                                                         leaf dhcp-option-type {
                                                                           type string;
                                                                           description "Type of value for the DHCP option (for example, string [word], integer, IP address)";
                                                                         }
                                                                         leaf dhcp-option-value {
                                                                           type string;
                                                                           description "Value of the DHCP option";
                                                                         }
                                                                       }
                                                                     }
                                                                     container dhcp-lease-information {
                                                                       description "Information about an address assignment";
                                                                       container dhcp-option-table {
                                                                         description "Information about one or more Dynamic Host Configuration Protocol options that are associated with the address assignment";
                                                                         list dhcp-option {
                                                                           description "Information about a Dynamic Host Configuration Protocol option that is associated with the address assignment";
                                                                           leaf dhcp-option-code {
                                                                             type int32;
                                                                             description "Numeric code assigned to the DHCP option";
                                                                           }
                                                                           leaf dhcp-option-name {
                                                                             type string;
                                                                             description "Name of the DHCP option";
                                                                           }
                                                                           leaf dhcp-option-type {
                                                                             type string;
                                                                             description "Type of value for the DHCP option (for example, string [word], integer, IP address)";
                                                                           }
                                                                           leaf dhcp-option-value {
                                                                             type string;
                                                                             description "Value of the DHCP option";
                                                                           }
                                                                         }
                                                                       }
                                                                       container dhcp-lease-information {
                                                                         description "Information about an address assignment";
                                                                         container dhcp-option-table {
                                                                           description "Information about one or more Dynamic Host Configuration Protocol options that are associated with the address assignment";
                                                                           list dhcp-option {
                                                                             description "Information about a Dynamic Host Configuration Protocol option that is associated with the address assignment";
                                                                             leaf dhcp-option-code {
                                                                               type int32;
                                                                               description "Numeric code assigned to the DHCP option";
                                                                             }
                                                                             leaf dhcp-option-name {
                                                                               type string;
                                                                               description "Name of the DHCP option";
                                                                             }
                                                                             leaf dhcp-option-type {
                                                                               type string;
                                                                               description "Type of value for the DHCP option (for example, string [word], integer, IP address)";
                                                                             }
                                                                             leaf dhcp-option-value {
                                                                               type string;
                                                                               description "Value of the DHCP option";
                                                                             }
                                                                           }
                                                                         }
                                                                         container dhcp-lease-information {
                                                                           description "Information about an address assignment";
                                                                           container dhcp-option-table {
                                                                             description "Information about one or more Dynamic Host Configuration Protocol options that are associated with the address assignment";
                                                                             list dhcp-option {
                                                                               description "Information about a Dynamic Host Configuration Protocol option that is associated with the address assignment";
                                                                               leaf dhcp-option-code {
                                                                                 type int32;
                                                                                 description "Numeric code assigned to the DHCP option";
                                                                               }
                                                                               leaf dhcp-option-name {
                                                                                 type string;
                                                                                 description "Name of the DHCP option";
                                                                               }
                                                                               leaf dhcp-option-type {
                                                                                 type string;
                                                                                 description "Type of value for the DHCP option (for example, string [word], integer, IP address)";
                                                                               }
                                                                               leaf dhcp-option-value {
                                                                                 type string;
                                                                                 description "Value of the DHCP option";
                                                                               }
                                                                             }
                                                                           }
                                                                           container dhcp-lease-information {
                                                                             description "Information about an address assignment";
                                                                             container dhcp-option-table {
                                                                               description "Information about one or more Dynamic Host Configuration Protocol options that are associated with the address assignment";
                                                                               list dhcp-option {
                                                                                 description "Information about a Dynamic Host Configuration Protocol option that is associated with the address assignment";
                                                                                 leaf dhcp-option-code {
                                                                                   type int32;
                                                                                   description "Numeric code assigned to the DHCP option";
                                                                                 }
                                                                                 leaf dhcp-option-name {
                                                                                   type string;
                                                                                   description "Name of the DHCP option";
                                                                                 }
                                                                                 leaf dhcp-option-type {
                                                                                   type string;
                                                                                   description "Type of value for the DHCP option (for example, string [word], integer, IP address)";
                                                                                 }
                                                                                 leaf dhcp-option-value {
                                                                                   type string;
                                                                                   description "Value of the DHCP option";
                                                                                 }
                                                                               }
                                                                             }
                                                                             container dhcp-lease-information {
                                                                               description "Information about an address assignment";
                                                                               container dhcp-option-table {
                                                                                 description "Information about one or more Dynamic Host Configuration Protocol options that are associated with the address assignment";
                                                                                 list dhcp-option {
                                                                                   description "Information about a Dynamic Host Configuration Protocol option that is associated with the address assignment";
                                                                                   leaf dhcp-option-code {
                                                                                     type int32;
                                                                                     description "Numeric code assigned to the DHCP option";
                                                                                   }
                                                                                   leaf dhcp-option-name {
                                                                                     type string;
                                                                                     description "Name of the DHCP option";
                                                                                   }
                                                                                   leaf dhcp-option-type {
                                                                                     type string;
                                                                                     description "Type of value for the DHCP option (for example, string [word], integer, IP address)";
                                                                                   }
                                                                                   leaf dhcp-option-value {
                                                                                     type string;
                                                                                     description "Value of the DHCP option";
                                                                                   }
                                                                                 }
                                                                               }
                                                                               container dhcp-lease-information {
                                                                                 description "Information about an address assignment";
                                                                                 container dhcp-option-table {
                                                                                   description "Information about one or more Dynamic Host Configuration Protocol options that are associated with the address assignment";
                                                                                   list dhcp-option {
                                                                                     description "Information about a Dynamic Host Configuration Protocol option that is associated with the address assignment";
                                                                                     leaf dhcp-option-code {
                                                                                       type int32;
                                                                                       description "Numeric code assigned to the DHCP option";
                                                                                     }
                                                                                     leaf dhcp-option-name {
                                                                                       type string;
                                                                                       description "Name of the DHCP option";
                                                                                     }
                                                                                     leaf dhcp-option-type {
                                                                                       type string;
                                                                                       description "Type of value for the DHCP option (for example, string [word], integer, IP address)";
                                                                                     }
                                                                                     leaf dhcp-option-value {
                                                                                       type string;
                                                                                       description "Value of the DHCP option";
                                                                                     }
                                                                                   }
                                                                                 }
                                                                                 container dhcp-lease-information {
                                                                                   description "Information about an address assignment";
                                                                                   container dhcp-option-table {
                                                                                     description "Information about one or more Dynamic Host Configuration Protocol options that are associated with the address assignment";
                                                                                     list dhcp-option {
                                                                                       description "Information about a Dynamic Host Configuration Protocol option that is associated with the address assignment";
                                                                                       leaf dhcp-option-code {
                                                                                         type int32;
                                                                                         description "Numeric code assigned to the DHCP option";
                                                                                       }
                                                                                       leaf dhcp-option-name {
                                                                                         type string;
                                                                                         description "Name of the DHCP option";
                                                                                       }
                                                                                       leaf dhcp-option-type {
                                                                                         type string;
                                                                                         description "Type of value for the DHCP option (for example, string [word], integer, IP address)";
                                                                                       }
                                                                                       leaf dhcp-option-value {
                                                                                         type string;
                                                                                         description "Value of the DHCP option";
                                                                                       }
                                                                                     }
                                                                                   }
                                                                                   container dhcp-lease-information {
                                                                                     description "Information about an address assignment";
                                                                                     container dhcp-option-table {
                                                                                       description "Information about one or more Dynamic Host Configuration Protocol options that are associated with the address assignment";
                                                                                       list dhcp-option {
                                                                                         description "Information about a Dynamic Host Configuration Protocol option that is associated with the address assignment";
                                                                                         leaf dhcp-option-code {
                                                                                           type int32;
                                                                                           description "Numeric code assigned to the DHCP option";
                                                                                         }
                                                                                         leaf dhcp-option-name {
                                                                                           type string;
                                                                                           description "Name of the DHCP option";
                                                                                         }
                                                                                         leaf dhcp-option-type {
                                                                                           type string;
                                                                                           description "Type of value for the DHCP option (for example, string [word], integer, IP address)";
                                                                                         }
                                                                                         leaf dhcp-option-value {
                                                                                           type string;
                                                                                           description "Value of the DHCP option";
                                                                                         }
                                                                                       }
                                                                                     }
                                                                                     container dhcp-lease-information {
                                                                                       description "Information about an address assignment";
                                                                                       container dhcp-option-table {
                                                                                         description "Information about one or more Dynamic Host Configuration Protocol options that are associated with the address assignment";
                                                                                         list dhcp-option {
                                                                                           description "Information about a Dynamic Host Configuration Protocol option that is associated with the address assignment";
                                                                                           leaf dhcp-option-code {
                                                                                             type int32;
                                                                                             description "Numeric code assigned to the DHCP option";
                                                                                           }
                                                                                           leaf dhcp-option-name {
                                                                                             type string;
                                                                                             description "Name of the DHCP option";
                                                                                           }
                                                                                           leaf dhcp-option-type {
                                                                                             type string;
                                                                                             description "Type of value for the DHCP option (for example, string [word], integer, IP address)";
                                                                                           }
                                                                                           leaf dhcp-option-value {
                                                                                             type string;
                                                                                             description "Value of the DHCP option";
                                                                                           }
                                                                                         }
                                                                                       }
                                                                                       container dhcp-lease-information {
                                                                                         description "Information about an address assignment";
                                                                                         container dhcp-option-table {
                                                                                           description "Information about one or more Dynamic Host Configuration Protocol options that are associated with the address assignment";
                                                                                           list dhcp-option {
                                                                                             description "Information about a Dynamic Host Configuration Protocol option that is associated with the address assignment";
                                                                                             leaf dhcp-option-code {
                                                                                               type int32;
                                                                                               description "Numeric code assigned to the DHCP option";
                                                                                             }
                                                                                             leaf dhcp-option-name {
                                                                                               type string;
                                                                                               description "Name of the DHCP option";
                                                                                             }
                                                                                             leaf dhcp-option-type {
                                                                                               type string;
                                                                                               description "Type of value for the DHCP option (for example, string [word], integer, IP address)";
                                                                                             }
                                                                                             leaf dhcp-option-value {
                                                                                               type string;
                                                                                               description "Value of the DHCP option";
                                                                                             }
                                                                                           }
                                                                                         }
                                                                                         container dhcp-lease-information {
                                                                                           description "Information about an address assignment";
                                                                                           container dhcp-option-table {
                                                                                             description "Information about one or more Dynamic Host Configuration Protocol options that are associated with the address assignment";
                                                                                             list dhcp-option {
                                                                                               description "Information about a Dynamic Host Configuration Protocol option that is associated with the address assignment";
                                                                                               leaf dhcp-option-code {
                                                                                                 type int32;
                                                                                                 description "Numeric code assigned to the DHCP option";
                                                                                               }
                                                                                               leaf dhcp-option-name {
                                                                                                 type string;
                                                                                                 description "Name of the DHCP option";
                                                                                               }
                                                                                               leaf dhcp-option-type {
                                                                                                 type string;
                                                                                                 description "Type of value for the DHCP option (for example, string [word], integer, IP address)";
                                                                                               }
                                                                                               leaf dhcp-option-value {
                                                                                                 type string;
                                                                                                 description "Value of the DHCP option";
                                                                                               }
                                                                                             }
                                                                                           }
                                                                                           container dhcp-lease-information {
                                                                                             description "Information about an address assignment";
                                                                                             container dhcp-option-table {
                                                                                               description "Information about one or more Dynamic Host Configuration Protocol options that are associated with the address assignment";
                                                                                               list dhcp-option {
                                                                                                 description "Information about a Dynamic Host Configuration Protocol option that is associated with the address assignment";
                                                                                                 leaf dhcp-option-code {
                                                                                                   type int32;
                                                                                                   description "Numeric code assigned to the DHCP option";
                                                                                                 }
                                                                                                 leaf dhcp-option-name {
                                                                                                   type string;
                                                                                                   description "Name of the DHCP option";
                                                                                                 }
                                                                                                 leaf dhcp-option-type {
                                                                                                   type string;
                                                                                                   description "Type of value for the DHCP option (for example, string [word], integer, IP address)";
                                                                                                 }
                                                                                                 leaf dhcp-option-value {
                                                                                                   type string;
                                                                                                   description "Value of the DHCP option";
                                                                                                 }
                                                                                               }
                                                                                             }
                                                                                             container dhcp-lease-information {
                                                                                               description "Information about an address assignment";
                                                                                               container dhcp-option-table {
                                                                                                 description "Information about one or more Dynamic Host Configuration Protocol options that are associated with the address assignment";
                                                                                                 list dhcp-option {
                                                                                                   description "Information about a Dynamic Host Configuration Protocol option that is associated with the address assignment";
                                                                                                   leaf dhcp-option-code {
                                                                                                     type int32;
                                                                                                     description "Numeric code assigned to the DHCP option";
                                                                                                   }
                                                                                                   leaf dhcp-option-name {
                                                                                                     type string;
                                                                                                     description "Name of the DHCP option";
                                                                                                   }
                                                                                                   leaf dhcp-option-type {
                                                                                                     type string;
                                                                                                     description "Type of value for the DHCP option (for example, string [word], integer, IP address)";
                                                                                                   }
                                                                                                   leaf dhcp-option-value {
                                                                                                     type string;
                                                                                                     description "Value of the DHCP option";
                                                                                                   }
                                                                                                 }
                                                                                               }
                                                                                               container dhcp-lease-information {
                                                                                                 description "Information about an address assignment";
                                                                                                 container dhcp-option-table {
                                                                                                   description "Information about one or more Dynamic Host Configuration Protocol options that are associated with the address assignment";
                                                                                                   list dhcp-option {
                                                                                                     description "Information about a Dynamic Host Configuration Protocol option that is associated with the address assignment";
                                                                                                     leaf dhcp-option-code {
                                                                                                       type int32;
                                                                                                       description "Numeric code assigned to the DHCP option";
                                                                                                     }
                                                                                                     leaf dhcp-option-name {
                                                                                                       type string;
                                                                                                       description "Name of the DHCP option";
                                                                                                     }
                                                                                                     leaf dhcp-option-type {
                                                                                                       type string;
                                                                                                       description "Type of value for the DHCP option (for example, string [word], integer, IP address)";
                                                                                                     }
                                                                                                     leaf dhcp-option-value {
                                                                                                       type string;
                                                                                                       description "Value of the DHCP option";
                                                                                                     }
                                                                                                   }
                                                                                                 }
                                                                                                 container dhcp-lease-information {
                                                                                                   description "Information about an address assignment";
                                                                                                   container dhcp-option-table {
                                                                                                     description "Information about one or more Dynamic Host Configuration Protocol options that are associated with the address assignment";
                                                                                                     list dhcp-option {
                                                                                                       description "Information about a Dynamic Host Configuration Protocol option that is associated with the address assignment";
                                                                                                       leaf dhcp-option-code {
                                                                                                         type int32;
                                                                                                         description "Numeric code assigned to the DHCP option";
                                                                                                       }
                                                                                                       leaf dhcp-option-name {
                                                                                                         type string;
                                                                                                         description "Name of the DHCP option";
                                                                                                       }
                                                                                                       leaf dhcp-option-type {
                                                                                                         type string;
                                                                                                         description "Type of value for the DHCP option (for example, string [word], integer, IP address)";
                                                                                                       }
                                                                                                       leaf dhcp-option-value {
                                                                                                         type string;
                                                                                                         description "Value of the DHCP option";
                                                                                                       }
                                                                                                     }
                                                                                                   }
                                                                                                   container dhcp-lease-information {
                                                                                                     description "Information about an address assignment";
                                                                                                     container dhcp-option-table {
                                                                                                       description "Information about one or more Dynamic Host Configuration Protocol options that are associated with the address assignment";
                                                                                                       list dhcp-option {
                                                                                                         description "Information about a Dynamic Host Configuration Protocol option that is associated with the address assignment";
                                                                                                         leaf dhcp-option-code {
                                                                                                           type int32;
                                                                                                           description "Numeric code assigned to the DHCP option";
                                                                                                         }
                                                                                                         leaf dhcp-option-name {
                                                                                                           type string;
                                                                                                           description "Name of the DHCP option";
                                                                                                         }
                                                                                                         leaf dhcp-option-type {
                                                                                                           type string;
                                                                                                           description "Type of value for the DHCP option (for example, string [word], integer, IP address)";
                                                                                                         }
                                                                                                         leaf dhcp-option-value {
                                                                                                           type string;
                                                                                                           description "Value of the DHCP option";
                                                                                                         }
                                                                                                       }
                                                                                                     }
                                                                                                     container dhcp-lease-information {
                                                                                                       description "Information about an address assignment";
                                                                                                       container dhcp-option-table {
                                                                                                         description "Information about one or more Dynamic Host Configuration Protocol options that are associated with the address assignment";
                                                                                                         list dhcp-option {
                                                                                                           description "Information about a Dynamic Host Configuration Protocol option that is associated with the address assignment";
                                                                                                           leaf dhcp-option-code {
                                                                                                             type int32;
                                                                                                             description "Numeric code assigned to the DHCP option";
                                                                                                           }
                                                                                                           leaf dhcp-option-name {
                                                                                                             type string;
                                                                                                             description "Name of the DHCP option";
                                                                                                           }
                                                                                                           leaf dhcp-option-type {
                                                                                                             type string;
                                                                                                             description "Type of value for the DHCP option (for example, string [word], integer, IP address)";
                                                                                                           }
                                                                                                           leaf dhcp-option-value {
                                                                                                             type string;
                                                                                                             description "Value of the DHCP option";
                                                                                                           }
                                                                                                         }
                                                                                                       }
                                                                                                       container dhcp-lease-information {
                                                                                                         description "Information about an address assignment";
                                                                                                         container dhcp-option-table {
                                                                                                           description "Information about one or more Dynamic Host Configuration Protocol options that are associated with the address assignment";
                                                                                                           list dhcp-option {
                                                                                                             description "Information about a Dynamic Host Configuration Protocol option that is associated with the address assignment";
                                                                                                             leaf dhcp-option-code {
                                                                                                               type int32;
                                                                                                               description "Numeric code assigned to the DHCP option";
                                                                                                             }
                                                                                                             leaf dhcp-option-name {
                                                                                                               type string;
                                                                                                               description "Name of the DHCP option";
                                                                                                             }
                                                                                                             leaf dhcp-option-type {
                                                                                                               type string;
                                                                                                               description "Type of value for the DHCP option (for example, string [word], integer, IP address)";
                                                                                                             }
                                                                                                             leaf dhcp-option-value {
                                                                                                               type string;
                                                                                                               description "Value of the DHCP option";
                                                                                                             }
                                                                                                           }
                                                                                                         }
                                                                                                         container dhcp-lease-information {
                                                                                                           description "Information about an address assignment";
                                                                                                           container dhcp-option-table {
                                                                                                             description "Information about one or more Dynamic Host Configuration Protocol options that are associated with the address assignment";
                                                                                                             list dhcp-option {
                                                                                                               description "Information about a Dynamic Host Configuration Protocol option that is associated with the address assignment";
                                                                                                               leaf dhcp-option-code {
                                                                                                                 type int32;
                                                                                                                 description "Numeric code assigned to the DHCP option";
                                                                                                               }
                                                                                                               leaf dhcp-option-name {
                                                                                                                 type string;
                                                                                                                 description "Name of the DHCP option";
                                                                                                               }
                                                                                                               leaf dhcp-option-type {
                                                                                                                 type string;
                                                                                                                 description "Type of value for the DHCP option (for example, string [word], integer, IP address)";
                                                                                                               }
                                                                                                               leaf dhcp-option-value {
                                                                                                                 type string;
                                                                                                                 description "Value of the DHCP option";
                                                                                                               }
                                                                                                             }
                                                                                                           }
                                                                                                           container dhcp-lease-information {
                                                                                                             description "Information about an address assignment";
                                                                                                             container dhcp-option-table {
                                                                                                               description "Information about one or more Dynamic Host Configuration Protocol options that are associated with the address assignment";
                                                                                                               list dhcp-option {
                                                                                                                 description "Information about a Dynamic Host Configuration Protocol option that is associated with the address assignment";
                                                                                                                 leaf dhcp-option-code {
                                                                                                                   type int32;
                                                                                                                   description "Numeric code assigned to the DHCP option";
                                                                                                                 }
                                                                                                                 leaf dhcp-option-name {
                                                                                                                   type string;
                                                                                                                   description "Name of the DHCP option";
                                                                                                                 }
                                                                                                                 leaf dhcp-option-type {
                                                                                                                   type string;
                                                                                                                   description "Type of value for the DHCP option (for example, string [word], integer, IP address)";
                                                                                                                 }
                                                                                                                 leaf dhcp-option-value {
                                                                                                                   type string;
                                                                                                                   description "Value of the DHCP option";
                                                                                                                 }
                                                                                                               }
                                                                                                             }
                                                                                                             container dhcp-lease-information {
                                                                                                               description "Information about an address assignment";
                                                                                                               container dhcp-option-table {
                                                                                                                 description "Information about one or more Dynamic Host Configuration Protocol options that are associated with the address assignment";
                                                                                                                 list dhcp-option {
                                                                                                                   description "Information about a Dynamic Host Configuration Protocol option that is associated with the address assignment";
                                                                                                                   leaf dhcp-option-code {
                                                                                                                     type int32;
                                                                                                                     description "Numeric code assigned to the DHCP option";
                                                                                                                   }
                                                                                                                   leaf dhcp-option-name {
                                                                                                                     type string;
                                                                                                                     description "Name of the DHCP option";
                                                                                                                   }
                                                                                                                   leaf dhcp-option-type {
                                                                                                                     type string;
                                                                                                                     description "Type of value for the DHCP option (for example, string [word], integer, IP address)";
                                                                                                                   }
                                                                                                                   leaf dhcp-option-value {
                                                                                                                     type string;
                                                                                                                     description "Value of the DHCP option";
                                                                                                                   }
                                                                                                                 }
                                                                                                               }
                                                                                                               container dhcp-lease-information {
                                                                                                                 description "Information about an address assignment";
                                                                                                                 container dhcp-option-table {
                                                                                                                   description "Information about one or more Dynamic Host Configuration Protocol options that are associated with the address assignment";
                                                                                                                   list dhcp-option {
                                                                                                                     description "Information about a Dynamic Host Configuration Protocol option that is associated with the address assignment";
                                                                                                                     leaf dhcp-option-code {
                                                                                                                       type int32;
                                                                                                                       description "Numeric code assigned to the DHCP option";
                                                                                                                     }
                                                                                                                     leaf dhcp-option-name {
                                                                                                                       type string;
                                                                                                                       description "Name of the DHCP option";
                                                                                                                     }
                                                                                                                     leaf dhcp-option-type {
                                                                                                                       type string;
                                                                                                                       description "Type of value for the DHCP option (for example, string [word], integer, IP address)";
                                                                                                                     }
                                                                                                                     leaf dhcp-option-value {
                                                                                                                       type string;
                                                                                                                       description "Value of the DHCP option";
                                                                                                                     }
                                                                                                                   }
                                                                                                                 }
                                                                                                                 container dhcp-lease-information {
                                                                                                                   description "Information about an address assignment";
                                                                                                                   container dhcp-option-table {
                                                                                                                     description "Information about one or more Dynamic Host Configuration Protocol options that are associated with the address assignment";
                                                                                                                     list dhcp-option {
                                                                                                                       description "Information about a Dynamic Host Configuration Protocol option that is associated with the address assignment";
                                                                                                                       leaf dhcp-option-code {
                                                                                                                         type int32;
                                                                                                                         description "Numeric code assigned to the DHCP option";
                                                                                                                       }
                                                                                                                       leaf dhcp-option-name {
                                                                                                                         type string;
                                                                                                                         description "Name of the DHCP option";
                                                                                                                       }
                                                                                                                       leaf dhcp-option-type {
                                                                                                                         type string;
                                                                                                                         description "Type of value for the DHCP option (for example, string [word], integer, IP address)";
                                                                                                                       }
                                                                                                                       leaf dhcp-option-value {
                                                                                                                         type string;
                                                                                                                         description "Value of the DHCP option";
                                                                                                                       }
                                                                                                                     }
                                                                                                                   }
                                                                                                                   container dhcp-lease-information {
                                                                                                                     description "Information about an address assignment";
                                                                                                                     container dhcp-option-table {
                                                                                                                       description "Information about one or more Dynamic Host Configuration Protocol options that are associated with the address assignment";
                                                                                                                       list dhcp-option {
                                                                                                                         description "Information about a Dynamic Host Configuration Protocol option that is associated with the address assignment";
                                                                                                                         leaf dhcp-option-code {
                                                                                                                           type int32;
                                                                                                                           description "Numeric code assigned to the DHCP option";
                                                                                                                         }
                                                                                                                         leaf dhcp-option-name {
                                                                                                                           type string;
                                                                                                                           description "Name of the DHCP option";
                                                                                                                         }
                                                                                                                         leaf dhcp-option-type {
                                                                                                                           type string;
                                                                                                                           description "Type of value for the DHCP option (for example, string [word], integer, IP address)";
                                                                                                                         }
                                                                                                                         leaf dhcp-option-value {
                                                                                                                           type string;
                                                                                                                           description "Value of the DHCP option";
                                                                                                                         }
                                                                                                                       }
                                                                                                                     }
                                                                                                                     container dhcp-lease-information {
                                                                                                                       description "Information about an address assignment";
                                                                                                                       container dhcp-option-table {
                                                                                                                         description "Information about one or more Dynamic Host Configuration Protocol options that are associated with the address assignment";
                                                                                                                         list dhcp-option {
                                                                                                                           description "Information about a Dynamic Host Configuration Protocol option that is associated with the address assignment";
                                                                                                                           leaf dhcp-option-code {
                                                                                                                             type int32;
                                                                                                                             description "Numeric code assigned to the DHCP option";
                                                                                                                           }
                                                                                                                           leaf dhcp-option-name {
                                                                                                                             type string;
                                                                                                                             description "Name of the DHCP option";
                                                                                                                           }
                                                                                                                           leaf dhcp-option-type {
                                                                                                                             type string;
                                                                                                                             description "Type of value for the DHCP option (for example, string [word], integer, IP address)";
                                                                                                                           }
                                                                                                                           leaf dhcp-option-value {
                                                                                                                             type string;
                                                                                                                             description "Value of the DHCP option";
                                                                                                                           }
                                                                                                                         }
                                                                                                                       }
                                                                                                                       container dhcp-lease-information {
                                                                                                                         description "Information about an address assignment";
                                                                                                                         container dhcp-option-table {
                                                                                                                           description "Information about one or more Dynamic Host Configuration Protocol options that are associated with the address assignment";
                                                                                                                           list dhcp-option {
                                                                                                                             description "Information about a Dynamic Host Configuration Protocol option that is associated with the address assignment";
                                                                                                                             leaf dhcp-option-code {
                                                                                                                               type int32;
                                                                                                                               description "Numeric code assigned to the DHCP option";
                                                                                                                             }
                                                                                                                             leaf dhcp-option-name {
                                                                                                                               type string;
                                                                                                                               description "Name of the DHCP option";
                                                                                                                             }
                                                                                                                             leaf dhcp-option-type {
                                                                                                                               type string;
                                                                                                                               description "Type of value for the DHCP option (for example, string [word], integer, IP address)";
                                                                                                                             }
                                                                                                                             leaf dhcp-option-value {
                                                                                                                               type string;
                                                                                                                               description "Value of the DHCP option";
                                                                                                                             }
                                                                                                                           }
                                                                                                                         }
                                                                                                                         container dhcp-lease-information {
                                                                                                                           description "Information about an address assignment";
                                                                                                                           container dhcp-option-table {
                                                                                                                             description "Information about one or more Dynamic Host Configuration Protocol options that are associated with the address assignment";
                                                                                                                             list dhcp-option {
                                                                                                                               description "Information about a Dynamic Host Configuration Protocol option that is associated with the address assignment";
                                                                                                                               leaf dhcp-option-code {
                                                                                                                                 type int32;
                                                                                                                                 description "Numeric code assigned to the DHCP option";
                                                                                                                               }
                                                                                                                               leaf dhcp-option-name {
                                                                                                                                 type string;
                                                                                                                                 description "Name of the DHCP option";
                                                                                                                               }
                                                                                                                               leaf dhcp-option-type {
                                                                                                                                 type string;
                                                                                                                                 description "Type of value for the DHCP option (for example, string [word], integer, IP address)";
                                                                                                                               }
                                                                                                                               leaf dhcp-option-value {
                                                                                                                                 type string;
                                                                                                                                 description "Value of the DHCP option";
                                                                                                                               }
                                                                                                                             }
                                                                                                                           }
                                                                                                                           container dhcp-lease-information {
                                                                                                                             description "Information about an address assignment";
                                                                                                                             container dhcp-option-table {
                                                                                                                               description "Information about one or more Dynamic Host Configuration Protocol options that are associated with the address assignment";
                                                                                                                               list dhcp-option {
                                                                                                                                 description "Information about a Dynamic Host Configuration Protocol option that is associated with the address assignment";
                                                                                                                                 leaf dhcp-option-code {
                                                                                                                                   type int32;
                                                                                                                                   description "Numeric code assigned to the DHCP option";
                                                                                                                                 }
                                                                                                                                 leaf dhcp-option-name {
                                                                                                                                   type string;
                                                                                                                                   description "Name of the DHCP option";
                                                                                                                                 }
                                                                                                                                 leaf dhcp-option-type {
                                                                                                                                   type string;
                                                                                                                                   description "Type of value for the DHCP option (for example, string [word], integer, IP address)";
                                                                                                                                 }
                                                                                                                                 leaf dhcp-option-value {
                                                                                                                                   type string;
                                                                                                                                   description "Value of the DHCP option";
                                                                                                                                 }
                                                                                                                               }
                                                                                                                             }
                                                                                                                             container dhcp-lease-information {
                                                                                                                               description "Information about an address assignment";
                                                                                                                               container dhcp-option-table {
                                                                                                                                 description "Information about one or more Dynamic Host Configuration Protocol options that are associated with the address assignment";
                                                                                                                                 list dhcp-option {
                                                                                                                                   description "Information about a Dynamic Host Configuration Protocol option that is associated with the address assignment";
                                                                                                                                   leaf dhcp-option-code {
                                                                                                                                     type int32;
                                                                                                                                     description "Numeric code assigned to the DHCP option";
                                                                                                                                   }
                                                                                                                                   leaf dhcp-option-name {
                                                                                                                                     type string;
                                                                                                                                     description "Name of the DHCP option";
                                                                                                                                   }
                                                                                                                                   leaf dhcp-option-type {
                                                                                                                                     type string;
                                                                                                                                     description "Type of value for the DHCP option (for example, string [word], integer, IP address)";
                                                                                                                                   }
                                                                                                                                   leaf dhcp-option-value {
                                                                                                                                     type string;
                                                                                                                                     description "Value of the DHCP option";
                                                                                                                                   }
                                                                                                                                 }
                                                                                                                               }
                                                                                                                               container dhcp-lease-information {
                                                                                                                                 description "Information about an address assignment";
                                                                                                                                 container dhcp-option-table {
                                                                                                                                   description "Information about one or more Dynamic Host Configuration Protocol options that are associated with the address assignment";
                                                                                                                                   list dhcp-option {
                                                                                                                                     description "Information about a Dynamic Host Configuration Protocol option that is associated with the address assignment";
                                                                                                                                     leaf dhcp-option-code {
                                                                                                                                       type int32;
                                                                                                                                       description "Numeric code assigned to the DHCP option";
                                                                                                                                     }
                                                                                                                                     leaf dhcp-option-name {
                                                                                                                                       type string;
                                                                                                                                       description "Name of the DHCP option";
                                                                                                                                     }
                                                                                                                                     leaf dhcp-option-type {
                                                                                                                                       type string;
                                                                                                                                       description "Type of value for the DHCP option (for example, string [word], integer, IP address)";
                                                                                                                                     }
                                                                                                                                     leaf dhcp-option-value {
                                                                                                                                       type string;
                                                                                                                                       description "Value of the DHCP option";
                                                                                                                                     }
                                                                                                                                   }
                                                                                                                                 }
                                                                                                                                 container dhcp-lease-information {
                                                                                                                                   description "Information about an address assignment";
                                                                                                                                   container dhcp-option-table {
                                                                                                                                     description "Information about one or more Dynamic Host Configuration Protocol options that are associated with the address assignment";
                                                                                                                                     list dhcp-option {
                                                                                                                                       description "Information about a Dynamic Host Configuration Protocol option that is associated with the address assignment";
                                                                                                                                       leaf dhcp-option-code {
                                                                                                                                         type int32;
                                                                                                                                         description "Numeric code assigned to the DHCP option";
                                                                                                                                       }
                                                                                                                                       leaf dhcp-option-name {
                                                                                                                                         type string;
                                                                                                                                         description "Name of the DHCP option";
                                                                                                                                       }
                                                                                                                                       leaf dhcp-option-type {
                                                                                                                                         type string;
                                                                                                                                         description "Type of value for the DHCP option (for example, string [word], integer, IP address)";
                                                                                                                                       }
                                                                                                                                       leaf dhcp-option-value {
                                                                                                                                         type string;
                                                                                                                                         description "Value of the DHCP option";
                                                                                                                                       }
                                                                                                                                     }
                                                                                                                                   }
                                                                                                                                   container dhcp-lease-information {
                                                                                                                                     description "Information about an address assignment";
                                                                                                                                     container dhcp-option-table {
                                                                                                                                       description "Information about one or more Dynamic Host Configuration Protocol options that are associated with the address assignment";
                                                                                                                                       list dhcp-option {
                                                                                                                                         description "Information about a Dynamic Host Configuration Protocol option that is associated with the address assignment";
                                                                                                                                         leaf dhcp-option-code {
                                                                                                                                           type int32;
                                                                                                                                           description "Numeric code assigned to the DHCP option";
                                                                                                                                         }
                                                                                                                                         leaf dhcp-option-name {
                                                                                                                                           type string;
                                                                                                                                           description "Name of the DHCP option";
                                                                                                                                         }
                                                                                                                                         leaf dhcp-option-type {
                                                                                                                                           type string;
                                                                                                                                           description "Type of value for the DHCP option (for example, string [word], integer, IP address)";
                                                                                                                                         }
                                                                                                                                         leaf dhcp-option-value {
                                                                                                                                           type string;
                                                                                                                                           description "Value of the DHCP option";
                                                                                                                                         }
                                                                                                                                       }
                                                                                                                                     }
                                                                                                                                     container dhcp-lease-information {
                                                                                                                                       description "Information about an address assignment";
                                                                                                                                       container dhcp-option-table {
                                                                                                                                         description "Information about one or more Dynamic Host Configuration Protocol options that are associated with the address assignment";
                                                                                                                                         list dhcp-option {
                                                                                                                                           description "Information about a Dynamic Host Configuration Protocol option that is associated with the address assignment";
                                                                                                                                           leaf dhcp-option-code {
                                                                                                                                             type int32;
                                                                                                                                             description "Numeric code assigned to the DHCP option";
                                                                                                                                           }
                                                                                                                                           leaf dhcp-option-name {
                                                                                                                                             type string;
                                                                                                                                             description "Name of the DHCP option";
                                                                                                                                           }
                                                                                                                                           leaf dhcp-option-type {
                                                                                                                                             type string;
                                                                                                                                             description "Type of value for the DHCP option (for example, string [word], integer, IP address)";
                                                                                                                                           }
                                                                                                                                           leaf dhcp-option-value {
                                                                                                                                             type string;
                                                                                                                                             description "Value of the DHCP option";
                                                                                                                                           }
                                                                                                                                         }
                                                                                                                                       }
                                                                                                                                       container dhcp-lease-information {
                                                                                                                                         description "Information about an address assignment";
                                                                                                                                         container dhcp-option-table {
                                                                                                                                           description "Information about one or more Dynamic Host Configuration Protocol options that are associated with the address assignment";
                                                                                                                                           list dhcp-option {
                                                                                                                                             description "Information about a Dynamic Host Configuration Protocol option that is associated with the address assignment";
                                                                                                                                             leaf dhcp-option-code {
                                                                                                                                               type int32;
                                                                                                                                               description "Numeric code assigned to the DHCP option";
                                                                                                                                             }
                                                                                                                                             leaf dhcp-option-name {
                                                                                                                                               type string;
                                                                                                                                               description "Name of the DHCP option";
                                                                                                                                             }
                                                                                                                                             leaf dhcp-option-type {
                                                                                                                                               type string;
                                                                                                                                               description "Type of value for the DHCP option (for example, string [word], integer, IP address)";
                                                                                                                                             }
                                                                                                                                             leaf dhcp-option-value {
                                                                                                                                               type string;
                                                                                                                                               description "Value of the DHCP option";
                                                                                                                                             }
                                                                                                                                           }
                                                                                                                                         }
                                                                                                                                         container dhcp-lease-information {
                                                                                                                                           description "Information about an address assignment";
                                                                                                                                           container dhcp-option-table {
                                                                                                                                             description "Information about one or more Dynamic Host Configuration Protocol options that are associated with the address assignment";
                                                                                                                                             list dhcp-option {
                                                                                                                                               description "Information about a Dynamic Host Configuration Protocol option that is associated with the address assignment";
                                                                                                                                               leaf dhcp-option-code {
                                                                                                                                                 type int32;
                                                                                                                                                 description "Numeric code assigned to the DHCP option";
                                                                                                                                               }
                                                                                                                                               leaf dhcp-option-name {
                                                                                                                                                 type string;
                                                                                                                                                 description "Name of the DHCP option";
                                                                                                                                               }
                                                                                                                                               leaf dhcp-option-type {
                                                                                                                                                 type string;
                                                                                                                                                 description "Type of value for the DHCP option (for example, string [word], integer, IP address)";
                                                                                                                                               }
                                                                                                                                               leaf dhcp-option-value {
                                                                                                                                                 type string;
                                                                                                                                                 description "Value of the DHCP option";
                                                                                                                                               }
                                                                                                                                             }
                                                                                                                                           }
                                                                                                                                           container dhcp-lease-information {
                                                                                                                                             description "Information about an address assignment";
                                                                                                                                             container dhcp-option-table {
                                                                                                                                               description "Information about one or more Dynamic Host Configuration Protocol options that are associated with the address assignment";
                                                                                                                                               list dhcp-option {
                                                                                                                                                 description "Information about a Dynamic Host Configuration Protocol option that is associated with the address assignment";
                                                                                                                                                 leaf dhcp-option-code {
                                                                                                                                                   type int32;
                                                                                                                                                   description "Numeric code assigned to the DHCP option";
                                                                                                                                                 }
                                                                                                                                                 leaf dhcp-option-name {
                                                                                                                                                   type string;
                                                                                                                                                   description "Name of the DHCP option";
                                                                                                                                                 }
                                                                                                                                                 leaf dhcp-option-type {
                                                                                                                                                   type string;
                                                                                                                                                   description "Type of value for the DHCP option (for example, string [word], integer, IP address)";
                                                                                                                                                 }
                                                                                                                                                 leaf dhcp-option-value {
                                                                                                                                                   type string;
                                                                                                                                                   description "Value of the DHCP option";
                                                                                                                                                 }
                                                                                                                                               }
                                                                                                                                             }
                                                                                                                                             container dhcp-lease-information {
                                                                                                                                               description "Information about an address assignment";
                                                                                                                                               container dhcp-option-table {
                                                                                                                                                 description "Information about one or more Dynamic Host Configuration Protocol options that are associated with the address assignment";
                                                                                                                                                 list dhcp-option {
                                                                                                                                                   description "Information about a Dynamic Host Configuration Protocol option that is associated with the address assignment";
                                                                                                                                                   leaf dhcp-option-code {
                                                                                                                                                     type int32;
                                                                                                                                                     description "Numeric code assigned to the DHCP option";
                                                                                                                                                   }
                                                                                                                                                   leaf dhcp-option-name {
                                                                                                                                                     type string;
                                                                                                                                                     description "Name of the DHCP option";
                                                                                                                                                   }
                                                                                                                                                   leaf dhcp-option-type {
                                                                                                                                                     type string;
                                                                                                                                                     description "Type of value for the DHCP option (for example, string [word], integer, IP address)";
                                                                                                                                                   }
                                                                                                                                                   leaf dhcp-option-value {
                                                                                                                                                     type string;
                                                                                                                                                     description "Value of the DHCP option";
                                                                                                                                                   }
                                                                                                                                                 }
                                                                                                                                               }
                                                                                                                                               container dhcp-lease-information {
                                                                                                                                                 description "Information about an address assignment";
                                                                                                                                                 container dhcp-option-table {
                                                                                                                                                   description "Information about one or more Dynamic Host Configuration Protocol options that are associated with the address assignment";
                                                                                                                                                   list dhcp-option {
                                                                                                                                                     description "Information about a Dynamic Host Configuration Protocol option that is associated with the address assignment";
                                                                                                                                                     leaf dhcp-option-code {
                                                                                                                                                       type int32;
                                                                                                                                                       description "Numeric code assigned to the DHCP option";
                                                                                                                                                     }
                                                                                                                                                     leaf dhcp-option-name {
                                                                                                                                                       type string;
                                                                                                                                                       description "Name of the DHCP option";
                                                                                                                                                     }
                                                                                                                                                     leaf dhcp-option-type {
                                                                                                                                                       type string;
                                                                                                                                                       description "Type of value for the DHCP option (for example, string [word], integer, IP address)";
                                                                                                                                                     }
                                                                                                                                                     leaf dhcp-option-value {
                                                                                                                                                       type string;
                                                                                                                                                       description "Value of the DHCP option";
                                                                                                                                                     }
                                                                                                                                                   }
                                                                                                                                                 }
                                                                                                                                                 container dhcp-lease-information {
                                                                                                                                                   description "Information about an address assignment";
                                                                                                                                                   container dhcp-option-table {
                                                                                                                                                     description "Information about one or more Dynamic Host Configuration Protocol options that are associated with the address assignment";
                                                                                                                                                     list dhcp-option {
                                                                                                                                                       description "Information about a Dynamic Host Configuration Protocol option that is associated with the address assignment";
                                                                                                                                                       leaf dhcp-option-code {
                                                                                                                                                         type int32;
                                                                                                                                                         description "Numeric code assigned to the DHCP option";
                                                                                                                                                       }
                                                                                                                                                       leaf dhcp-option-name {
                                                                                                                                                         type string;
                                                                                                                                                         description "Name of the DHCP option";
                                                                                                                                                       }
                                                                                                                                                       leaf dhcp-option-type {
                                                                                                                                                         type string;
                                                                                                                                                         description "Type of value for the DHCP option (for example, string [word], integer, IP address)";
                                                                                                                                                       }
                                                                                                                                                       leaf dhcp-option-value {
                                                                                                                                                         type string;
                                                                                                                                                         description "Value of the DHCP option";
                                                                                                                                                       }
                                                                                                                                                     }
                                                                                                                                                   }
                                                                                                                                                   container dhcp-lease-information {
                                                                                                                                                     description "Information about an address assignment";
                                                                                                                                                     container dhcp-option-table {
                                                                                                                                                       description "Information about one or more Dynamic Host Configuration Protocol options that are associated with the address assignment";
                                                                                                                                                       list dhcp-option {
                                                                                                                                                         description "Information about a Dynamic Host Configuration Protocol option that is associated with the address assignment";
                                                                                                                                                         leaf dhcp-option-code {
                                                                                                                                                           type int32;
                                                                                                                                                           description "Numeric code assigned to the DHCP option";
                                                                                                                                                         }
                                                                                                                                                         leaf dhcp-option-name {
                                                                                                                                                           type string;
                                                                                                                                                           description "Name of the DHCP option";
                                                                                                                                                         }
                                                                                                                                                         leaf dhcp-option-type {
                                                                                                                                                           type string;
                                                                                                                                                           description "Type of value for the DHCP option (for example, string [word], integer, IP address)";
                                                                                                                                                         }
                                                                                                                                                         leaf dhcp-option-value {
                                                                                                                                                           type string;
                                                                                                                                                           description "Value of the DHCP option";
                                                                                                                                                         }
                                                                                                                                                       }
                                                                                                                                                     }
                                                                                                                                                     container dhcp-lease-information {
                                                                                                                                                       description "Information about an address assignment";
                                                                                                                                                       container dhcp-option-table {
                                                                                                                                                         description "Information about one or more Dynamic Host Configuration Protocol options that are associated with the address assignment";
                                                                                                                                                         list dhcp-option {
                                                                                                                                                           description "Information about a Dynamic Host Configuration Protocol option that is associated with the address assignment";
                                                                                                                                                           leaf dhcp-option-code {
                                                                                                                                                             type int32;
                                                                                                                                                             description "Numeric code assigned to the DHCP option";
                                                                                                                                                           }
                                                                                                                                                           leaf dhcp-option-name {
                                                                                                                                                             type string;
                                                                                                                                                             description "Name of the DHCP option";
                                                                                                                                                           }
                                                                                                                                                           leaf dhcp-option-type {
                                                                                                                                                             type string;
                                                                                                                                                             description "Type of value for the DHCP option (for example, string [word], integer, IP address)";
                                                                                                                                                           }
                                                                                                                                                           leaf dhcp-option-value {
                                                                                                                                                             type string;
                                                                                                                                                             description "Value of the DHCP option";
                                                                                                                                                           }
                                                                                                                                                         }
                                                                                                                                                       }
                                                                                                                                                       container dhcp-lease-information {
                                                                                                                                                         description "Information about an address assignment";
                                                                                                                                                         container dhcp-option-table {
                                                                                                                                                           description "Information about one or more Dynamic Host Configuration Protocol options that are associated with the address assignment";
                                                                                                                                                           list dhcp-option {
                                                                                                                                                             description "Information about a Dynamic Host Configuration Protocol option that is associated with the address assignment";
                                                                                                                                                             leaf dhcp-option-code {
                                                                                                                                                               type int32;
                                                                                                                                                               description "Numeric code assigned to the DHCP option";
                                                                                                                                                             }
                                                                                                                                                             leaf dhcp-option-name {
                                                                                                                                                               type string;
                                                                                                                                                               description "Name of the DHCP option";
                                                                                                                                                             }
                                                                                                                                                             leaf dhcp-option-type {
                                                                                                                                                               type string;
                                                                                                                                                               description "Type of value for the DHCP option (for example, string [word], integer, IP address)";
                                                                                                                                                             }
                                                                                                                                                             leaf dhcp-option-value {
                                                                                                                                                               type string;
                                                                                                                                                               description "Value of the DHCP option";
                                                                                                                                                             }
                                                                                                                                                           }
                                                                                                                                                         }
                                                                                                                                                         container dhcp-lease-information {
                                                                                                                                                           description "Information about an address assignment";
                                                                                                                                                           container dhcp-option-table {
                                                                                                                                                             description "Information about one or more Dynamic Host Configuration Protocol options that are associated with the address assignment";
                                                                                                                                                             list dhcp-option {
                                                                                                                                                               description "Information about a Dynamic Host Configuration Protocol option that is associated with the address assignment";
                                                                                                                                                               leaf dhcp-option-code {
                                                                                                                                                                 type int32;
                                                                                                                                                                 description "Numeric code assigned to the DHCP option";
                                                                                                                                                               }
                                                                                                                                                               leaf dhcp-option-name {
                                                                                                                                                                 type string;
                                                                                                                                                                 description "Name of the DHCP option";
                                                                                                                                                               }
                                                                                                                                                               leaf dhcp-option-type {
                                                                                                                                                                 type string;
                                                                                                                                                                 description "Type of value for the DHCP option (for example, string [word], integer, IP address)";
                                                                                                                                                               }
                                                                                                                                                               leaf dhcp-option-value {
                                                                                                                                                                 type string;
                                                                                                                                                                 description "Value of the DHCP option";
                                                                                                                                                               }
                                                                                                                                                             }
                                                                                                                                                           }
                                                                                                                                                           container dhcp-lease-information {
                                                                                                                                                             description "Information about an address assignment";
                                                                                                                                                             container dhcp-option-table {
                                                                                                                                                               description "Information about one or more Dynamic Host Configuration Protocol options that are associated with the address assignment";
                                                                                                                                                               list dhcp-option {
                                                                                                                                                                 description "Information about a Dynamic Host Configuration Protocol option that is associated with the address assignment";
                                                                                                                                                                 leaf dhcp-option-code {
                                                                                                                                                                   type int32;
                                                                                                                                                                   description "Numeric code assigned to the DHCP option";
                                                                                                                                                                 }
                                                                                                                                                                 leaf dhcp-option-name {
                                                                                                                                                                   type string;
                                                                                                                                                                   description "Name of the DHCP option";
                                                                                                                                                                 }
                                                                                                                                                                 leaf dhcp-option-type {
                                                                                                                                                                   type string;
                                                                                                                                                                   description "Type of value for the DHCP option (for example, string [word], integer, IP address)";
                                                                                                                                                                 }
                                                                                                                                                                 leaf dhcp-option-value {
                                                                                                                                                                   type string;
                                                                                                                                                                   description "Value of the DHCP option";
                                                                                                                                                                 }
                                                                                                                                                               }
                                                                                                                                                             }
                                                                                                                                                             container dhcp-lease-information {
                                                                                                                                                               description "Information about an address assignment";
                                                                                                                                                               container dhcp-option-table {
                                                                                                                                                                 description "Information about one or more Dynamic Host Configuration Protocol options that are associated with the address assignment";
                                                                                                                                                                 list dhcp-option {
                                                                                                                                                                   description "Information about a Dynamic Host Configuration Protocol option that is associated with the address assignment";
                                                                                                                                                                   leaf dhcp-option-code {
                                                                                                                                                                     type int32;
                                                                                                                                                                     description "Numeric code assigned to the DHCP option";
                                                                                                                                                                   }
                                                                                                                                                                   leaf dhcp-option-name {
                                                                                                                                                                     type string;
                                                                                                                                                                     description "Name of the DHCP option";
                                                                                                                                                                   }
                                                                                                                                                                   leaf dhcp-option-type {
                                                                                                                                                                     type string;
                                                                                                                                                                     description "Type of value for the DHCP option (for example, string [word], integer, IP address)";
                                                                                                                                                                   }
                                                                                                                                                                   leaf dhcp-option-value {
                                                                                                                                                                     type string;
                                                                                                                                                                     description "Value of the DHCP option";
                                                                                                                                                                   }
                                                                                                                                                                 }
                                                                                                                                                               }
                                                                                                                                                               container dhcp-lease-information {
                                                                                                                                                                 description "Information about an address assignment";
                                                                                                                                                                 container dhcp-option-table {
                                                                                                                                                                   description "Information about one or more Dynamic Host Configuration Protocol options that are associated with the address assignment";
                                                                                                                                                                   list dhcp-option {
                                                                                                                                                                     description "Information about a Dynamic Host Configuration Protocol option that is associated with the address assignment";
                                                                                                                                                                     leaf dhcp-option-code {
                                                                                                                                                                       type int32;
                                                                                                                                                                       description "Numeric code assigned to the DHCP option";
                                                                                                                                                                     }
                                                                                                                                                                     leaf dhcp-option-name {
                                                                                                                                                                       type string;
                                                                                                                                                                       description "Name of the DHCP option";
                                                                                                                                                                     }
                                                                                                                                                                     leaf dhcp-option-type {
                                                                                                                                                                       type string;
                                                                                                                                                                       description "Type of value for the DHCP option (for example, string [word], integer, IP address)";
                                                                                                                                                                     }
                                                                                                                                                                     leaf dhcp-option-value {
                                                                                                                                                                       type string;
                                                                                                                                                                       description "Value of the DHCP option";
                                                                                                                                                                     }
                                                                                                                                                                   }
                                                                                                                                                                 }
                                                                                                                                                                 container dhcp-lease-information {
                                                                                                                                                                   description "Information about an address assignment";
                                                                                                                                                                   container dhcp-option-table {
                                                                                                                                                                     description "Information about one or more Dynamic Host Configuration Protocol options that are associated with the address assignment";
                                                                                                                                                                     list dhcp-option {
                                                                                                                                                                       description "Information about a Dynamic Host Configuration Protocol option that is associated with the address assignment";
                                                                                                                                                                       leaf dhcp-option-code {
                                                                                                                                                                         type int32;
                                                                                                                                                                         description "Numeric code assigned to the DHCP option";
                                                                                                                                                                       }
                                                                                                                                                                       leaf dhcp-option-name {
                                                                                                                                                                         type string;
                                                                                                                                                                         description "Name of the DHCP option";
                                                                                                                                                                       }
                                                                                                                                                                       leaf dhcp-option-type {
                                                                                                                                                                         type string;
                                                                                                                                                                         description "Type of value for the DHCP option (for example, string [word], integer, IP address)";
                                                                                                                                                                       }
                                                                                                                                                                       leaf dhcp-option-value {
                                                                                                                                                                         type string;
                                                                                                                                                                         description "Value of the DHCP option";
                                                                                                                                                                       }
                                                                                                                                                                     }
                                                                                                                                                                   }
                                                                                                                                                                   container dhcp-lease-information {
                                                                                                                                                                     description "Information about an address assignment";
                                                                                                                                                                     container dhcp-option-table {
                                                                                                                                                                       description "Information about one or more Dynamic Host Configuration Protocol options that are associated with the address assignment";
                                                                                                                                                                       list dhcp-option {
                                                                                                                                                                         description "Information about a Dynamic Host Configuration Protocol option that is associated with the address assignment";
                                                                                                                                                                         leaf dhcp-option-code {
                                                                                                                                                                           type int32;
                                                                                                                                                                           description "Numeric code assigned to the DHCP option";
                                                                                                                                                                         }
                                                                                                                                                                         leaf dhcp-option-name {
                                                                                                                                                                           type string;
                                                                                                                                                                           description "Name of the DHCP option";
                                                                                                                                                                         }
                                                                                                                                                                         leaf dhcp-option-type {
                                                                                                                                                                           type string;
                                                                                                                                                                           description "Type of value for the DHCP option (for example, string [word], integer, IP address)";
                                                                                                                                                                         }
                                                                                                                                                                         leaf dhcp-option-value {
                                                                                                                                                                           type string;
                                                                                                                                                                           description "Value of the DHCP option";
                                                                                                                                                                         }
                                                                                                                                                                       }
                                                                                                                                                                     }
                                                                                                                                                                     container dhcp-lease-information {
                                                                                                                                                                       description "Information about an address assignment";
                                                                                                                                                                       container dhcp-option-table {
                                                                                                                                                                         description "Information about one or more Dynamic Host Configuration Protocol options that are associated with the address assignment";
                                                                                                                                                                         list dhcp-option {
                                                                                                                                                                           description "Information about a Dynamic Host Configuration Protocol option that is associated with the address assignment";
                                                                                                                                                                           leaf dhcp-option-code {
                                                                                                                                                                             type int32;
                                                                                                                                                                             description "Numeric code assigned to the DHCP option";
                                                                                                                                                                           }
                                                                                                                                                                           leaf dhcp-option-name {
                                                                                                                                                                             type string;
                                                                                                                                                                             description "Name of the DHCP option";
                                                                                                                                                                           }
                                                                                                                                                                           leaf dhcp-option-type {
                                                                                                                                                                             type string;
                                                                                                                                                                             description "Type of value for the DHCP option (for example, string [word], integer, IP address)";
                                                                                                                                                                           }
                                                                                                                                                                           leaf dhcp-option-value {
                                                                                                                                                                             type string;
                                                                                                                                                                             description "Value of the DHCP option";
                                                                                                                                                                           }
                                                                                                                                                                         }
                                                                                                                                                                       }
                                                                                                                                                                       container dhcp-lease-information {
                                                                                                                                                                         description "Information about an address assignment";
                                                                                                                                                                         container dhcp-option-table {
                                                                                                                                                                           description "Information about one or more Dynamic Host Configuration Protocol options that are associated with the address assignment";
                                                                                                                                                                           list dhcp-option {
                                                                                                                                                                             description "Information about a Dynamic Host Configuration Protocol option that is associated with the address assignment";
                                                                                                                                                                             leaf dhcp-option-code {
                                                                                                                                                                               type int32;
                                                                                                                                                                               description "Numeric code assigned to the DHCP option";
                                                                                                                                                                             }
                                                                                                                                                                             leaf dhcp-option-name {
                                                                                                                                                                               type string;
                                                                                                                                                                               description "Name of the DHCP option";
                                                                                                                                                                             }
                                                                                                                                                                             leaf dhcp-option-type {
                                                                                                                                                                               type string;
                                                                                                                                                                               description "Type of value for the DHCP option (for example, string [word], integer, IP address)";
                                                                                                                                                                             }
                                                                                                                                                                             leaf dhcp-option-value {
                                                                                                                                                                               type string;
                                                                                                                                                                               description "Value of the DHCP option";
                                                                                                                                                                             }
                                                                                                                                                                           }
                                                                                                                                                                         }
                                                                                                                                                                         container dhcp-lease-information {
                                                                                                                                                                           description "Information about an address assignment";
                                                                                                                                                                           container dhcp-option-table {
                                                                                                                                                                             description "Information about one or more Dynamic Host Configuration Protocol options that are associated with the address assignment";
                                                                                                                                                                             list dhcp-option {
                                                                                                                                                                               description "Information about a Dynamic Host Configuration Protocol option that is associated with the address assignment";
                                                                                                                                                                               leaf dhcp-option-code {
                                                                                                                                                                                 type int32;
                                                                                                                                                                                 description "Numeric code assigned to the DHCP option";
                                                                                                                                                                               }
                                                                                                                                                                               leaf dhcp-option-name {
                                                                                                                                                                                 type string;
                                                                                                                                                                                 description "Name of the DHCP option";
                                                                                                                                                                               }
                                                                                                                                                                               leaf dhcp-option-type {
                                                                                                                                                                                 type string;
                                                                                                                                                                                 description "Type of value for the DHCP option (for example, string [word], integer, IP address)";
                                                                                                                                                                               }
                                                                                                                                                                               leaf dhcp-option-value {
                                                                                                                                                                                 type string;
                                                                                                                                                                                 description "Value of the DHCP option";
                                                                                                                                                                               }
                                                                                                                                                                             }
                                                                                                                                                                           }
                                                                                                                                                                           container dhcp-lease-information {
                                                                                                                                                                             description "Information about an address assignment";
                                                                                                                                                                             container dhcp-option-table {
                                                                                                                                                                               description "Information about one or more Dynamic Host Configuration Protocol options that are associated with the address assignment";
                                                                                                                                                                               list dhcp-option {
                                                                                                                                                                                 description "Information about a Dynamic Host Configuration Protocol option that is associated with the address assignment";
                                                                                                                                                                                 leaf dhcp-option-code {
                                                                                                                                                                                   type int32;
                                                                                                                                                                                   description "Numeric code assigned to the DHCP option";
                                                                                                                                                                                 }
                                                                                                                                                                                 leaf dhcp-option-name {
                                                                                                                                                                                   type string;
                                                                                                                                                                                   description "Name of the DHCP option";
                                                                                                                                                                                 }
                                                                                                                                                                                 leaf dhcp-option-type {
                                                                                                                                                                                   type string;
                                                                                                                                                                                   description "Type of value for the DHCP option (for example, string [word], integer, IP address)";
                                                                                                                                                                                 }
                                                                                                                                                                                 leaf dhcp-option-value {
                                                                                                                                                                                   type string;
                                                                                                                                                                                   description "Value of the DHCP option";
                                                                                                                                                                                 }
                                                                                                                                                                               }
                                                                                                                                                                             }
                                                                                                                                                                             container dhcp-lease-information {
                                                                                                                                                                               description "Information about an address assignment";
                                                                                                                                                                               container dhcp-option-table {
                                                                                                                                                                                 description "Information about one or more Dynamic Host Configuration Protocol options that are associated with the address assignment";
                                                                                                                                                                                 list dhcp-option {
                                                                                                                                                                                   description "Information about a Dynamic Host Configuration Protocol option that is associated with the address assignment";
                                                                                                                                                                                   leaf dhcp-option-code {
                                                                                                                                                                                     type int32;
                                                                                                                                                                                     description "Numeric code assigned to the DHCP option";
                                                                                                                                                                                   }
                                                                                                                                                                                   leaf dhcp-option-name {
                                                                                                                                                                                     type string;
                                                                                                                                                                                     description "Name of the DHCP option";
                                                                                                                                                                                   }
                                                                                                                                                                                   leaf dhcp-option-type {
                                                                                                                                                                                     type string;
                                                                                                                                                                                     description "Type of value for the DHCP option (for example, string [word], integer, IP address)";
                                                                                                                                                                                   }
                                                                                                                                                                                   leaf dhcp-option-value {
                                                                                                                                                                                     type string;
                                                                                                                                                                                     description "Value of the DHCP option";
                                                                                                                                                                                   }
                                                                                                                                                                                 }
                                                                                                                                                                               }
                                                                                                                                                                               container dhcp-lease-information {
                                                                                                                                                                                 description "Information about an address assignment";
                                                                                                                                                                                 container dhcp-option-table {
                                                                                                                                                                                   description "Information about one or more Dynamic Host Configuration Protocol options that are associated with the address assignment";
                                                                                                                                                                                   list dhcp-option {
                                                                                                                                                                                     description "Information about a Dynamic Host Configuration Protocol option that is associated with the address assignment";
                                                                                                                                                                                     leaf dhcp-option-code {
                                                                                                                                                                                       type int32;
                                                                                                                                                                                       description "Numeric code assigned to the DHCP option";
                                                                                                                                                                                     }
                                                                                                                                                                                     leaf dhcp-option-name {
                                                                                                                                                                                       type string;
                                                                                                                                                                                       description "Name of the DHCP option";
                                                                                                                                                                                     }
                                                                                                                                                                                     leaf dhcp-option-type {
                                                                                                                                                                                       type string;
                                                                                                                                                                                       description "Type of value for the DHCP option (for example, string [word], integer, IP address)";
                                                                                                                                                                                     }
                                                                                                                                                                                     leaf dhcp-option-value {
                                                                                                                                                                                       type string;
                                                                                                                                                                                       description "Value of the DHCP option";
                                                                                                                                                                                     }
                                                                                                                                                                                   }
                                                                                                                                                                                 }
                                                                                                                                                                                 container dhcp-lease-information {
                                                                                                                                                                                   description "Information about an address assignment";
                                                                                                                                                                                   container dhcp-option-table {
                                                                                                                                                                                     description "Information about one or more Dynamic Host Configuration Protocol options that are associated with the address assignment";
                                                                                                                                                                                     list dhcp-option {
                                                                                                                                                                                       description "Information about a Dynamic Host Configuration Protocol option that is associated with the address assignment";
                                                                                                                                                                                       leaf dhcp-option-code {
                                                                                                                                                                                         type int32;
                                                                                                                                                                                         description "Numeric code assigned to the DHCP option";
                                                                                                                                                                                       }
                                                                                                                                                                                       leaf dhcp-option-name {
                                                                                                                                                                                         type string;
                                                                                                                                                                                         description "Name of the DHCP option";
                                                                                                                                                                                       }
                                                                                                                                                                                       leaf dhcp-option-type {
                                                                                                                                                                                         type string;
                                                                                                                                                                                         description "Type of value for the DHCP option (for example, string [word], integer, IP address)";
                                                                                                                                                                                       }
                                                                                                                                                                                       leaf dhcp-option-value {
                                                                                                                                                                                         type string;
                                                                                                                                                                                         description "Value of the DHCP option";
                                                                                                                                                                                       }
                                                                                                                                                                                     }
                                                                                                                                                                                   }
                                                                                                                                                                                   container dhcp-lease-information {
                                                                                                                                                                                     description "Information about an address assignment";
                                                                                                                                                                                     container dhcp-option-table {
                                                                                                                                                                                       description "Information about one or more Dynamic Host Configuration Protocol options that are associated with the address assignment";
                                                                                                                                                                                       list dhcp-option {
                                                                                                                                                                                         description "Information about a Dynamic Host Configuration Protocol option that is associated with the address assignment";
                                                                                                                                                                                         leaf dhcp-option-code {
                                                                                                                                                                                           type int32;
                                                                                                                                                                                           description "Numeric code assigned to the DHCP option";
                                                                                                                                                                                         }
                                                                                                                                                                                         leaf dhcp-option-name {
                                                                                                                                                                                           type string;
                                                                                                                                                                                           description "Name of the DHCP option";
                                                                                                                                                                                         }
                                                                                                                                                                                         leaf dhcp-option-type {
                                                                                                                                                                                           type string;
                                                                                                                                                                                           description "Type of value for the DHCP option (for example, string [word], integer, IP address)";
                                                                                                                                                                                         }
                                                                                                                                                                                         leaf dhcp-option-value {
                                                                                                                                                                                           type string;
                                                                                                                                                                                           description "Value of the DHCP option";
                                                                                                                                                                                         }
                                                                                                                                                                                       }
                                                                                                                                                                                     }
                                                                                                                                                                                     container dhcp-lease-information {
                                                                                                                                                                                       description "Information about an address assignment";
                                                                                                                                                                                       container dhcp-option-table {
                                                                                                                                                                                         description "Information about one or more Dynamic Host Configuration Protocol options that are associated with the address assignment";
                                                                                                                                                                                         list dhcp-option {
                                                                                                                                                                                           description "Information about a Dynamic Host Configuration Protocol option that is associated with the address assignment";
                                                                                                                                                                                           leaf dhcp-option-code {
                                                                                                                                                                                             type int32;
                                                                                                                                                                                             description "Numeric code assigned to the DHCP option";
                                                                                                                                                                                           }
                                                                                                                                                                                           leaf dhcp-option-name {
                                                                                                                                                                                             type string;
                                                                                                                                                                                             description "Name of the DHCP option";
                                                                                                                                                                                           }
                                                                                                                                                                                           leaf dhcp-option-type {
                                                                                                                                                                                             type string;
                                                                                                                                                                                             description "Type of value for the DHCP option (for example, string [word], integer, IP address)";
                                                                                                                                                                                           }
                                                                                                                                                                                           leaf dhcp-option-value {
                                                                                                                                                                                             type string;
                                                                                                                                                                                             description "Value of the DHCP option";
                                                                                                                                                                                           }
                                                                                                                                                                                         }
                                                                                                                                                                                       }
                                                                                                                                                                                       container dhcp-lease-information {
                                                                                                                                                                                         description "Information about an address assignment";
                                                                                                                                                                                         container dhcp-option-table {
                                                                                                                                                                                           description "Information about one or more Dynamic Host Configuration Protocol options that are associated with the address assignment";
                                                                                                                                                                                           list dhcp-option {
                                                                                                                                                                                             description "Information about a Dynamic Host Configuration Protocol option that is associated with the address assignment";
                                                                                                                                                                                             leaf dhcp-option-code {
                                                                                                                                                                                               type int32;
                                                                                                                                                                                               description "Numeric code assigned to the DHCP option";
                                                                                                                                                                                             }
                                                                                                                                                                                             leaf dhcp-option-name {
                                                                                                                                                                                               type string;
                                                                                                                                                                                               description "Name of the DHCP option";
                                                                                                                                                                                             }
                                                                                                                                                                                             leaf dhcp-option-type {
                                                                                                                                                                                               type string;
                                                                                                                                                                                               description "Type of value for the DHCP option (for example, string [word], integer, IP address)";
                                                                                                                                                                                             }
                                                                                                                                                                                             leaf dhcp-option-value {
                                                                                                                                                                                               type string;
                                                                                                                                                                                               description "Value of the DHCP option";
                                                                                                                                                                                             }
                                                                                                                                                                                           }
                                                                                                                                                                                         }
                                                                                                                                                                                         container dhcp-lease-information {
                                                                                                                                                                                           description "Information about an address assignment";
                                                                                                                                                                                           container dhcp-option-table {
                                                                                                                                                                                             description "Information about one or more Dynamic Host Configuration Protocol options that are associated with the address assignment";
                                                                                                                                                                                             list dhcp-option {
                                                                                                                                                                                               description "Information about a Dynamic Host Configuration Protocol option that is associated with the address assignment";
                                                                                                                                                                                               leaf dhcp-option-code {
                                                                                                                                                                                                 type int32;
                                                                                                                                                                                                 description "Numeric code assigned to the DHCP option";
                                                                                                                                                                                               }
                                                                                                                                                                                               leaf dhcp-option-name {
                                                                                                                                                                                                 type string;
                                                                                                                                                                                                 description "Name of the DHCP option";
                                                                                                                                                                                               }
                                                                                                                                                                                               leaf dhcp-option-type {
                                                                                                                                                                                                 type string;
                                                                                                                                                                                                 description "Type of value for the DHCP option (for example, string [word], integer, IP address)";
                                                                                                                                                                                               }
                                                                                                                                                                                               leaf dhcp-option-value {
                                                                                                                                                                                                 type string;
                                                                                                                                                                                                 description "Value of the DHCP option";
                                                                                                                                                                                               }
                                                                                                                                                                                             }
                                                                                                                                                                                           }
                                                                                                                                                                                           container dhcp-lease-information {
                                                                                                                                                                                             description "Information about an address assignment";
                                                                                                                                                                                             container dhcp-option-table {
                                                                                                                                                                                               description "Information about one or more Dynamic Host Configuration Protocol options that are associated with the address assignment";
                                                                                                                                                                                               list dhcp-option {
                                                                                                                                                                                                 description "Information about a Dynamic Host Configuration Protocol option that is associated with the address assignment";
                                                                                                                                                                                                 leaf dhcp-option-code {
                                                                                                                                                                                                   type int32;
                                                                                                                                                                                                   description "Numeric code assigned to the DHCP option";
                                                                                                                                                                                                 }
                                                                                                                                                                                                 leaf dhcp-option-name {
                                                                                                                                                                                                   type string;
                                                                                                                                                                                                   description "Name of the DHCP option";
                                                                                                                                                                                                 }
                                                                                                                                                                                                 leaf dhcp-option-type {
                                                                                                                                                                                                   type string;
                                                                                                                                                                                                   description "Type of value for the DHCP option (for example, string [word], integer, IP address)";
                                                                                                                                                                                                 }
                                                                                                                                                                                                 leaf dhcp-option-value {
                                                                                                                                                                                                   type string;
                                                                                                                                                                                                   description "Value of the DHCP option";
                                                                                                                                                                                                 }
                                                                                                                                                                                               }
                                                                                                                                                                                             }
                                                                                                                                                                                             container dhcp-lease-information {
                                                                                                                                                                                               description "Information about an address assignment";
                                                                                                                                                                                               container dhcp-option-table {
                                                                                                                                                                                                 description "Information about one or more Dynamic Host Configuration Protocol options that are associated with the address assignment";
                                                                                                                                                                                                 list dhcp-option {
                                                                                                                                                                                                   description "Information about a Dynamic Host Configuration Protocol option that is associated with the address assignment";
                                                                                                                                                                                                   leaf dhcp-option-code {
                                                                                                                                                                                                     type int32;
                                                                                                                                                                                                     description "Numeric code assigned to the DHCP option";
                                                                                                                                                                                                   }
                                                                                                                                                                                                   leaf dhcp-option-name {
                                                                                                                                                                                                     type string;
                                                                                                                                                                                                     description "Name of the DHCP option";
                                                                                                                                                                                                   }
                                                                                                                                                                                                   leaf dhcp-option-type {
                                                                                                                                                                                                     type string;
                                                                                                                                                                                                     description "Type of value for the DHCP option (for example, string [word], integer, IP address)";
                                                                                                                                                                                                   }
                                                                                                                                                                                                   leaf dhcp-option-value {
                                                                                                                                                                                                     type string;
                                                                                                                                                                                                     description "Value of the DHCP option";
                                                                                                                                                                                                   }
                                                                                                                                                                                                 }
                                                                                                                                                                                               }
                                                                                                                                                                                               container dhcp-lease-information {
                                                                                                                                                                                                 description "Information about an address assignment";
                                                                                                                                                                                                 container dhcp-option-table {
                                                                                                                                                                                                   description "Information about one or more Dynamic Host Configuration Protocol options that are associated with the address assignment";
                                                                                                                                                                                                   list dhcp-option {
                                                                                                                                                                                                     description "Information about a Dynamic Host Configuration Protocol option that is associated with the address assignment";
                                                                                                                                                                                                     leaf dhcp-option-code {
                                                                                                                                                                                                       type int32;
                                                                                                                                                                                                       description "Numeric code assigned to the DHCP option";
                                                                                                                                                                                                     }
                                                                                                                                                                                                     leaf dhcp-option-name {
                                                                                                                                                                                                       type string;
                                                                                                                                                                                                       description "Name of the DHCP option";
                                                                                                                                                                                                     }
                                                                                                                                                                                                     leaf dhcp-option-type {
                                                                                                                                                                                                       type string;
                                                                                                                                                                                                       description "Type of value for the DHCP option (for example, string [word], integer, IP address)";
                                                                                                                                                                                                     }
                                                                                                                                                                                                     leaf dhcp-option-value {
                                                                                                                                                                                                       type string;
                                                                                                                                                                                                       description "Value of the DHCP option";
                                                                                                                                                                                                     }
                                                                                                                                                                                                   }
                                                                                                                                                                                                 }
                                                                                                                                                                                                 container dhcp-lease-information {
                                                                                                                                                                                                   description "Information about an address assignment";
                                                                                                                                                                                                   container dhcp-option-table {
                                                                                                                                                                                                     description "Information about one or more Dynamic Host Configuration Protocol options that are associated with the address assignment";
                                                                                                                                                                                                     list dhcp-option {
                                                                                                                                                                                                       description "Information about a Dynamic Host Configuration Protocol option that is associated with the address assignment";
                                                                                                                                                                                                       leaf dhcp-option-code {
                                                                                                                                                                                                         type int32;
                                                                                                                                                                                                         description "Numeric code assigned to the DHCP option";
                                                                                                                                                                                                       }
                                                                                                                                                                                                       leaf dhcp-option-name {
                                                                                                                                                                                                         type string;
                                                                                                                                                                                                         description "Name of the DHCP option";
                                                                                                                                                                                                       }
                                                                                                                                                                                                       leaf dhcp-option-type {
                                                                                                                                                                                                         type string;
                                                                                                                                                                                                         description "Type of value for the DHCP option (for example, string [word], integer, IP address)";
                                                                                                                                                                                                       }
                                                                                                                                                                                                       leaf dhcp-option-value {
                                                                                                                                                                                                         type string;
                                                                                                                                                                                                         description "Value of the DHCP option";
                                                                                                                                                                                                       }
                                                                                                                                                                                                     }
                                                                                                                                                                                                   }
                                                                                                                                                                                                   container dhcp-lease-information {
                                                                                                                                                                                                     description "Information about an address assignment";
                                                                                                                                                                                                     container dhcp-option-table {
                                                                                                                                                                                                       description "Information about one or more Dynamic Host Configuration Protocol options that are associated with the address assignment";
                                                                                                                                                                                                       list dhcp-option {
                                                                                                                                                                                                         description "Information about a Dynamic Host Configuration Protocol option that is associated with the address assignment";
                                                                                                                                                                                                         leaf dhcp-option-code {
                                                                                                                                                                                                           type int32;
                                                                                                                                                                                                           description "Numeric code assigned to the DHCP option";
                                                                                                                                                                                                         }
                                                                                                                                                                                                         leaf dhcp-option-name {
                                                                                                                                                                                                           type string;
                                                                                                                                                                                                           description "Name of the DHCP option";
                                                                                                                                                                                                         }
                                                                                                                                                                                                         leaf dhcp-option-type {
                                                                                                                                                                                                           type string;
                                                                                                                                                                                                           description "Type of value for the DHCP option (for example, string [word], integer, IP address)";
                                                                                                                                                                                                         }
                                                                                                                                                                                                         leaf dhcp-option-value {
                                                                                                                                                                                                           type string;
                                                                                                                                                                                                           description "Value of the DHCP option";
                                                                                                                                                                                                         }
                                                                                                                                                                                                       }
                                                                                                                                                                                                     }
                                                                                                                                                                                                     container dhcp-lease-information {
                                                                                                                                                                                                       description "Information about an address assignment";
                                                                                                                                                                                                       container dhcp-option-table {
                                                                                                                                                                                                         description "Information about one or more Dynamic Host Configuration Protocol options that are associated with the address assignment";
                                                                                                                                                                                                         list dhcp-option {
                                                                                                                                                                                                           description "Information about a Dynamic Host Configuration Protocol option that is associated with the address assignment";
                                                                                                                                                                                                           leaf dhcp-option-code {
                                                                                                                                                                                                             type int32;
                                                                                                                                                                                                             description "Numeric code assigned to the DHCP option";
                                                                                                                                                                                                           }
                                                                                                                                                                                                           leaf dhcp-option-name {
                                                                                                                                                                                                             type string;
                                                                                                                                                                                                             description "Name of the DHCP option";
                                                                                                                                                                                                           }
                                                                                                                                                                                                           leaf dhcp-option-type {
                                                                                                                                                                                                             type string;
                                                                                                                                                                                                             description "Type of value for the DHCP option (for example, string [word], integer, IP address)";
                                                                                                                                                                                                           }
                                                                                                                                                                                                           leaf dhcp-option-value {
                                                                                                                                                                                                             type string;
                                                                                                                                                                                                             description "Value of the DHCP option";
                                                                                                                                                                                                           }
                                                                                                                                                                                                         }
                                                                                                                                                                                                       }
                                                                                                                                                                                                       container dhcp-lease-information {
                                                                                                                                                                                                         description "Information about an address assignment";
                                                                                                                                                                                                         container dhcp-option-table {
                                                                                                                                                                                                           description "Information about one or more Dynamic Host Configuration Protocol options that are associated with the address assignment";
                                                                                                                                                                                                           list dhcp-option {
                                                                                                                                                                                                             description "Information about a Dynamic Host Configuration Protocol option that is associated with the address assignment";
                                                                                                                                                                                                             leaf dhcp-option-code {
                                                                                                                                                                                                               type int32;
                                                                                                                                                                                                               description "Numeric code assigned to the DHCP option";
                                                                                                                                                                                                             }
                                                                                                                                                                                                             leaf dhcp-option-name {
                                                                                                                                                                                                               type string;
                                                                                                                                                                                                               description "Name of the DHCP option";
                                                                                                                                                                                                             }
                                                                                                                                                                                                             leaf dhcp-option-type {
                                                                                                                                                                                                               type string;
                                                                                                                                                                                                               description "Type of value for the DHCP option (for example, string [word], integer, IP address)";
                                                                                                                                                                                                             }
                                                                                                                                                                                                             leaf dhcp-option-value {
                                                                                                                                                                                                               type string;
                                                                                                                                                                                                               description "Value of the DHCP option";
                                                                                                                                                                                                             }
                                                                                                                                                                                                           }
                                                                                                                                                                                                         }
                                                                                                                                                                                                         container dhcp-lease-information {
                                                                                                                                                                                                           description "Information about an address assignment";
                                                                                                                                                                                                           container dhcp-option-table {
                                                                                                                                                                                                             description "Information about one or more Dynamic Host Configuration Protocol options that are associated with the address assignment";
                                                                                                                                                                                                             list dhcp-option {
                                                                                                                                                                                                               description "Information about a Dynamic Host Configuration Protocol option that is associated with the address assignment";
                                                                                                                                                                                                               leaf dhcp-option-code {
                                                                                                                                                                                                                 type int32;
                                                                                                                                                                                                                 description "Numeric code assigned to the DHCP option";
                                                                                                                                                                                                               }
                                                                                                                                                                                                               leaf dhcp-option-name {
                                                                                                                                                                                                                 type string;
                                                                                                                                                                                                                 description "Name of the DHCP option";
                                                                                                                                                                                                               }
                                                                                                                                                                                                               leaf dhcp-option-type {
                                                                                                                                                                                                                 type string;
                                                                                                                                                                                                                 description "Type of value for the DHCP option (for example, string [word], integer, IP address)";
                                                                                                                                                                                                               }
                                                                                                                                                                                                               leaf dhcp-option-value {
                                                                                                                                                                                                                 type string;
                                                                                                                                                                                                                 description "Value of the DHCP option";
                                                                                                                                                                                                               }
                                                                                                                                                                                                             }
                                                                                                                                                                                                           }
                                                                                                                                                                                                           container dhcp-lease-information {
                                                                                                                                                                                                             description "Information about an address assignment";
                                                                                                                                                                                                             container dhcp-option-table {
                                                                                                                                                                                                               description "Information about one or more Dynamic Host Configuration Protocol options that are associated with the address assignment";
                                                                                                                                                                                                               list dhcp-option {
                                                                                                                                                                                                                 description "Information about a Dynamic Host Configuration Protocol option that is associated with the address assignment";
                                                                                                                                                                                                                 leaf dhcp-option-code {
                                                                                                                                                                                                                   type int32;
                                                                                                                                                                                                                   description "Numeric code assigned to the DHCP option";
                                                                                                                                                                                                                 }
                                                                                                                                                                                                                 leaf dhcp-option-name {
                                                                                                                                                                                                                   type string;
                                                                                                                                                                                                                   description "Name of the DHCP option";
                                                                                                                                                                                                                 }
                                                                                                                                                                                                                 leaf dhcp-option-type {
                                                                                                                                                                                                                   type string;
                                                                                                                                                                                                                   description "Type of value for the DHCP option (for example, string [word], integer, IP address)";
                                                                                                                                                                                                                 }
                                                                                                                                                                                                                 leaf dhcp-option-value {
                                                                                                                                                                                                                   type string;
                                                                                                                                                                                                                   description "Value of the DHCP option";
                                                                                                                                                                                                                 }
                                                                                                                                                                                                               }
                                                                                                                                                                                                             }
                                                                                                                                                                                                             container dhcp-lease-information {
                                                                                                                                                                                                               description "Information about an address assignment";
                                                                                                                                                                                                               container dhcp-option-table {
                                                                                                                                                                                                                 description "Information about one or more Dynamic Host Configuration Protocol options that are associated with the address assignment";
                                                                                                                                                                                                                 list dhcp-option {
                                                                                                                                                                                                                   description "Information about a Dynamic Host Configuration Protocol option that is associated with the address assignment";
                                                                                                                                                                                                                   leaf dhcp-option-code {
                                                                                                                                                                                                                     type int32;
                                                                                                                                                                                                                     description "Numeric code assigned to the DHCP option";
                                                                                                                                                                                                                   }
                                                                                                                                                                                                                   leaf dhcp-option-name {
                                                                                                                                                                                                                     type string;
                                                                                                                                                                                                                     description "Name of the DHCP option";
                                                                                                                                                                                                                   }
                                                                                                                                                                                                                   leaf dhcp-option-type {
                                                                                                                                                                                                                     type string;
                                                                                                                                                                                                                     description "Type of value for the DHCP option (for example, string [word], integer, IP address)";
                                                                                                                                                                                                                   }
                                                                                                                                                                                                                   leaf dhcp-option-value {
                                                                                                                                                                                                                     type string;
                                                                                                                                                                                                                     description "Value of the DHCP option";
                                                                                                                                                                                                                   }
                                                                                                                                                                                                                 }
                                                                                                                                                                                                               }
                                                                                                                                                                                                               container dhcp-lease-information {
                                                                                                                                                                                                                 description "Information about an address assignment";
                                                                                                                                                                                                                 container dhcp-option-table {
                                                                                                                                                                                                                   description "Information about one or more Dynamic Host Configuration Protocol options that are associated with the address assignment";
                                                                                                                                                                                                                   list dhcp-option {
                                                                                                                                                                                                                     description "Information about a Dynamic Host Configuration Protocol option that is associated with the address assignment";
                                                                                                                                                                                                                     leaf dhcp-option-code {
                                                                                                                                                                                                                       type int32;
                                                                                                                                                                                                                       description "Numeric code assigned to the DHCP option";
                                                                                                                                                                                                                     }
                                                                                                                                                                                                                     leaf dhcp-option-name {
                                                                                                                                                                                                                       type string;
                                                                                                                                                                                                                       description "Name of the DHCP option";
                                                                                                                                                                                                                     }
                                                                                                                                                                                                                     leaf dhcp-option-type {
                                                                                                                                                                                                                       type string;
                                                                                                                                                                                                                       description "Type of value for the DHCP option (for example, string [word], integer, IP address)";
                                                                                                                                                                                                                     }
                                                                                                                                                                                                                     leaf dhcp-option-value {
                                                                                                                                                                                                                       type string;
                                                                                                                                                                                                                       description "Value of the DHCP option";
                                                                                                                                                                                                                     }
                                                                                                                                                                                                                   }
                                                                                                                                                                                                                 }
                                                                                                                                                                                                                 container dhcp-lease-information {
                                                                                                                                                                                                                   description "Information about an address assignment";
                                                                                                                                                                                                                   container dhcp-option-table {
                                                                                                                                                                                                                     description "Information about one or more Dynamic Host Configuration Protocol options that are associated with the address assignment";
                                                                                                                                                                                                                     list dhcp-option {
                                                                                                                                                                                                                       description "Information about a Dynamic Host Configuration Protocol option that is associated with the address assignment";
                                                                                                                                                                                                                       leaf dhcp-option-code {
                                                                                                                                                                                                                         type int32;
                                                                                                                                                                                                                         description "Numeric code assigned to the DHCP option";
                                                                                                                                                                                                                       }
                                                                                                                                                                                                                       leaf dhcp-option-name {
                                                                                                                                                                                                                         type string;
                                                                                                                                                                                                                         description "Name of the DHCP option";
                                                                                                                                                                                                                       }
                                                                                                                                                                                                                       leaf dhcp-option-type {
                                                                                                                                                                                                                         type string;
                                                                                                                                                                                                                         description "Type of value for the DHCP option (for example, string [word], integer, IP address)";
                                                                                                                                                                                                                       }
                                                                                                                                                                                                                       leaf dhcp-option-value {
                                                                                                                                                                                                                         type string;
                                                                                                                                                                                                                         description "Value of the DHCP option";
                                                                                                                                                                                                                       }
                                                                                                                                                                                                                     }
                                                                                                                                                                                                                   }
                                                                                                                                                                                                                   container dhcp-lease-information {
                                                                                                                                                                                                                     description "Information about an address assignment";
                                                                                                                                                                                                                     container dhcp-option-table {
                                                                                                                                                                                                                       description "Information about one or more Dynamic Host Configuration Protocol options that are associated with the address assignment";
                                                                                                                                                                                                                       list dhcp-option {
                                                                                                                                                                                                                         description "Information about a Dynamic Host Configuration Protocol option that is associated with the address assignment";
                                                                                                                                                                                                                         leaf dhcp-option-code {
                                                                                                                                                                                                                           type int32;
                                                                                                                                                                                                                           description "Numeric code assigned to the DHCP option";
                                                                                                                                                                                                                         }
                                                                                                                                                                                                                         leaf dhcp-option-name {
                                                                                                                                                                                                                           type string;
                                                                                                                                                                                                                           description "Name of the DHCP option";
                                                                                                                                                                                                                         }
                                                                                                                                                                                                                         leaf dhcp-option-type {
                                                                                                                                                                                                                           type string;
                                                                                                                                                                                                                           description "Type of value for the DHCP option (for example, string [word], integer, IP address)";
                                                                                                                                                                                                                         }
                                                                                                                                                                                                                         leaf dhcp-option-value {
                                                                                                                                                                                                                           type string;
                                                                                                                                                                                                                           description "Value of the DHCP option";
                                                                                                                                                                                                                         }
                                                                                                                                                                                                                       }
                                                                                                                                                                                                                     }
                                                                                                                                                                                                                     container dhcp-lease-information {
                                                                                                                                                                                                                       description "Information about an address assignment";
                                                                                                                                                                                                                       container dhcp-option-table {
                                                                                                                                                                                                                         description "Information about one or more Dynamic Host Configuration Protocol options that are associated with the address assignment";
                                                                                                                                                                                                                         list dhcp-option {
                                                                                                                                                                                                                           description "Information about a Dynamic Host Configuration Protocol option that is associated with the address assignment";
                                                                                                                                                                                                                           leaf dhcp-option-code {
                                                                                                                                                                                                                             type int32;
                                                                                                                                                                                                                             description "Numeric code assigned to the DHCP option";
                                                                                                                                                                                                                           }
                                                                                                                                                                                                                           leaf dhcp-option-name {
                                                                                                                                                                                                                             type string;
                                                                                                                                                                                                                             description "Name of the DHCP option";
                                                                                                                                                                                                                           }
                                                                                                                                                                                                                           leaf dhcp-option-type {
                                                                                                                                                                                                                             type string;
                                                                                                                                                                                                                             description "Type of value for the DHCP option (for example, string [word], integer, IP address)";
                                                                                                                                                                                                                           }
                                                                                                                                                                                                                           leaf dhcp-option-value {
                                                                                                                                                                                                                             type string;
                                                                                                                                                                                                                             description "Value of the DHCP option";
                                                                                                                                                                                                                           }
                                                                                                                                                                                                                         }
                                                                                                                                                                                                                       }
                                                                                                                                                                                                                       container dhcp-lease-information {
                                                                                                                                                                                                                         description "Information about an address assignment";
                                                                                                                                                                                                                         container dhcp-option-table {
                                                                                                                                                                                                                           description "Information about one or more Dynamic Host Configuration Protocol options that are associated with the address assignment";
                                                                                                                                                                                                                           list dhcp-option {
                                                                                                                                                                                                                             description "Information about a Dynamic Host Configuration Protocol option that is associated with the address assignment";
                                                                                                                                                                                                                             leaf dhcp-option-code {
                                                                                                                                                                                                                               type int32;
                                                                                                                                                                                                                               description "Numeric code assigned to the DHCP option";
                                                                                                                                                                                                                             }
                                                                                                                                                                                                                             leaf dhcp-option-name {
                                                                                                                                                                                                                               type string;
                                                                                                                                                                                                                               description "Name of the DHCP option";
                                                                                                                                                                                                                             }
                                                                                                                                                                                                                             leaf dhcp-option-type {
                                                                                                                                                                                                                               type string;
                                                                                                                                                                                                                               description "Type of value for the DHCP option (for example, string [word], integer, IP address)";
                                                                                                                                                                                                                             }
                                                                                                                                                                                                                             leaf dhcp-option-value {
                                                                                                                                                                                                                               type string;
                                                                                                                                                                                                                               description "Value of the DHCP option";
                                                                                                                                                                                                                             }
                                                                                                                                                                                                                           }
                                                                                                                                                                                                                         }
                                                                                                                                                                                                                         container dhcp-lease-information {
                                                                                                                                                                                                                           description "Information about an address assignment";
                                                                                                                                                                                                                           container dhcp-option-table {
                                                                                                                                                                                                                             description "Information about one or more Dynamic Host Configuration Protocol options that are associated with the address assignment";
                                                                                                                                                                                                                             list dhcp-option {
                                                                                                                                                                                                                               description "Information about a Dynamic Host Configuration Protocol option that is associated with the address assignment";
                                                                                                                                                                                                                               leaf dhcp-option-code {
                                                                                                                                                                                                                                 type int32;
                                                                                                                                                                                                                                 description "Numeric code assigned to the DHCP option";
                                                                                                                                                                                                                               }
                                                                                                                                                                                                                               leaf dhcp-option-name {
                                                                                                                                                                                                                                 type string;
                                                                                                                                                                                                                                 description "Name of the DHCP option";
                                                                                                                                                                                                                               }
                                                                                                                                                                                                                               leaf dhcp-option-type {
                                                                                                                                                                                                                                 type string;
                                                                                                                                                                                                                                 description "Type of value for the DHCP option (for example, string [word], integer, IP address)";
                                                                                                                                                                                                                               }
                                                                                                                                                                                                                               leaf dhcp-option-value {
                                                                                                                                                                                                                                 type string;
                                                                                                                                                                                                                                 description "Value of the DHCP option";
                                                                                                                                                                                                                               }
                                                                                                                                                                                                                             }
                                                                                                                                                                                                                           }
                                                                                                                                                                                                                           container dhcp-lease-information {
                                                                                                                                                                                                                             description "Information about an address assignment";
                                                                                                                                                                                                                             container dhcp-option-table {
                                                                                                                                                                                                                               description "Information about one or more Dynamic Host Configuration Protocol options that are associated with the address assignment";
                                                                                                                                                                                                                               list dhcp-option {
                                                                                                                                                                                                                                 description "Information about a Dynamic Host Configuration Protocol option that is associated with the address assignment";
                                                                                                                                                                                                                                 leaf dhcp-option-code {
                                                                                                                                                                                                                                   type int32;
                                                                                                                                                                                                                                   description "Numeric code assigned to the DHCP option";
                                                                                                                                                                                                                                 }
                                                                                                                                                                                                                                 leaf dhcp-option-name {
                                                                                                                                                                                                                                   type string;
                                                                                                                                                                                                                                   description "Name of the DHCP option";
                                                                                                                                                                                                                                 }
                                                                                                                                                                                                                                 leaf dhcp-option-type {
                                                                                                                                                                                                                                   type string;
                                                                                                                                                                                                                                   description "Type of value for the DHCP option (for example, string [word], integer, IP address)";
                                                                                                                                                                                                                                 }
                                                                                                                                                                                                                                 leaf dhcp-option-value {
                                                                                                                                                                                                                                   type string;
                                                                                                                                                                                                                                   description "Value of the DHCP option";
                                                                                                                                                                                                                                 }
                                                                                                                                                                                                                               }
                                                                                                                                                                                                                             }
                                                                                                                                                                                                                             container dhcp-lease-information {
                                                                                                                                                                                                                               description "Information about an address assignment";
                                                                                                                                                                                                                               container dhcp-option-table {
                                                                                                                                                                                                                                 description "Information about one or more Dynamic Host Configuration Protocol options that are associated with the address assignment";
                                                                                                                                                                                                                                 list dhcp-option {
                                                                                                                                                                                                                                   description "Information about a Dynamic Host Configuration Protocol option that is associated with the address assignment";
                                                                                                                                                                                                                                   leaf dhcp-option-code {
                                                                                                                                                                                                                                     type int32;
                                                                                                                                                                                                                                     description "Numeric code assigned to the DHCP option";
                                                                                                                                                                                                                                   }
                                                                                                                                                                                                                                   leaf dhcp-option-name {
                                                                                                                                                                                                                                     type string;
                                                                                                                                                                                                                                     description "Name of the DHCP option";
                                                                                                                                                                                                                                   }
                                                                                                                                                                                                                                   leaf dhcp-option-type {
                                                                                                                                                                                                                                     type string;
                                                                                                                                                                                                                                     description "Type of value for the DHCP option (for example, string [word], integer, IP address)";
                                                                                                                                                                                                                                   }
                                                                                                                                                                                                                                   leaf dhcp-option-value {
                                                                                                                                                                                                                                     type string;
                                                                                                                                                                                                                                     description "Value of the DHCP option";
                                                                                                                                                                                                                                   }
                                                                                                                                                                                                                                 }
                                                                                                                                                                                                                               }
                                                                                                                                                                                                                               container dhcp-lease-information {
                                                                                                                                                                                                                                 description "Information about an address assignment";
                                                                                                                                                                                                                                 container dhcp-option-table {
                                                                                                                                                                                                                                   description "Information about one or more Dynamic Host Configuration Protocol options that are associated with the address assignment";
                                                                                                                                                                                                                                   list dhcp-option {
                                                                                                                                                                                                                                     description "Information about a Dynamic Host Configuration Protocol option that is associated with the address assignment";
                                                                                                                                                                                                                                     leaf dhcp-option-code {
                                                                                                                                                                                                                                       type int32;
                                                                                                                                                                                                                                       description "Numeric code assigned to the DHCP option";
                                                                                                                                                                                                                                     }
                                                                                                                                                                                                                                     leaf dhcp-option-name {
                                                                                                                                                                                                                                       type string;
                                                                                                                                                                                                                                       description "Name of the DHCP option";
                                                                                                                                                                                                                                     }
                                                                                                                                                                                                                                     leaf dhcp-option-type {
                                                                                                                                                                                                                                       type string;
                                                                                                                                                                                                                                       description "Type of value for the DHCP option (for example, string [word], integer, IP address)";
                                                                                                                                                                                                                                     }
                                                                                                                                                                                                                                     leaf dhcp-option-value {
                                                                                                                                                                                                                                       type string;
                                                                                                                                                                                                                                       description "Value of the DHCP option";
                                                                                                                                                                                                                                     }
                                                                                                                                                                                                                                   }
                                                                                                                                                                                                                                 }
                                                                                                                                                                                                                                 container dhcp-lease-information {
                                                                                                                                                                                                                                   description "Information about an address assignment";
                                                                                                                                                                                                                                   container dhcp-option-table {
                                                                                                                                                                                                                                     description "Information about one or more Dynamic Host Configuration Protocol options that are associated with the address assignment";
                                                                                                                                                                                                                                     list dhcp-option {
                                                                                                                                                                                                                                       description "Information about a Dynamic Host Configuration Protocol option that is associated with the address assignment";
                                                                                                                                                                                                                                       leaf dhcp-option-code {
                                                                                                                                                                                                                                         type int32;
                                                                                                                                                                                                                                         description "Numeric code assigned to the DHCP option";
                                                                                                                                                                                                                                       }
                                                                                                                                                                                                                                       leaf dhcp-option-name {
                                                                                                                                                                                                                                         type string;
                                                                                                                                                                                                                                         description "Name of the DHCP option";
                                                                                                                                                                                                                                       }
                                                                                                                                                                                                                                       leaf dhcp-option-type {
                                                                                                                                                                                                                                         type string;
                                                                                                                                                                                                                                         description "Type of value for the DHCP option (for example, string [word], integer, IP address)";
                                                                                                                                                                                                                                       }
                                                                                                                                                                                                                                       leaf dhcp-option-value {
                                                                                                                                                                                                                                         type string;
                                                                                                                                                                                                                                         description "Value of the DHCP option";
                                                                                                                                                                                                                                       }
                                                                                                                                                                                                                                     }
                                                                                                                                                                                                                                   }
                                                                                                                                                                                                                                   container dhcp-lease-information {
                                                                                                                                                                                                                                     description "Information about an address assignment";
                                                                                                                                                                                                                                     container dhcp-option-table {
                                                                                                                                                                                                                                       description "Information about one or more Dynamic Host Configuration Protocol options that are associated with the address assignment";
                                                                                                                                                                                                                                       list dhcp-option {
                                                                                                                                                                                                                                         description "Information about a Dynamic Host Configuration Protocol option that is associated with the address assignment";
                                                                                                                                                                                                                                         leaf dhcp-option-code {
                                                                                                                                                                                                                                           type int32;
                                                                                                                                                                                                                                           description "Numeric code assigned to the DHCP option";
                                                                                                                                                                                                                                         }
                                                                                                                                                                                                                                         leaf dhcp-option-name {
                                                                                                                                                                                                                                           type string;
                                                                                                                                                                                                                                           description "Name of the DHCP option";
                                                                                                                                                                                                                                         }
                                                                                                                                                                                                                                         leaf dhcp-option-type {
                                                                                                                                                                                                                                           type string;
                                                                                                                                                                                                                                           description "Type of value for the DHCP option (for example, string [word], integer, IP address)";
                                                                                                                                                                                                                                         }
                                                                                                                                                                                                                                         leaf dhcp-option-value {
                                                                                                                                                                                                                                           type string;
                                                                                                                                                                                                                                           description "Value of the DHCP option";
                                                                                                                                                                                                                                         }
                                                                                                                                                                                                                                       }
                                                                                                                                                                                                                                     }
                                                                                                                                                                                                                                     container dhcp-lease-information {
                                                                                                                                                                                                                                       description "Information about an address assignment";
                                                                                                                                                                                                                                       container dhcp-option-table {
                                                                                                                                                                                                                                         description "Information about one or more Dynamic Host Configuration Protocol options that are associated with the address assignment";
                                                                                                                                                                                                                                         list dhcp-option {
                                                                                                                                                                                                                                           description "Information about a Dynamic Host Configuration Protocol option that is associated with the address assignment";
                                                                                                                                                                                                                                           leaf dhcp-option-code {
                                                                                                                                                                                                                                             type int32;
                                                                                                                                                                                                                                             description "Numeric code assigned to the DHCP option";
                                                                                                                                                                                                                                           }
                                                                                                                                                                                                                                           leaf dhcp-option-name {
                                                                                                                                                                                                                                             type string;
                                                                                                                                                                                                                                             description "Name of the DHCP option";
                                                                                                                                                                                                                                           }
                                                                                                                                                                                                                                           leaf dhcp-option-type {
                                                                                                                                                                                                                                             type string;
                                                                                                                                                                                                                                             description "Type of value for the DHCP option (for example, string [word], integer, IP address)";
                                                                                                                                                                                                                                           }
                                                                                                                                                                                                                                           leaf dhcp-option-value {
                                                                                                                                                                                                                                             type string;
                                                                                                                                                                                                                                             description "Value of the DHCP option";
                                                                                                                                                                                                                                           }
                                                                                                                                                                                                                                         }
                                                                                                                                                                                                                                       }
                                                                                                                                                                                                                                       container dhcp-lease-information {
                                                                                                                                                                                                                                         description "Information about an address assignment";
                                                                                                                                                                                                                                         container dhcp-option-table {
                                                                                                                                                                                                                                           description "Information about one or more Dynamic Host Configuration Protocol options that are associated with the address assignment";
                                                                                                                                                                                                                                           list dhcp-option {
                                                                                                                                                                                                                                             description "Information about a Dynamic Host Configuration Protocol option that is associated with the address assignment";
                                                                                                                                                                                                                                             leaf dhcp-option-code {
                                                                                                                                                                                                                                               type int32;
                                                                                                                                                                                                                                               description "Numeric code assigned to the DHCP option";
                                                                                                                                                                                                                                             }
                                                                                                                                                                                                                                             leaf dhcp-option-name {
                                                                                                                                                                                                                                               type string;
                                                                                                                                                                                                                                               description "Name of the DHCP option";
                                                                                                                                                                                                                                             }
                                                                                                                                                                                                                                             leaf dhcp-option-type {
                                                                                                                                                                                                                                               type string;
                                                                                                                                                                                                                                               description "Type of value for the DHCP option (for example, string [word], integer, IP address)";
                                                                                                                                                                                                                                             }
                                                                                                                                                                                                                                             leaf dhcp-option-value {
                                                                                                                                                                                                                                               type string;
                                                                                                                                                                                                                                               description "Value of the DHCP option";
                                                                                                                                                                                                                                             }
                                                                                                                                                                                                                                           }
                                                                                                                                                                                                                                         }
                                                                                                                                                                                                                                         container dhcp-lease-information {
                                                                                                                                                                                                                                           description "Information about an address assignment";
                                                                                                                                                                                                                                           container dhcp-option-table {
                                                                                                                                                                                                                                             description "Information about one or more Dynamic Host Configuration Protocol options that are associated with the address assignment";
                                                                                                                                                                                                                                             list dhcp-option {
                                                                                                                                                                                                                                               description "Information about a Dynamic Host Configuration Protocol option that is associated with the address assignment";
                                                                                                                                                                                                                                               leaf dhcp-option-code {
                                                                                                                                                                                                                                                 type int32;
                                                                                                                                                                                                                                                 description "Numeric code assigned to the DHCP option";
                                                                                                                                                                                                                                               }
                                                                                                                                                                                                                                               leaf dhcp-option-name {
                                                                                                                                                                                                                                                 type string;
                                                                                                                                                                                                                                                 description "Name of the DHCP option";
                                                                                                                                                                                                                                               }
                                                                                                                                                                                                                                               leaf dhcp-option-type {
                                                                                                                                                                                                                                                 type string;
                                                                                                                                                                                                                                                 description "Type of value for the DHCP option (for example, string [word], integer, IP address)";
                                                                                                                                                                                                                                               }
                                                                                                                                                                                                                                               leaf dhcp-option-value {
                                                                                                                                                                                                                                                 type string;
                                                                                                                                                                                                                                                 description "Value of the DHCP option";
                                                                                                                                                                                                                                               }
                                                                                                                                                                                                                                             }
                                                                                                                                                                                                                                           }
                                                                                                                                                                                                                                           container dhcp-lease-information {
                                                                                                                                                                                                                                             description "Information about an address assignment";
                                                                                                                                                                                                                                             container dhcp-option-table {
                                                                                                                                                                                                                                               description "Information about one or more Dynamic Host Configuration Protocol options that are associated with the address assignment";
                                                                                                                                                                                                                                               list dhcp-option {
                                                                                                                                                                                                                                                 description "Information about a Dynamic Host Configuration Protocol option that is associated with the address assignment";
                                                                                                                                                                                                                                                 leaf dhcp-option-code {
                                                                                                                                                                                                                                                   type int32;
                                                                                                                                                                                                                                                   description "Numeric code assigned to the DHCP option";
                                                                                                                                                                                                                                                 }
                                                                                                                                                                                                                                                 leaf dhcp-option-name {
                                                                                                                                                                                                                                                   type string;
                                                                                                                                                                                                                                                   description "Name of the DHCP option";
                                                                                                                                                                                                                                                 }
                                                                                                                                                                                                                                                 leaf dhcp-option-type {
                                                                                                                                                                                                                                                   type string;
                                                                                                                                                                                                                                                   description "Type of value for the DHCP option (for example, string [word], integer, IP address)";
                                                                                                                                                                                                                                                 }
                                                                                                                                                                                                                                                 leaf dhcp-option-value {
                                                                                                                                                                                                                                                   type string;
                                                                                                                                                                                                                                                   description "Value of the DHCP option";
                                                                                                                                                                                                                                                 }
                                                                                                                                                                                                                                               }
                                                                                                                                                                                                                                             }
                                                                                                                                                                                                                                             container dhcp-lease-information {
                                                                                                                                                                                                                                               description "Information about an address assignment";
                                                                                                                                                                                                                                               container dhcp-option-table {
                                                                                                                                                                                                                                                 description "Information about one or more Dynamic Host Configuration Protocol options that are associated with the address assignment";
                                                                                                                                                                                                                                                 list dhcp-option {
                                                                                                                                                                                                                                                   description "Information about a Dynamic Host Configuration Protocol option that is associated with the address assignment";
                                                                                                                                                                                                                                                   leaf dhcp-option-code {
                                                                                                                                                                                                                                                     type int32;
                                                                                                                                                                                                                                                     description "Numeric code assigned to the DHCP option";
                                                                                                                                                                                                                                                   }
                                                                                                                                                                                                                                                   leaf dhcp-option-name {
                                                                                                                                                                                                                                                     type string;
                                                                                                                                                                                                                                                     description "Name of the DHCP option";
                                                                                                                                                                                                                                                   }
                                                                                                                                                                                                                                                   leaf dhcp-option-type {
                                                                                                                                                                                                                                                     type string;
                                                                                                                                                                                                                                                     description "Type of value for the DHCP option (for example, string [word], integer, IP address)";
                                                                                                                                                                                                                                                   }
                                                                                                                                                                                                                                                   leaf dhcp-option-value {
                                                                                                                                                                                                                                                     type string;
                                                                                                                                                                                                                                                     description "Value of the DHCP option";
                                                                                                                                                                                                                                                   }
                                                                                                                                                                                                                                                 }
                                                                                                                                                                                                                                               }
                                                                                                                                                                                                                                               container dhcp-lease-information {
                                                                                                                                                                                                                                                 description "Information about an address assignment";
                                                                                                                                                                                                                                                 container dhcp-option-table {
                                                                                                                                                                                                                                                   description "Information about one or more Dynamic Host Configuration Protocol options that are associated with the address assignment";
                                                                                                                                                                                                                                                   list dhcp-option {
                                                                                                                                                                                                                                                     description "Information about a Dynamic Host Configuration Protocol option that is associated with the address assignment";
                                                                                                                                                                                                                                                     leaf dhcp-option-code {
                                                                                                                                                                                                                                                       type int32;
                                                                                                                                                                                                                                                       description "Numeric code assigned to the DHCP option";
                                                                                                                                                                                                                                                     }
                                                                                                                                                                                                                                                     leaf dhcp-option-name {
                                                                                                                                                                                                                                                       type string;
                                                                                                                                                                                                                                                       description "Name of the DHCP option";
                                                                                                                                                                                                                                                     }
                                                                                                                                                                                                                                                     leaf dhcp-option-type {
                                                                                                                                                                                                                                                       type string;
                                                                                                                                                                                                                                                       description "Type of value for the DHCP option (for example, string [word], integer, IP address)";
                                                                                                                                                                                                                                                     }
                                                                                                                                                                                                                                                     leaf dhcp-option-value {
                                                                                                                                                                                                                                                       type string;
                                                                                                                                                                                                                                                       description "Value of the DHCP option";
                                                                                                                                                                                                                                                     }
                                                                                                                                                                                                                                                   }
                                                                                                                                                                                                                                                 }
                                                                                                                                                                                                                                                 container dhcp-lease-information {
                                                                                                                                                                                                                                                   description "Information about an address assignment";
                                                                                                                                                                                                                                                   container dhcp-option-table {
                                                                                                                                                                                                                                                     description "Information about one or more Dynamic Host Configuration Protocol options that are associated with the address assignment";
                                                                                                                                                                                                                                                     list dhcp-option {
                                                                                                                                                                                                                                                       description "Information about a Dynamic Host Configuration Protocol option that is associated with the address assignment";
                                                                                                                                                                                                                                                       leaf dhcp-option-code {
                                                                                                                                                                                                                                                         type int32;
                                                                                                                                                                                                                                                         description "Numeric code assigned to the DHCP option";
                                                                                                                                                                                                                                                       }
                                                                                                                                                                                                                                                       leaf dhcp-option-name {
                                                                                                                                                                                                                                                         type string;
                                                                                                                                                                                                                                                         description "Name of the DHCP option";
                                                                                                                                                                                                                                                       }
                                                                                                                                                                                                                                                       leaf dhcp-option-type {
                                                                                                                                                                                                                                                         type string;
                                                                                                                                                                                                                                                         description "Type of value for the DHCP option (for example, string [word], integer, IP address)";
                                                                                                                                                                                                                                                       }
                                                                                                                                                                                                                                                       leaf dhcp-option-value {
                                                                                                                                                                                                                                                         type string;
                                                                                                                                                                                                                                                         description "Value of the DHCP option";
                                                                                                                                                                                                                                                       }
                                                                                                                                                                                                                                                     }
                                                                                                                                                                                                                                                   }
                                                                                                                                                                                                                                                   container dhcp-lease-information {
                                                                                                                                                                                                                                                     description "Information about an address assignment";
                                                                                                                                                                                                                                                     container dhcp-option-table {
                                                                                                                                                                                                                                                       description "Information about one or more Dynamic Host Configuration Protocol options that are associated with the address assignment";
                                                                                                                                                                                                                                                       list dhcp-option {
                                                                                                                                                                                                                                                         description "Information about a Dynamic Host Configuration Protocol option that is associated with the address assignment";
                                                                                                                                                                                                                                                         leaf dhcp-option-code {
                                                                                                                                                                                                                                                           type int32;
                                                                                                                                                                                                                                                           description "Numeric code assigned to the DHCP option";
                                                                                                                                                                                                                                                         }
                                                                                                                                                                                                                                                         leaf dhcp-option-name {
                                                                                                                                                                                                                                                           type string;
                                                                                                                                                                                                                                                           description "Name of the DHCP option";
                                                                                                                                                                                                                                                         }
                                                                                                                                                                                                                                                         leaf dhcp-option-type {
                                                                                                                                                                                                                                                           type string;
                                                                                                                                                                                                                                                           description "Type of value for the DHCP option (for example, string [word], integer, IP address)";
                                                                                                                                                                                                                                                         }
                                                                                                                                                                                                                                                         leaf dhcp-option-value {
                                                                                                                                                                                                                                                           type string;
                                                                                                                                                                                                                                                           description "Value of the DHCP option";
                                                                                                                                                                                                                                                         }
                                                                                                                                                                                                                                                       }
                                                                                                                                                                                                                                                     }
                                                                                                                                                                                                                                                     container dhcp-lease-information {
                                                                                                                                                                                                                                                       description "Information about an address assignment";
                                                                                                                                                                                                                                                       container dhcp-option-table {
                                                                                                                                                                                                                                                         description "Information about one or more Dynamic Host Configuration Protocol options that are associated with the address assignment";
                                                                                                                                                                                                                                                         list dhcp-option {
                                                                                                                                                                                                                                                           description "Information about a Dynamic Host Configuration Protocol option that is associated with the address assignment";
                                                                                                                                                                                                                                                           leaf dhcp-option-code {
                                                                                                                                                                                                                                                             type int32;
                                                                                                                                                                                                                                                             description "Numeric code assigned to the DHCP option";
                                                                                                                                                                                                                                                           }
                                                                                                                                                                                                                                                           leaf dhcp-option-name {
                                                                                                                                                                                                                                                             type string;
                                                                                                                                                                                                                                                             description "Name of the DHCP option";
                                                                                                                                                                                                                                                           }
                                                                                                                                                                                                                                                           leaf dhcp-option-type {
                                                                                                                                                                                                                                                             type string;
                                                                                                                                                                                                                                                             description "Type of value for the DHCP option (for example, string [word], integer, IP address)";
                                                                                                                                                                                                                                                           }
                                                                                                                                                                                                                                                           leaf dhcp-option-value {
                                                                                                                                                                                                                                                             type string;
                                                                                                                                                                                                                                                             description "Value of the DHCP option";
                                                                                                                                                                                                                                                           }
                                                                                                                                                                                                                                                         }
                                                                                                                                                                                                                                                       }
                                                                                                                                                                                                                                                       container dhcp-lease-information {
                                                                                                                                                                                                                                                         description "Information about an address assignment";
                                                                                                                                                                                                                                                         container dhcp-option-table {
                                                                                                                                                                                                                                                           description "Information about one or more Dynamic Host Configuration Protocol options that are associated with the address assignment";
                                                                                                                                                                                                                                                           list dhcp-option {
                                                                                                                                                                                                                                                             description "Information about a Dynamic Host Configuration Protocol option that is associated with the address assignment";
                                                                                                                                                                                                                                                             leaf dhcp-option-code {
                                                                                                                                                                                                                                                               type int32;
                                                                                                                                                                                                                                                               description "Numeric code assigned to the DHCP option";
                                                                                                                                                                                                                                                             }
                                                                                                                                                                                                                                                             leaf dhcp-option-name {
                                                                                                                                                                                                                                                               type string;
                                                                                                                                                                                                                                                               description "Name of the DHCP option";
                                                                                                                                                                                                                                                             }
                                                                                                                                                                                                                                                             leaf dhcp-option-type {
                                                                                                                                                                                                                                                               type string;
                                                                                                                                                                                                                                                               description "Type of value for the DHCP option (for example, string [word], integer, IP address)";
                                                                                                                                                                                                                                                             }
                                                                                                                                                                                                                                                             leaf dhcp-option-value {
                                                                                                                                                                                                                                                               type string;
                                                                                                                                                                                                                                                               description "Value of the DHCP option";
                                                                                                                                                                                                                                                             }
                                                                                                                                                                                                                                                           }
                                                                                                                                                                                                                                                         }
                                                                                                                                                                                                                                                         container dhcp-lease-information {
                                                                                                                                                                                                                                                           description "Information about an address assignment";
                                                                                                                                                                                                                                                           container dhcp-option-table {
                                                                                                                                                                                                                                                             description "Information about one or more Dynamic Host Configuration Protocol options that are associated with the address assignment";
                                                                                                                                                                                                                                                             list dhcp-option {
                                                                                                                                                                                                                                                               description "Information about a Dynamic Host Configuration Protocol option that is associated with the address assignment";
                                                                                                                                                                                                                                                               leaf dhcp-option-code {
                                                                                                                                                                                                                                                                 type int32;
                                                                                                                                                                                                                                                                 description "Numeric code assigned to the DHCP option";
                                                                                                                                                                                                                                                               }
                                                                                                                                                                                                                                                               leaf dhcp-option-name {
                                                                                                                                                                                                                                                                 type string;
                                                                                                                                                                                                                                                                 description "Name of the DHCP option";
                                                                                                                                                                                                                                                               }
                                                                                                                                                                                                                                                               leaf dhcp-option-type {
                                                                                                                                                                                                                                                                 type string;
                                                                                                                                                                                                                                                                 description "Type of value for the DHCP option (for example, string [word], integer, IP address)";
                                                                                                                                                                                                                                                               }
                                                                                                                                                                                                                                                               leaf dhcp-option-value {
                                                                                                                                                                                                                                                                 type string;
                                                                                                                                                                                                                                                                 description "Value of the DHCP option";
                                                                                                                                                                                                                                                               }
                                                                                                                                                                                                                                                             }
                                                                                                                                                                                                                                                           }
                                                                                                                                                                                                                                                           container dhcp-lease-information {
                                                                                                                                                                                                                                                             description "Information about an address assignment";
                                                                                                                                                                                                                                                             container dhcp-option-table {
                                                                                                                                                                                                                                                               description "Information about one or more Dynamic Host Configuration Protocol options that are associated with the address assignment";
                                                                                                                                                                                                                                                               list dhcp-option {
                                                                                                                                                                                                                                                                 description "Information about a Dynamic Host Configuration Protocol option that is associated with the address assignment";
                                                                                                                                                                                                                                                                 leaf dhcp-option-code {
                                                                                                                                                                                                                                                                   type int32;
                                                                                                                                                                                                                                                                   description "Numeric code assigned to the DHCP option";
                                                                                                                                                                                                                                                                 }
                                                                                                                                                                                                                                                                 leaf dhcp-option-name {
                                                                                                                                                                                                                                                                   type string;
                                                                                                                                                                                                                                                                   description "Name of the DHCP option";
                                                                                                                                                                                                                                                                 }
                                                                                                                                                                                                                                                                 leaf dhcp-option-type {
                                                                                                                                                                                                                                                                   type string;
                                                                                                                                                                                                                                                                   description "Type of value for the DHCP option (for example, string [word], integer, IP address)";
                                                                                                                                                                                                                                                                 }
                                                                                                                                                                                                                                                                 leaf dhcp-option-value {
                                                                                                                                                                                                                                                                   type string;
                                                                                                                                                                                                                                                                   description "Value of the DHCP option";
                                                                                                                                                                                                                                                                 }
                                                                                                                                                                                                                                                               }
                                                                                                                                                                                                                                                             }
                                                                                                                                                                                                                                                             container dhcp-lease-information {
                                                                                                                                                                                                                                                               description "Information about an address assignment";
                                                                                                                                                                                                                                                               container dhcp-option-table {
                                                                                                                                                                                                                                                                 description "Information about one or more Dynamic Host Configuration Protocol options that are associated with the address assignment";
                                                                                                                                                                                                                                                                 list dhcp-option {
                                                                                                                                                                                                                                                                   description "Information about a Dynamic Host Configuration Protocol option that is associated with the address assignment";
                                                                                                                                                                                                                                                                   leaf dhcp-option-code {
                                                                                                                                                                                                                                                                     type int32;
                                                                                                                                                                                                                                                                     description "Numeric code assigned to the DHCP option";
                                                                                                                                                                                                                                                                   }
                                                                                                                                                                                                                                                                   leaf dhcp-option-name {
                                                                                                                                                                                                                                                                     type string;
                                                                                                                                                                                                                                                                     description "Name of the DHCP option";
                                                                                                                                                                                                                                                                   }
                                                                                                                                                                                                                                                                   leaf dhcp-option-type {
                                                                                                                                                                                                                                                                     type string;
                                                                                                                                                                                                                                                                     description "Type of value for the DHCP option (for example, string [word], integer, IP address)";
                                                                                                                                                                                                                                                                   }
                                                                                                                                                                                                                                                                   leaf dhcp-option-value {
                                                                                                                                                                                                                                                                     type string;
                                                                                                                                                                                                                                                                     description "Value of the DHCP option";
                                                                                                                                                                                                                                                                   }
                                                                                                                                                                                                                                                                 }
                                                                                                                                                                                                                                                               }
                                                                                                                                                                                                                                                               container dhcp-lease-information {
                                                                                                                                                                                                                                                                 description "Information about an address assignment";
                                                                                                                                                                                                                                                                 container dhcp-option-table {
                                                                                                                                                                                                                                                                   description "Information about one or more Dynamic Host Configuration Protocol options that are associated with the address assignment";
                                                                                                                                                                                                                                                                   list dhcp-option {
                                                                                                                                                                                                                                                                     description "Information about a Dynamic Host Configuration Protocol option that is associated with the address assignment";
                                                                                                                                                                                                                                                                     leaf dhcp-option-code {
                                                                                                                                                                                                                                                                       type int32;
                                                                                                                                                                                                                                                                       description "Numeric code assigned to the DHCP option";
                                                                                                                                                                                                                                                                     }
                                                                                                                                                                                                                                                                     leaf dhcp-option-name {
                                                                                                                                                                                                                                                                       type string;
                                                                                                                                                                                                                                                                       description "Name of the DHCP option";
                                                                                                                                                                                                                                                                     }
                                                                                                                                                                                                                                                                     leaf dhcp-option-type {
                                                                                                                                                                                                                                                                       type string;
                                                                                                                                                                                                                                                                       description "Type of value for the DHCP option (for example, string [word], integer, IP address)";
                                                                                                                                                                                                                                                                     }
                                                                                                                                                                                                                                                                     leaf dhcp-option-value {
                                                                                                                                                                                                                                                                       type string;
                                                                                                                                                                                                                                                                       description "Value of the DHCP option";
                                                                                                                                                                                                                                                                     }
                                                                                                                                                                                                                                                                   }
                                                                                                                                                                                                                                                                 }
                                                                                                                                                                                                                                                                 container client-identifier {
                                                                                                                                                                                                                                                                   description "Identifier that the DHCP client provided for itself when it requested an address assignment";
                                                                                                                                                                                                                                                                   leaf hex-data-line {
                                                                                                                                                                                                                                                                     type string;
                                                                                                                                                                                                                                                                     description "Line of data in hexadecimal format";
                                                                                                                                                                                                                                                                   }
                                                                                                                                                                                                                                                                   leaf printable-data-line {
                                                                                                                                                                                                                                                                     type string;
                                                                                                                                                                                                                                                                     description "Line of data in printable format";
                                                                                                                                                                                                                                                                   }
                                                                                                                                                                                                                                                                 }
                                                                                                                                                                                                                                                               }
                                                                                                                                                                                                                                                             }
                                                                                                                                                                                                                                                             container client-identifier {
                                                                                                                                                                                                                                                               description "Identifier that the DHCP client provided for itself when it requested an address assignment";
                                                                                                                                                                                                                                                               leaf hex-data-line {
                                                                                                                                                                                                                                                                 type string;
                                                                                                                                                                                                                                                                 description "Line of data in hexadecimal format";
                                                                                                                                                                                                                                                               }
                                                                                                                                                                                                                                                               leaf printable-data-line {
                                                                                                                                                                                                                                                                 type string;
                                                                                                                                                                                                                                                                 description "Line of data in printable format";
                                                                                                                                                                                                                                                               }
                                                                                                                                                                                                                                                             }
                                                                                                                                                                                                                                                           }
                                                                                                                                                                                                                                                         }
                                                                                                                                                                                                                                                         container client-identifier {
                                                                                                                                                                                                                                                           description "Identifier that the DHCP client provided for itself when it requested an address assignment";
                                                                                                                                                                                                                                                           leaf hex-data-line {
                                                                                                                                                                                                                                                             type string;
                                                                                                                                                                                                                                                             description "Line of data in hexadecimal format";
                                                                                                                                                                                                                                                           }
                                                                                                                                                                                                                                                           leaf printable-data-line {
                                                                                                                                                                                                                                                             type string;
                                                                                                                                                                                                                                                             description "Line of data in printable format";
                                                                                                                                                                                                                                                           }
                                                                                                                                                                                                                                                         }
                                                                                                                                                                                                                                                       }
                                                                                                                                                                                                                                                     }
                                                                                                                                                                                                                                                     container client-identifier {
                                                                                                                                                                                                                                                       description "Identifier that the DHCP client provided for itself when it requested an address assignment";
                                                                                                                                                                                                                                                       leaf hex-data-line {
                                                                                                                                                                                                                                                         type string;
                                                                                                                                                                                                                                                         description "Line of data in hexadecimal format";
                                                                                                                                                                                                                                                       }
                                                                                                                                                                                                                                                       leaf printable-data-line {
                                                                                                                                                                                                                                                         type string;
                                                                                                                                                                                                                                                         description "Line of data in printable format";
                                                                                                                                                                                                                                                       }
                                                                                                                                                                                                                                                     }
                                                                                                                                                                                                                                                   }
                                                                                                                                                                                                                                                 }
                                                                                                                                                                                                                                                 container client-identifier {
                                                                                                                                                                                                                                                   description "Identifier that the DHCP client provided for itself when it requested an address assignment";
                                                                                                                                                                                                                                                   leaf hex-data-line {
                                                                                                                                                                                                                                                     type string;
                                                                                                                                                                                                                                                     description "Line of data in hexadecimal format";
                                                                                                                                                                                                                                                   }
                                                                                                                                                                                                                                                   leaf printable-data-line {
                                                                                                                                                                                                                                                     type string;
                                                                                                                                                                                                                                                     description "Line of data in printable format";
                                                                                                                                                                                                                                                   }
                                                                                                                                                                                                                                                 }
                                                                                                                                                                                                                                               }
                                                                                                                                                                                                                                             }
                                                                                                                                                                                                                                             container client-identifier {
                                                                                                                                                                                                                                               description "Identifier that the DHCP client provided for itself when it requested an address assignment";
                                                                                                                                                                                                                                               leaf hex-data-line {
                                                                                                                                                                                                                                                 type string;
                                                                                                                                                                                                                                                 description "Line of data in hexadecimal format";
                                                                                                                                                                                                                                               }
                                                                                                                                                                                                                                               leaf printable-data-line {
                                                                                                                                                                                                                                                 type string;
                                                                                                                                                                                                                                                 description "Line of data in printable format";
                                                                                                                                                                                                                                               }
                                                                                                                                                                                                                                             }
                                                                                                                                                                                                                                           }
                                                                                                                                                                                                                                         }
                                                                                                                                                                                                                                         container client-identifier {
                                                                                                                                                                                                                                           description "Identifier that the DHCP client provided for itself when it requested an address assignment";
                                                                                                                                                                                                                                           leaf hex-data-line {
                                                                                                                                                                                                                                             type string;
                                                                                                                                                                                                                                             description "Line of data in hexadecimal format";
                                                                                                                                                                                                                                           }
                                                                                                                                                                                                                                           leaf printable-data-line {
                                                                                                                                                                                                                                             type string;
                                                                                                                                                                                                                                             description "Line of data in printable format";
                                                                                                                                                                                                                                           }
                                                                                                                                                                                                                                         }
                                                                                                                                                                                                                                       }
                                                                                                                                                                                                                                     }
                                                                                                                                                                                                                                     container client-identifier {
                                                                                                                                                                                                                                       description "Identifier that the DHCP client provided for itself when it requested an address assignment";
                                                                                                                                                                                                                                       leaf hex-data-line {
                                                                                                                                                                                                                                         type string;
                                                                                                                                                                                                                                         description "Line of data in hexadecimal format";
                                                                                                                                                                                                                                       }
                                                                                                                                                                                                                                       leaf printable-data-line {
                                                                                                                                                                                                                                         type string;
                                                                                                                                                                                                                                         description "Line of data in printable format";
                                                                                                                                                                                                                                       }
                                                                                                                                                                                                                                     }
                                                                                                                                                                                                                                   }
                                                                                                                                                                                                                                 }
                                                                                                                                                                                                                                 container client-identifier {
                                                                                                                                                                                                                                   description "Identifier that the DHCP client provided for itself when it requested an address assignment";
                                                                                                                                                                                                                                   leaf hex-data-line {
                                                                                                                                                                                                                                     type string;
                                                                                                                                                                                                                                     description "Line of data in hexadecimal format";
                                                                                                                                                                                                                                   }
                                                                                                                                                                                                                                   leaf printable-data-line {
                                                                                                                                                                                                                                     type string;
                                                                                                                                                                                                                                     description "Line of data in printable format";
                                                                                                                                                                                                                                   }
                                                                                                                                                                                                                                 }
                                                                                                                                                                                                                               }
                                                                                                                                                                                                                             }
                                                                                                                                                                                                                             container client-identifier {
                                                                                                                                                                                                                               description "Identifier that the DHCP client provided for itself when it requested an address assignment";
                                                                                                                                                                                                                               leaf hex-data-line {
                                                                                                                                                                                                                                 type string;
                                                                                                                                                                                                                                 description "Line of data in hexadecimal format";
                                                                                                                                                                                                                               }
                                                                                                                                                                                                                               leaf printable-data-line {
                                                                                                                                                                                                                                 type string;
                                                                                                                                                                                                                                 description "Line of data in printable format";
                                                                                                                                                                                                                               }
                                                                                                                                                                                                                             }
                                                                                                                                                                                                                           }
                                                                                                                                                                                                                         }
                                                                                                                                                                                                                         container client-identifier {
                                                                                                                                                                                                                           description "Identifier that the DHCP client provided for itself when it requested an address assignment";
                                                                                                                                                                                                                           leaf hex-data-line {
                                                                                                                                                                                                                             type string;
                                                                                                                                                                                                                             description "Line of data in hexadecimal format";
                                                                                                                                                                                                                           }
                                                                                                                                                                                                                           leaf printable-data-line {
                                                                                                                                                                                                                             type string;
                                                                                                                                                                                                                             description "Line of data in printable format";
                                                                                                                                                                                                                           }
                                                                                                                                                                                                                         }
                                                                                                                                                                                                                       }
                                                                                                                                                                                                                     }
                                                                                                                                                                                                                     container client-identifier {
                                                                                                                                                                                                                       description "Identifier that the DHCP client provided for itself when it requested an address assignment";
                                                                                                                                                                                                                       leaf hex-data-line {
                                                                                                                                                                                                                         type string;
                                                                                                                                                                                                                         description "Line of data in hexadecimal format";
                                                                                                                                                                                                                       }
                                                                                                                                                                                                                       leaf printable-data-line {
                                                                                                                                                                                                                         type string;
                                                                                                                                                                                                                         description "Line of data in printable format";
                                                                                                                                                                                                                       }
                                                                                                                                                                                                                     }
                                                                                                                                                                                                                   }
                                                                                                                                                                                                                 }
                                                                                                                                                                                                                 container client-identifier {
                                                                                                                                                                                                                   description "Identifier that the DHCP client provided for itself when it requested an address assignment";
                                                                                                                                                                                                                   leaf hex-data-line {
                                                                                                                                                                                                                     type string;
                                                                                                                                                                                                                     description "Line of data in hexadecimal format";
                                                                                                                                                                                                                   }
                                                                                                                                                                                                                   leaf printable-data-line {
                                                                                                                                                                                                                     type string;
                                                                                                                                                                                                                     description "Line of data in printable format";
                                                                                                                                                                                                                   }
                                                                                                                                                                                                                 }
                                                                                                                                                                                                               }
                                                                                                                                                                                                             }
                                                                                                                                                                                                             container client-identifier {
                                                                                                                                                                                                               description "Identifier that the DHCP client provided for itself when it requested an address assignment";
                                                                                                                                                                                                               leaf hex-data-line {
                                                                                                                                                                                                                 type string;
                                                                                                                                                                                                                 description "Line of data in hexadecimal format";
                                                                                                                                                                                                               }
                                                                                                                                                                                                               leaf printable-data-line {
                                                                                                                                                                                                                 type string;
                                                                                                                                                                                                                 description "Line of data in printable format";
                                                                                                                                                                                                               }
                                                                                                                                                                                                             }
                                                                                                                                                                                                           }
                                                                                                                                                                                                         }
                                                                                                                                                                                                         container client-identifier {
                                                                                                                                                                                                           description "Identifier that the DHCP client provided for itself when it requested an address assignment";
                                                                                                                                                                                                           leaf hex-data-line {
                                                                                                                                                                                                             type string;
                                                                                                                                                                                                             description "Line of data in hexadecimal format";
                                                                                                                                                                                                           }
                                                                                                                                                                                                           leaf printable-data-line {
                                                                                                                                                                                                             type string;
                                                                                                                                                                                                             description "Line of data in printable format";
                                                                                                                                                                                                           }
                                                                                                                                                                                                         }
                                                                                                                                                                                                       }
                                                                                                                                                                                                     }
                                                                                                                                                                                                     container client-identifier {
                                                                                                                                                                                                       description "Identifier that the DHCP client provided for itself when it requested an address assignment";
                                                                                                                                                                                                       leaf hex-data-line {
                                                                                                                                                                                                         type string;
                                                                                                                                                                                                         description "Line of data in hexadecimal format";
                                                                                                                                                                                                       }
                                                                                                                                                                                                       leaf printable-data-line {
                                                                                                                                                                                                         type string;
                                                                                                                                                                                                         description "Line of data in printable format";
                                                                                                                                                                                                       }
                                                                                                                                                                                                     }
                                                                                                                                                                                                   }
                                                                                                                                                                                                 }
                                                                                                                                                                                                 container client-identifier {
                                                                                                                                                                                                   description "Identifier that the DHCP client provided for itself when it requested an address assignment";
                                                                                                                                                                                                   leaf hex-data-line {
                                                                                                                                                                                                     type string;
                                                                                                                                                                                                     description "Line of data in hexadecimal format";
                                                                                                                                                                                                   }
                                                                                                                                                                                                   leaf printable-data-line {
                                                                                                                                                                                                     type string;
                                                                                                                                                                                                     description "Line of data in printable format";
                                                                                                                                                                                                   }
                                                                                                                                                                                                 }
                                                                                                                                                                                               }
                                                                                                                                                                                             }
                                                                                                                                                                                             container client-identifier {
                                                                                                                                                                                               description "Identifier that the DHCP client provided for itself when it requested an address assignment";
                                                                                                                                                                                               leaf hex-data-line {
                                                                                                                                                                                                 type string;
                                                                                                                                                                                                 description "Line of data in hexadecimal format";
                                                                                                                                                                                               }
                                                                                                                                                                                               leaf printable-data-line {
                                                                                                                                                                                                 type string;
                                                                                                                                                                                                 description "Line of data in printable format";
                                                                                                                                                                                               }
                                                                                                                                                                                             }
                                                                                                                                                                                           }
                                                                                                                                                                                         }
                                                                                                                                                                                         container client-identifier {
                                                                                                                                                                                           description "Identifier that the DHCP client provided for itself when it requested an address assignment";
                                                                                                                                                                                           leaf hex-data-line {
                                                                                                                                                                                             type string;
                                                                                                                                                                                             description "Line of data in hexadecimal format";
                                                                                                                                                                                           }
                                                                                                                                                                                           leaf printable-data-line {
                                                                                                                                                                                             type string;
                                                                                                                                                                                             description "Line of data in printable format";
                                                                                                                                                                                           }
                                                                                                                                                                                         }
                                                                                                                                                                                       }
                                                                                                                                                                                     }
                                                                                                                                                                                     container client-identifier {
                                                                                                                                                                                       description "Identifier that the DHCP client provided for itself when it requested an address assignment";
                                                                                                                                                                                       leaf hex-data-line {
                                                                                                                                                                                         type string;
                                                                                                                                                                                         description "Line of data in hexadecimal format";
                                                                                                                                                                                       }
                                                                                                                                                                                       leaf printable-data-line {
                                                                                                                                                                                         type string;
                                                                                                                                                                                         description "Line of data in printable format";
                                                                                                                                                                                       }
                                                                                                                                                                                     }
                                                                                                                                                                                   }
                                                                                                                                                                                 }
                                                                                                                                                                                 container client-identifier {
                                                                                                                                                                                   description "Identifier that the DHCP client provided for itself when it requested an address assignment";
                                                                                                                                                                                   leaf hex-data-line {
                                                                                                                                                                                     type string;
                                                                                                                                                                                     description "Line of data in hexadecimal format";
                                                                                                                                                                                   }
                                                                                                                                                                                   leaf printable-data-line {
                                                                                                                                                                                     type string;
                                                                                                                                                                                     description "Line of data in printable format";
                                                                                                                                                                                   }
                                                                                                                                                                                 }
                                                                                                                                                                               }
                                                                                                                                                                             }
                                                                                                                                                                             container client-identifier {
                                                                                                                                                                               description "Identifier that the DHCP client provided for itself when it requested an address assignment";
                                                                                                                                                                               leaf hex-data-line {
                                                                                                                                                                                 type string;
                                                                                                                                                                                 description "Line of data in hexadecimal format";
                                                                                                                                                                               }
                                                                                                                                                                               leaf printable-data-line {
                                                                                                                                                                                 type string;
                                                                                                                                                                                 description "Line of data in printable format";
                                                                                                                                                                               }
                                                                                                                                                                             }
                                                                                                                                                                           }
                                                                                                                                                                         }
                                                                                                                                                                         container client-identifier {
                                                                                                                                                                           description "Identifier that the DHCP client provided for itself when it requested an address assignment";
                                                                                                                                                                           leaf hex-data-line {
                                                                                                                                                                             type string;
                                                                                                                                                                             description "Line of data in hexadecimal format";
                                                                                                                                                                           }
                                                                                                                                                                           leaf printable-data-line {
                                                                                                                                                                             type string;
                                                                                                                                                                             description "Line of data in printable format";
                                                                                                                                                                           }
                                                                                                                                                                         }
                                                                                                                                                                       }
                                                                                                                                                                     }
                                                                                                                                                                     container client-identifier {
                                                                                                                                                                       description "Identifier that the DHCP client provided for itself when it requested an address assignment";
                                                                                                                                                                       leaf hex-data-line {
                                                                                                                                                                         type string;
                                                                                                                                                                         description "Line of data in hexadecimal format";
                                                                                                                                                                       }
                                                                                                                                                                       leaf printable-data-line {
                                                                                                                                                                         type string;
                                                                                                                                                                         description "Line of data in printable format";
                                                                                                                                                                       }
                                                                                                                                                                     }
                                                                                                                                                                   }
                                                                                                                                                                 }
                                                                                                                                                                 container client-identifier {
                                                                                                                                                                   description "Identifier that the DHCP client provided for itself when it requested an address assignment";
                                                                                                                                                                   leaf hex-data-line {
                                                                                                                                                                     type string;
                                                                                                                                                                     description "Line of data in hexadecimal format";
                                                                                                                                                                   }
                                                                                                                                                                   leaf printable-data-line {
                                                                                                                                                                     type string;
                                                                                                                                                                     description "Line of data in printable format";
                                                                                                                                                                   }
                                                                                                                                                                 }
                                                                                                                                                               }
                                                                                                                                                             }
                                                                                                                                                             container client-identifier {
                                                                                                                                                               description "Identifier that the DHCP client provided for itself when it requested an address assignment";
                                                                                                                                                               leaf hex-data-line {
                                                                                                                                                                 type string;
                                                                                                                                                                 description "Line of data in hexadecimal format";
                                                                                                                                                               }
                                                                                                                                                               leaf printable-data-line {
                                                                                                                                                                 type string;
                                                                                                                                                                 description "Line of data in printable format";
                                                                                                                                                               }
                                                                                                                                                             }
                                                                                                                                                           }
                                                                                                                                                         }
                                                                                                                                                         container client-identifier {
                                                                                                                                                           description "Identifier that the DHCP client provided for itself when it requested an address assignment";
                                                                                                                                                           leaf hex-data-line {
                                                                                                                                                             type string;
                                                                                                                                                             description "Line of data in hexadecimal format";
                                                                                                                                                           }
                                                                                                                                                           leaf printable-data-line {
                                                                                                                                                             type string;
                                                                                                                                                             description "Line of data in printable format";
                                                                                                                                                           }
                                                                                                                                                         }
                                                                                                                                                       }
                                                                                                                                                     }
                                                                                                                                                     container client-identifier {
                                                                                                                                                       description "Identifier that the DHCP client provided for itself when it requested an address assignment";
                                                                                                                                                       leaf hex-data-line {
                                                                                                                                                         type string;
                                                                                                                                                         description "Line of data in hexadecimal format";
                                                                                                                                                       }
                                                                                                                                                       leaf printable-data-line {
                                                                                                                                                         type string;
                                                                                                                                                         description "Line of data in printable format";
                                                                                                                                                       }
                                                                                                                                                     }
                                                                                                                                                   }
                                                                                                                                                 }
                                                                                                                                                 container client-identifier {
                                                                                                                                                   description "Identifier that the DHCP client provided for itself when it requested an address assignment";
                                                                                                                                                   leaf hex-data-line {
                                                                                                                                                     type string;
                                                                                                                                                     description "Line of data in hexadecimal format";
                                                                                                                                                   }
                                                                                                                                                   leaf printable-data-line {
                                                                                                                                                     type string;
                                                                                                                                                     description "Line of data in printable format";
                                                                                                                                                   }
                                                                                                                                                 }
                                                                                                                                               }
                                                                                                                                             }
                                                                                                                                             container client-identifier {
                                                                                                                                               description "Identifier that the DHCP client provided for itself when it requested an address assignment";
                                                                                                                                               leaf hex-data-line {
                                                                                                                                                 type string;
                                                                                                                                                 description "Line of data in hexadecimal format";
                                                                                                                                               }
                                                                                                                                               leaf printable-data-line {
                                                                                                                                                 type string;
                                                                                                                                                 description "Line of data in printable format";
                                                                                                                                               }
                                                                                                                                             }
                                                                                                                                           }
                                                                                                                                         }
                                                                                                                                         container client-identifier {
                                                                                                                                           description "Identifier that the DHCP client provided for itself when it requested an address assignment";
                                                                                                                                           leaf hex-data-line {
                                                                                                                                             type string;
                                                                                                                                             description "Line of data in hexadecimal format";
                                                                                                                                           }
                                                                                                                                           leaf printable-data-line {
                                                                                                                                             type string;
                                                                                                                                             description "Line of data in printable format";
                                                                                                                                           }
                                                                                                                                         }
                                                                                                                                       }
                                                                                                                                     }
                                                                                                                                     container client-identifier {
                                                                                                                                       description "Identifier that the DHCP client provided for itself when it requested an address assignment";
                                                                                                                                       leaf hex-data-line {
                                                                                                                                         type string;
                                                                                                                                         description "Line of data in hexadecimal format";
                                                                                                                                       }
                                                                                                                                       leaf printable-data-line {
                                                                                                                                         type string;
                                                                                                                                         description "Line of data in printable format";
                                                                                                                                       }
                                                                                                                                     }
                                                                                                                                   }
                                                                                                                                 }
                                                                                                                                 container client-identifier {
                                                                                                                                   description "Identifier that the DHCP client provided for itself when it requested an address assignment";
                                                                                                                                   leaf hex-data-line {
                                                                                                                                     type string;
                                                                                                                                     description "Line of data in hexadecimal format";
                                                                                                                                   }
                                                                                                                                   leaf printable-data-line {
                                                                                                                                     type string;
                                                                                                                                     description "Line of data in printable format";
                                                                                                                                   }
                                                                                                                                 }
                                                                                                                               }
                                                                                                                             }
                                                                                                                             container client-identifier {
                                                                                                                               description "Identifier that the DHCP client provided for itself when it requested an address assignment";
                                                                                                                               leaf hex-data-line {
                                                                                                                                 type string;
                                                                                                                                 description "Line of data in hexadecimal format";
                                                                                                                               }
                                                                                                                               leaf printable-data-line {
                                                                                                                                 type string;
                                                                                                                                 description "Line of data in printable format";
                                                                                                                               }
                                                                                                                             }
                                                                                                                           }
                                                                                                                         }
                                                                                                                         container client-identifier {
                                                                                                                           description "Identifier that the DHCP client provided for itself when it requested an address assignment";
                                                                                                                           leaf hex-data-line {
                                                                                                                             type string;
                                                                                                                             description "Line of data in hexadecimal format";
                                                                                                                           }
                                                                                                                           leaf printable-data-line {
                                                                                                                             type string;
                                                                                                                             description "Line of data in printable format";
                                                                                                                           }
                                                                                                                         }
                                                                                                                       }
                                                                                                                     }
                                                                                                                     container client-identifier {
                                                                                                                       description "Identifier that the DHCP client provided for itself when it requested an address assignment";
                                                                                                                       leaf hex-data-line {
                                                                                                                         type string;
                                                                                                                         description "Line of data in hexadecimal format";
                                                                                                                       }
                                                                                                                       leaf printable-data-line {
                                                                                                                         type string;
                                                                                                                         description "Line of data in printable format";
                                                                                                                       }
                                                                                                                     }
                                                                                                                   }
                                                                                                                 }
                                                                                                                 container client-identifier {
                                                                                                                   description "Identifier that the DHCP client provided for itself when it requested an address assignment";
                                                                                                                   leaf hex-data-line {
                                                                                                                     type string;
                                                                                                                     description "Line of data in hexadecimal format";
                                                                                                                   }
                                                                                                                   leaf printable-data-line {
                                                                                                                     type string;
                                                                                                                     description "Line of data in printable format";
                                                                                                                   }
                                                                                                                 }
                                                                                                               }
                                                                                                             }
                                                                                                             container client-identifier {
                                                                                                               description "Identifier that the DHCP client provided for itself when it requested an address assignment";
                                                                                                               leaf hex-data-line {
                                                                                                                 type string;
                                                                                                                 description "Line of data in hexadecimal format";
                                                                                                               }
                                                                                                               leaf printable-data-line {
                                                                                                                 type string;
                                                                                                                 description "Line of data in printable format";
                                                                                                               }
                                                                                                             }
                                                                                                           }
                                                                                                         }
                                                                                                         container client-identifier {
                                                                                                           description "Identifier that the DHCP client provided for itself when it requested an address assignment";
                                                                                                           leaf hex-data-line {
                                                                                                             type string;
                                                                                                             description "Line of data in hexadecimal format";
                                                                                                           }
                                                                                                           leaf printable-data-line {
                                                                                                             type string;
                                                                                                             description "Line of data in printable format";
                                                                                                           }
                                                                                                         }
                                                                                                       }
                                                                                                     }
                                                                                                     container client-identifier {
                                                                                                       description "Identifier that the DHCP client provided for itself when it requested an address assignment";
                                                                                                       leaf hex-data-line {
                                                                                                         type string;
                                                                                                         description "Line of data in hexadecimal format";
                                                                                                       }
                                                                                                       leaf printable-data-line {
                                                                                                         type string;
                                                                                                         description "Line of data in printable format";
                                                                                                       }
                                                                                                     }
                                                                                                   }
                                                                                                 }
                                                                                                 container client-identifier {
                                                                                                   description "Identifier that the DHCP client provided for itself when it requested an address assignment";
                                                                                                   leaf hex-data-line {
                                                                                                     type string;
                                                                                                     description "Line of data in hexadecimal format";
                                                                                                   }
                                                                                                   leaf printable-data-line {
                                                                                                     type string;
                                                                                                     description "Line of data in printable format";
                                                                                                   }
                                                                                                 }
                                                                                               }
                                                                                             }
                                                                                             container client-identifier {
                                                                                               description "Identifier that the DHCP client provided for itself when it requested an address assignment";
                                                                                               leaf hex-data-line {
                                                                                                 type string;
                                                                                                 description "Line of data in hexadecimal format";
                                                                                               }
                                                                                               leaf printable-data-line {
                                                                                                 type string;
                                                                                                 description "Line of data in printable format";
                                                                                               }
                                                                                             }
                                                                                           }
                                                                                         }
                                                                                         container client-identifier {
                                                                                           description "Identifier that the DHCP client provided for itself when it requested an address assignment";
                                                                                           leaf hex-data-line {
                                                                                             type string;
                                                                                             description "Line of data in hexadecimal format";
                                                                                           }
                                                                                           leaf printable-data-line {
                                                                                             type string;
                                                                                             description "Line of data in printable format";
                                                                                           }
                                                                                         }
                                                                                       }
                                                                                     }
                                                                                     container client-identifier {
                                                                                       description "Identifier that the DHCP client provided for itself when it requested an address assignment";
                                                                                       leaf hex-data-line {
                                                                                         type string;
                                                                                         description "Line of data in hexadecimal format";
                                                                                       }
                                                                                       leaf printable-data-line {
                                                                                         type string;
                                                                                         description "Line of data in printable format";
                                                                                       }
                                                                                     }
                                                                                   }
                                                                                 }
                                                                                 container client-identifier {
                                                                                   description "Identifier that the DHCP client provided for itself when it requested an address assignment";
                                                                                   leaf hex-data-line {
                                                                                     type string;
                                                                                     description "Line of data in hexadecimal format";
                                                                                   }
                                                                                   leaf printable-data-line {
                                                                                     type string;
                                                                                     description "Line of data in printable format";
                                                                                   }
                                                                                 }
                                                                               }
                                                                             }
                                                                             container client-identifier {
                                                                               description "Identifier that the DHCP client provided for itself when it requested an address assignment";
                                                                               leaf hex-data-line {
                                                                                 type string;
                                                                                 description "Line of data in hexadecimal format";
                                                                               }
                                                                               leaf printable-data-line {
                                                                                 type string;
                                                                                 description "Line of data in printable format";
                                                                               }
                                                                             }
                                                                           }
                                                                         }
                                                                         container client-identifier {
                                                                           description "Identifier that the DHCP client provided for itself when it requested an address assignment";
                                                                           leaf hex-data-line {
                                                                             type string;
                                                                             description "Line of data in hexadecimal format";
                                                                           }
                                                                           leaf printable-data-line {
                                                                             type string;
                                                                             description "Line of data in printable format";
                                                                           }
                                                                         }
                                                                       }
                                                                     }
                                                                     container client-identifier {
                                                                       description "Identifier that the DHCP client provided for itself when it requested an address assignment";
                                                                       leaf hex-data-line {
                                                                         type string;
                                                                         description "Line of data in hexadecimal format";
                                                                       }
                                                                       leaf printable-data-line {
                                                                         type string;
                                                                         description "Line of data in printable format";
                                                                       }
                                                                     }
                                                                   }
                                                                 }
                                                                 container client-identifier {
                                                                   description "Identifier that the DHCP client provided for itself when it requested an address assignment";
                                                                   leaf hex-data-line {
                                                                     type string;
                                                                     description "Line of data in hexadecimal format";
                                                                   }
                                                                   leaf printable-data-line {
                                                                     type string;
                                                                     description "Line of data in printable format";
                                                                   }
                                                                 }
                                                               }
                                                             }
                                                             container client-identifier {
                                                               description "Identifier that the DHCP client provided for itself when it requested an address assignment";
                                                               leaf hex-data-line {
                                                                 type string;
                                                                 description "Line of data in hexadecimal format";
                                                               }
                                                               leaf printable-data-line {
                                                                 type string;
                                                                 description "Line of data in printable format";
                                                               }
                                                             }
                                                           }
                                                         }
                                                         container client-identifier {
                                                           description "Identifier that the DHCP client provided for itself when it requested an address assignment";
                                                           leaf hex-data-line {
                                                             type string;
                                                             description "Line of data in hexadecimal format";
                                                           }
                                                           leaf printable-data-line {
                                                             type string;
                                                             description "Line of data in printable format";
                                                           }
                                                         }
                                                       }
                                                     }
                                                     container client-identifier {
                                                       description "Identifier that the DHCP client provided for itself when it requested an address assignment";
                                                       leaf hex-data-line {
                                                         type string;
                                                         description "Line of data in hexadecimal format";
                                                       }
                                                       leaf printable-data-line {
                                                         type string;
                                                         description "Line of data in printable format";
                                                       }
                                                     }
                                                   }
                                                 }
                                                 container client-identifier {
                                                   description "Identifier that the DHCP client provided for itself when it requested an address assignment";
                                                   leaf hex-data-line {
                                                     type string;
                                                     description "Line of data in hexadecimal format";
                                                   }
                                                   leaf printable-data-line {
                                                     type string;
                                                     description "Line of data in printable format";
                                                   }
                                                 }
                                               }
                                             }
                                             container client-identifier {
                                               description "Identifier that the DHCP client provided for itself when it requested an address assignment";
                                               leaf hex-data-line {
                                                 type string;
                                                 description "Line of data in hexadecimal format";
                                               }
                                               leaf printable-data-line {
                                                 type string;
                                                 description "Line of data in printable format";
                                               }
                                             }
                                           }
                                         }
                                         container client-identifier {
                                           description "Identifier that the DHCP client provided for itself when it requested an address assignment";
                                           leaf hex-data-line {
                                             type string;
                                             description "Line of data in hexadecimal format";
                                           }
                                           leaf printable-data-line {
                                             type string;
                                             description "Line of data in printable format";
                                           }
                                         }
                                       }
                                     }
                                     container client-identifier {
                                       description "Identifier that the DHCP client provided for itself when it requested an address assignment";
                                       leaf hex-data-line {
                                         type string;
                                         description "Line of data in hexadecimal format";
                                       }
                                       leaf printable-data-line {
                                         type string;
                                         description "Line of data in printable format";
                                       }
                                     }
                                   }
                                 }
                                 container client-identifier {
                                   description "Identifier that the DHCP client provided for itself when it requested an address assignment";
                                   leaf hex-data-line {
                                     type string;
                                     description "Line of data in hexadecimal format";
                                   }
                                   leaf printable-data-line {
                                     type string;
                                     description "Line of data in printable format";
                                   }
                                 }
                               }
                             }
                             container client-identifier {
                               description "Identifier that the DHCP client provided for itself when it requested an address assignment";
                               leaf hex-data-line {
                                 type string;
                                 description "Line of data in hexadecimal format";
                               }
                               leaf printable-data-line {
                                 type string;
                                 description "Line of data in printable format";
                               }
                             }
                           }
                         }
                         container client-identifier {
                           description "Identifier that the DHCP client provided for itself when it requested an address assignment";
                           leaf hex-data-line {
                             type string;
                             description "Line of data in hexadecimal format";
                           }
                           leaf printable-data-line {
                             type string;
                             description "Line of data in printable format";
                           }
                         }
                       }
                     }
                     container client-identifier {
                       description "Identifier that the DHCP client provided for itself when it requested an address assignment";
                       leaf hex-data-line {
                         type string;
                         description "Line of data in hexadecimal format";
                       }
                       leaf printable-data-line {
                         type string;
                         description "Line of data in printable format";
                       }
                     }
                   }
                 }
                 container client-identifier {
                   description "Identifier that the DHCP client provided for itself when it requested an address assignment";
                   leaf hex-data-line {
                     type string;
                     description "Line of data in hexadecimal format";
                   }
                   leaf printable-data-line {
                     type string;
                     description "Line of data in printable format";
                   }
                 }
               }
             }
             container client-identifier {
               description "Identifier that the DHCP client provided for itself when it requested an address assignment";
               leaf hex-data-line {
                 type string;
                 description "Line of data in hexadecimal format";
               }
               leaf printable-data-line {
                 type string;
                 description "Line of data in printable format";
               }
             }
           }
         }
         container client-identifier {
           description "Identifier that the DHCP client provided for itself when it requested an address assignment";
           leaf hex-data-line {
             type string;
             description "Line of data in hexadecimal format";
           }
           leaf printable-data-line {
             type string;
             description "Line of data in printable format";
           }
         }
       }
     }
   }
 }
 grouping dhcp-conflict-information-block {
   list dhcp-conflict {
     description "Information about a Dynamic Host Configuration Protocol conflict. A conflict arises when an address assigned to DHCP client is already assigned to another entity (computer or interface, for example).";
     leaf detection-time {
       type string;
       description "Time when the conflict was detected, in the format YYYY-MM-DD hh:mm:ss TZ (year, month, date, hour in 24-hour format, minute, second, time zone)";
     }
     leaf detection-method {
       type string;
       description "Method used to detect the conflict";
     }
     leaf conflict-address {
       type ipaddr;
       description "IPv4 address that is already in use by another host";
     }
   }
 }
 grouping dhcp-global-information-block {
   leaf bootp-lease-length {
     type string;
     description "Duration of address assignments to bootstrap protocol (BOOTP) clients";
   }
   leaf bootp-lease-cutoff {
     type string;
     description "Time at which address assignments to all bootstrap protocol (BOOTP) clients expire, in the format YYYY-MM-DD hh:mm:ss TZ (year, month, date, hour in 24-hour format, minute, second, time zone). The duration of an address assignment to a BOOTP client is set to the number of seconds between the assignment time and this time.";
   }
   container dhcp-lease-time-information {
     description "Information about configured default, maximum, and minimum duration for address assignments";
     leaf default-lease-time {
       type string;
       description "Duration of an address assignment when the DHCP client does not specify a duration in its request";
     }
     leaf minimum-lease-time {
       type string;
       description "Minimum possible duration of an address assignment";
     }
     leaf maximum-lease-time {
       type string;
       description "Maximum possible duration of an address assignment";
     }
   }
   container dhcp-option-table {
     description "Information about one or more Dynamic Host Configuration Protocol options that are associated with the address assignment";
     list dhcp-option {
       description "Information about a Dynamic Host Configuration Protocol option that is associated with the address assignment";
       leaf dhcp-option-code {
         type int32;
         description "Numeric code assigned to the DHCP option";
       }
       leaf dhcp-option-name {
         type string;
         description "Name of the DHCP option";
       }
       leaf dhcp-option-type {
         type string;
         description "Type of value for the DHCP option (for example, string [word], integer, IP address)";
       }
       leaf dhcp-option-value {
         type string;
         description "Value of the DHCP option";
       }
     }
   }
 }
 grouping dhcp-pool-information-block {
   container tabular {
     description "Information about one or more Dynamic Host Configuration Protocol address pools";
     list dhcp-pool {
       description "Information about a Dynamic Host Configuration Protocol address pool";
       leaf address-pool-name {
         type string;
         description "Name of the address pool";
       }
       leaf address-pool-low-address {
         type ipaddr;
         description "Lowest IP address that can be assigned from the pool";
       }
       leaf address-pool-high-address {
         type ipaddr;
         description "Highest IP address that can be assigned from the pool";
       }
       leaf address-pool-excluded-address {
         type ipaddr;
         description "IP address that the DHCP relay process does not assign even though the address is in the configured range of addresses in the address pool";
       }
       container dhcp-option-table {
         description "Information about one or more Dynamic Host Configuration Protocol options that are associated with the address assignment";
         list dhcp-option {
           description "Information about a Dynamic Host Configuration Protocol option that is associated with the address assignment";
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
     }
   }
   container summary {
     description "Information about one or more Dynamic Host Configuration Protocol address pools";
     list dhcp-pool {
       description "Information about a Dynamic Host Configuration Protocol address pool";
       leaf address-pool-name {
         type string;
         description "Name of the address pool";
       }
       leaf address-pool-low-address {
         type ipaddr;
         description "Lowest IP address that can be assigned from the pool";
       }
       leaf address-pool-high-address {
         type ipaddr;
         description "Highest IP address that can be assigned from the pool";
       }
       leaf assigned-lease-count {
         type int32;
         description "Number of addresses currently assigned";
       }
       leaf address-count {
         type int32;
         description "Number of addresses in the pool";
       }
       leaf address-pool-excluded-address {
         type ipaddr;
         description "IP address that the DHCP relay process does not assign even though the address is in the configured range of addresses in the address pool";
       }
       container dhcp-option-table {
         description "Information about one or more Dynamic Host Configuration Protocol options that are associated with the address assignment";
         list dhcp-option {
           description "Information about a Dynamic Host Configuration Protocol option that is associated with the address assignment";
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
     }
   }
   container detail {
     description "Information about one or more Dynamic Host Configuration Protocol address pools";
     list dhcp-pool {
       description "Information about a Dynamic Host Configuration Protocol address pool";
       leaf address-pool-name {
         type string;
         description "Name of the address pool";
       }
       leaf address-pool-low-address {
         type ipaddr;
         description "Lowest IP address that can be assigned from the pool";
       }
       leaf address-pool-high-address {
         type ipaddr;
         description "Highest IP address that can be assigned from the pool";
       }
       leaf assigned-lease-count {
         type int32;
         description "Number of addresses currently assigned";
       }
       leaf address-count {
         type int32;
         description "Number of addresses in the pool";
       }
       leaf active-lease-count {
         type int32;
         description "Number of active address assignments";
       }
       leaf offered-lease-count {
         type int32;
         description "Number of address assignments offered";
       }
       leaf expired-lease-count {
         type int32;
         description "Number of expired address assignments";
       }
       leaf conflict-count {
         type int32;
         description "Number of addresses in conflict";
       }
       leaf exclusion-count {
         type int32;
         description "Number of addresses excluded from the address pool";
       }
       leaf address-pool-excluded-address {
         type ipaddr;
         description "IP address that the DHCP relay process does not assign even though the address is in the configured range of addresses in the address pool";
       }
       container dhcp-lease-time-information {
         description "Information about configured default, maximum, and minimum duration for address assignments";
       }
       container dhcp-option-table {
         description "Information about one or more Dynamic Host Configuration Protocol options that are associated with the address assignment";
         list dhcp-option {
           description "Information about a Dynamic Host Configuration Protocol option that is associated with the address assignment";
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
     }
   }
 }
 grouping dhcp-statistics-information-block {
   leaf dropped-packet-total {
     type uint32;
     description "Total number of packets discarded by the DHCP relay process because of errors";
   }
   leaf dropped-packet-bad-hardware {
     type uint32;
     description "Number of packets discarded by the DHCP relay process because they specified an invalid hardware address";
   }
   leaf dropped-packet-bad-opcode {
     type uint32;
     description "Number of packets discarded by the DHCP relay process because they specified an invalid operation code";
   }
   leaf dropped-packet-bad-options {
     type uint32;
     description "Number of packets discarded by the DHCP relay process because they specified invalid options";
   }
   leaf dropped-packet-invalid-server-address {
     type uint32;
     description "Number of packets discarded by the DHCP relay process because they specified an invalid server address";
   }
   leaf dropped-packet-no-addresses {
     type uint32;
     description "Number of packets discarded by the DHCP relay process because there were no addresses available for it to assign";
   }
   leaf dropped-packet-no-interface {
     type uint32;
     description "Number of packets discarded by the DHCP relay process because of an interface mismatch";
   }
   leaf dropped-packet-no-routing-instance {
     type uint32;
     description "Number of packets discarded by the DHCP relay process because of a routing-instance mismatch";
   }
   leaf dropped-packet-no-local-address {
     type uint32;
     description "Number of packets discarded by the DHCP relay process because there was no valid local address";
   }
   leaf dropped-packet-too-short {
     type uint32;
     description "Number of packets discarded by the DHCP relay process because they were too short";
   }
   leaf dropped-packet-read-error {
     type uint32;
     description "Number of packets discarded by the DHCP relay process because of a read error";
   }
   leaf dropped-packet-send-error {
     type uint32;
     description "Number of packets that the DHCP relay process could not send";
   }
   list message-table {
     description "Information about one or more DHCP or bootstrap protocol (BOOTP) messages sent or received by the DHCP relay process";
     leaf message-direction {
       type string;
       description "Indicator of whether the DHCP relay process sent or received the messages";
     }
     list message {
       description "Information about a DHCP or BOOTP message";
       leaf message-name {
         type string;
         description "Name of the message";
       }
       leaf message-count {
         type uint32;
         description "Number of times the DCHP relay process received or sent the message";
       }
     }
   }
 }
 grouping dhcp-client-information-block {
   container information {
     description "Information about one or more Dynamic Host Configuration Protocol clients";
     list dhcp-client {
       description "Information about a DHCP client";
       leaf logical-interface {
         type string;
         description "Interface name";
       }
       leaf mac-address {
         type mac-addr;
         description "Media access control (hardware) address of the DHCP client";
       }
       leaf client-status {
         type string;
         description "Status of the DHCP client interface";
       }
       leaf vendor-identifier {
         type string;
         description "Vendor identifier of the client interface";
       }
       leaf server-address {
         type ipaddr;
         description "IP address of the DHCP server";
       }
       leaf address-obtained {
         type ipaddr;
         description "IP address obtained by DHCP client interface";
       }
       leaf update-server {
         type string;
         description "Update server flag to update TCP/IP settings downstream";
       }
       leaf lease-obtained {
         type string;
         description "Time at which lease is obtained";
       }
       leaf lease-expires-in-seconds {
         type int32;
         description "No: of seconds lease will expire in";
       }
       leaf lease-expires {
         type string;
         description "Time at which lease expires";
       }
       container dhcp-option-table {
         description "Information about one or more Dynamic Host Configuration Protocol options that are associated with the address assignment";
         list dhcp-option {
           description "Information about a Dynamic Host Configuration Protocol option that is associated with the address assignment";
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
     }
   }
 }
 grouping dhcp-helper-statistics-block {
   list helper-statistics-service-information {
     description "Port forwarding helper statistics for a particular service";
     leaf service-name {
       type string;
       description "Name of this service";
     }
     leaf received-packets {
       type int32;
       description "Number of packets received";
     }
     leaf forwarded-packets {
       type int32;
       description "Number of packets forwarded";
     }
     leaf dropped-packets {
       type int32;
       description "Number of packets dropped";
     }
     leaf dropped-packets-no-interface {
       type int32;
       description "Number of packets dropped because of missing interface";
     }
     leaf dropped-packets-no-rtinst {
       type int32;
       description "Number of packets dropped because of missing routing instance";
     }
     leaf dropped-packets-badread {
       type int32;
       description "Number of packets dropped because of an error during the packet read";
     }
     leaf dropped-packets-badsend {
       type int32;
       description "Number of packets dropped because of an error during the packet send";
     }
     leaf dropped-packets-badaddr {
       type int32;
       description "Number of packets dropped because of an invalid server address";
     }
     leaf dropped-packets-no-localaddr {
       type int32;
       description "Number of packets dropped because of missing valid local address";
     }
     leaf dropped-packets-no-route {
       type int32;
       description "Number of packets dropped because of missing route to server/client";
     }
   }
 }
 grouping core-information-block {
   container brief {
     leaf process-name {
       type string;
       description "Process name";
     }
     leaf signal-number {
       type string;
       description "Signal number";
     }
     leaf signal-description {
       type string;
       description "Description of signal";
     }
     leaf stack-trace {
       type string;
       description "Stack trace of the core file";
     }
   }
   container detail {
     leaf process-name {
       type string;
       description "Process name";
     }
     leaf signal-number {
       type string;
       description "Signal number";
     }
     leaf signal-description {
       type string;
       description "Description of signal";
     }
     leaf release {
       type string;
       description "Release name";
     }
     leaf build-server {
       type string;
       description "Build server";
     }
     leaf binary-path {
       type string;
       description "Binary path of the process";
     }
     leaf build-date {
       type string;
       description "Build date";
     }
     leaf stack-trace {
       type string;
       description "Stack trace of the core file";
     }
     leaf binary-details {
       type string;
       description "Detailed information about the binary of core file";
     }
   }
 }
 grouping directory-usage-information-block {
   container directory {
     description "Information about system directory usage";
     leaf used-space {
       type string;
       description "Total amount of space used";
     }
     leaf directory-name {
       type string;
       description "Directory name";
     }
   }
 }
 grouping auto-snapshot-information-block {
   leaf auto-snapshot-configuration {
     type string;
     description "Autosnapshot configuration";
   }
   leaf auto-snapshot-state {
     type string;
     description "Autosnapshot current state";
   }
   leaf auto-snapshot-note {
     type string;
     description "Autosnapshot note";
   }
 }
 grouping snapshot-information-block {
   leaf snapshot-medium {
     type string;
     description "Media type of the snapshot";
   }
   leaf creation-date {
     type string;
     description "Snapshot creation date";
   }
   container inform {
     leaf source-daemon {
       type string;
     }
     leaf message {
       type string;
       description "Syslog message text";
     }
   }
   container snapshot-copy {
     leaf source-directory {
       type string;
       description "Directory to backup";
     }
     leaf destination-directory {
       type string;
       description "Backup directory";
     }
   }
   container archived-directory-list {
     leaf directory-name {
       type string;
       description "Directory name";
     }
   }
   container snapshot-partitions {
     description "Partitions on snapshot medium";
     list partition-information {
       description "Partition information";
       leaf partition {
         type string;
         description "Partition letter";
       }
       leaf mount-point {
         type string;
         description "Mount point";
       }
       leaf partition-size {
         type string;
         description "Size of partition";
       }
       leaf snapshot-argument {
         type string;
         description "Argument to snapshot used to configure size";
       }
     }
   }
   container software-version {
     description "Version of software snapshot";
     list package {
       description "Package in software snapshot";
       leaf package-name {
         type string;
         description "Name of software package";
       }
       leaf package-version {
         type string;
         description "Version of software package";
       }
     }
   }
 }
 grouping software-installation-status-block {
 }
 grouping package-backup-information-block {
   container package-backup {
     leaf file-name {
       type string;
       description "File name";
     }
     leaf file-size {
       type int32;
       description "File size";
     }
   }
 }
 grouping system-processes-health-information-block {
   list process-health {
     description "Information about the health of a process";
     leaf pid {
       type uint32;
       description "Process identifier";
     }
     leaf process-name {
       type string;
       description "Process name";
     }
     leaf provider-prefix {
       type string;
       description "Provider identification prefix";
     }
     container process-family-tree {
       description "Parent and child information for a process";
       container parent-process {
         description "Parent process";
       }
       container child-processes {
         description "Child process";
         leaf number-child-processes {
           type int32;
           description "Number of child processes";
         }
         list process-list {
           description "List of processes";
           container process-information {
             description "Information about a process";
             leaf pid {
               type uint32;
               description "Process identifier";
             }
             leaf process-name {
               type string;
               description "Process name";
             }
           }
         }
       }
     }
     container cpu-information {
       description "Information about CPU usage by a process";
       leaf cpu-time-accumulated {
         type string;
         description "Amount of user and system time used by a process";
       }
     }
     container heartbeat-information {
       description "Information about heartbeat updates from process";
       leaf interval {
         type string;
         description "Length of time between heartbeat pulses";
       }
       leaf grace-count {
         type uint32;
         description "Maximum number of consecutive heartbeat pulses missed beforeprocess is considered dead";
       }
       leaf last-seen {
         type string;
         description "Length of time since the last heartbeat pulse was seen";
       }
       leaf missed {
         type uint32;
         description "Number of consecutive heartbeat pulses missed";
       }
       leaf total-missed {
         type uint32;
         description "Total number of missed heartbeat pulses";
       }
     }
     container resource-utilization {
       description "Resources used by a process";
       list resource {
         description "Resource information";
       }
     }
   }
 }
 grouping secpolinfo-policy-information-block {
   list secpolinfo-policy {
     list brief {
       container resource-utilization {
         description "Resources used by a process";
         list resource {
           description "Resource information";
         }
       }
     }
     list detail {
       leaf secpolinfo-policy-provider-id {
         type string;
         description "16-bit ID assigned to the provider";
       }
       leaf secpolinfo-policy-provider-prefix {
         type string;
         description "Prefix assigned to the provider";
       }
       leaf secpolinfo-policy-applied-role {
         type string;
         description "Role applied to the process";
       }
       leaf secpolinfo-policy-applied-policy {
         type string;
         description "Policy which defines the applied role";
       }
       leaf secpolinfo-policy-inherited-role {
         type string;
         description "Role inherited by the role applied to the process";
       }
       leaf secpolinfo-policy-inherited-policy {
         type string;
         description "Policy which defines the inherited role";
       }
       container resource-utilization {
         description "Resources used by a process";
         list resource {
           description "Resource information";
         }
       }
     }
   }
 }
 grouping statistics-block {
   container tcp {
     leaf packets-sent {
       type uint32;
       description "Packets sent";
     }
     leaf sent-data-packets {
       type uint32;
       description "Data packets";
     }
     leaf data-packets-bytes {
       type uint32;
       description "In terms of bytes";
     }
     leaf sent-data-packets-retransmitted {
       type uint32;
       description "Data packets retransmitted";
     }
     leaf retransmitted-bytes {
       type uint32;
       description "In terms of bytes";
     }
     leaf sent-resends-by-mtu-discovery {
       type uint32;
       description "Resends initiated by MTU discovery";
     }
     leaf sent-ack-only-packets {
       type uint32;
       description "Ack-only packets";
     }
     leaf sent-packets-delayed {
       type uint32;
       description "Number of packets delayed";
     }
     leaf sent-urg-only-packets {
       type uint32;
       description "URG only packets";
     }
     leaf sent-window-probe-packets {
       type uint32;
       description "Window probe packets";
     }
     leaf sent-window-update-packets {
       type uint32;
       description "Window update packets";
     }
     leaf sent-control-packets {
       type uint32;
       description "Control packets";
     }
     leaf packets-received {
       type uint32;
       description "Packets received";
     }
     leaf received-acks {
       type uint32;
       description "Acks";
     }
     leaf acks-bytes {
       type uint32;
       description "Number of bytes";
     }
     leaf received-duplicate-acks {
       type uint32;
       description "Dupliacte acks";
     }
     leaf received-acks-for-unsent-data {
       type uint32;
       description "Acks for unsent data";
     }
     leaf packets-received-in-sequence {
       type uint32;
       description "Packets received in-sequence";
     }
     leaf in-sequence-bytes {
       type uint32;
       description "Packets received in-sequence in bytes";
     }
     leaf received-completely-duplicate-packet {
       type uint32;
       description "Completely duplicate packets";
     }
     leaf duplicate-in-bytes {
       type uint32;
       description "Completely duplicate packets in bytes";
     }
     leaf received-old-duplicate-packets {
       type uint32;
       description "Old duplicate packets";
     }
     leaf received-packets-with-some-dupliacte-data {
       type uint32;
       description "Packets with some duplicate data";
     }
     leaf some-duplicate-in-bytes {
       type uint32;
       description "Packets with some duplicate data in bytes";
     }
     leaf received-out-of-order-packets {
       type uint32;
       description "Out-of-order packets";
     }
     leaf out-of-order-in-bytes {
       type uint32;
       description "Out-of-order packets in bytes";
     }
     leaf received-packets-of-data-after-window {
       type uint32;
       description "Packets of data after window";
     }
     leaf bytes {
       type uint32;
       description "Packets of data after window in bytes";
     }
     leaf received-window-probes {
       type uint32;
       description "Window probes";
     }
     leaf received-window-update-packets {
       type uint32;
     }
     leaf packets-received-after-close {
       type uint32;
       description "Packets received after close";
     }
     leaf received-discarded-for-bad-checksum {
       type uint32;
       description "Discarded for bad checksum";
     }
     leaf received-discarded-for-bad-header-offset {
       type uint32;
       description "Discarded for bad header offset fields";
     }
     leaf received-discarded-because-packet-too-short {
       type uint32;
       description "Discarded because packet too short";
     }
     leaf connection-requests {
       type uint32;
       description "Connection requests";
     }
     leaf connection-accepts {
       type uint32;
       description "Connection accepts";
     }
     leaf bad-connection-attempts {
       type uint32;
       description "Bad connection attempts";
     }
     leaf listen-queue-overflows {
       type uint32;
       description "Listen queue overflows";
     }
     leaf connections-established {
       type uint32;
       description "Connections established";
     }
     leaf connections-closed {
       type uint32;
       description "Connections closed";
     }
     leaf drops {
       type uint32;
       description "Drops";
     }
     leaf connections-updated-rtt-on-close {
       type uint32;
       description "Connections updated cached RTT on close";
     }
     leaf connections-updated-variance-on-close {
       type uint32;
       description "Connections updated cached RTT variance on close";
     }
     leaf connections-updated-ssthresh-on-close {
       type uint32;
       description "Connections updated cached ssthresh on close";
     }
     leaf embryonic-connections-dropped {
       type uint32;
       description "Embryonic connections dropped";
     }
     leaf segments-updated-rtt {
       type uint32;
       description "Segments updated RTT";
     }
     leaf attempts {
       type uint32;
       description "Attempts";
     }
     leaf retransmit-timeouts {
       type uint32;
       description "Retransmit timeouts";
     }
     leaf connections-dropped-by-retransmit-timeout {
       type uint32;
       description "Connections dropped";
     }
     leaf persist-timeouts {
       type uint32;
       description "Persist timeouts";
     }
     leaf connections-dropped-by-persist-timeout {
       type uint32;
     }
     leaf keepalive-timeouts {
       type uint32;
       description "Keepalive timeouts";
     }
     leaf keepalive-probes-sent {
       type uint32;
       description "Keepalive probes sent";
     }
     leaf keepalive-connections-dropped {
       type uint32;
       description "Keepalive connections dropped";
     }
     leaf ack-header-predictions {
       type uint32;
       description "Correct ACK header predictions";
     }
     leaf data-packet-header-predictions {
       type uint32;
       description "Correct data packet header predictions";
     }
     leaf syncache-entries-added {
       type uint32;
       description "Syncache entries added";
     }
     leaf retransmitted {
       type uint32;
       description "Retransmitted in syncache entries added";
     }
     leaf dupsyn {
       type uint32;
       description "Dupsyn in syncache entries added";
     }
     leaf dropped {
       type uint32;
       description "Dropped in syncache entries added";
     }
     leaf completed {
       type uint32;
       description "Completed in syncache entries added";
     }
     leaf bucket-overflow {
       type uint32;
       description "Bucket overflow in syncache entries added";
     }
     leaf cache-overflow {
       type uint32;
       description "Cache overflow in syncache entries added";
     }
     leaf reset {
       type uint32;
       description "Reset in syncache entries added";
     }
     leaf stale {
       type uint32;
       description "Stale in syncache entries added";
     }
     leaf aborted {
       type uint32;
       description "Aborted in syncache entries added";
     }
     leaf badack {
       type uint32;
       description "Bad ACK in syncache entries added";
     }
     leaf unreach {
       type uint32;
       description "Unreach in syncache entries added";
     }
     leaf zone-failures {
       type uint32;
       description "Zone failures in syncache entries added";
     }
     leaf cookies-sent {
       type uint32;
       description "Cookies sent";
     }
     leaf cookies-received {
       type uint32;
       description "Cookies received";
     }
     leaf sack-recovery-episodes {
       type uint32;
       description "SACK recovery episodes";
     }
     leaf segment-retransmits {
       type uint32;
       description "Segment retransmits in SACK recovery episodes";
     }
     leaf byte-retransmits {
       type uint32;
       description "Byte retransmits in SACK recovery episodes";
     }
     leaf sack-options-received {
       type uint32;
       description "SACK options (SACK blocks) received";
     }
     leaf sack-opitions-sent {
       type uint32;
       description "SACK options (SACK blocks) sent";
     }
     leaf sack-scoreboard-overflow {
       type uint32;
       description "SACK scoreboard overflow";
     }
     leaf acks-sent-in-response-but-not-exact-rsts {
       type uint32;
       description "ACKs sent in response to in-window but not exact RSTs";
     }
     leaf acks-sent-in-response-to-syns-on-established-connections {
       type uint32;
       description "ACKs sent in response to in-window SYNs on established connections";
     }
     leaf rcv-packets-dropped-due-to-bad-address {
       type uint32;
       description "Rcv packets dropped dropped by TCP due to bad address";
     }
     leaf out-of-sequence-segment-drops {
       type uint32;
       description "Out-of-sequence segment drops due to insufficient memory";
     }
     leaf rst-packets {
       type uint32;
       description "RST packets";
     }
     leaf icmp-packets-ignored {
       type uint32;
       description "ICMP packets ignored by TCP";
     }
     leaf send-packets-dropped {
       type uint32;
       description "Send packets dropped by TCP due to auth errors";
     }
     leaf rcv-packets-dropped {
       type uint32;
     }
     leaf outgoing-segments-dropped {
       type uint32;
       description "Outgoing segments dropped due to policing";
     }
   }
   container udp {
     leaf datagrams-received {
       type uint32;
       description "Datagrams received";
     }
     leaf datagrams-with-incomplete-header {
       type uint32;
       description "Datagrams with incomplete header";
     }
     leaf datagrams-with-bad-datalength-field {
       type uint32;
       description "Datagrams with bad data length field";
     }
     leaf datagrams-with-bad-checksum {
       type uint32;
       description "Datagrams with bad checksum";
     }
     leaf datagrams-dropped-due-to-no-socket {
       type uint32;
       description "Datagrams dropped due to no socket";
     }
     leaf broadcast-or-multicast-datagrams-dropped-due-to-no-socket {
       type uint32;
       description "Broadcast/multicast datagrams dropped due to no socket";
     }
     leaf datagrams-dropped-due-to-full-socket-buffers {
       type uint32;
       description "Datagrams dropped due to full socket buffers";
     }
     leaf datagrams-not-for-hashed-pcb {
       type uint32;
       description "Datagrams not for hashed pcb";
     }
     leaf datagrams-delivered {
       type uint32;
       description "Datagrams delivered";
     }
     leaf datagrams-output {
       type uint32;
       description "Datagrams output";
     }
   }
   container ip {
     leaf packets-received {
       type uint32;
       description "Packets received";
     }
     leaf bad-header-checksums {
       type uint32;
       description "Bad header checksums";
     }
     leaf packets-with-size-smaller-than-minimum {
       type uint32;
       description "Packets with size smaller than minimum";
     }
     leaf packets-with-data-size-less-than-datalength {
       type uint32;
       description "Packets with data size < data length";
     }
     leaf packets-with-header-length-less-than-data-size {
       type uint32;
       description "Packets with header length < data size";
     }
     leaf packets-with-data-length-less-than-headerlength {
       type uint32;
       description "Packets with data length < header length";
     }
     leaf packets-with-incorrect-version-number {
       type uint32;
       description "Packets with incorrect version number";
     }
     leaf packets-destined-to-dead-next-hop {
       type uint32;
       description "Packets destined to dead nexthop";
     }
     leaf fragments-received {
       type uint32;
       description "Fragments received";
     }
     leaf fragments-dropped-due-to-outofspace-or-dup {
       type uint32;
       description "Fragments dropped due to out of space/dup";
     }
     leaf fragments-dropped-due-to-queueoverflow {
       type uint32;
       description "Fragment sessions dropped due to queue overflow";
     }
     leaf fragments-dropped-after-timeout {
       type uint32;
       description "Fragments dropped after timeout";
     }
     leaf packets-reassembled-ok {
       type uint32;
       description "Packets reassembled ok";
     }
     leaf packets-for-this-host {
       type uint32;
       description "Packets-for-this-host";
     }
     leaf packets-for-unknown-or-unsupported-protocol {
       type uint32;
       description "Packets for unknown/unsupported protocol";
     }
     leaf packets-forwarded {
       type uint32;
       description "Packets forwarded";
     }
     leaf packets-not-forwardable {
       type uint32;
       description "Packets not forwardable";
     }
     leaf redirects-sent {
       type uint32;
       description "Redirects sent";
     }
     leaf packets-sent-from-this-host {
       type uint32;
       description "Packets sent from this host";
     }
     leaf packets-sent-with-fabricated-ip-header {
       type uint32;
       description "Packets sent with fabricated ip header";
     }
     leaf output-packets-dropped-due-to-no-bufs {
       type uint32;
       description "Output packets dropped due to no bufs";
     }
     leaf output-packets-discarded-due-to-no-route {
       type uint32;
       description "Output packets discarded due to no route";
     }
     leaf output-datagrams-fragmented {
       type uint32;
       description "Output datagrams fragmented";
     }
     leaf fragments-created {
       type uint32;
       description "Fragments created";
     }
     leaf datagrams-that-can-not-be-fragmented {
       type uint32;
       description "Datagrams that can't be fragmented";
     }
     leaf packets-with-bad-options {
       type uint32;
       description "Packets with bad options";
     }
     leaf packets-with-options-handled-without-error {
       type uint32;
       description "Packets with options handled without error";
     }
     leaf strict-source-and-record-route-options {
       type uint32;
       description "Strict source and record route options";
     }
     leaf loose-source-and-record-route-options {
       type uint32;
       description "Loose source and record route options";
     }
     leaf record-route-options {
       type uint32;
       description "Record route options";
     }
     leaf timestamp-options {
       type uint32;
       description "Timestamp options";
     }
     leaf timestamp-and-address-options {
       type uint32;
       description "Timestamp and address options";
     }
     leaf timestamp-and-prespecified-address-options {
       type uint32;
       description "Timestamp and prespecified address options";
     }
     leaf option-packets-dropped-due-to-rate-limit {
       type uint32;
       description "Option packets dropped due to rate limit";
     }
     leaf router-alert-options {
       type uint32;
       description "Router alert options";
     }
     leaf multicast-packets-dropped {
       type uint32;
       description "Multicast packets dropped (no iflist)";
     }
     leaf packets-dropped {
       type uint32;
       description "Packets dropped (src and int don't match)";
     }
     leaf transit-re-packets-dropped-on-mgmt-interface {
       type uint32;
       description "Transit RE packets dropped on mgmt interface";
     }
     leaf packets-used-first-nexthop-in-ecmp-unilist {
       type uint32;
       description "Packets used first nexthop in ecmp unilist";
     }
     leaf incoming-ttpoip-packets-received {
       type uint32;
       description "Incoming TTPoIP packets received";
     }
     leaf incoming-ttpoip-packets-dropped {
       type uint32;
       description "Incoming TTPoIP packets dropped";
     }
     leaf outgoing-ttpoip-packets-sent {
       type uint32;
       description "Outgoing TTPoIP packets sent";
     }
     leaf outgoing-ttpoip-packets-dropped {
       type uint32;
       description "Outgoing TTPoIP packets dropped";
     }
     leaf incoming-rawip-packets-dropped-no-socket-buffer {
       type uint32;
       description "Incoming raw ip packets dropped. No space in recv socket buffer";
     }
     leaf incoming-virtual-node-packets-delivered {
       type uint32;
       description "Incoming packets consumed by virtual-node processing";
     }
   }
   container icmp {
     leaf drops-due-to-rate-limit {
       type uint32;
       description "Drops due to rate limit";
     }
     leaf drops-at-server-ine {
       type uint32;
       description "Drops at server INE";
     }
     leaf calls-to-icmp-error {
       type uint32;
       description "Calls to icmp_error";
     }
     leaf errors-not-generated-because-old-message-was-icmp {
       type uint32;
       description "Errors not generated because old message was icmp";
     }
     leaf messages-with-bad-code-fields {
       type uint32;
       description "Messages with bad code fields";
     }
     leaf messages-less-than-the-minimum-length {
       type uint32;
       description "Messages less than the minimum length";
     }
     leaf messages-with-bad-checksum {
       type uint32;
       description "Messages with bad checksum";
     }
     leaf messages-with-bad-source-address {
       type uint32;
       description "Messages with bad source address";
     }
     leaf messages-with-bad-length {
       type uint32;
       description "Messages with bad length";
     }
     leaf echo-drops-with-broadcast-or-multicast-destinaton-address {
       type uint32;
       description "Echo drops with broadcast or multicast destinaton address";
     }
     leaf timestamp-drops-with-broadcast-or-multicast-destination-address {
       type uint32;
       description "Timestamp drops with broadcast or multicast destination address";
     }
     leaf message-responses-generated {
       type uint32;
       description "Message responses generated";
     }
     container histogram {
       leaf type-of-histogram {
         type string;
         description "Input/ouput histogram";
       }
       leaf icmp-echo-reply {
         type uint32;
         description "Echo reply";
       }
       leaf destination-unreachable {
         type uint32;
         description "Destination unreachable";
       }
       leaf source-quench {
         type uint32;
         description "Source-quench";
       }
       leaf routing-redirect {
         type uint32;
         description "Routing redirect";
       }
       leaf alternate-host-address {
         type uint32;
         description "Alternate host address";
       }
       leaf icmp-echo {
         type uint32;
         description "Echo";
       }
       leaf router-advertisement {
         type uint32;
         description "Router advertisement";
       }
       leaf router-solicitation {
         type uint32;
         description "Router solicitation";
       }
       leaf time-exceeded {
         type uint32;
         description "Time exceeded";
       }
       leaf parameter-problem {
         type uint32;
         description "Parameter problem";
       }
       leaf time-stamp {
         type uint32;
         description "Time stamp";
       }
       leaf time-stamp-reply {
         type uint32;
         description "Time stamp reply";
       }
       leaf information-request {
         type uint32;
         description "Information request";
       }
       leaf information-request-reply {
         type uint32;
         description "Information request reply";
       }
       leaf address-mask-request {
         type uint32;
         description "Address mask request";
       }
       leaf address-mask-reply {
         type uint32;
         description "Address mask reply";
       }
       leaf traceroute {
         type uint32;
         description "Traceroute";
       }
       leaf data-conversion-error {
         type uint32;
         description "Data conversion error";
       }
       leaf mobile-host-redirect {
         type uint32;
         description "Mobile host redirect";
       }
       leaf ipv6-where-are-you {
         type uint32;
         description "IPv6 where-are-you";
       }
       leaf ipv6-i-am-here {
         type uint32;
         description "IPv6 i-am-here";
       }
       leaf mobile-registration-request {
         type uint32;
         description "Mobile registration request";
       }
       leaf mobile-registration-reply {
         type uint32;
         description "Mobile registration reply";
       }
       leaf skip {
         type uint32;
         description "Skip";
       }
       leaf photuris {
         type uint32;
         description "Photuris";
       }
     }
   }
   container igmp {
     leaf messages-received {
       type uint32;
       description "Messages received";
     }
     leaf messages-received-with-too-few-bytes {
       type uint32;
       description "Messages received with too few bytes";
     }
     leaf messages-received-with-bad-checksum {
       type uint32;
       description "Messages received with bad checksum";
     }
     leaf membership-queries-received {
       type uint32;
       description "Membership queries received";
     }
     leaf membership-queries-received-with-invalid-fields {
       type uint32;
       description "Membership queries received with invalid fields";
     }
     leaf membership-reports-received {
       type uint32;
       description "Membership reports received";
     }
     leaf membership-reports-received-with-invalid-fields {
       type uint32;
       description "Membership reports received with invalid fields";
     }
     leaf membership-reports-received-for-groups-to-which-we-belong {
       type uint32;
       description "Membership reports received for groups to which we belong";
     }
     leaf membership-reports-sent {
       type uint32;
       description "Membership reports sent";
     }
   }
   container ipsec {
     leaf inbound-packets-processed-successfully {
       type uint64;
       description "Inbound packets processed successfully";
     }
     leaf inbound-packets-violated-process-security-policy {
       type uint64;
       description "Inbound packets violated process security policy";
     }
     leaf inbound-packets-with-no-sa-available {
       type uint64;
       description "Inbound packets with no SA available";
     }
     leaf invalid-inbound-packets {
       type uint64;
       description "Invalid inbound packets";
     }
     leaf inbound-packets-failed-due-to-insufficient-memory {
       type uint64;
       description "Inbound packets failed due to insufficient memory";
     }
     leaf inbound-packets-failed-getting-spi {
       type uint64;
       description "Inbound packets failed getting SPI";
     }
     leaf inbound-packets-failed-on-ah-replay-check {
       type uint64;
       description "Inbound packets failed on AH replay check";
     }
     leaf inbound-packets-failed-on-esp-replay-check {
       type uint64;
       description "Inbound packets failed on ESP replay check";
     }
     leaf inbound-packets-considered-authentic {
       type uint64;
       description "Inbound packets considered authentic";
     }
     leaf inbound-packets-failed-on-authentication {
       type uint64;
       description "Inbound packets failed on authentication";
     }
     leaf inbound-esp-packets-considered-authentic {
       type uint64;
       description "Inbound ESP packets considered authentic";
     }
     leaf inbound-esp-packets-failed-on-authentication {
       type uint64;
       description "Inbound ESP packets failed on authentication";
     }
     leaf histogram {
       type string;
     }
     leaf ahnames-none {
       type uint64;
       description "AH names";
     }
     leaf ahnames-hmac-md5 {
       type uint64;
       description "HMAC MD5";
     }
     leaf ahnames-hmac-sha1 {
       type uint64;
       description "HMAC SHA1";
     }
     leaf ahnames-md5 {
       type uint64;
       description "MD5";
     }
     leaf ahnames-sha {
       type uint64;
       description "SHA";
     }
     leaf ahnames-null {
       type uint64;
       description "NULL AH name";
     }
     leaf ahnames-hmac-sha2-256 {
       type uint64;
       description "HMAC SHA2-256";
     }
     leaf ahnames-hmac-sha2-384 {
       type uint64;
       description "HMAC SHA2-384";
     }
     leaf ahnames-hmac-sha2-512 {
       type uint64;
       description "HMAC SHA2-512";
     }
     leaf ahnames-hmac-ripemd160 {
       type uint64;
       description "HAMC RIPEMD160";
     }
     leaf ahnames-aes-xcbc-mac {
       type uint64;
       description "AES XCBC MAC";
     }
     leaf espnames-none {
       type uint64;
       description "ESP names";
     }
     leaf espnames-des-cbc {
       type uint64;
       description "DES CBC";
     }
     leaf espnames-null {
       type uint64;
       description "NULL ESP name";
     }
     leaf espnames-cast128-cbc {
       type uint64;
       description "CAST128 CBC";
     }
     leaf espnames-blowfish-cbc {
       type uint64;
       description "BLOWFISH CBC";
     }
     leaf espnames-rijndael-cbc {
       type uint64;
       description "RIJDAEL CBC";
     }
     leaf espnames-aes-ctr {
       type uint64;
       description "AES CTR";
     }
     leaf compnames-none {
       type uint64;
       description "NONE COMP names";
     }
     leaf compnames-oui {
       type uint64;
       description "OUI";
     }
     leaf compnames-deflate {
       type uint64;
       description "DEFLATE";
     }
     leaf compnames-lzs {
       type uint64;
       description "LZS";
     }
     leaf protocol {
       type uint64;
       description "Protocol";
     }
     leaf outbound-packets-processed-successfully {
       type uint64;
       description "Outbound packets processed successfully";
     }
     leaf outbound-packets-violated-process-security-policy {
       type uint64;
       description "Outbound packets violated process security policy";
     }
     leaf outbound-packets-with-no-sa-available {
       type uint64;
       description "Outbound packets with no SA available";
     }
     leaf invalid-outbound-packets {
       type uint64;
       description "Invalid outbound packets";
     }
     leaf outbound-packets-failed-due-to-insufficient-memory {
       type uint64;
       description "Outbound packets failed due to insufficient memory";
     }
     leaf outbound-packets-with-no-route {
       type uint64;
       description "Outbound packets with no route";
     }
     leaf spd-cache-lookups {
       type uint64;
       description "SPD cache lookups";
     }
     leaf spd-cache-misses {
       type uint64;
       description "SPD cache misses";
     }
     leaf outbound-packets-with-bundled-sa {
       type uint64;
       description "Outbound packets with bundles SAs";
     }
     leaf mbuf-coalesced-during-clone {
       type uint64;
       description "Mbuf coleasced during clone";
     }
     leaf cluster-coalesced-during-clone {
       type uint64;
       description "Cluster coalesced during clone";
     }
     leaf cluster-copied-during-clone {
       type uint64;
       description "Cluster copied during clone";
     }
     leaf mbuf-inserted-during-makespace {
       type uint64;
       description "Mbuf inserted during makespace";
     }
   }
   container ah {
     description "Authentication header";
     leaf packets-shorter-than-header-shows {
       type uint64;
       description "Packets shorter than header shows";
     }
     leaf packets-dropped-as-protocol-unsupported {
       type uint64;
       description "Packets dropped protocol unsupported";
     }
     leaf packets-dropped-due-to-no-tdb {
       type uint64;
       description "Packets dropped no TDB";
     }
     leaf packets-dropped-due-to-bad-kcr {
       type uint64;
       description "Packets dropped bad KCR";
     }
     leaf packets-dropped-due-to-queue-full {
       type uint64;
       description "Packets dropped queue full";
     }
     leaf packets-dropped-due-to-no-transform {
       type uint64;
       description "Packets dropped no transform";
     }
     leaf replay-counter-wrap {
       type uint64;
       description "Replay counter wrap";
     }
     leaf packets-dropped-as-bad-authentication-detected {
       type uint64;
       description "Packets dropped bad authentication detected";
     }
     leaf packets-dropped-due-to-bad-authentication-length {
       type uint64;
       description "Packets dropped bad authentication length";
     }
     leaf possible-replay-packets-detected {
       type uint64;
       description "Possible replay packets detected";
     }
     leaf packets-in {
       type uint64;
       description "Packets in";
     }
     leaf packets-out {
       type uint64;
       description "Packets out";
     }
     leaf packets-dropped-due-to-invalid-tdb {
       type uint64;
       description "Packets dropped invalid TDB";
     }
     leaf bytes-in {
       type uint64;
       description "Bytes in";
     }
     leaf bytes-out {
       type uint64;
       description "Bytes out";
     }
     leaf packets-dropped-as-larger-than-ip-maxpacket {
       type uint64;
       description "Packets dropped larger than maxpacket";
     }
     leaf packets-blocked-due-to-policy {
       type uint64;
       description "Packets blocked due to policy";
     }
     leaf crypto-processing-failure {
       type uint64;
       description "Crypto processing failure";
     }
     leaf tunnel-sanity-check-failures {
       type uint64;
       description "Tunnel sanity check failures";
     }
   }
   container esp {
     description "Encapsulating Security Payloads";
     leaf esp-packets-shorter-than-header-shows {
       type uint64;
       description "Packets shorter than header shows";
     }
     leaf esp-packets-dropped-as-protocol-not-supported {
       type uint64;
       description "Packets dropped protocol unsupported";
     }
     leaf esp-packets-dropped-due-to-no-tdb {
       type uint64;
       description "Packets dropped no TDB";
     }
     leaf esp-packets-dropped-due-to-bad-kcr {
       type uint64;
       description "Packets dropped bad KCR";
     }
     leaf esp-packets-dropped-due-to-queue-full {
       type uint64;
       description "Packets dropped queue full";
     }
     leaf esp-packets-dropped-due-to-no-transform {
       type uint64;
       description "Packets dropped no transform";
     }
     leaf esp-packets-dropped-as-bad-ilen {
       type uint64;
       description "Packets dropped bad ilen";
     }
     leaf esp-replay-counter-wrap {
       type uint64;
       description "Replay counter wrap";
     }
     leaf esp-packets-dropped-as-bad-encryption-detected {
       type uint64;
       description "Packets dropped bad encryption detected";
     }
     leaf esp-packets-dropped-as-bad-authentication-detected {
       type uint64;
       description "Packets dropped bad authentication detected";
     }
     leaf esp-possible-replay-packets-detected {
       type uint64;
       description "Possible replay packets detected";
     }
     leaf esp-packets-in {
       type uint64;
       description "Packets in";
     }
     leaf esp-packets-out {
       type uint64;
       description "Packets out";
     }
     leaf esp-packets-dropped-as-invalid-tdb {
       type uint64;
       description "Packets dropped invalid TDB";
     }
     leaf esp-bytes-in {
       type uint64;
       description "Bytes in";
     }
     leaf esp-bytes-out {
       type uint64;
       description "Bytes out";
     }
     leaf esp-packets-dropped-as-larger-than-ip-maxpacket {
       type uint64;
       description "Packets dropped larger than maxpacket";
     }
     leaf esp-packets-blocked-due-to-policy {
       type uint64;
       description "Packets blocked due to policy";
     }
     leaf esp-crypto-processing-failure {
       type uint64;
       description "Crypto processing failure";
     }
     leaf esp-tunnel-sanity-check-failures {
       type uint64;
       description "Tunnel sanity check failures";
     }
   }
   container ipcomp {
     description "IP Payload Compression Protocol";
     leaf ipcomp-packets-shorter-than-header-shows {
       type uint64;
       description "Packets shorter than header shows";
     }
     leaf ipcomp-packets-dropped-as-protocol-not-supported {
       type uint64;
       description "Packets dropped protocol unsupported";
     }
     leaf ipcomp-packets-dropped-due-to-no-tdb {
       type uint64;
       description "Packets dropped no TDB";
     }
     leaf ipcomp-packets-dropped-due-to-bad-kcr {
       type uint64;
       description "Packets dropped bad KCR";
     }
     leaf ipcomp-packets-dropped-due-to-queue-full {
       type uint64;
       description "Packets dropped queue full";
     }
     leaf ipcomp-packets-dropped-due-to-no-transform {
       type uint64;
       description "Packets dropped no transform";
     }
     leaf ipcomp-replay-counter-wrap {
       type uint64;
       description "Replay counter wrap";
     }
     leaf ipcomp-packets-in {
       type uint64;
       description "Packets in";
     }
     leaf ipcomp-packets-out {
       type uint64;
       description "Packets out";
     }
     leaf ipcomp-packets-dropped-as-invalid-tdb {
       type uint64;
       description "Packets dropped invalid TDB";
     }
     leaf ipcomp-bytes-in {
       type uint64;
       description "Bytes in";
     }
     leaf ipcomp-bytes-out {
       type uint64;
       description "Bytes out";
     }
     leaf ipcomp-packets-dropped-as-larger-than-ip-maxpacket {
       type uint64;
       description "Packets dropped larger than maxpacket";
     }
     leaf ipcomp-packets-blocked-due-to-policy {
       type uint64;
       description "Packets blocked due to policy";
     }
     leaf ipcomp-crypto-processing-failure {
       type uint64;
       description "Crypto processing failure";
     }
     leaf packets-sent-uncompressed-threshold {
       type uint64;
       description "Packets sent uncompressed threshold";
     }
     leaf packets-sent-uncompressed-useless {
       type uint64;
       description "Packets sent uncompressed useless";
     }
   }
   container raw-interface {
     leaf raw-packets-transmitted {
       type uint32;
       description "RAW packets transmitted";
     }
     leaf ppoe-packets-transmitted {
       type uint32;
       description "PPPOE packets transmitted";
     }
     leaf isdn-packets-transmitted {
       type uint32;
       description "ISDN packets transmitted";
     }
     leaf dialer-packets-transmitted {
       type uint32;
       description "DIALER packets transmitted";
     }
     leaf ppp-packets-transmitted-to-pppd {
       type uint32;
       description "PPP packets transmitted to pppd";
     }
     leaf ppp-packets-transmitted-to-jppd {
       type uint32;
       description "PPP packets transmitted to jppd";
     }
     leaf igmpl2-packets-transmitted {
       type uint32;
       description "IGMPL2 packets transmitted";
     }
     leaf mldl2-packets-transmitted {
       type uint32;
       description "MLDL2 packets transmitted";
     }
     leaf fibre-channel-packets-transmitted {
       type uint32;
       description "Fibre Channel packets transmitted";
     }
     leaf fip-packets-transmitted {
       type uint32;
       description "FIP packets transmitted";
     }
     leaf stp-packets-transmitted {
       type uint32;
       description "STP packets transmitted";
     }
     leaf lacp-packets-transmitted {
       type uint32;
       description "LACP packets transmitted";
     }
     leaf vccp-packets-transmitted {
       type uint32;
       description "VCCP packets transmitted";
     }
     leaf output-drops-due-to-transmit-error {
       type uint32;
       description "Output drops due to tx error";
     }
     leaf mpu-packets-transmitted {
       type uint32;
       description "MPU packets transmitted";
     }
     leaf faboam-packets-transmitted {
       type uint32;
       description "Fabric OAM packets transmitted";
     }
     leaf pppoe-packets-received {
       type uint32;
       description "PPPOE packets received";
     }
     leaf isdn-packets-received {
       type uint32;
       description "ISDN packets received";
     }
     leaf dialer-packets-received {
       type uint32;
       description "DIALER packets received";
     }
     leaf ppp-packets-received-from-pppd {
       type uint32;
       description "PPP packets received from pppd";
     }
     leaf mpu-packets-received {
       type uint32;
       description "MPU packets received";
     }
     leaf ppp-packets-received-from-jppd {
       type uint32;
       description "PPP packets received from jppd";
     }
     leaf igmpl2-packets-received {
       type uint32;
       description "IGMPL2 packets received";
     }
     leaf fibre-channel-packets-received {
       type uint32;
       description "Fibre Channel packets received";
     }
     leaf fip-packets-received {
       type uint32;
       description "FIP packets received";
     }
     leaf stp-packets-received {
       type uint32;
       description "STP packets received";
     }
     leaf lacp-packets-received {
       type uint32;
       description "LACP packets received";
     }
     leaf vccp-packets-received {
       type uint32;
       description "VCCP packets received";
     }
     leaf faboam-packets-received {
       type uint32;
       description "Fabric OAM packets received";
     }
     leaf fibre-channel-packets-dropped {
       type uint32;
       description "Fibre Channel packets dropped";
     }
     leaf fip-packets-dropped {
       type uint32;
       description "FIP packets dropped";
     }
     leaf stp-packets-dropped {
       type uint32;
       description "STP packets dropped";
     }
     leaf lacp-packets-dropped {
       type uint32;
       description "LACP packets dropped";
     }
     leaf vccp-packets-dropped {
       type uint32;
       description "VCCP packets dropped";
     }
     leaf faboam-packets-dropped {
       type uint32;
       description "Fabric OAM packets dropped";
     }
     leaf mldl2-packets-received {
       type uint32;
       description "MLDL2 packets received";
     }
     leaf input-drops-due-to-bogus-protocol {
       type uint32;
       description "Input drops due to bogus protocol";
     }
     leaf input-drops-due-to-no-mbufs-available {
       type uint32;
       description "Input drops due to no mbufs available";
     }
     leaf input-drops-due-to-no-space-in-socket {
       type uint32;
       description "Input drops due to no space in socket";
     }
     leaf input-drops-due-to-no-socket {
       type uint32;
       description "Input drops due to no socket";
     }
   }
   container arp {
     leaf datagrams-received {
       type uint32;
       description "Datagrams received";
     }
     leaf arp-requests-received {
       type uint32;
       description "ARP requests received";
     }
     leaf arp-replies-received {
       type uint32;
       description "ARP replies received";
     }
     leaf resolution-request-received {
       type uint32;
       description "Resolution request received";
     }
     leaf resolution-request-dropped {
       type uint32;
       description "Resolution request dropped";
     }
     leaf unrestricted-proxy-requests {
       type uint32;
       description "Unrestricted proxy requests";
     }
     leaf restricted-proxy-requests {
       type uint32;
       description "Restricted proxy requests";
     }
     leaf received-proxy-requests {
       type uint32;
       description "Received proxy requests";
     }
     leaf proxy-requests-not-proxied {
       type uint32;
       description "Unrestricted proxy requests not proxied";
     }
     leaf restricted-proxy-requests-not-proxied {
       type uint32;
       description "Restricted proxy requests not proxied";
     }
     leaf datagrams-with-bogus-interface {
       type uint32;
       description "Datagrams with bogus interface";
     }
     leaf datagrams-with-incorrect-length {
       type uint32;
       description "Datagrams with incorrect length";
     }
     leaf datagrams-for-non-ip-protocol {
       type uint32;
       description "Datagrams for non-IP protocol";
     }
     leaf datagrams-with-unsupported-opcode {
       type uint32;
       description "Datagrams with unsupported op code";
     }
     leaf datagrams-with-bad-protocol-address-length {
       type uint32;
       description "Datagrams with bad protocol address length";
     }
     leaf datagrams-with-bad-hardware-address-length {
       type uint32;
       description "Datagrams with bad hardware address length";
     }
     leaf datagrams-with-multicast-source-address {
       type uint32;
       description "Datagrams with multicast source address";
     }
     leaf datagrams-with-multicast-target-address {
       type uint32;
       description "Datagrams with multicast target address";
     }
     leaf datagrams-with-my-own-hardware-address {
       type uint32;
       description "Datagrams with my own hardware address";
     }
     leaf datagrams-for-an-address-not-on-the-interface {
       type uint32;
       description "Datagrams for an address not on the interface";
     }
     leaf datagrams-with-a-broadcast-source-address {
       type uint32;
       description "Datagrams with a broadcast source address";
     }
     leaf datagrams-with-source-address-duplicate-to-mine {
       type uint32;
       description "Datagrams with source address duplicate to mine";
     }
     leaf datagrams-which-were-not-for-me {
       type uint32;
       description "Datagrams which were not for me";
     }
     leaf packets-discarded-waiting-for-resolution {
       type uint32;
       description "Packets discarded waiting for resolution";
     }
     leaf packets-sent-after-waiting-for-resolution {
       type uint32;
       description "Packets sent after waiting for resolution";
     }
     leaf arp-requests-sent {
       type uint32;
       description "ARP requests sent";
     }
     leaf arp-replies-sent {
       type uint32;
       description "ARP replies sent";
     }
     leaf requests-for-memory-denied {
       type uint32;
       description "Requests for memory denied";
     }
     leaf requests-dropped-on-entry {
       type uint32;
       description "Requests dropped on entry";
     }
     leaf requests-dropped-during-retry {
       type uint32;
       description "Requests dropped during retry";
     }
     leaf requests-dropped-due-to-interface-deletion {
       type uint32;
       description "Requests dropped due to interface deletion";
     }
     leaf requests-on-unnumbered-interfaces {
       type uint32;
       description "Requests on unnumbered interfaces";
     }
     leaf new-requests-on-unnumbered-interfaces {
       type uint32;
       description "New requests on unnumbered interfaces";
     }
     leaf replies-from-unnumbered-interfaces {
       type uint32;
       description "Replies for from unnumbered interfaces";
     }
     leaf requests-on-unnumbered-interface-with-non-subnetted-donor {
       type uint32;
       description "Requests on unnumbered interface with non-subnetted donor";
     }
     leaf replies-from-unnumbered-interface-with-non-subnetted-donor {
       type uint32;
       description "Replies from unnumbered interface with non-subnetted donor";
     }
     leaf arp-packets-rejected-as-family-is-configured-with-deny-arp {
       type uint32;
       description "Arp packets rejected as family is configured with deny arp";
     }
     leaf arp-response-packets-are-rejected-on-mace-icl-interface {
       type uint32;
       description "Arp response packets are rejected on mace icl interface";
     }
     leaf arp-replies-are-rejected-as-source-and-destination-is-same {
       type uint32;
       description "Arp replies are rejected as source and destination is same";
     }
     leaf arp-probe-for-proxy-address-reachable-from-the-incoming-interface {
       type uint32;
       description "Arp probe for proxy address reachable from the incoming interface";
     }
     leaf arp-request-discarded-for-vrrp-source-address {
       type uint32;
       description "Arp request discarded for vrrp source address";
     }
     leaf self-arp-request-packet-received-on-irb-interface {
       type uint32;
       description "Self arp request packet received on irb interface";
     }
     leaf proxy-arp-request-discarded-as-source-ip-is-a-proxy-target {
       type uint32;
       description "Proxy arp request discarded as source ip is a proxy target";
     }
     leaf arp-packets-are-dropped-as-nexthop-allocation-failed {
       type uint32;
       description "Arp packets are dropped as nexthop allocation failed";
     }
     leaf arp-packets-received-from-peer-vrrp-router-and-discarded {
       type uint32;
       description "Arp packets received from peer vrrp router and discarded";
     }
     leaf arp-packets-are-rejected-as-target-ip-arp-resolve-is-in-progress {
       type uint32;
       description "Arp packets are rejected as target ip arp resolve is in progress";
     }
     leaf grat-arp-packets-are-ignored-as-mac-address-is-not-changed {
       type uint32;
       description "Grat arp packets are ignored as mac address is not changed";
     }
     leaf arp-packets-are-dropped-from-peer-vrrp {
       type uint32;
       description "Arp packets are dropped from peer vrrp";
     }
     leaf arp-packets-are-dropped-as-driver-call-failed {
       type uint32;
       description "Arp packets are dropped as driver call failed";
     }
     leaf arp-packets-are-dropped-as-source-is-not-validated {
       type uint32;
       description "Arp packets are dropped as source is not validated";
     }
     leaf arp-system-max {
       type uint64;
       description "Max ARP NH system cache";
     }
     leaf arp-public-max {
       type uint64;
       description "Max public ARP NH cache";
     }
     leaf arp-iri-max {
       type uint64;
       description "Max iri ARP NH cache";
     }
     leaf arp-mgt-max {
       type uint64;
       description "Max mgt intf ARP NH cache";
     }
     leaf arp-public-cnt {
       type uint64;
       description "Current public ARP NH count";
     }
     leaf arp-iri-cnt {
       type uint64;
       description "Current iri ARP NH count";
     }
     leaf arp-mgt-cnt {
       type uint64;
       description "Current management ARP NH count";
     }
     leaf arp-system-drop {
       type uint64;
       description "System ARP NH drops";
     }
     leaf arp-public-drop {
       type uint64;
       description "Public ARP NH drops";
     }
     leaf arp-iri-drop {
       type uint64;
       description "IRI ARP NH drops";
     }
     leaf arp-mgt-drop {
       type uint64;
       description "Management intf ARP NH drops";
     }
   }
   container ip6 {
     leaf total-packets-received {
       type uint64;
       description "Total packets received";
     }
     leaf ip6-packets-with-size-smaller-than-minimum {
       type uint64;
       description "Ip6 packets with size smaller than minimum";
     }
     leaf packets-with-datasize-less-than-data-length {
       type uint64;
       description "Packets with data size < data length";
     }
     leaf ip6-packets-with-bad-options {
       type uint64;
       description "Ip6 packets with bad options";
     }
     leaf ip6-packets-with-incorrect-version-number {
       type uint64;
       description "Ip6 packets with incorrect version number";
     }
     leaf ip6-fragments-received {
       type uint64;
       description "Ip6 fragments received";
     }
     leaf duplicate-or-out-of-space-fragments-dropped {
       type uint64;
       description "Fragments dropped (dup or out of space)";
     }
     leaf ip6-fragments-dropped-after-timeout {
       type uint64;
       description "Ip6 fragments dropped after timeout";
     }
     leaf fragments-that-exceeded-limit {
       type uint64;
       description "Fragment sessions dropped due to queue overflow";
     }
     leaf ip6-packets-reassembled-ok {
       type uint64;
       description "Ip6 packets reassembled ok";
     }
     leaf ip6-packets-for-this-host {
       type uint64;
       description "Ip6 packets for this host";
     }
     leaf ip6-packets-forwarded {
       type uint64;
       description "Ip6 packets forwarded";
     }
     leaf ip6-packets-not-forwardable {
       type uint64;
       description "Ip6 packets not forwardable";
     }
     leaf ip6-redirects-sent {
       type uint64;
       description "Ip6 redirects sent";
     }
     leaf ip6-packets-sent-from-this-host {
       type uint64;
       description "Ip6 packets sent from this host";
     }
     leaf ip6-packets-sent-with-fabricated-ip-header {
       type uint64;
       description "Ip6 packets sent with fabricated ip header";
     }
     leaf ip6-output-packets-dropped-due-to-no-bufs {
       type uint64;
       description "Ip6 output packets dropped due to no bufs";
     }
     leaf ip6-output-packets-discarded-due-to-no-route {
       type uint64;
       description "Ip6 output packets discarded due to no route";
     }
     leaf ip6-output-datagrams-fragmented {
       type uint64;
       description "Ip6output datagrams fragmented";
     }
     leaf ip6-fragments-created {
       type uint64;
       description "Ip6 fragments created";
     }
     leaf ip6-datagrams-that-can-not-be-fragmented {
       type uint64;
       description "Ip6 datagrams that can not be fragmented";
     }
     leaf packets-that-violated-scope-rules {
       type uint64;
       description "Packets that violated scope rules";
     }
     leaf multicast-packets-which-we-do-not-join {
       type uint64;
       description "Multicast packets which we don't join";
     }
     leaf histogram {
       type string;
     }
     leaf ip6nh-hop-by-hop {
       type uint64;
       description "Hop by hop";
     }
     leaf ip6nh-icmp {
       type uint64;
       description "ICMP";
     }
     leaf ip6nh-igmp {
       type uint64;
       description "IGMP";
     }
     leaf ip6nh-ip {
       type uint64;
       description "IP";
     }
     leaf ip6nh-tcp {
       type uint64;
       description "TCP";
     }
     leaf ip6nh-udp {
       type uint64;
       description "UDP";
     }
     leaf ip6nh-idp {
       type uint64;
       description "IDP";
     }
     leaf ip6nh-tp {
       type uint64;
       description "TP";
     }
     leaf ip6nh-ip6 {
       type uint64;
       description "IP6";
     }
     leaf ip6nh-routing {
       type uint64;
       description "Routing";
     }
     leaf ip6nh-fragment {
       type uint64;
       description "Fragment";
     }
     leaf ip6nh-esp {
       type uint64;
       description "Esp";
     }
     leaf ip6nh-ah {
       type uint64;
       description "AH";
     }
     leaf ip6nh-icmp6 {
       type uint64;
       description "ICMP6";
     }
     leaf ip6nh-no-next-header {
       type uint64;
       description "No next header";
     }
     leaf ip6nh-destination-option {
       type uint64;
       description "Destination option";
     }
     leaf ip6nh-isoip {
       type uint64;
       description "ISOIP";
     }
     leaf ip6nh-ospf {
       type uint64;
       description "OSPF";
     }
     leaf ip6nh-ethernet {
       type uint64;
       description "Ethernet";
     }
     leaf ip6nh-pim {
       type uint64;
       description "PIM";
     }
     leaf mbuf-statistics {
       type string;
       description "Header";
     }
     leaf node-locals {
       type uint64;
       description "Node locals as source address";
     }
     leaf link-locals {
       type uint64;
       description "Link locals as source address";
     }
     leaf site-locals {
       type uint64;
       description "Site locals as source address";
     }
     leaf globals {
       type uint64;
       description "Globals as source address";
     }
     leaf address-scope {
       type uint64;
       description "Address scope";
     }
     leaf hex-value {
       type uint64;
       description "Hexa decimal value";
     }
     leaf header-for-source-address-selection {
       type string;
       description "Header";
     }
     leaf packets-whose-headers-are-not-continuous {
       type uint64;
       description "Packets whose headers are not continuous";
     }
     leaf tunneling-packets-that-can-not-find-gif {
       type uint64;
       description "Tunneling packets that can't find GIF";
     }
     leaf packets-discarded-due-to-too-may-headers {
       type uint64;
       description "Packets discarded due to too may headers";
     }
     leaf failures-of-source-address-selection {
       type uint64;
       description "Failures of source address selection";
     }
     leaf forward-cache-hit {
       type uint64;
       description "Forward cache hit";
     }
     leaf forward-cache-miss {
       type uint64;
       description "Forward cache miss";
     }
     leaf ip6-packets-destined-to-dead-next-hop {
       type uint64;
       description "Ip6 packets destined to dead next hop";
     }
     leaf ip6-option-packets-dropped-due-to-rate-limit {
       type uint64;
       description "Ip6 option packets dropped due to rate limit";
     }
     leaf ip6-packets-dropped {
       type uint64;
       description "Ip6 packets dropped";
     }
     leaf packets-dropped-due-to-bad-protocol {
       type uint64;
       description "Packets dropped due to bad protocol";
     }
     leaf transit-re-packet-dropped-on-mgmt-interface {
       type uint64;
       description "Transit re packet(null) dropped on mgmt interface";
     }
     leaf packet-used-first-nexthop-in-ecmp-unilist {
       type uint64;
       description "Packet(null) used first nexthop in ecmp unilist";
     }
   }
   container icmp6 {
     leaf protocol-name {
       type string;
     }
     leaf calls-to-icmp6-error {
       type uint64;
       description "Calls to icmp6 error";
     }
     leaf errors-not-generated-because-old-message-was-icmp-error {
       type uint64;
       description "Errors not generated because old message was icmp error";
     }
     leaf errors-not-generated-because-rate-limitation {
       type uint64;
       description "Errors not generated because rate limitation";
     }
     leaf icmp6-messages-with-bad-code-fields {
       type uint64;
       description "Icmp6 messages with bad code fields";
     }
     leaf messages-less-than-minimum-length {
       type uint64;
       description "Messages < minimum length";
     }
     leaf bad-checksums {
       type uint64;
       description "Bad checksums";
     }
     leaf icmp6-messages-with-bad-length {
       type uint64;
       description "Icmp6 messages with bad length";
     }
     leaf histogram-of-error-messages-to-be-generated {
       type string;
       description "Header";
     }
     leaf no-route {
       type uint64;
       description "No route";
     }
     leaf administratively-prohibited {
       type uint64;
       description "Administratively prohibited";
     }
     leaf beyond-scope {
       type uint64;
       description "Beyond scope";
     }
     leaf address-unreachable {
       type uint64;
       description "Address unreachable";
     }
     leaf port-unreachable {
       type uint64;
       description "Port unreachable";
     }
     leaf time-exceed-transit {
       type uint64;
       description "Time exceed transit";
     }
     leaf time-exceed-reassembly {
       type uint64;
       description "Time exceed reassembly";
     }
     leaf erroneous-header-field {
       type uint64;
       description "Erroneous header field";
     }
     leaf unrecognized-next-header {
       type uint64;
       description "Unrecognized next header";
     }
     leaf unrecognized-option {
       type uint64;
       description "Unrecognized option";
     }
     leaf unknown {
       type uint64;
       description "Unknown";
     }
     leaf icmp6-message-responses-generated {
       type uint64;
       description "Icmp6 message responses generated";
     }
     leaf messages-with-too-many-nd-options {
       type uint64;
       description "Messages with too many ND options";
     }
     leaf nd-system-max {
       type uint64;
       description "Max ND NH system cache";
     }
     leaf nd-public-max {
       type uint64;
       description "Max public ND NH cache";
     }
     leaf nd-iri-max {
       type uint64;
       description "Max iri ND NH cache";
     }
     leaf nd-mgt-max {
       type uint64;
       description "Max mgt intf ND NH cache";
     }
     leaf nd-public-cnt {
       type uint64;
       description "Current public ND NH count";
     }
     leaf nd-iri-cnt {
       type uint64;
       description "Current iri ND NH count";
     }
     leaf nd-mgt-cnt {
       type uint64;
       description "Current management ND NH count";
     }
     leaf nd-system-drop {
       type uint64;
       description "System ND NH drops";
     }
     leaf nd-public-drop {
       type uint64;
       description "Public ND NH drops";
     }
     leaf nd-iri-drop {
       type uint64;
       description "IRI ND NH drops";
     }
     leaf nd-mgt-drop {
       type uint64;
       description "Management intf ND NH drops";
     }
     leaf nd6-requests-dropped-on-entry {
       type uint64;
       description "ND nexthops dropped on entry by RED mark";
     }
     leaf nd6-requests-dropped-during-retry {
       type uint64;
       description "ND nexthop%s dropped on timer expire by RED mark";
     }
     container output-histogram {
       container output {
         leaf histogram-type {
           type string;
         }
         leaf unreachable-icmp6-packets {
           type uint64;
           description "Unreachable icmp6 packets";
         }
         leaf packet-too-big {
           type uint64;
           description "Packet too big";
         }
         leaf time-exceeded-icmp6-packets {
           type uint64;
           description "Time exceeded icmp6 packets";
         }
         leaf parameter-problem-icmp6-packets {
           type uint64;
           description "Parameter problem icmp6 packets";
         }
         leaf icmp6-echo {
           type uint64;
         }
         leaf icmp6-echo-reply {
           type uint64;
         }
         leaf multicast-listener-query {
           type uint64;
           description "Multicast listener query";
         }
         leaf multicast-listener-report {
           type uint64;
           description "Multicast listener report";
         }
         leaf multicast-listener-done {
           type uint64;
           description "Multicast listener done";
         }
         leaf router-solicitation-icmp6-packets {
           type uint64;
           description "Router solicitation icmp6 packets";
         }
         leaf router-advertisement-icmp6-packets {
           type uint64;
           description "Router advertisement icmp6 packets";
         }
         leaf neighbor-solicitation {
           type uint64;
           description "Neighbor solicitation";
         }
         leaf neighbor-advertisement {
           type uint64;
           description "Neighbor advertisement";
         }
         leaf redirect {
           type uint64;
           description "Redirect";
         }
         leaf router-renumbering {
           type uint64;
           description "Router renumbering";
         }
         leaf node-information-request {
           type uint64;
           description "Node information request";
         }
         leaf node-information-reply {
           type uint64;
           description "Node information reply";
         }
         leaf version-2-multicast-listener-report {
           type uint64;
           description "Version 2 Multicast Listener Report";
         }
       }
     }
     container input-histogram {
       container input {
         leaf histogram-type {
           type string;
         }
         leaf unreachable-icmp6-packets {
           type uint64;
           description "Unreachable icmp6 packets";
         }
         leaf packet-too-big {
           type uint64;
           description "Packet too big";
         }
         leaf time-exceeded-icmp6-packets {
           type uint64;
           description "Time exceeded icmp6 packets";
         }
         leaf parameter-problem-icmp6-packets {
           type uint64;
           description "Parameter problem icmp6 packets";
         }
         leaf icmp6-echo {
           type uint64;
         }
         leaf icmp6-echo-reply {
           type uint64;
         }
         leaf multicast-listener-query {
           type uint64;
           description "Multicast listener query";
         }
         leaf multicast-listener-report {
           type uint64;
           description "Multicast listener report";
         }
         leaf multicast-listener-done {
           type uint64;
           description "Multicast listener done";
         }
         leaf router-solicitation-icmp6-packets {
           type uint64;
           description "Router solicitation icmp6 packets";
         }
         leaf router-advertisement-icmp6-packets {
           type uint64;
           description "Router advertisement icmp6 packets";
         }
         leaf neighbor-solicitation {
           type uint64;
           description "Neighbor solicitation";
         }
         leaf neighbor-advertisement {
           type uint64;
           description "Neighbor advertisement";
         }
         leaf redirect {
           type uint64;
           description "Redirect";
         }
         leaf router-renumbering {
           type uint64;
           description "Router renumbering";
         }
         leaf node-information-request {
           type uint64;
           description "Node information request";
         }
         leaf node-information-reply {
           type uint64;
           description "Node information reply";
         }
         leaf version-2-multicast-listener-report {
           type uint64;
           description "Version 2 Multicast Listener Report";
         }
       }
     }
   }
   container ipsec6 {
     leaf inbound-packets-processed-successfully {
       type uint64;
       description "Inbound packets processed successfully";
     }
     leaf inbound-packets-violated-process-security-policy {
       type uint64;
       description "Inbound packets violated process security policy";
     }
     leaf inbound-packets-with-no-sa-available {
       type uint64;
       description "Inbound packets with no SA available";
     }
     leaf invalid-inbound-packets {
       type uint64;
       description "Invalid inbound packets";
     }
     leaf inbound-packets-failed-due-to-insufficient-memory {
       type uint64;
       description "Inbound packets failed due to insufficient memory";
     }
     leaf inbound-packets-failed-getting-spi {
       type uint64;
       description "Inbound packets failed getting SPI";
     }
     leaf inbound-packets-failed-on-ah-replay-check {
       type uint64;
       description "Inbound packets failed on AH replay check";
     }
     leaf inbound-packets-failed-on-esp-replay-check {
       type uint64;
       description "Inbound packets failed on ESP replay check";
     }
     leaf inbound-packets-considered-authentic {
       type uint64;
       description "Inbound packets considered authentic";
     }
     leaf inbound-packets-failed-on-authentication {
       type uint64;
       description "Inbound packets failed on authentication";
     }
     leaf inbound-esp-packets-considered-authentic {
       type uint64;
       description "Inbound ESP packets considered authentic";
     }
     leaf inbound-esp-packets-failed-on-authentication {
       type uint64;
       description "Inbound ESP packets failed on authentication";
     }
     leaf histogram {
       type string;
     }
     leaf ahnames-none {
       type uint64;
       description "AH names";
     }
     leaf ahnames-hmac-md5 {
       type uint64;
       description "HMAC MD5";
     }
     leaf ahnames-hmac-sha1 {
       type uint64;
       description "HMAC SHA1";
     }
     leaf ahnames-md5 {
       type uint64;
       description "MD5";
     }
     leaf ahnames-sha {
       type uint64;
       description "SHA";
     }
     leaf ahnames-null {
       type uint64;
       description "NULL AH name";
     }
     leaf ahnames-hmac-sha2-256 {
       type uint64;
       description "HMAC SHA2-256";
     }
     leaf ahnames-hmac-sha2-384 {
       type uint64;
       description "HMAC SHA2-384";
     }
     leaf ahnames-hmac-sha2-512 {
       type uint64;
       description "HMAC SHA2-512";
     }
     leaf ahnames-hmac-ripemd160 {
       type uint64;
       description "HAMC RIPEMD160";
     }
     leaf ahnames-aes-xcbc-mac {
       type uint64;
       description "AES XCBC MAC";
     }
     leaf espnames-none {
       type uint64;
       description "ESP names";
     }
     leaf espnames-des-cbc {
       type uint64;
       description "DES CBC";
     }
     leaf espnames-null {
       type uint64;
       description "NULL ESP name";
     }
     leaf espnames-cast128-cbc {
       type uint64;
       description "CAST128 CBC";
     }
     leaf espnames-blowfish-cbc {
       type uint64;
       description "BLOWFISH CBC";
     }
     leaf espnames-rijndael-cbc {
       type uint64;
       description "RIJDAEL CBC";
     }
     leaf espnames-aes-ctr {
       type uint64;
       description "AES CTR";
     }
     leaf compnames-none {
       type uint64;
       description "NONE COMP names";
     }
     leaf compnames-oui {
       type uint64;
       description "OUI";
     }
     leaf compnames-deflate {
       type uint64;
       description "DEFLATE";
     }
     leaf compnames-lzs {
       type uint64;
       description "LZS";
     }
     leaf proto {
       type uint64;
     }
     leaf outbound-packets-processed-successfully {
       type uint64;
       description "Outbound packets processed successfully";
     }
     leaf outbound-packets-violated-process-security-policy {
       type uint64;
       description "Outbound packets violated process security policy";
     }
     leaf outbound-packets-with-no-sa-available {
       type uint64;
       description "Outbound packets with no SA available";
     }
     leaf invalid-outbound-packets {
       type uint64;
       description "Invalid outbound packets";
     }
     leaf outbound-packets-failed-due-to-insufficient-memory {
       type uint64;
       description "Outbound packets failed due to insufficient memory";
     }
     leaf outbound-packets-with-no-route {
       type uint64;
       description "Outbound packets with no route";
     }
     leaf spd-cache-lookups {
       type uint64;
       description "SPD cache lookups";
     }
     leaf spd-cache-misses {
       type uint64;
       description "SPD cache misses";
     }
     leaf outbound-packets-with-bundled-sa {
       type uint64;
       description "Outbound packets with bundles SAs";
     }
     leaf mbuf-coalesced-during-clone {
       type uint64;
       description "Mbuf coleasced during clone";
     }
     leaf cluster-coalesced-during-clone {
       type uint64;
       description "Cluster coalesced during clone";
     }
     leaf cluster-copied-during-clone {
       type uint64;
       description "Cluster copied during clone";
     }
     leaf mbuf-inserted-during-makespace {
       type uint64;
       description "Mbuf inserted during makespace";
     }
   }
   container pfkey {
     leaf requests-sent-from-userland {
       type uint64;
       description "Requests sent from userland";
     }
     leaf bytes-sent-from-userland {
       type uint64;
       description "Bytes sent from userland";
     }
     leaf histogram {
       type string;
     }
     leaf reserved {
       type uint64;
       description "Reserved";
     }
     leaf getspi {
       type uint64;
       description "Getspi";
     }
     leaf update {
       type uint64;
       description "Update";
     }
     leaf add {
       type uint64;
       description "Add";
     }
     leaf delete {
       type uint64;
       description "Delete";
     }
     leaf get {
       type uint64;
       description "Get";
     }
     leaf acquire {
       type uint64;
       description "Acquire";
     }
     leaf register {
       type uint64;
       description "Register";
     }
     leaf expire {
       type uint64;
       description "Expire";
     }
     leaf flush {
       type uint64;
       description "Flush";
     }
     leaf dump {
       type uint64;
       description "Dump";
     }
     leaf x-promisc {
       type uint64;
       description "X_PROMISC";
     }
     leaf x-pchange {
       type uint64;
       description "X_PCHANGE";
     }
     leaf x-spdupdate {
       type uint64;
       description "X_SPDUPDATE";
     }
     leaf x-spdadd {
       type uint64;
       description "X_SPDADD";
     }
     leaf x-spddelete {
       type uint64;
       description "X_SPDDELETE";
     }
     leaf x-spdget {
       type uint64;
       description "X_SPDGET";
     }
     leaf x-spdacquire {
       type uint64;
       description "X_SPDACQUIRE";
     }
     leaf x-spddump {
       type uint64;
       description "X_SPDDUMP";
     }
     leaf x-spdflush {
       type uint64;
       description "X_SPDFLUSH";
     }
     leaf x-spdsetidx {
       type uint64;
       description "X_SPDSETIDX";
     }
     leaf x-spdexpire {
       type uint64;
       description "X_SPDEXPIRE";
     }
     leaf x-spddelete2 {
       type uint64;
       description "X_SPDDELETE2";
     }
     leaf messages-with-invalid-length-field {
       type uint64;
       description "Messages with invalid length field";
     }
     leaf messages-with-invalid-version-field {
       type uint64;
       description "Messages with invalid version field";
     }
     leaf messages-with-invalid-message-type-field {
       type uint64;
       description "Messages with invalid message type field";
     }
     leaf messages-too-short {
       type uint64;
       description "Messages too short";
     }
     leaf outgoing-messages-with-memory-allocation-failure {
       type uint64;
       description "Outgoing messages with memory allocation failure";
     }
     leaf messages-with-duplicate-extension {
       type uint64;
       description "Messages with duplicate extension";
     }
     leaf messages-with-invalid-extension-type {
       type uint64;
       description "Messages with invalid extension type";
     }
     leaf messages-with-invalid-sa-type {
       type uint64;
       description "Messages with invalid SA type";
     }
     leaf messages-with-invalid-address-extension {
       type uint64;
       description "Messages with invalid address extension";
     }
     leaf requests-sent-to-userland {
       type uint64;
       description "Requests sent to userland";
     }
     leaf bytes-sent-to-userland {
       type uint64;
       description "Bytes sent to userland";
     }
     leaf messages-toward-single-socket {
       type uint64;
       description "Messages toward single socket";
     }
     leaf messages-toward-all-sockets {
       type uint64;
       description "Messages toward all sockets";
     }
     leaf messages-toward-registered-sockets {
       type uint64;
       description "Messages toward registered sockets";
     }
     leaf incoming-messages-with-memory-allocation-failure {
       type uint64;
       description "Incoming messages with memory allocation failure";
     }
   }
   container clnl {
     leaf total-clnl-packets-received {
       type uint32;
       description "Total clnl packets received";
     }
     leaf packets-delivered {
       type uint32;
       description "Packets delivered";
     }
     leaf too-small-packets {
       type uint32;
       description "Too small packets";
     }
     leaf packets-with-bad-header-length {
       type uint32;
       description "Packets with bad header length";
     }
     leaf packets-with-bad-checksum {
       type uint32;
       description "Packets with bad checksum";
     }
     leaf bad-version-packets {
       type uint32;
       description "Bad version packets";
     }
     leaf unknown-or-unsupported-protocol-packets {
       type uint32;
       description "Unknown or unsupported protocol packets";
     }
     leaf packets-with-bogus-sdl-size {
       type uint32;
       description "Packets with bogus sdl size";
     }
     leaf no-free-memory-in-socket-buffer {
       type uint32;
       description "No free memory in socket buffer";
     }
     leaf send-packets-discarded {
       type uint32;
       description "Send packets discarded";
     }
     leaf sbappend-failure {
       type uint32;
       description "Sbappend failure";
     }
     leaf mcopy-failure {
       type uint32;
       description "Mcopy failure";
     }
     leaf address-fields-were-not-reasonable {
       type uint32;
       description "Address fields were not reasonable";
     }
     leaf segment-information-forgotten {
       type uint32;
       description "Segment information forgotten";
     }
     leaf forwarded-packets {
       type uint32;
       description "Forwarded packets";
     }
     leaf total-packets-sent {
       type uint32;
       description "Total packets sent";
     }
     leaf output-packets-discarded {
       type uint32;
       description "Output packets discarded";
     }
     leaf non-forwarded-packets {
       type uint32;
       description "Non-forwarded packets";
     }
     leaf packets-fragmented {
       type uint32;
       description "Packets fragmented";
     }
     leaf fragments-sent {
       type uint32;
       description "Fragments sent";
     }
     leaf fragments-discarded {
       type uint32;
       description "Fragments discarded";
     }
     leaf fragments-timed-out {
       type uint32;
       description "Fragments timed out";
     }
     leaf fragmentation-prohibited {
       type uint32;
       description "Fragmentation prohibited";
     }
     leaf packets-reconstructed {
       type uint32;
       description "Packets reconstructed";
     }
     leaf packets-destined-to-dead-nexthop {
       type uint32;
       description "Packets destined to dead nexthop";
     }
     leaf packets-discarded-due-to-no-route {
       type uint32;
       description "Packets discarded due to no route";
     }
     leaf error-pdu-rate-drops {
       type uint32;
       description "Error pdu rate drops";
     }
     leaf er-pdu-generation-failure {
       type uint32;
       description "ER pdu generation failure";
     }
   }
   container esis {
     leaf total-esis-packets-received {
       type uint32;
       description "Total esis packets received";
     }
     leaf total-packets-consumed-by-protocol {
       type uint32;
       description "Total packets consumed by protocol";
     }
     leaf pdus-received-with-bad-checksum {
       type uint32;
       description "PDUs received with bad checksum";
     }
     leaf pdus-received-with-bad-version-number {
       type uint32;
       description "PDUs received with bad version number";
     }
     leaf pdus-received-with-bad-type-field {
       type uint32;
       description "PDUs received with bad type field";
     }
     leaf short-pdus-received {
       type uint32;
       description "Short pdus received";
     }
     leaf pdus-with-bogus-sdl-size {
       type uint32;
       description "Pdus withbogus sdl size";
     }
     leaf pdus-with-bad-header-length {
       type uint32;
       description "Pdus with bad header length";
     }
     leaf pdus-with-unknown-or-unsupport-protocol {
       type uint32;
       description "Pdus with unknown or unsupport protocol";
     }
     leaf no-free-memory-in-socket-buffer {
       type uint32;
       description "No free memory in socket buffer";
     }
     leaf send-packets-discarded {
       type uint32;
       description "Send packets discarded";
     }
     leaf sbappend-failure {
       type uint32;
       description "Sbappend failure";
     }
     leaf mcopy-failure {
       type uint32;
       description "Mcopy failure";
     }
     leaf iso-family-not-configured {
       type uint32;
       description "ISO family not configured";
     }
   }
   container tnp {
     leaf unicast-packets-received {
       type uint64;
       description "Unicast packets received";
     }
     leaf broadcast-packets-received {
       type uint64;
       description "Broadcast packets received";
     }
     leaf fragmented-packets-received {
       type uint64;
       description "Fragmented packets received";
     }
     leaf received-hello-packets-dropped {
       type uint64;
       description "Hello packets dropped";
     }
     leaf received-fragments-dropped {
       type uint64;
       description "Fragments dropped";
     }
     leaf fragment-reassembly-queue-flushes {
       type uint64;
       description "Fragment reassembly queue flushes";
     }
     leaf packets-with-tnp-src-address-collision-received {
       type uint64;
       description "Packets with tnp src address collision received";
     }
     leaf hello-packets-received {
       type uint64;
       description "Hello packets received";
     }
     leaf control-packets-received {
       type uint64;
       description "Control packets received";
     }
     leaf rdp-packets-received {
       type uint64;
       description "RDP packets received";
     }
     leaf udp-packets-received {
       type uint64;
       description "UDP packets received";
     }
     leaf tunnel-packets-received {
       type uint64;
       description "Tunnel packets received";
     }
     leaf input-packets-discarded-with-no-protocol {
       type uint64;
       description "Input packets discarded with no protocol";
     }
     leaf packets-of-version-unspecified-received {
       type uint64;
       description "Packets of version unspecified received";
     }
     leaf packets-of-version1-received {
       type uint64;
       description "Packets of version 1 received";
     }
     leaf packets-of-version2-received {
       type uint64;
       description "Packets of version 2 received";
     }
     leaf packets-of-version3-received {
       type uint64;
       description "Packets of version 3 received";
     }
     leaf unicast-packets-sent {
       type uint64;
       description "Unicast packets sent";
     }
     leaf broadcast-packets-sent {
       type uint64;
       description "Broadcast packets sent";
     }
     leaf fragmented-packets-sent {
       type uint64;
       description "Fragmented packets sent";
     }
     leaf sent-hello-packets-dropped {
       type uint64;
       description "Hello packets dropped";
     }
     leaf sent-fragments-dropped {
       type uint64;
       description "Fragments dropped";
     }
     leaf hello-packets-sent {
       type uint64;
       description "Hello packets sent";
     }
     leaf control-packets-sent {
       type uint64;
       description "Control packets sent";
     }
     leaf rdp-packets-sent {
       type uint64;
       description "Rdp packets sent";
     }
     leaf udp-packets-sent {
       type uint64;
       description "Udp packets sent";
     }
     leaf tunnel-packets-sent {
       type uint64;
       description "Tunnel packets sent";
     }
     leaf packets-sent-with-unknown-protocol {
       type uint64;
       description "Packets sent with unknown protocol";
     }
     leaf packets-of-version-unspecified-sent {
       type uint64;
       description "Packets of version unspecified sent";
     }
     leaf packets-of-version1-sent {
       type uint64;
       description "Packets of version 1 sent";
     }
     leaf packets-of-version2-sent {
       type uint64;
       description "Packets of version 2 sent";
     }
     leaf packets-of-version3-sent {
       type uint64;
       description "Packets of version 3 sent";
     }
   }
   container rdp {
     leaf input-packets {
       type uint64;
       description "Input packets";
     }
     leaf packets-discarded-for-bad-checksum {
       type uint64;
       description "Packets discarded for bad checksum";
     }
     leaf packets-discarded-due-to-bad-sequence-number {
       type uint64;
       description "Packets discarded due to bad sequence number";
     }
     leaf refused-connections {
       type uint64;
       description "Refused connections";
     }
     leaf acks-received {
       type uint64;
       description "Acks received";
     }
     leaf packets-dropped-due-to-full-socket-buffers {
       type uint64;
       description "Packets dropped due to full socket buffers";
     }
     leaf retransmits {
       type uint64;
       description "Retransmits";
     }
     leaf output-packets {
       type uint64;
       description "Output packets";
     }
     leaf acks-sent {
       type uint64;
       description "Acks sent";
     }
     leaf connects {
       type uint64;
       description "Connects";
     }
     leaf closes {
       type uint64;
       description "Closes";
     }
     leaf keepalives-received {
       type uint64;
       description "Keepalives received";
     }
     leaf keepalives-sent {
       type uint64;
       description "Keepalives sent";
     }
   }
   container tudp {
     leaf datagrams-received {
       type uint32;
       description "Datagrams received";
     }
     leaf datagrams-with-incomplete-header {
       type uint32;
       description "Datagrams with incomplete header";
     }
     leaf datagrams-with-bad-data-length-field {
       type uint32;
       description "Datagrams with bad data length field";
     }
     leaf datagrams-with-bad-checksum {
       type uint32;
       description "Datagrams with bad checksum";
     }
     leaf datagrams-dropped-due-to-no-socket {
       type uint32;
       description "Datagrams dropped due to no socket";
     }
     leaf broadcast-or-multicast-datagrams-dropped-due-to-no-socket {
       type uint32;
       description "Broadcast/multicast datagrams dropped due to no socket";
     }
     leaf datagrams-dropped-due-to-full-socket-buffers {
       type uint32;
       description "Datagrams dropped due to full socket buffers";
     }
     leaf delivered {
       type uint32;
       description "Delivered";
     }
     leaf datagrams-output {
       type uint32;
       description "Datagrams output";
     }
   }
   container ttp {
     leaf ttp-packets-sent {
       type uint64;
       description "Ttp packets sent";
     }
     leaf packets-sent-while-unconnected {
       type uint64;
       description "Packets sent while unconnected";
     }
     leaf packets-sent-while-interface-down {
       type uint64;
       description "Packets sent while interface down";
     }
     leaf packets-sent-could-not-get-buffer {
       type uint64;
       description "Packets sent couldn't get buffer";
     }
     leaf packets-sent-could-not-find-neighbor {
       type uint64;
       description "Packets sent could't find neighbor";
     }
     leaf packets-sent-when-transmit-disabled {
       type uint64;
       description "Packets sent when transmit is disabled";
     }
     leaf packets-sent-when-host_unreachable {
       type uint64;
       description "Packets sent when host unreachable";
     }
     leaf l3-packets-sent-could-not-get-buffer {
       type uint64;
       description "L3 Packets sent couldn't get buffer";
     }
     leaf l3-packets-dropped {
       type uint64;
       description "L3 Packets dropped";
     }
     leaf packets-sent-with-bad-ifl {
       type uint64;
       description "Packets sent with bad logical interface";
     }
     leaf packets-sent-with-bad-af {
       type uint64;
       description "Packets sent with bad address family";
     }
     leaf l2-packets-received {
       type uint64;
       description "L2 packets received";
     }
     leaf unknown-l3-packets-received {
       type uint64;
       description "Unknown L3 packets received";
     }
     leaf ipv4-l3-packets-received {
       type uint64;
       description "IPv4 L3 packets received";
     }
     leaf mpls-l3-packets-received {
       type uint64;
       description "MPLS L3 packets received";
     }
     leaf mpls-to-ipv4-l3-packets-received {
       type uint64;
       description "MPLS->IPV4 L3 packets received";
     }
     leaf ipv4-to-mpls-l3-packets-received {
       type uint64;
       description "IPv4->MPLS L3 packets received";
     }
     leaf vpls-l3-packets-received {
       type uint64;
       description "VPLS L3 packets received";
     }
     leaf ipv6-l3-packets-received {
       type uint64;
       description "IPv6 L3 packets received";
     }
     leaf arp-l3-packets-received {
       type uint64;
       description "ARP L3 packets received";
     }
     leaf clnp-l3-packets-received {
       type uint64;
       description "CLNP L3 packets received";
     }
     leaf tnp-l3-packets-received {
       type uint64;
       description "TNP L3 packets received";
     }
     leaf null-l3-packets-received {
       type uint64;
       description "NULL L3 packets received";
     }
     leaf cyclotron-cycle-l3-packets-received {
       type uint64;
       description "Cyclotron cycle L3 packets received";
     }
     leaf cyclotron-send-l3-packets-received {
       type uint64;
       description "Cyclotron send L3 packets received";
     }
     leaf openflow-packets-received {
       type uint64;
       description "Openflow packets received";
     }
     leaf packets-received-while-unconnected {
       type uint64;
       description "Packets received while unconnected";
     }
     leaf packets-received-from-unknown-ifl {
       type uint64;
       description "Packets received from unknown ifl";
     }
     leaf input-packets-could-not-get-buffer {
       type uint64;
       description "Input packets couldn't get buffer";
     }
     leaf input-packets-with-bad-type {
       type uint64;
       description "Input packets with bad type";
     }
     leaf input-packets-with-discard-type {
       type uint64;
       description "Input packets with discard type";
     }
     leaf input-packets-with-too-many-tlvs {
       type uint64;
       description "Input packets with too many tlvs";
     }
     leaf input-packets-with-bad-tlv-header {
       type uint64;
       description "Input packets with tlv header error";
     }
     leaf input-packets-with-bad-tlv-type {
       type uint64;
       description "Input packets with bad tlv type";
     }
     leaf input-packets-tlv-dropped {
       type uint64;
       description "Input packets dropped based on tlv result";
     }
     leaf input-packets-with-bad-af {
       type uint64;
       description "Input packets with bad address family";
     }
     leaf input-packets-for-which-route-lookup-is-bypassed {
       type uint64;
       description "Input packets for which route lookup is bypassed";
     }
     leaf input-packets-with-ttp-tlv-p2mp-nbr-nhid-type {
       type uint64;
       description "Input packets with ttp tlv of type TTP_TLV_P2MP_NBR_NHID";
     }
     leaf input-packets-with-unknown-p2mp-nbr-nhid {
       type uint64;
       description "Input packets with unknown p2mp_nbr_nhid value";
     }
     leaf input-packets-with-vxlan-bfd-pkts {
       type uint64;
       description "Input packets of type vxlan bfd";
     }
   }
   container mpls {
     leaf total-mpls-packets-received {
       type uint32;
       description "Total MPLS packets received";
     }
     leaf packets-forwarded {
       type uint32;
       description "Packets forwarded";
     }
     leaf packets-dropped {
       type uint32;
       description "Packets dropped (src and int don't match)";
     }
     leaf packets-with-header-too-small {
       type uint32;
       description "Packets with header too small";
     }
     leaf after-tagging-packets-can-not-fit-link-mtu {
       type uint32;
       description "After tagging, packets can't fit link MTU";
     }
     leaf packets-with-ipv4-explicit-null-tag {
       type uint32;
       description "Packets with IPv4 explicit NULL tag";
     }
     leaf packets-with-ipv4-explicit-null-checksum-errors {
       type uint32;
       description "Packets with IPv4 explicit NULL cksum errors";
     }
     leaf packets-with-router-alert-tag {
       type uint32;
       description "Packets with router alert tag";
     }
     leaf lsp-ping-packets {
       type uint32;
       description "LSP ping packets (ttl-expired/router alert)";
     }
     leaf packets-with-ttl-expired {
       type uint32;
       description "Packets with ttl expired";
     }
     leaf packets-with-tag-encoding-error {
       type uint32;
       description "Packets with tag encoding error";
     }
     leaf packets-discarded-due-to-no-route {
       type uint32;
       description "Packets discarded due to no route";
     }
     leaf packets-used-first-nexthop-in-ecmp-unilist {
       type uint32;
       description "Packets used first nexthop in ecmp unilist";
     }
     leaf packets-dropped-due-to-ifl-down {
       type uint32;
       description "Packets dropped due to ifl down";
     }
   }
   container vpls {
     leaf total-packets-received {
       type uint64;
       description "Total packets received";
     }
     leaf vpls-packets-with-size-smaller-than-minimum {
       type uint64;
       description "Vpls packets with size smaller than minimum";
     }
     leaf vpls-packets-with-incorrect-version-number {
       type uint64;
       description "Vpls packets with incorrect version number";
     }
     leaf vpls-packets-for-this-host {
       type uint64;
       description "Vpls packets for this host";
     }
     leaf packets-with-no-logical-interface {
       type uint64;
       description "Packets with no logical interface";
     }
     leaf packets-with-no-family {
       type uint64;
       description "Packets with no family";
     }
     leaf packets-with-no-route-table {
       type uint64;
       description "Packets with no route table";
     }
     leaf packets-with-no-auxiliary-table {
       type uint64;
       description "Packets with no auxiliary table";
     }
     leaf packets-with-no-corefacing-entry {
       type uint64;
       description "Packets with no corefacing entry";
     }
     leaf packets-with-no-ce-facing-entry {
       type uint64;
       description "Packets with no CE-facing entry";
     }
     leaf mac-route-learning-requests {
       type uint64;
       description "MAC route learning requests";
     }
     leaf mac-routes-learned {
       type uint64;
       description "MAC routes learnt";
     }
     leaf requests-to-learn-an-existing-route {
       type uint64;
       description "Requests to learn an existing route";
     }
     leaf learning-requests-while-learning-disabled-on-interface {
       type uint64;
       description "Learning requests while learning disabled on interface";
     }
     leaf learning-requests-over-capacity {
       type uint64;
       description "Learning requests over capacity";
     }
     leaf mac-routes-moved {
       type uint64;
       description "MAC routes moved";
     }
     leaf requests-to-move-static-route {
       type uint64;
       description "Requests to move static route";
     }
     leaf mac-route-aging-requests {
       type uint64;
       description "MAC route aging requests";
     }
     leaf mac-routes-aged {
       type uint64;
       description "MAC routes aged";
     }
     leaf bogus-address-in-aging-requests {
       type uint64;
       description "Bogus address in aging requests";
     }
     leaf requests-to-age-static-route {
       type uint64;
       description "Requests to age static route";
     }
     leaf requests-to-re-ageout-aged-route {
       type uint64;
       description "Requests to re-ageout aged route";
     }
     leaf requests-involving-multiple-peer-fes {
       type uint64;
       description "Requests involving multiple peer FEs";
     }
     leaf aging-acks-from-pfe {
       type uint64;
       description "Aging acks from PFE";
     }
     leaf aging-non-acks-from-pfe {
       type uint64;
       description "Aging non-acks from PFE";
     }
     leaf aging-requests-timed-out-waiting-on-fes {
       type uint64;
       description "Aging requests timed out waiting on FEs";
     }
     leaf aging-requests-over-max-rate {
       type uint64;
       description "Aging requests over max-rate";
     }
     leaf errors-finding-peer-fes {
       type uint64;
       description "Errors finding peer FEs";
     }
     leaf unsupported-platform {
       type uint64;
       description "Unsupported platform";
     }
     leaf packets-dropped-due-to-no-l3-route-table {
       type uint64;
       description "Packets dropped due to no l3 route table";
     }
     leaf packets-dropped-due-to-no-local-ifl {
       type uint64;
       description "Packets dropped due to no local ifl";
     }
     leaf packets-punted {
       type uint64;
       description "Packets punted";
     }
     leaf packets-dropped-due-to-no-socket {
       type uint64;
       description "Packets dropped due to no socket";
     }
   }
   container bridge {
     leaf heading {
       type string;
       description "Header";
     }
     leaf bridge-packets-received {
       type uint64;
       description "Bridge packets received";
     }
     leaf bridge-packets-forwarded {
       type uint64;
       description "Bridge packets forwarded";
     }
     leaf packets-failed-to-forward {
       type uint64;
       description "Packets failed to forward";
     }
     leaf bridge-packets-dropped {
       type uint64;
       description "Bridge packets dropped";
     }
     leaf packets-with-vmember-lookup-failures {
       type uint64;
       description "Packets with vmember lookup failures";
     }
     leaf packets-with-vlan-lookup-failures {
       type uint64;
       description "Packets with VLAN lookup failures";
     }
     leaf packets-with-stp-state-lookup-failures {
       type uint64;
       description "Packets with STP state lookup failures";
     }
     leaf packets-dropped-due-to-stp-blocked-or-listening {
       type uint64;
       description "Packets dropped due to STP blocked/listening";
     }
     leaf packets-dropped-due-to-stp-learning {
       type uint64;
       description "Packets dropped due to STP learning";
     }
     leaf packets-with-src-mac-learning-failures {
       type uint64;
       description "Packets with src MAC learning failures";
     }
     leaf packets-with-input-control-processing-failures {
       type uint64;
       description "Packets with input control processing failures";
     }
     leaf packets-sent-successfully {
       type uint64;
       description "Packets sent successfully";
     }
     leaf packets-with-send-failures {
       type uint64;
       description "Packets with send failures";
     }
     leaf packets-forwarded-to-l3-interface {
       type uint64;
       description "Packets forwarded to l3 interface";
     }
     leaf packets-with-l3-send-failures {
       type uint64;
       description "Packets with l3 send failures";
     }
     leaf packets-discarded {
       type uint64;
       description "Packets discarded";
     }
     leaf packets-with-l2-ifl-store-failures {
       type uint64;
       description "Packets with l2ifl store failures";
     }
     leaf packets-with-ifl-mismatch-failures {
       type uint64;
       description "Packets with ifl mismatch failures";
     }
     leaf packets-with-packet-duplication-failures {
       type uint64;
       description "Packets with packet duplication failures";
     }
     leaf packets-with-tag-lookup-failures {
       type uint64;
       description "Packets with tag lookup failures";
     }
     leaf packets-with-no-route-for-dmac {
       type uint64;
       description "Packets with no route for DMAC";
     }
     leaf packets-with-no-route-table {
       type uint64;
       description "Packets with no route table";
     }
     leaf packets-with-no-nexthop {
       type uint64;
       description "Packets with no nexthop";
     }
     leaf packets-with-dead-nexthop {
       type uint64;
       description "Packets with dead nexthop";
     }
     leaf packets-with-eof-reached-error {
       type uint64;
       description "Packets with eof reached error";
     }
     leaf macs-learned {
       type uint64;
       description "MACs learned";
     }
     leaf packets-sent-to-l3-interface {
       type uint64;
       description "Packets sent to l3 interface";
     }
     leaf packets-hit-hold-queue-while-learning {
       type uint64;
       description "Packets hit hold queue while learning";
     }
     leaf mac-moves {
       type uint64;
       description "MAC moves";
     }
     leaf packets-with-no-route-for-smac {
       type uint64;
       description "Packets with no route for SMAC";
     }
     leaf packets-dropped-due-to-no-resolve-route {
       type uint64;
       description "Packets dropped due to no resolve route";
     }
     leaf packets-with-l3-ifd-lookup-failures {
       type uint64;
       description "Packets with l3 ifd lookup failures";
     }
     leaf packets-with-l3-ifl-lookup-failures {
       type uint64;
       description "Packets with l3 ifl lookup failures";
     }
     leaf packets-with-l3-invalid-rnh {
       type uint64;
       description "Packets with l3 invalid RNH";
     }
     leaf packets-with-no-route-for-smac-in-clone-learning {
       type uint64;
       description "Packets with no route for SMAC in clone learning";
     }
     leaf packets-with-no-nexthop-in-clone-learning {
       type uint64;
       description "Packets with no nexhop in clone learning";
     }
     leaf packets-with-dead-nexthop-in-clone-learning {
       type uint64;
       description "Packets with dead nexthop in clone learning";
     }
     leaf packets-dropped-due-to-no-resolve-nh-in-clone-learning {
       type uint64;
       description "Packets dropped due to no resolve nh in clone learning";
     }
     leaf packets-dropped-due-to-interface-down {
       type uint64;
       description "Packets dropped due to interface down";
     }
     leaf packets-with-dev-output-failures {
       type uint64;
       description "Packets with dev output failures";
     }
     leaf blocked-ifl-discards {
       type uint64;
       description "Blocked ifl discards";
     }
     leaf packets-with-tag-insertion-failures {
       type uint64;
       description "Packets with tag insertion failures";
     }
     leaf packets-with-tag-removal-failures {
       type uint64;
       description "Packets with tag removal failures";
     }
     leaf packets-flooded {
       type uint64;
       description "Packets flooded";
     }
     leaf flood-failures {
       type uint64;
       description "Flood failures";
     }
     leaf packets-with-mpull-failures {
       type uint64;
       description "Packets with mpull failures";
     }
     leaf packets-with-ifl-lookup-failures {
       type uint64;
       description "Packets with ifl lookup failures";
     }
     leaf bridge-packets-with-size-smaller-than-minimum {
       type uint64;
       description "Bridge packets with size smaller than minimum";
     }
     leaf packets-with-double-tags {
       type uint64;
       description "Packets with double tags";
     }
     leaf packets-with-no-ifl {
       type uint64;
     }
     leaf packets-with-no-family {
       type uint64;
       description "Packets with no family";
     }
     leaf packets-with-receive-failures {
       type uint64;
       description "Packets with receive failures";
     }
   }
   container ethoamcfm {
     leaf total-packets-received {
       type uint64;
       description "Total packets received";
     }
     leaf input-packets-drop-bad-interface-state {
       type uint32;
       description "Input packets drop due to bad interface state";
     }
     leaf received-packets-forwarded {
       type uint32;
       description "Received packets forwarded";
     }
     leaf total-packets-transmitted {
       type uint32;
       description "Total transmitted packets";
     }
     leaf packets-sent {
       type uint32;
       description "Packets sent";
     }
     leaf output-packets-drop-bad-interface-state {
       type uint32;
       description "Output packets drop due to bad interface state";
     }
     leaf flood-requests-forwarded-to-pfe {
       type uint32;
       description "Flood requests forwarded to PFE";
     }
     leaf flood-requests-dropped {
       type uint32;
       description "Flood requests dropped";
     }
   }
   container ethoamlfm {
     leaf total-packets-received {
       type uint64;
       description "Total packets received";
     }
     leaf input-packets-drop-bad-interface-state {
       type uint32;
       description "Input packets drop due to bad interface state";
     }
     leaf received-packets-forwarded {
       type uint32;
       description "Received packets forwarded";
     }
     leaf total-packets-transmitted {
       type uint32;
       description "Total transmitted packets";
     }
     leaf packets-sent {
       type uint32;
       description "Packets sent";
     }
     leaf output-packets-drop-bad-interface-state {
       type uint32;
       description "Output packets drop due to bad interface state";
     }
   }
   container jsr {
     leaf handle-info {
       type string;
     }
     leaf handles-in-use {
       type uint32;
       description "Handles in use";
     }
     leaf handles-allocated-so-far {
       type uint32;
       description "Handles allocated so far";
     }
     leaf handles-freed-so-far {
       type uint32;
       description "Handles freed so far";
     }
     leaf handles-in-delayed-free-state {
       type uint32;
       description "Handles in delayed free state";
     }
     leaf iha {
       type string;
     }
     leaf iha-invalid-subtype-messages {
       type uint32;
       description "Invalid subtype messages";
     }
     leaf iha-invalid-length-messages {
       type uint32;
       description "Invalid length messages";
     }
     leaf iha-invalid-version-messages {
       type uint32;
       description "Invalid version messages";
     }
     leaf iha-too-short-messages {
       type uint32;
       description "IHA too short messages";
     }
     leaf iha-invalid-dst-handle-messages {
       type uint32;
       description "IHA invalid dst handle messages";
     }
     leaf iha-invalid-src-handle-messages {
       type uint32;
       description "IHA invalid src handle messages";
     }
     leaf iha-unmatched-src-handle-messages {
       type uint32;
       description "IHA unmatched src handle messages";
     }
     leaf iha-invalid-messages-for-primary {
       type uint32;
       description "IHA invalid messages for primary";
     }
     leaf iha-invalid-messages-for-secondary {
       type uint32;
       description "IHA invalid messages for secondary";
     }
     leaf iha-invalid-messages-for-current-state {
       type uint32;
       description "IHA invalid messages for current state";
     }
     leaf iha-messages-sent-for-subtype-init {
       type uint32;
       description "IHA messages sent for subtype init";
     }
     leaf iha-messages-rcvd-for-subtype-init {
       type uint32;
       description "IHA messages rcvd for subytpe init";
     }
     leaf iha-messages-sent-for-subtype-ack {
       type uint32;
       description "IHA messages sent for subtype ack";
     }
     leaf iha-messages-rcvd-for-subtype-ack {
       type uint32;
       description "IHA messages rcvd for subtype ack";
     }
     leaf iha-messages-sent-for-subtype-unrepl-sec {
       type uint32;
       description "IHA messages sent for subtype unrepl_sec";
     }
     leaf iha-messages-rcvd-for-subtype-unrepl-sec {
       type uint32;
       description "IHA messages rcvd for subtype unrepl_sec";
     }
     leaf iha-messages-sent-for-subtype-unrepl-pri {
       type uint32;
       description "IHA messages sent for subtype unrepl_pri";
     }
     leaf iha-messages-rcvd-for-subtype-unrepl-pri {
       type uint32;
       description "IHA messages rcvd for subtype unrepl_pri";
     }
     leaf iha-messages-sent-for-subtype-unrepl-am-sec {
       type uint32;
       description "IHA messages sent for subtype unrepl_am_sec";
     }
     leaf iha-messages-rcvd-for-subtype-unrepl-am-sec {
       type uint32;
       description "IHA messages rcvd for subtype unrepl_am_sec";
     }
     leaf iha-message-timeouts {
       type uint32;
       description "IHA message timeouts";
     }
     leaf iha-socket-unreplicate-messages {
       type uint32;
       description "IHA socket unreplicate messages";
     }
     leaf sdrl {
       type string;
     }
     leaf sdrl-socket-teardowns {
       type uint32;
       description "SDRL socket teardowns";
     }
     leaf sdrl-socket-teardown-failures {
       type uint32;
       description "SDRL socket teardown failures";
     }
     leaf sdrl-socket-unreplicates {
       type uint32;
       description "SDRL socket unreplicates";
     }
     leaf sdrl-socket-unreplicate-failures {
       type uint32;
       description "SDRL socket unreplicate failures";
     }
     leaf sdrl-external-timeouts {
       type uint32;
       description "SDRL external timeouts";
     }
     leaf sdrl-internal-timeouts {
       type uint32;
       description "SDRL internal timeouts";
     }
     leaf sdrl-ipc-messages-sent {
       type uint32;
       description "SDRL ipc messages sent";
     }
     leaf sdrl-ipc-send-failures {
       type uint32;
       description "SDRL ipc send failures";
     }
     leaf sdrl-ipc-messages-recvd {
       type uint32;
       description "SDRL ipc messages recvd";
     }
     leaf sdrl-ipc-recv-failures {
       type uint32;
       description "SDRL ipc recv failures";
     }
     leaf sdrl-primary-replication-messages-sent {
       type uint32;
       description "SDRL primary replication messages sent";
     }
     leaf sdrl-primary-replication-message-send-failures {
       type uint32;
       description "SDRL primary replication message send failures";
     }
     leaf sdrl-primary-ack-messages-received {
       type uint32;
       description "SDRL primary ack messages received";
     }
     leaf sdrl-primary-ack-message-receive-failures {
       type uint32;
       description "SDRL primary ack message receive failures";
     }
     leaf sdrl-primary-sock-replication-inits {
       type uint32;
       description "SDRL primary sock replication inits";
     }
     leaf sdrl-primary-sock-replication-init-failures {
       type uint32;
       description "SDRL primary sock message init failures";
     }
     leaf sdrl-primary-throttle-remove-messages {
       type uint32;
       description "SDRL primary throttle remove messages";
     }
     leaf sdrl-primary-throttle-remove-failures {
       type uint32;
       description "SDRL primary throtle remove failures";
     }
     leaf sdrl-primary-init-handshake-messages {
       type uint32;
       description "SDRL primary init handshake messages";
     }
     leaf sdrl-primary-init-handshake-failures {
       type uint32;
       description "SDRL primary init handshake failures";
     }
     leaf sdrl-secondary-replication-messages-received {
       type uint32;
       description "SDRL secondary replication messages received";
     }
     leaf sdrl-secondary-replication-message-receive-failures {
       type uint32;
       description "SDRL secondary replication message receive failures";
     }
     leaf sdrl-secondary-replication-acks-sent {
       type uint32;
       description "SDRL secondary replication acks sent";
     }
     leaf sdrl-secondary-replication-ack-send-failures {
       type uint32;
       description "SDRL secondary replication ack send failures";
     }
     leaf sdrl-secondary-sock-splits {
       type uint32;
       description "SDRL secondary sock splits";
     }
     leaf sdrl-secondary-sock-split-failures {
       type uint32;
       description "SDRL secondary sock split failures";
     }
     leaf sdrl-secondary-sock-merges {
       type uint32;
       description "SDRL secondary sock merges";
     }
     leaf sdrl-secondary-sock-merge-failures {
       type uint32;
       description "SDRL secondary sock merge failures";
     }
     leaf sdrl-secondary-sockets-closed {
       type uint32;
       description "SDRL secondary sockets closed";
     }
     leaf sdrl-secondary-rcv-snoop-fd-close-failures {
       type uint32;
       description "SDRL secondary rcv snoop fd close failures";
     }
     leaf sdrl-secondary-snd-snoop-fd-close-failures {
       type uint32;
       description "SDRL secondary snd snoop fd close failures";
     }
     leaf sdrl-secondary-init-handshake-messages {
       type uint32;
       description "SDRL secondary init handshake messages";
     }
     leaf sdrl-secondary-init-handshake-failures {
       type uint32;
       description "SDRL secondary init handshake failures";
     }
     leaf prl {
       type string;
     }
     leaf prl-packets-enqueued {
       type uint32;
       description "PRL packets enqueued";
     }
     leaf prl-packets-failed-to-enqueue {
       type uint32;
       description "PRL packets failed to enqueue";
     }
     leaf prl-packets-dequeued {
       type uint32;
       description "PRL packets dequeued";
     }
     leaf prl-packets-failed-to-dequeue {
       type uint32;
       description "PRL packets failed to dequeue";
     }
     leaf prl-queue-entry-allocations {
       type uint32;
       description "PRL queue entry allocations";
     }
     leaf prl-queue-entry-frees {
       type uint32;
       description "PRL queue entry frees";
     }
     leaf prl-calls-to-layer4-input-handlers {
       type uint32;
       description "Calls to layer 4 input handlers";
     }
     leaf prl-failed-calls-to-layer4-input-handlers {
       type uint32;
       description "Failed calls to layer 4 input handlers";
     }
     leaf prl-queue-drains {
       type uint32;
       description "PRL queue drains";
     }
     leaf prl-replication-timeouts {
       type uint32;
       description "PRL replication timeouts";
     }
     leaf prl-replication-messages-sent {
       type uint32;
       description "PRL replication messages sent";
     }
     leaf prl-replication-message-send-failures {
       type uint32;
       description "PRL replication message send failures";
     }
     leaf prl-acknowledgement-messages-sent {
       type uint32;
       description "PRL acknowledgment messages sent";
     }
     leaf prl-acknowledgement-message-send-failures {
       type uint32;
       description "PRL acknowledgement message send failures";
     }
     leaf prl-replication-message-received {
       type uint32;
       description "PRL replication message received";
     }
     leaf prl-replication-message-receive-failures {
       type uint32;
       description "PRL replication message receive failures";
     }
     leaf prl-acknowledgement-messages-received {
       type uint32;
       description "PRL acknowledgement message received";
     }
     leaf prl-acknowledgement-message-receive-failures {
       type uint32;
       description "PRL acknowledgment message receive failures";
     }
     leaf prl-messages-with-bad-ipc-type {
       type uint32;
       description "PRL messages with bad IPC type";
     }
     leaf prl-messages-with-no-handler {
       type uint32;
       description "PRL messages with no handler";
     }
     leaf prl-global-state-initializations {
       type uint32;
       description "PRL global state initializations";
     }
     leaf prl-global-state-cleanups {
       type uint32;
       description "PRL global state cleanups";
     }
     leaf prl-per-socket-state-creations {
       type uint32;
       description "PRL per-socket state creations";
     }
     leaf prl-per-socket-state-creation-failures {
       type uint32;
       description "PRL per-socket state creation failures";
     }
     leaf prl-per-socket-state-cleanups {
       type uint32;
       description "PRL per-socket state cleanups";
     }
     leaf prl-socket-closes {
       type uint32;
       description "PRL socket closes";
     }
     leaf prl-socket-merges {
       type uint32;
       description "PRL socket merges";
     }
     leaf prl-socket-unreplicates {
       type uint32;
       description "PRL socket unreplicates";
     }
     leaf prl-primary-socket-replication-initializations {
       type uint32;
       description "PRL primary socket replication initializations";
     }
     leaf prl-secondary-socket-replication-initializations {
       type uint32;
       description "PRL secondary socket replication initializations";
     }
     leaf prl-primary-socket-replication-activations {
       type int32;
       description "PRL primary socket replication activations";
     }
     leaf prl-secondary-socket-replication-activations {
       type uint32;
       description "PRL secondary socket replication activations";
     }
     leaf prl-packets-received-from-peers {
       type uint32;
       description "Packets received from peers";
     }
     leaf prl-packets-receive-operations-from-peer-failed {
       type uint32;
       description "PRL packets receive operations from peer failed";
     }
     leaf prl-buffer-pullup-failures {
       type uint32;
       description "PRL buffer pullup failures";
     }
     leaf prl-new-packets-dropped-on-security-socket {
       type uint32;
       description "New pkts dropped on secondary socket";
     }
     leaf psrm {
       type string;
     }
     leaf psrm-replication-timeouts {
       type uint32;
       description "PSRM replication timeouts";
     }
     leaf psrm-replication-messages-sent {
       type uint32;
       description "PSRM replication messages sent";
     }
     leaf psrm-replication-message-send-failures {
       type uint32;
       description "PSRM replication message send failures";
     }
     leaf psrm-acknowledgement-messages-sent {
       type uint32;
       description "PSRM acknowledgment messages sent";
     }
     leaf psrm-acknowledgement-message-send-failures {
       type uint32;
       description "PSRM acknowledgement message send failures";
     }
     leaf psrm-flow-control-messages-sent {
       type uint32;
       description "PSRM flow control messages sent";
     }
     leaf psrm-flow-control-message-send-failures {
       type uint32;
       description "PSRM flow control message send failures";
     }
     leaf psrm-replication-messages-received {
       type uint32;
       description "PSRM replication messages received";
     }
     leaf psrm-replication-message-receive-failures {
       type uint32;
       description "PSRM replication message receive failures";
     }
     leaf psrm-acknowledgement-messages-received {
       type uint32;
       description "PSRM acknowledgment messages received";
     }
     leaf psrm-acknowledgement-message-receive-failures {
       type uint32;
       description "PSRM acknowledgment message receive failures";
     }
     leaf psrm-flow-control-messages-received {
       type uint32;
       description "PSRM flow control messages received";
     }
     leaf psrm-flow-control-message-receive-failures {
       type uint32;
       description "PSRM flow control message receive failures";
     }
     leaf psrm-messages-with-bad-ipc-type {
       type uint32;
       description "PSRM messages with bad IPC type";
     }
     leaf psrm-messages-with-no-handler {
       type uint32;
       description "PSRM messages with no handler";
     }
     leaf psrm-global-state-initializations {
       type uint32;
       description "PSRM global state initializations";
     }
     leaf psrm-global-state-cleanups {
       type uint32;
       description "PSRM global state cleanups";
     }
     leaf psrm-per-socket-state-creations {
       type uint32;
       description "PSRM per-socket state creations";
     }
     leaf psrm-per-socket-state-creation-failures {
       type uint32;
       description "PSRM per-socket state creation failures";
     }
     leaf psrm-per-socket-state-cleanups {
       type uint32;
       description "PSRM per-socket state cleanups";
     }
     leaf psrm-socket-closes {
       type uint32;
       description "PSRM socket closes";
     }
     leaf psrm-socket-merges {
       type uint32;
       description "PSRM socket merges";
     }
     leaf psrm-socket-unreplicates {
       type uint32;
       description "PSRM socket unreplicates";
     }
     leaf psrm-primary-socket-replication-initializations {
       type uint32;
       description "PSRM primary socket replication initializations";
     }
     leaf psrm-secondary-socket-replication-initializations {
       type uint32;
       description "PSRM secondary socket replication initializations";
     }
     leaf psrm-primary-socket-replication-activations {
       type uint32;
       description "PSRM primary socket replication activations";
     }
     leaf psrm-secondary-socket-replication-activations {
       type uint32;
       description "PSRM secondary socket replication activations";
     }
     leaf psrm-tcpcb-updates {
       type uint32;
       description "PSRM tcpcb updates";
     }
     leaf psrm-buffer-pullup-failures {
       type uint32;
       description "PSRM buffer pullup failures";
     }
     leaf psrm-tcp-timestamp-msg-recv-counters {
       type uint32;
       description "PSRM tcp timestamp msg recv counters";
     }
     leaf psrm-tcp-timestamp-msg-recv-failures {
       type uint32;
       description "PSRM tcp timestamp msg recv failures";
     }
     leaf psrm-tcp-timestamp-msg-send-counters {
       type uint32;
       description "PSRM tcp timestamp msg send counters";
     }
     leaf psrm-tcp-timestamp-msg-send-failures {
       type uint32;
       description "PSRM tcp timestamp msg send failures";
     }
     leaf tcp-field {
       type string;
     }
     leaf tcp-out-of-order-packets-on-jsr-sockets {
       type uint32;
       description "TCP out-of-order packets on JSR sockets";
     }
   }
   container virtual-node-statistics {
     leaf number-of-virtual-node-route-tables {
       type uint32;
       description "Number of route-tables marked with virtual-node";
     }
     leaf number-of-virtual-node-vlan-ids {
       type uint32;
       description "Number of vlan-ids on virtual-node route-tables";
     }
     leaf no-route-table-auxiliary-structure {
       type uint32;
       description "No helper structure found for virtual-node route-table";
     }
     leaf route-table-non-virtual-node-local-address {
       type uint32;
       description "IFA callbacks on non-virtual-node tables";
     }
     leaf route-table-virtual-node-local-address {
       type uint32;
       description "IFA callbacks on virtual-node tables";
     }
     leaf route-table-no-mbuf-tag {
       type uint32;
       description "Route-table mbuf tag not found in a virtual-node context";
     }
     leaf route-table-not-found {
       type uint32;
       description "Route-table indicated by virtual-node mbuf tag not found";
     }
     leaf route-table-non-virtual-node {
       type uint32;
       description "Route-table found from tag was not enabled for virtual-node";
     }
     leaf route-table-no-shared-vlan {
       type uint32;
       description "No shared vlan associated with virtual-node table";
     }
     leaf packets-transmitted-to-fabric {
       type uint32;
       description "Packets transmitted to the virtual-node fabric";
     }
     leaf packets-received-from-fabric {
       type uint32;
       description "Packets received from the virtual-node fabric";
     }
     leaf no-interface-for-egress-statistics {
       type uint32;
       description "Interface not found to update traffic statistics";
     }
     leaf duplicate-vlan-id {
       type uint32;
       description "Route table update attempts with duplicate vlan-id";
     }
   }
   container virtual-node-packet-record-statistics {
     leaf packet_recording_status {
       type string;
       description "Control packet recording status on the virtual-node";
     }
     leaf packet-records-created {
       type uint32;
       description "ICMP/UDP records added";
     }
     leaf packet-records-deleted {
       type uint32;
       description "ICMP/UDP records removed";
     }
     leaf packet-record-create-errors {
       type uint32;
       description "Record creations errored out";
     }
     leaf packet-record-delete-errors {
       type uint32;
       description "Record deletions errored out";
     }
     leaf packet-record-get-errors {
       type uint32;
       description "Records not found";
     }
     leaf udp-records-timed-out {
       type uint32;
       description "UDP packet records timed out";
     }
     leaf icmp-records-timed-out {
       type uint32;
       description "ICMP packet records timed out";
     }
     leaf to-fabric-dont-care-protocol {
       type uint32;
       description "To-fabric OAM packets, no matching reply expected";
     }
     leaf from-fabric-dont-care-protocol {
       type uint32;
       description "From-fabric OAM packets, no matching reply expected";
     }
     leaf to-fabric-unchecked-icmp {
       type uint32;
       description "To-fabric ICMP packets, with no record created";
     }
     leaf from-fabric-unchecked-icmp {
       type uint32;
       description "From-fabric ICMP packets, with no record consulted";
     }
     leaf to-fabric-unchecked-udp {
       type uint32;
       description "To-fabric UDP packets, with no record created";
     }
     leaf from-fabric-unchecked-udp {
       type uint32;
       description "From-fabric UDP packets, with no record consulted";
     }
     leaf from-fabric-unhandled-protocol {
       type uint32;
       description "From-fabric packets, protocol not handled by records";
     }
     leaf to-fabric-unhandled-protocol {
       type uint32;
       description "To-fabric packets, protocol not handled by records";
     }
     leaf to-fabric-drops {
       type uint32;
       description "Packets dropped at egress to fabric";
     }
     leaf from-fabric-drops {
       type uint32;
       description "Packets dropped at ingress from fabric";
     }
     leaf to-fabric-not-my-packet {
       type uint32;
       description "Packets re-sent to fabric due to unmatched record";
     }
     leaf to-fabric-split-horizon-suppress {
       type uint32;
       description "Unmatched packets not re-sent due to ingress from fabric";
     }
     leaf active-timers {
       type uint32;
       description "Packet timers active";
     }
     leaf requests-over-limit {
       type uint32;
       description "Packets not recorded due to resource constraints";
     }
   }
 }
 grouping extended-system-stats-block {
   leaf ip-systemstats-inreceives {
     type uint64;
     description "In Recieves";
   }
   leaf ip-systemstats-inoctets {
     type uint64;
     description "In Octets";
   }
   leaf ip-systemstats-inhdrerrors {
     type uint64;
     description "In Header Errors";
   }
   leaf ip-systemstats-innoroutes {
     type uint64;
     description "In No Routes";
   }
   leaf ip-systemstats-inaddrerrors {
     type uint64;
     description "In Address Errors";
   }
   leaf ip-systemstats-inunknownprotos {
     type uint64;
     description "In Unknown protocols";
   }
   leaf ip-systemstats-intruncatedpkts {
     type uint64;
     description "In Truncated Packets";
   }
   leaf ip-systemstats-inforwdatagrams {
     type uint64;
     description "In Forward Datagrams";
   }
   leaf ip-systemstats-reasmreqds {
     type uint64;
     description "Reassemble Reqds";
   }
   leaf ip-systemstats-reasmoks {
     type uint64;
     description "Reassmeble OKs";
   }
   leaf ip-systemstats-reasmfails {
     type uint64;
     description "Reassemble Fails";
   }
   leaf ip-systemstats-indiscards {
     type uint64;
     description "In Discards";
   }
   leaf ip-systemstats-indelivers {
     type uint64;
     description "In Delivers";
   }
   leaf ip-systemstats-outrequets {
     type uint64;
     description "Out Requests";
   }
   leaf ip-systemstats-outnoroutes {
     type uint64;
     description "OUt No Routes";
   }
   leaf ip-systemstats-outforwdatagrams {
     type uint64;
     description "Out Forward Datagrams";
   }
   leaf ip-systemstats-outdiscards {
     type uint64;
     description "Out Discards";
   }
   leaf ip-systemstats-outfragreqds {
     type uint64;
     description "Out Fragmentation Reqds";
   }
   leaf ip-systemstats-outfragoks {
     type uint64;
     description "Out Fragmentaion OK";
   }
   leaf ip-systemstats-outfragfails {
     type uint64;
     description "Out Fragmentation Fails";
   }
   leaf ip-systemstats-outfragcreats {
     type uint64;
     description "Out Fragment Creats";
   }
   leaf ip-systemstats-outtransmits {
     type uint64;
     description "Out Transmits";
   }
   leaf ip-systemstats-outoctets {
     type uint64;
     description "Out Octets";
   }
   leaf ip-systemstats-inmcastpkts {
     type uint64;
     description "In Multicats Packets";
   }
   leaf ip-systemstats-inmcastoctets {
     type uint64;
     description "In Multicast Octets";
   }
   leaf ip-systemstats-outmcastpkts {
     type uint64;
     description "Out Multicats Packets";
   }
   leaf ip-systemstats-outmcastoctets {
     type uint64;
     description "Out Multicast Octets";
   }
   leaf ip-systemstats-discontinuitytime {
     type string;
     description "Sysstats disconuity time";
   }
 }
 grouping system-storage-information-block {
   container detail {
     container filesystem {
       description "Information about system storage";
       leaf filesystem-name {
         type string;
         description "Name of the filesystem";
       }
       leaf total-blocks {
         type int32;
         description "Number of 512 blocks";
       }
       leaf used-blocks {
         type int32;
         description "Used storage space";
       }
       leaf available-blocks {
         type int32;
         description "Available storage space";
       }
       leaf used-percent {
         type int32;
         description "Percent of filesystem in use";
       }
       leaf mounted-on {
         type string;
         description "Filesystem mounted on";
       }
     }
   }
   container brief {
     container filesystem {
       description "Information about system storage";
       leaf filesystem-name {
         type string;
         description "Name of the filesystem";
       }
       leaf total-blocks {
         type int32;
         description "Number of 512 blocks";
       }
       leaf used-blocks {
         type int32;
         description "Used storage space";
       }
       leaf available-blocks {
         type int32;
         description "Available storage space";
       }
       leaf used-percent {
         type int32;
         description "Percent of filesystem in use";
       }
       leaf mounted-on {
         type string;
         description "Filesystem mounted on";
       }
     }
   }
 }
 grouping switchover-information-block {
   leaf switchover-state {
     type string;
   }
   container switchover-mode {
     leaf multichassis-mode {
       type empty;
       description "Kernel replication for multichassis";
     }
     leaf gres-mode {
       type empty;
       description "Kernel replication for graceful switchover";
     }
     leaf unknown-mode {
       type empty;
       description "Kernel replication for unknown mode";
     }
   }
   container configuration-state {
     leaf configuration-ready {
       type empty;
       description "Configuration database is synchronized with master";
     }
     leaf configuration-synchronizing {
       type empty;
       description "Synchronizing configuration database with master";
     }
     leaf configuration-synchronize-error {
       type empty;
       description "Failure during configuration database synchronize";
     }
   }
   container replication-state {
     leaf replication-ready {
       type empty;
       description "Replicated kernel state is synchronized with master";
     }
     leaf replication-synchronizing {
       type empty;
       description "Replicated kernel is receiving state updates from master";
     }
     leaf replication-error {
       type empty;
       description "Replicated and master kernels do not have identical state";
     }
     leaf replication-version-mismatch {
       type empty;
       description "Replicated and master kernels running incompatible versions";
     }
     leaf replication-connection-error {
       type empty;
       description "Master connection error";
     }
     leaf replication-reconnect-error {
       type empty;
       description "Reconnect to master failed";
     }
     leaf replication-init-error {
       type empty;
       description "Error during initialization";
     }
   }
   container peer-transition-state {
     leaf peer-connected {
       type empty;
       description "Peer in switchover transition";
     }
     leaf peer-in-steady-state {
       type empty;
       description "Peer completed switchover transition";
     }
   }
 }
 grouping system-memory-information-block {
   container system-memory-summary-information {
     leaf system-memory-total {
       type string;
       description "Total system memory";
     }
     leaf system-memory-total-percent {
       type string;
       description "Total system memory as percent of total";
     }
     leaf system-memory-reserved {
       type string;
       description "Reserved system memory";
     }
     leaf system-memory-reserved-percent {
       type string;
       description "Reserved system memory as percent of total";
     }
     leaf system-memory-wired {
       type string;
       description "Wired system memory";
     }
     leaf system-memory-wired-percent {
       type string;
       description "Wired system memory as percent of total";
     }
     leaf system-memory-active {
       type string;
       description "Active system memory";
     }
     leaf system-memory-active-percent {
       type string;
       description "Active system memory as percent of total";
     }
     leaf system-memory-inactive {
       type string;
       description "Inctive system memory";
     }
     leaf system-memory-inactive-percent {
       type string;
       description "Inctive system memory as percent of total";
     }
     leaf system-memory-cache {
       type string;
       description "Cache system memory";
     }
     leaf system-memory-cache-percent {
       type string;
       description "Cache system memory as percent of total";
     }
     leaf system-memory-free {
       type string;
       description "Free system memory";
     }
     leaf system-memory-free-percent {
       type string;
       description "Free system memory as percent of total";
     }
   }
   container memory-disk-resident-information {
     leaf resident-memory {
       type string;
     }
   }
   container pmap-brief-information {
     description "Memory usage brief summary of an entry (Process/map)";
     container pmap-brief-summary {
       description "Memory usage brief summary of an entry (Process/map)";
       container pmap-process-brief-summary {
         description "Memory usage brief summary of an entry (Process/map)";
         leaf pid {
           type int32;
           description "PID of the process that generated the event";
         }
         leaf size {
           type int32;
           description "File size in bytes";
         }
         leaf resident {
           type uint32;
           description "Physical memory resident for mapping";
         }
         leaf shared {
           type uint32;
           description "Shared memory of mapping";
         }
         leaf private {
           type uint32;
           description "Private memory of mapping";
         }
         leaf process-name {
           type string;
           description "Process name";
         }
       }
       container pmap-map-brief-summary {
         description "Memory usage brief summary of an entry (Process/map)";
         leaf size {
           type int32;
           description "File size in bytes";
         }
         leaf resident {
           type uint32;
           description "Physical memory resident for mapping";
         }
         leaf shared {
           type uint32;
           description "Shared memory of mapping";
         }
         leaf private {
           type uint32;
           description "Private memory of mapping";
         }
         leaf map-name {
           type string;
           description "Map name";
         }
       }
     }
   }
   container pmap-terse-information {
     description "Memory usage terse summary of an entry (Process/map)";
     container pmap-terse-summary {
       description "Memory usage terse summary of an entry (Process/map)";
       container pmap-process-terse-summary {
         description "Memory usage terse summary of an entry (Process/map)";
         leaf pid {
           type int32;
           description "PID of the process that generated the event";
         }
         leaf size {
           type int32;
           description "File size in bytes";
         }
         leaf size-percent {
           type string;
           description "Virtual size of mapping as percent of total based on limit";
         }
         leaf resident {
           type uint32;
           description "Physical memory resident for mapping";
         }
         leaf resident-percent {
           type string;
           description "Physical memory resident for mapping as percent of total";
         }
         leaf process-name {
           type string;
           description "Process name";
         }
       }
       container pmap-map-terse-summary {
         description "Memory usage terse summary of an entry (Process/map)";
         leaf size {
           type int32;
           description "File size in bytes";
         }
         leaf size-percent {
           type string;
           description "Virtual size of mapping as percent of total based on limit";
         }
         leaf resident {
           type uint32;
           description "Physical memory resident for mapping";
         }
         leaf resident-percent {
           type string;
           description "Physical memory resident for mapping as percent of total";
         }
         leaf map-name {
           type string;
           description "Map name";
         }
       }
     }
   }
 }
 grouping system-virtual-memory-information-block {
   list vmstat-memstat-malloc {
     description "Kernel malloc information";
     leaf memstat-name {
       type string;
     }
     leaf inuse {
       type int32;
     }
     leaf memuse {
       type int32;
     }
     leaf high-use {
       type string;
     }
     leaf memstat-req {
       type int32;
     }
     leaf memstat-size {
       type string;
     }
   }
   container vmstat-memstat-zone {
     leaf zone-name {
       type string;
     }
     leaf zone-size {
       type uint32;
     }
     leaf count-limit {
       type uint32;
     }
     leaf used {
       type uint32;
     }
     leaf free {
       type uint32;
     }
     leaf zone-req {
       type uint32;
     }
   }
   container vmstat-intr {
     leaf intr-name {
       type string;
     }
     leaf intr-cnt {
       type string;
     }
     leaf intr-rate {
       type string;
     }
   }
   container vmstat-sumstat {
     leaf cpu-context-switch {
       type uint32;
     }
     leaf dev-intr {
       type uint32;
     }
     leaf soft-intr {
       type uint32;
     }
     leaf traps {
       type uint32;
     }
     leaf sys-calls {
       type uint32;
     }
     leaf kernel-thrds {
       type uint32;
     }
     leaf fork-calls {
       type uint32;
     }
     leaf vfork-calls {
       type uint32;
     }
     leaf rfork-calls {
       type uint32;
     }
     leaf swap-pageins {
       type uint32;
     }
     leaf swap-pagedin {
       type uint32;
     }
     leaf swap-pageouts {
       type uint32;
     }
     leaf swap-pagedout {
       type uint32;
     }
     leaf vnode-pageins {
       type uint32;
     }
     leaf vnode-pagedin {
       type uint32;
     }
     leaf vnode-pageouts {
       type uint32;
     }
     leaf vnode-pagedout {
       type uint32;
     }
     leaf page-daemon-wakeup {
       type uint32;
     }
     leaf page-daemon-examined-pages {
       type uint32;
     }
     leaf pages-reactivated {
       type uint32;
     }
     leaf copy-on-write-faults {
       type uint32;
     }
     leaf copy-on-write-optimized-faults {
       type uint32;
     }
     leaf zero-fill-pages-zeroed {
       type uint32;
     }
     leaf zero-fill-pages-prezeroed {
       type uint32;
     }
     leaf transit-blocking-page-faults {
       type uint32;
     }
     leaf total-vm-faults {
       type uint32;
     }
     leaf page-faults-requiring-io {
       type uint32;
     }
     leaf pages-affected-by-kernel-thrd-creat {
       type uint32;
     }
     leaf pages-affected-by-fork {
       type uint32;
     }
     leaf pages-affected-by-vfork {
       type uint32;
     }
     leaf pages-affected-by-rfork {
       type uint32;
     }
     leaf pages-freed {
       type uint32;
     }
     leaf pages-freed-by-deamon {
       type uint32;
     }
     leaf pages-freed-by-exiting-proc {
       type uint32;
     }
     leaf pages-active {
       type uint32;
     }
     leaf pages-inactive {
       type uint32;
     }
     leaf pages-in-vm-cache {
       type uint32;
     }
     leaf pages-wired-down {
       type uint32;
     }
     leaf pages-free {
       type uint32;
     }
     leaf bytes-per-page {
       type uint32;
     }
     leaf swap-pages-used {
       type uint32;
     }
     leaf peak-swap-pages-used {
       type uint32;
     }
     leaf total-name-lookups {
       type int32;
     }
     leaf positive-cache-hits {
       type int32;
     }
     leaf negative-cache-hits {
       type int32;
     }
     leaf pass2 {
       type int32;
     }
     leaf cache-deletions {
       type int32;
     }
     leaf cache-falsehits {
       type int32;
     }
     leaf toolong {
       type int32;
     }
   }
   container vm-kernel-state {
     leaf vm-kmem-map-free {
       type string;
     }
   }
   container kernel-direct-mm-size-information {
     leaf vm-directmm-size-used {
       type string;
       description "Direct memory map used size in pages";
     }
     leaf vm-directmm-size-max {
       type string;
       description "Direct memory map max size in pages";
     }
   }
   container vmstat-fork-stat {
     leaf fork-stat {
       type uint32;
     }
     leaf fork-pages {
       type uint32;
     }
     leaf fork-average-pages-per-fork {
       type uint32;
     }
     leaf vfork-stat {
       type uint32;
     }
     leaf vfork-pages {
       type uint32;
     }
     leaf vfork-average-pages-per-vfork {
       type uint32;
     }
     leaf rfork-stat {
       type uint32;
     }
     leaf rfork-pages {
       type uint32;
     }
     leaf rfork-average-pages-per-rfork {
       type uint32;
     }
   }
   container vmstat-times {
     leaf vmstat-times-reclaims {
       type uint32;
     }
     leaf vmstat-times-reclaims-total-time {
       type uint32;
     }
     leaf vmstat-times-average-time-to-reclaim {
       type uint32;
     }
     leaf vmstat-times-pageins {
       type uint32;
     }
     leaf vmstat-times-pageins-total-time {
       type uint32;
     }
     leaf vmstat-times-average-time-to-pageins {
       type string;
     }
   }
 }
 grouping system-users-information-block {
   container uptime-information {
     description "System uptime details";
     leaf date-time {
       type string;
     }
     leaf up-time {
       type string;
       description "Uptime in ascii format";
     }
     leaf active-user-count {
       type int32;
       description "Number of users currently logged in";
     }
     leaf load-average-1 {
       type string;
       description "Load average for last 1 minute";
     }
     leaf load-average-5 {
       type string;
       description "Load average for last 5 minutes";
     }
     leaf load-average-15 {
       type string;
       description "Load average for last 15 minutes";
     }
     container user-table {
       list user-entry {
         leaf user {
           type string;
           description "User name executing this script";
         }
         leaf tty {
           type string;
           description "Name of the terminal the user is on";
         }
         leaf from {
           type string;
           description "Host from which the user is logged on";
         }
         leaf login-time {
           type string;
           description "Time the user logged on";
         }
         leaf idle-time {
           type string;
           description "Time since the user last typed anything";
         }
         leaf command {
           type string;
         }
       }
       container process-table {
         list process-entry {
         }
       }
     }
   }
   container web-management-users {
     list web-management-user {
       leaf user {
         type string;
         description "User name executing this script";
       }
       leaf tty {
         type string;
         description "Name of the terminal the user is on";
       }
       leaf from {
         type string;
         description "Host from which the user is logged on";
       }
       leaf login-time {
         type string;
         description "Time the user logged on";
       }
       leaf idle-time {
         type string;
         description "Time since the user last typed anything";
       }
     }
   }
 }
 grouping syslog-events-block {
   container data {
     description "Syslog events in structured-data format";
     container netconf-state {
       container schemas {
         list schema {
         }
       }
     }
   }
 }
 grouping system-resource-cleanup-processes-information-block {
   container summary {
     description "Resource clean up information for one or more processes";
     list process-resource-cleanup {
       description "Resource clean up information for a process";
       leaf pid {
         type uint32;
         description "Process identifier";
       }
       leaf process-name {
         type string;
         description "Process name";
       }
       container cleanup-resources {
         description "Resources that can be cleaned up";
         list resource {
           description "Resource information";
         }
       }
     }
   }
   container detail {
     description "Resource clean up information for one or more processes";
     list process-resource-cleanup {
       description "Resource clean up information for a process";
       leaf pid {
         type uint32;
         description "Process identifier";
       }
       leaf process-name {
         type string;
         description "Process name";
       }
       container cleanup-resources {
         description "Resources that can be cleaned up";
         list resource {
           description "Resource information";
         }
       }
     }
   }
 }
 grouping subscriber-management-summary-information-block {
   leaf subscriber-management-gres {
     type string;
     description "Subscriber management GRES status";
   }
   leaf subscriber-management-mastership {
     type string;
     description "Subscriber management mastership status";
   }
   leaf subscriber-management-db {
     type string;
     description "Subscriber management database status";
   }
   leaf subscriber-management-standby {
     type string;
     description "Enhanced session management standby status";
   }
   leaf subscriber-management-chassisd-issu-state {
     type string;
     description "Subscriber management chassisd ISSU state";
   }
   leaf subscriber-management-issu-state {
     type string;
     description "Subscriber management ISSU state";
   }
   leaf subscriber-management-issu-wait {
     type int32;
     description "Subscriber management ISSU wait time";
   }
   leaf no-information {
     type string;
   }
 }
 grouping subscriber-management-route-information-block {
   container summary {
     description "Information about the IPv4/IPv6 subscriber-management routes";
     list subscriber-management-route {
       description "Information about the IPv4/IPv6 subscriber-management route";
       leaf routing-instance {
         type string;
         description "Routing instance associated with the route";
       }
       leaf krt-table-kernel-id {
         type int32;
         description "Kernel identifier for table";
       }
       leaf address-family {
         type string;
         description "Route address family";
       }
       leaf local-route-count {
         type int32;
         description "Number of local routes in this routing instance";
       }
       leaf access-route-count {
         type int32;
         description "Number of access routes in this routing instance";
       }
       leaf access-int-route-count {
         type int32;
         description "Number of access-internal routes in this routing instance";
       }
       leaf kernel-route-count {
         type int32;
         description "Number of kernel routes in this routing instance";
       }
       leaf dirty-local-route-count {
         type int32;
         description "Number of incomplete local routes in this routing instance";
       }
       leaf dirty-access-route-count {
         type int32;
         description "Number of incomplete access routes in this routing instance";
       }
       leaf dirty-access-int-route-count {
         type int32;
         description "Number of incomplete access-internal routes in this routing instance";
       }
       leaf dirty-kernel-route-count {
         type int32;
         description "Number of incomplete kernel routes in this routing instance";
       }
       leaf dirty-inflight-route-count {
         type int32;
         description "Number of incomplete inflight routes in this routing instance";
       }
     }
     container subscriber-management-route-nh {
       container brief {
         leaf route-nh-index {
           type int32;
           description "Index of next-hop associated with the route";
         }
         leaf pseudo-ifl-index {
           type int32;
           description "Pseudo IFL index";
         }
         leaf nh-bbe-index {
           type int32;
           description "Next-hop BBE index";
         }
         leaf nh-ref-count {
           type int32;
           description "Next-hop reference count";
         }
         leaf nh-flags {
           type string;
           description "Next-hop flags";
         }
         leaf address-family {
           type string;
           description "Route address family";
         }
       }
     }
     list subscriber-management-route-summary {
       description "Summarized information about the IPv4/IPv6 subscriber-management routes";
       leaf routing-instance {
         type string;
         description "Routing instance associated with the route";
       }
       leaf krt-table-kernel-id {
         type int32;
         description "Kernel identifier for table";
       }
       leaf address-family {
         type string;
         description "Route address family";
       }
       leaf local-route-count {
         type int32;
         description "Number of local routes in this routing instance";
       }
       leaf access-route-count {
         type int32;
         description "Number of access routes in this routing instance";
       }
       leaf access-int-route-count {
         type int32;
         description "Number of access-internal routes in this routing instance";
       }
       leaf kernel-route-count {
         type int32;
         description "Number of kernel routes in this routing instance";
       }
       leaf dirty-local-route-count {
         type int32;
         description "Number of incomplete local routes in this routing instance";
       }
       leaf dirty-access-route-count {
         type int32;
         description "Number of incomplete access routes in this routing instance";
       }
       leaf dirty-access-int-route-count {
         type int32;
         description "Number of incomplete access-internal routes in this routing instance";
       }
       leaf dirty-kernel-route-count {
         type int32;
         description "Number of incomplete kernel routes in this routing instance";
       }
       leaf dirty-inflight-route-count {
         type int32;
         description "Number of incomplete inflight routes in this routing instance";
       }
     }
   }
   container brief {
     description "Information about the IPv4/IPv6 subscriber-management routes";
     list subscriber-management-route {
       description "Information about the IPv4/IPv6 subscriber-management route";
       leaf route-prefix {
         type ipaddr;
         description "IPv4 or IPv6 prefix for the route";
       }
       leaf route-type {
         type string;
         description "Route type associated with the route";
       }
       leaf interface-name {
         type string;
         description "Name of the interface associated with the route";
       }
       leaf route-nh-index {
         type int32;
         description "Index of next-hop associated with the route";
       }
     }
     container subscriber-management-route-nh {
       container brief {
         leaf route-nh-index {
           type int32;
           description "Index of next-hop associated with the route";
         }
         leaf pseudo-ifl-index {
           type int32;
           description "Pseudo IFL index";
         }
         leaf nh-bbe-index {
           type int32;
           description "Next-hop BBE index";
         }
         leaf nh-ref-count {
           type int32;
           description "Next-hop reference count";
         }
         leaf nh-flags {
           type string;
           description "Next-hop flags";
         }
         leaf address-family {
           type string;
           description "Route address family";
         }
       }
     }
     list subscriber-management-route-summary {
       description "Summarized information about the IPv4/IPv6 subscriber-management routes";
     }
   }
   container detail {
     description "Information about the IPv4/IPv6 subscriber-management routes";
     list subscriber-management-route {
       description "Information about the IPv4/IPv6 subscriber-management route";
       leaf route-prefix {
         type ipaddr;
         description "IPv4 or IPv6 prefix for the route";
       }
       leaf routing-instance {
         type string;
         description "Routing instance associated with the route";
       }
       leaf krt-table-kernel-id {
         type int32;
         description "Kernel identifier for table";
       }
       leaf address-family {
         type string;
         description "Route address family";
       }
       leaf route-type {
         type string;
         description "Route type associated with the route";
       }
       leaf route-proto-type {
         type string;
         description "Protocol associated with the route";
       }
       leaf interface-name {
         type string;
         description "Name of the interface associated with the route";
       }
       leaf route-intf-index {
         type uint32;
         description "Index of interface associated with the route";
       }
       leaf route-int-intf-index {
         type uint32;
         description "Index of internal interface associated with the route";
       }
       leaf route-index {
         type int32;
         description "Route index associated with the route";
       }
       leaf route-nh-index {
         type int32;
         description "Index of next-hop associated with the route";
       }
       leaf route-tag {
         type int32;
         description "Route tag";
       }
       leaf route-metric {
         type int32;
         description "Route metric";
       }
       leaf route-preference {
         type int32;
         description "Route preference";
       }
       leaf route-ref-count {
         type int32;
         description "Route reference count";
       }
       leaf mac-addr {
         type mac-addr;
         description "Media access control (hardware) address associated with the route";
       }
       leaf route-flags {
         type string;
         description "Route flags";
       }
     }
     container subscriber-management-route-nh {
       container brief {
         leaf route-nh-index {
           type int32;
           description "Index of next-hop associated with the route";
         }
         leaf pseudo-ifl-index {
           type int32;
           description "Pseudo IFL index";
         }
         leaf nh-bbe-index {
           type int32;
           description "Next-hop BBE index";
         }
         leaf nh-ref-count {
           type int32;
           description "Next-hop reference count";
         }
         leaf nh-flags {
           type string;
           description "Next-hop flags";
         }
         leaf address-family {
           type string;
           description "Route address family";
         }
       }
     }
     list subscriber-management-route-summary {
       description "Summarized information about the IPv4/IPv6 subscriber-management routes";
     }
   }
 }
 grouping autoinstallation-status-information-block {
   leaf master-state {
     type string;
     description "State of master state machine";
   }
   leaf last-configuration-filename {
     type string;
     description "Name of last configuration file committed";
   }
   leaf last-configuration-server {
     type string;
     description "IP address of last configuration server";
   }
   list autoinstallation-status-interface-information {
     description "Autoinstallation status for a particular interface";
     leaf interface-name {
       type string;
       description "Interface name";
     }
     leaf interface-state {
       type string;
       description "State of interface state machine";
     }
     leaf interface-acquired-address {
       type string;
       description "IP address acquired on this interface";
     }
     leaf interface-acquired-hostname {
       type string;
       description "Hostname acquired on this interface";
     }
     leaf interface-acquired-hostname-source {
       type string;
       description "Source of hostname acquired on this interface";
     }
     leaf interface-acquired-configuration-filename {
       type string;
       description "Name of configuration file acquired on this interface";
     }
     leaf interface-acquired-configuration-server {
       type string;
       description "IP address of configuration server acquired on this interface";
     }
     list autoinstallation-status-interface-address-information {
       description "Autoinstallation status for address acquisition protocols on a particular interface";
       leaf protocol-name {
         type string;
         description "Address acquisition protocol on this interface";
       }
       leaf protocol-address {
         type string;
         description "Address acquired on this interface using this address acquisition protocol";
       }
     }
   }
 }
 grouping system-firmware-information-block {
   container system-firmware {
     leaf firmware-name {
       type string;
       description "Name of this component";
     }
     leaf firmware-type {
       type string;
       description "Type of this component";
     }
     leaf firmware-tag {
       type int32;
       description "Multiple firmware per FRU delimiter";
     }
     leaf firmware-revision {
       type string;
       description "Firmware version for this component";
     }
     leaf firmware-revision-available {
       type string;
       description "Firmware version available on disk for this component";
     }
     leaf firmware-status {
       type string;
       description "Firmware status for this component";
     }
     container tvp {
       container system-module {
         container firmware-state {
           description "Firmware status per component type";
         }
       }
       container system-sub-module-firmware-list {
         list system-sub-module-firmware {
           description "Firmware sub module";
           leaf firmware-name {
             type string;
             description "Name of this component";
           }
           leaf firmware-type {
             type string;
             description "Type of this component";
           }
           leaf firmware-tag {
             type int32;
             description "Multiple firmware per FRU delimiter";
           }
           leaf firmware-revision {
             type string;
             description "Firmware version for this component";
           }
           leaf firmware-revision-available {
             type string;
             description "Firmware version available on disk for this component";
           }
           leaf firmware-status {
             type string;
             description "Firmware status for this component";
           }
         }
       }
     }
   }
 }
 grouping system-crypto-information-block {
   leaf crypto {
     type string;
   }
 }
 }
