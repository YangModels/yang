/*
 * Copyright (c) 2017 Juniper Networks, Inc.
 * All rights reserved.
 */
 module show-oam {
  namespace "http://yang.juniper.net/yang/1.1/jrpc/show-oam/junos-qfx/17.2R1.13";
  prefix show-oam;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-lfmd-information {
     description "Show link-fault-management information";
     input {
       leaf level {
         default "brief";
         type enumeration {
           enum "detail" {
             description "Display detailed data";
           }
           enum "brief" {
             description "Display brief data (default)";
           }
         }
       }
       leaf interface-name {
         description "Name of physical interface";
         type interface-device;
       }
     }
     output {
       container lfmd-information {
         uses lfmd-information-block;
       }
     }
   }
   rpc get-cfm-interfaces-information {
     description "Show Ethernet OAM information for interface";
     input {
       leaf interface-name {
         description "Name of interface";
         type string;
       }
       leaf vlan {
         description "Trunk interface VLAN";
         type int32 {
           range "1 .. 4094";
         }
       }
       leaf level {
         description "Level value for maintenance domain";
         type int32 {
           range "0 .. 7";
         }
       }
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity {
         default "brief";
         type enumeration {
           enum "brief" {
             description "Display brief output";
           }
           enum "detail" {
             description "Display detail output";
           }
           enum "extensive" {
             description "Display extensive output";
           }
           enum "summary" {
             description "Display summary output";
           }
         }
       }
     }
     output {
       container cfm-interface {
         uses cfm-interface-block;
       }
     }
   }
   rpc get-cfm-mep-database {
     description "Show Ethernet OAM maintenance endpoint database information";
     input {
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type uint32 {
           range "1 .. 8191";
         }
       }
       leaf remote-mep {
         description "Identifier for remote maintenance endpoint";
         type uint32 {
           range "1 .. 8191";
         }
       }
       leaf logical-system {
         description "Name of logical system";
         type string {
           junos:posix-pattern "^[a-zA-Z0-9_-]{1,63}$";
           junos:pattern-message "Logical-system name is a string consisting of up to 63 letters, numbers, dashes and underscores";
         }
       }
     }
     output {
       container cfm-mep-database {
         uses cfm-mep-database-block;
       }
     }
   }
   rpc get-cfm-forwarding-state-instance-information {
     description "Show Ethernet OAM state for a forwarding instance";
     input {
       leaf instance-name {
         description "Show information for a particular routing instance";
         default "all";
         type string;
       }
       leaf bridge-domain {
         description "Show information for a particular bridge domain";
         default "all";
         type string;
       }
       leaf logical-system {
         description "Name of logical system";
         type string {
           junos:posix-pattern "^[a-zA-Z0-9_-]{1,63}$";
           junos:pattern-message "Logical-system name is a string consisting of up to 63 letters, numbers, dashes and underscores";
         }
       }
       leaf verbosity {
         default "brief";
         type enumeration {
           enum "brief" {
             description "Display brief output";
           }
           enum "detail" {
             description "Display detail output";
           }
           enum "extensive" {
             description "Display extensive output";
           }
           enum "summary" {
             description "Display summary output";
           }
         }
       }
     }
     output {
       container cfm-flood-instance-information {
         uses cfm-flood-instance-information-block;
       }
     }
   }
   rpc get-cfm-forwarding-state-interface-information {
     description "Show Ethernet OAM state for an interface";
     input {
       leaf interface-name {
         description "Display information for this logical interface";
         default "all";
         type interface-unit;
       }
       leaf logical-system {
         description "Name of logical system";
         type string {
           junos:posix-pattern "^[a-zA-Z0-9_-]{1,63}$";
           junos:pattern-message "Logical-system name is a string consisting of up to 63 letters, numbers, dashes and underscores";
         }
       }
       leaf verbosity {
         default "brief";
         type enumeration {
           enum "brief" {
             description "Display brief output";
           }
           enum "detail" {
             description "Display detail output";
           }
           enum "extensive" {
             description "Display extensive output";
           }
           enum "summary" {
             description "Display summary output";
           }
         }
       }
     }
     output {
       container cfm-flood-interface-information {
         uses cfm-flood-interface-information-block;
       }
     }
   }
   rpc get-cfm-linktrace-path-database {
     description "Display the linktrace path-database for a remote host";
     input {
       leaf logical-system {
         description "Name of logical system";
         type string {
           junos:posix-pattern "^[a-zA-Z0-9_-]{1,63}$";
           junos:pattern-message "Logical-system name is a string consisting of up to 63 letters, numbers, dashes and underscores";
         }
       }
       leaf maintenance-domain {
         description "Name of maintenance domain";
         type string {
           length "1 .. 45";
         }
         mandatory true;
       }
       leaf maintenance-association {
         description "Name of maintenance association";
         type string {
           length "1 .. 45";
         }
         mandatory true;
       }
       leaf host {
         description "MAC address of remote host in xx:xx:xx:xx:xx:xx format";
         type mac-unicast;
         mandatory true;
       }
     }
     output {
       container cfm-linktrace-path-database {
         uses cfm-linktrace-path-database-block;
       }
     }
   }
   rpc get-cfm-mip-information {
     description "Display MIP information";
     input {
       leaf logical-system {
         description "Name of logical system";
         type string {
           junos:posix-pattern "^[a-zA-Z0-9_-]{1,63}$";
           junos:pattern-message "Logical-system name is a string consisting of up to 63 letters, numbers, dashes and underscores";
         }
       }
       leaf instance-name {
         description "Show information for a particular routing instance";
         default "all";
         type string;
       }
       leaf bridge-domain {
         description "Show information for a particular bridge domain";
         default "all";
         type string;
       }
       leaf interface-name {
         description "Display information for this logical interface";
         default "all";
         type string;
       }
       leaf vlan {
         description "Show information for a particular VLAN within a bridge domain";
         type int32 {
           range "1 .. 4094";
         }
       }
     }
     output {
       container cfm-mip-information {
         uses cfm-mip-information-block;
       }
     }
   }
   rpc get-cfm-policer-information {
     description "Show Ethernet OAM policer information";
     input {
       leaf maintenance-domain {
         description "Name of maintenance domain";
         type string {
           length "1 .. 45";
         }
       }
       leaf maintenance-association {
         description "Name of maintenance association";
         type string {
           length "1 .. 45";
         }
       }
       leaf logical-system {
         description "Name of logical system";
         type string {
           junos:posix-pattern "^[a-zA-Z0-9_-]{1,63}$";
           junos:pattern-message "Logical-system name is a string consisting of up to 63 letters, numbers, dashes and underscores";
         }
       }
     }
     output {
       container cfm-policer {
         uses cfm-policer-block;
       }
     }
   }
   rpc get-cfm-cfmman-conn-statistics {
     description "Show Ethernet OAM cfmman connection statistics information";
     input {
       leaf fpc-slot {
         description "Fpc slot number";
         type uint32 {
           range "0 .. 80";
         }
       }
       leaf extensive {
         description "Display stats based on RPC types";
         type empty;
       }
       leaf summary {
         description "Display global statistics";
         type empty;
       }
     }
   }
   rpc get-cfm-iterator-history {
     description "Show Ethernet OAM SLA iterator 5 munutes history information";
     input {
       leaf sla-iterator {
         description "Name of the iterator profile";
         type string;
       }
       leaf maintenance-domain {
         description "Name of maintenance domain";
         type string {
           length "1 .. 45";
         }
       }
       leaf maintenance-association {
         description "Name of maintenance association";
         type string {
           length "1 .. 45";
         }
       }
       leaf local-mep {
         description "Identifier for local maintenance endpoint";
         type uint32 {
           range "1 .. 8191";
         }
       }
       leaf remote-mep {
         description "MEP identifier of remote host";
         type int32 {
           range "1 .. 8191";
         }
       }
       leaf history-statistics-type {
         type enumeration {
           enum "delay-measurement" {
             description "Show history Delay measurements";
           }
           enum "bin" {
             description "History Delay measurement bin";
           }
           enum "loss-measurement" {
             description "History Frame Loss measurements";
           }
           enum "availability" {
             description "History Availability for SLM/LM measurements";
           }
         }
       }
       leaf record-number {
         description "History record number";
         type int32 {
           range "1 .. 32";
         }
       }
       leaf logical-system {
         description "Name of logical system";
         type string {
           junos:posix-pattern "^[a-zA-Z0-9_-]{1,63}$";
           junos:pattern-message "Logical-system name is a string consisting of up to 63 letters, numbers, dashes and underscores";
         }
       }
     }
     output {
       container cfm-iterator-history {
         uses cfm-iterator-history-block;
       }
     }
   }
   rpc get-evc-infromation {
     description "Show ethernet virtual circuit information";
     input {
       leaf evc-id {
         description "EVC identifier";
         type string;
       }
     }
     output {
       container elmi-evc-information {
         uses elmi-evc-information-block;
       }
     }
   }
   rpc get-elmi-information {
     description "Show ethernet local management information";
     input {
       leaf interface {
         description "Name of interface";
         type interface-device;
       }
     }
     output {
       container elmi-interface-information {
         uses elmi-interface-information-block;
       }
     }
   }
   rpc get-elmi-statistics {
     description "Show ethernet local management statistics";
     input {
       leaf interface {
         description "Name of interface";
         type interface-device;
       }
     }
     output {
       container elmi-interface-statistics {
         uses elmi-interface-statistics-block;
       }
     }
   }
   rpc get-fnp-interface-information {
     description "Show FNP interface information";
     input {
       leaf interface {
         description "Name of interface";
         type interface-unit;
       }
       leaf routing-instance {
         description "Name of routing instance";
         type string;
       }
       leaf vlan {
         description "VLAN ID";
         type int32 {
           range "1 .. 4094";
         }
       }
       leaf all {
         description "Show all interfaces";
         type empty;
       }
     }
     output {
       container fnp-interface-information {
         uses fnp-interface-information-block;
       }
     }
   }
   rpc get-fnp-status {
     description "Show FNP status";
     input {
       leaf interface {
         description "Name of interface";
         type interface-device;
       }
       leaf routing-instance {
         description "Name of routing instance";
         type string;
       }
     }
     output {
       container fnp-status-information {
         uses fnp-status-information-block;
       }
     }
   }
   rpc get-fnp-messages {
     description "Show active FNP messages";
     input {
       leaf interface {
         description "Name of interface";
         type interface-unit;
       }
       leaf routing-instance {
         description "Name of routing instance";
         type string;
       }
     }
     output {
       container fnp-messages-information {
         uses fnp-messages-information-block;
       }
     }
   }
   rpc get-gre-ka-information {
     description "Show GRE Keepalive information";
     input {
       leaf interface-name {
         description "Display information for this logical interface";
         default "all";
         type string;
       }
     }
   }
 grouping lfmd-information-block {
   container brief {
     description "Information about the Link-Fault Management protocol";
     list lfmd-interface-information {
       description "Link-fault management information for one or more interfaces";
       leaf lfmd-interface-name {
         type string;
         description "Name of interface";
       }
       leaf lfmd-status {
         type string;
         description "Status of 802.3ah on the interface";
       }
       leaf lfmd-discovery-state {
         type string;
       }
       leaf lfmd-local-in-issu {
         type empty;
         description "In ISSU";
       }
       leaf lfmd-pdu-transmit-interval {
         type uint32;
         description "LFM keepalive PDU periodic transmit interval";
       }
       leaf lfmd-pdu-threshold {
         type uint32;
         description "Number of OAMPDUs missed before declaring peer lost";
       }
       leaf lfmd-pdu-hold-time {
         type uint32;
         description "Time for which no OAMPDU is received before declaring peer lost";
       }
       leaf lfmd-peer-address {
         type mac-addr;
       }
       leaf lfmd-loopback-local-enabled {
         type empty;
       }
       leaf lfmd-loopback-remote-enabled {
         type empty;
       }
       leaf lfmd-loopback-tracking-status {
         type string;
         description "Loopback tracking enabled or not";
       }
       leaf lfmd-loopback-tracking-loop-status {
         type string;
       }
       leaf lfmd-detect-loc-status {
         type string;
         description "Detect loc enabled or not";
       }
       leaf lfmd-detect-loc-loc-status {
         type string;
       }
       leaf lfmd-peer-mux-action {
         type string;
         description "Remote multiplexor action";
       }
       leaf lfmd-peer-parser-action {
         type string;
         description "Remote parser action";
       }
       leaf lfmd-peer-config-mode {
         type string;
         description "Remote peer discovery configuration";
       }
       leaf lfmd-peer-config-unidirectional {
         type string;
         description "Support for remote peer unidirectional mode";
       }
       leaf lfmd-peer-config-loopback {
         type string;
         description "Support for remote peer loopback mode";
       }
       leaf lfmd-peer-config-link-events {
         type string;
         description "Support for remote peer link events";
       }
       leaf lfmd-peer-config-variable-request {
         type string;
         description "Support for remote peer variable requests";
       }
       leaf lfmd-peer-in-issu {
         type empty;
         description "Peer is in ISSU";
       }
       container lfmd-discovery-flags {
       }
       container lfmd-statistics {
         description "Interface statistics";
       }
       container lfmd-events {
         description "Event information";
         container lfmd-events-received {
           description "Received link events";
         }
         container lfmd-events-transmitted {
           description "Transmitted link events";
         }
         container lfmd-events-current {
           description "Current link events";
         }
       }
     }
     list lfmd-action-profile-information {
       description "Link-fault action profile information";
       leaf lfmd-action-profile-name {
         type string;
         description "Name of action profile";
       }
       leaf lfmd-action-profile-invoke-count {
         type uint32;
         description "Number of times the action profile has been invoked";
       }
       leaf lfmd-action-profile-execution-count {
         type uint32;
         description "Number of times the action profile has been executed";
       }
     }
   }
   container detail {
     description "Information about the Link-Fault Management protocol";
     list lfmd-interface-information {
       description "Link-fault management information for one or more interfaces";
       leaf lfmd-interface-name {
         type string;
         description "Name of interface";
       }
       leaf lfmd-status {
         type string;
         description "Status of 802.3ah on the interface";
       }
       leaf lfmd-discovery-state {
         type string;
       }
       leaf lfmd-local-in-issu {
         type empty;
         description "In ISSU";
       }
       leaf lfmd-pdu-transmit-interval {
         type uint32;
         description "LFM keepalive PDU periodic transmit interval";
       }
       leaf lfmd-pdu-threshold {
         type uint32;
         description "Number of OAMPDUs missed before declaring peer lost";
       }
       leaf lfmd-pdu-hold-time {
         type uint32;
         description "Time for which no OAMPDU is received before declaring peer lost";
       }
       leaf lfmd-peer-address {
         type mac-addr;
       }
       leaf lfmd-loopback-local-enabled {
         type empty;
       }
       leaf lfmd-loopback-remote-enabled {
         type empty;
       }
       leaf lfmd-loopback-tracking-status {
         type string;
         description "Loopback tracking enabled or not";
       }
       leaf lfmd-loopback-tracking-loop-status {
         type string;
       }
       leaf lfmd-detect-loc-status {
         type string;
         description "Detect loc enabled or not";
       }
       leaf lfmd-detect-loc-loc-status {
         type string;
       }
       leaf lfmd-peer-mux-action {
         type string;
         description "Remote multiplexor action";
       }
       leaf lfmd-peer-parser-action {
         type string;
         description "Remote parser action";
       }
       leaf lfmd-peer-config-mode {
         type string;
         description "Remote peer discovery configuration";
       }
       leaf lfmd-peer-config-unidirectional {
         type string;
         description "Support for remote peer unidirectional mode";
       }
       leaf lfmd-peer-config-loopback {
         type string;
         description "Support for remote peer loopback mode";
       }
       leaf lfmd-peer-config-link-events {
         type string;
         description "Support for remote peer link events";
       }
       leaf lfmd-peer-config-variable-request {
         type string;
         description "Support for remote peer variable requests";
       }
       leaf lfmd-peer-in-issu {
         type empty;
         description "Peer is in ISSU";
       }
       container lfmd-discovery-flags {
       }
       container lfmd-statistics {
         description "Interface statistics";
         container lfmd-statistics-received {
           description "OAM receive statistics";
         }
         container lfmd-statistics-transmitted {
           description "OAM transmit statistics";
         }
       }
       container lfmd-events {
         description "Event information";
         container lfmd-events-received {
           description "Received link events";
           container lfmd-event-received-symbol-error {
             description "Errored symbol period event information";
           }
           container lfmd-event-received-frame-error {
             description "Errored frame event information";
           }
           container lfmd-event-received-frame-period-error {
             description "Errored frame period event information";
           }
           container lfmd-event-received-frame-seconds-error {
             description "Errored frame seconds event information";
           }
         }
         container lfmd-events-transmitted {
           description "Transmitted link events";
           container lfmd-event-transmitted-symbol-error {
             description "Errored symbol period event information";
           }
           container lfmd-event-transmitted-frame-error {
             description "Errored frame event information";
           }
         }
         container lfmd-events-current {
           description "Current link events";
           container lfmd-event-current-symbol-error {
             description "Errored symbol period event current information";
           }
           container lfmd-event-current-frame-error {
             description "Errored frame event current information";
           }
         }
       }
     }
     list lfmd-action-profile-information {
       description "Link-fault action profile information";
       leaf lfmd-action-profile-name {
         type string;
         description "Name of action profile";
       }
       leaf lfmd-action-profile-invoke-count {
         type uint32;
         description "Number of times the action profile has been invoked";
       }
       leaf lfmd-action-profile-execution-count {
         type uint32;
         description "Number of times the action profile has been executed";
       }
     }
   }
 }
 grouping cfm-interface-block {
   list cfm-interface-snapshot {
     list brief {
       leaf cfm-interface-name {
         type string;
         description "Name of interface";
       }
       leaf cfm-interface-link-status {
         type string;
         description "Operational status of this interface";
       }
       leaf cfm-interface-status {
         type string;
         description "Status of 802.1ag on the interface";
       }
       list cfm-interface-session-snapshot {
         leaf cfm-level {
           type uint32;
           description "Maintenance-domain level";
         }
         leaf cfm-mep-identifier {
           type uint32;
           description "Identifier of MEP";
         }
         leaf cfm-remote-mep-count {
           type uint32;
           description "Number of remote MEP configured or learnt";
         }
       }
     }
   }
   list cfm-interface-summary {
     list summary {
       leaf cfm-interface-name {
         type string;
         description "Name of interface";
       }
       list cfm-interface-session-summary {
         leaf cfm-interface-link-status {
           type string;
           description "Operational status of this interface";
         }
         leaf cfm-interface-status {
           type string;
           description "Status of 802.1ag on the interface";
         }
         leaf cfm-level {
           type uint32;
           description "Maintenance-domain level";
         }
         leaf cfm-mep-identifier {
           type uint32;
           description "Identifier of MEP";
         }
         leaf cfm-remote-mep-identifier {
           type uint32;
           description "Identifier of remote MEP";
         }
         leaf cfm-remote-mep-state {
           type string;
           description "State of the remote MEP";
         }
       }
     }
   }
   list cfm-entry {
     container cfm-interface-entry {
       leaf cfm-interface-name {
         type string;
         description "Name of interface";
       }
       leaf cfm-interface-status {
         type string;
         description "Status of 802.1ag on the interface";
       }
       leaf cfm-interface-link-status {
         type string;
         description "Operational status of this interface";
       }
     }
     container cfm-interface-sessions {
       list cfm-interface-session {
         container cfm-interface-session-identifier {
           leaf cfm-maintenance-domain-name {
             type string;
             description "Name of maintenance domain";
           }
           leaf cfm-maintenance-domain-name-format {
             type string;
             description "Format of maintenance domain name";
           }
           leaf cfm-level {
             type uint32;
             description "Maintenance-domain level";
           }
           leaf cfm-maintenance-domain-index {
             type uint32;
             description "Index of MD";
           }
           leaf cfm-maintenance-association-name {
             type string;
             description "Name of maintenance association";
           }
           leaf cfm-maintenance-association-name-format {
             type string;
             description "Format of maintenance association name";
           }
           leaf cfm-maintenance-association-index {
             type uint32;
             description "Index of MA";
           }
         }
         container cfm-interface-continuity-check {
           leaf cfm-continuity-check-status {
             type string;
             description "Continuity-check protocol status";
           }
           leaf cfm-continuity-check-interval {
             type uint32;
             description "Continuity-check message interval";
           }
           leaf cfm-continuity-check-loss-threshold {
             type uint32;
             description "Maximum number of continuity-check messages that the endpoint can fail to acknowledge before it is marked as inoperative";
           }
         }
         container cfm-interface-ethernet-ais {
           leaf cfm-ethernet-ais-status {
             type string;
             description "Ethernet AIS message status";
           }
           leaf cfm-ethernet-ais-interval {
             type uint32;
             description "Ethernet AIS message interval";
           }
           leaf cfm-ethernet-ais-level {
             type string;
             description "MD levels to which AIS messages are generated";
           }
           leaf cfm-ethernet-ais-priority {
             type uint32;
             description "VLAN priority used in the Ethernet AIS messages";
           }
         }
         container cfm-interface-local-mep-tlv-info {
           leaf cfm-local-mep-interface-status-tlv {
             type string;
             description "Interface status TLV information in the last transmitted CCM from local MEP";
           }
           leaf cfm-local-mep-port-status-tlv {
             type string;
             description "Port status TLV information in the last transmitted CCM from local MEP";
           }
           leaf cfm-system-chassis-mac-address {
             type string;
             description "MAC address of remote MEP";
           }
           leaf cfm-management-address {
             type string;
             description "CFM Management address";
           }
           leaf cfm-sendid-tlv {
             type string;
             description "CFM Sendid TLV Status";
           }
           container cfm-local-mep-connection-protection-tlv {
             description "Connection Protection TLV information in the last transmitted CCM from local MEP";
             leaf cfm-connection-protection-tlv-status {
               type string;
               description "To indicate the status of connection protection TLV in last transmitted CCM";
             }
             leaf cfm-connection-protection-tlv-prefer-me {
               type string;
               description "To indicate switchover to protect path";
             }
             leaf cfm-connection-protection-tlv-protection-in-use {
               type string;
               description "To indicate protection path in use";
             }
             leaf cfm-connection-protection-tlv-frr-flag {
               type string;
               description "To indicate FRR active for the working path";
             }
           }
           container cfm-local-mep-loss-threshold-tlv {
             description "Loss Threshold TLV information in the last transmitted CCM from Local MEP";
             leaf cfm-loss-threshold-tlv-value {
               type uint32;
               description "Indicate Loss Threshold value";
             }
             leaf cfm-loss-threshold-tlv-flag {
               type uint32;
               description "To indicate ISSU info";
             }
           }
         }
         container cfm-interface-local-mep-info {
           leaf cfm-local-mep-identifier {
             type uint32;
             description "Identifier of local MEP";
           }
           leaf cfm-local-mep-direction {
             type string;
             description "Direction in which continuity-check messages are sent";
           }
           leaf cfm-local-mep-mac-address {
             type string;
             description "MAC address of local MEP";
           }
           leaf cfm-local-mep-status {
             type string;
             description "Status of maintenance association endpoint";
           }
         }
         container cfm-interface-local-mep-defects {
           leaf cfm-defect-remote-mep-no-ccm {
             type string;
             description "Indicates whether remote MEPs are receiving continuity-check messages (CCMs)";
           }
           leaf cfm-defect-error-ccm {
             type string;
             description "Indicates whether erroneous continuity-check messages (CCMs) were received";
           }
           leaf cfm-defect-cross-connect-ccm {
             type string;
             description "Indicates whether cross-connect continuity-check messages (CCMs) were received";
           }
           leaf cfm-defect-rdi-in-some-mep {
             type string;
             description "Indicates whether any remote MEPs are sending continuity-check messages (CCMs) with the RDI bit set";
           }
           leaf cfm-defect-mac-status {
             type string;
             description "Indicates whether any remote MEP's associated MAC is reporting an error status via the Port Status or Interface Status TLVs";
           }
           leaf cfm-defect-ais {
             type string;
             description "Indicates whether local MEP generated or received an AIS message";
           }
         }
         container cfm-interface-local-mep-statistics {
           leaf cfm-total-ccm-sent {
             type uint32;
             description "Number of continuity-check messages sent";
           }
           leaf cfm-out-of-sequence-ccm-received {
             type uint32;
             description "Number of continuity-check messages received out of sequence";
           }
           leaf cfm-lbm-sent {
             type uint32;
             description "Number of loopback messages sent";
           }
           leaf cfm-lbr-sent {
             type uint32;
             description "Number of loopback responses sent";
           }
           leaf cfm-lbr-received {
             type uint32;
             description "Number of valid in-order loopback responses received";
           }
           leaf cfm-lbr-received-out-of-order {
             type uint32;
             description "Number of valid out-of-order loopback responses received";
           }
           leaf cfm-lbr-bad-msdu {
             type uint32;
             description "Number of loopback responses received with corrupted data";
           }
           leaf cfm-total-ltm-sent {
             type uint32;
             description "Number of linktrace-request messages sent";
           }
           leaf cfm-total-ltm-received {
             type uint32;
             description "Number of linktrace-request messages received";
           }
           leaf cfm-total-ltr-sent {
             type uint32;
             description "Number of linktrace-response messages sent";
           }
           leaf cfm-total-ltr-received {
             type uint32;
             description "Number of linktrace-response messages received";
           }
           leaf cfm-next-ltm-sequence-number {
             type uint32;
             description "Sequence Number of the next LTM request";
           }
           leaf cfm-onedm-sent {
             type uint32;
             description "Number of one-way delay measurement request packets sent";
           }
           leaf cfm-onedm-received {
             type uint32;
             description "Number of valid one-way delay measurement request packets received";
           }
           leaf cfm-onedm-received-invalid {
             type uint32;
             description "Number of invalid one-way delay measurement request packets received";
           }
           leaf cfm-onedm-received-outofsync {
             type uint32;
             description "Number of out of sync one-way delay measurement request packets received";
           }
           leaf cfm-dmm-sent {
             type uint32;
             description "Number of two-way delay measurement request packets sent";
           }
           leaf cfm-dmm-received {
             type uint32;
             description "Number of valid two-way delay measurement request packets received";
           }
           leaf cfm-dmm-received-invalid {
             type uint32;
             description "Number of invalid two-way delay measurement request packets received";
           }
           leaf cfm-dmr-sent {
             type uint32;
             description "Number of two-way delay measurement response packets sent";
           }
           leaf cfm-dmr-received {
             type uint32;
             description "Number of valid two-way delay measurement response packets received";
           }
           leaf cfm-dmr-received-invalid {
             type uint32;
             description "Number of invalid two-way delay measurement response packets received";
           }
           leaf cfm-lmm-sent {
             type uint32;
             description "Number of loss measurement request message packets sent";
           }
           leaf cfm-lmm-received {
             type uint32;
             description "Number of valid loss measurement request message packets received";
           }
           leaf cfm-lmm-received-invalid {
             type uint32;
             description "Number of invalid loss measurement request message packets received";
           }
           leaf cfm-lmr-sent {
             type uint32;
             description "Number of loss measurement response packets sent";
           }
           leaf cfm-lmr-received {
             type uint32;
             description "Number of valid loss measurement response message packets received";
           }
           leaf cfm-lmr-received-invalid {
             type uint32;
             description "Number of invalid loss measurement response message packets received";
           }
           leaf cfm-slm-received {
             type uint32;
             description "Number of valid synthetic loss measurement request message packets received";
           }
           leaf cfm-slm-sent {
             type uint32;
             description "Number of synthetic loss measurement request message packets sent";
           }
           leaf cfm-slm-received-invalid {
             type uint32;
             description "Number of invalid synthetic loss measurement request message packets received";
           }
           leaf cfm-slr-sent {
             type uint32;
             description "Number of synthetic loss measurement response packets sent";
           }
           leaf cfm-slr-received {
             type uint32;
             description "Number of valid synthetic loss measurement response message packets received";
           }
           leaf cfm-slr-received-invalid {
             type uint32;
             description "Number of invalid synthetic loss measurement response message packets received";
           }
           leaf cfm-ais-sent {
             type uint32;
             description "Number of valid alarm indication signal messages generated";
           }
           leaf cfm-ais-received {
             type uint32;
             description "Number of valid alarm indication signal messages received";
           }
           leaf cfm-ais-received-invalid {
             type uint32;
             description "Number of invalid alarm indication signal messages received";
           }
         }
         container cfm-interface-remote-meps {
           container summary {
             leaf cfm-remote-mep-count {
               type uint32;
               description "Number of remote MEP configured or learnt";
             }
             list cfm-remote-mep {
               leaf cfm-remote-mep-identifier {
                 type uint32;
                 description "Identifier of remote MEP";
               }
               leaf cfm-remote-mep-mac-address {
                 type string;
                 description "MAC address of remote MEP";
               }
               leaf cfm-remote-mep-state {
                 type string;
                 description "State of the remote MEP";
               }
               leaf cfm-remote-mep-interface {
                 type string;
                 description "Interface on which this remote MEP has been discovered";
               }
               container cfm-remote-mep-connection-protection-tlv {
                 description "Connection Protection TLV information in the last recieved CCM from Remote MEP";
                 leaf cfm-connection-protection-tlv-prefer-me {
                   type string;
                   description "To indicate switchover to protect path";
                 }
                 leaf cfm-connection-protection-tlv-protection-in-use {
                   type string;
                   description "To indicate protection path in use";
                 }
                 leaf cfm-connection-protection-tlv-frr-flag {
                   type string;
                   description "To indicate FRR active for the working path";
                 }
               }
               container cfm-remote-mep-loss-threshold-tlv {
                 description "Loss Threshold TLV information in the last Last received CCM from remote MEP";
                 leaf cfm-loss-threshold-tlv-value {
                   type uint32;
                   description "Indicate Loss Threshold value";
                 }
                 leaf cfm-loss-threshold-tlv-flag {
                   type uint32;
                   description "To indicate ISSU info";
                 }
               }
             }
           }
         }
       }
     }
     container cfm-mep-database-session {
       leaf cfm-maintenance-domain-name {
         type string;
         description "Name of maintenance domain";
       }
       leaf cfm-maintenance-domain-name-format {
         type string;
         description "Format of maintenance domain name";
       }
       leaf cfm-level {
         type uint32;
         description "Maintenance-domain level";
       }
       leaf cfm-maintenance-association-name {
         type string;
         description "Name of maintenance association";
       }
       leaf cfm-maintenance-association-name-format {
         type string;
         description "Format of maintenance association name";
       }
     }
     container cfm-mep-database-continuity-check {
       leaf cfm-continuity-check-status {
         type string;
         description "Continuity-check protocol status";
       }
       leaf cfm-continuity-check-interval {
         type uint32;
         description "Continuity-check message interval";
       }
       leaf cfm-continuity-check-loss-threshold {
         type uint32;
         description "Maximum number of continuity-check messages that the endpoint can fail to acknowledge before it is marked as inoperative";
       }
     }
     container cfm-mep-database-ethernet-ais {
       leaf cfm-ethernet-ais-status {
         type string;
         description "Ethernet AIS message status";
       }
       leaf cfm-ethernet-ais-interval {
         type uint32;
         description "Ethernet AIS message interval";
       }
       leaf cfm-ethernet-ais-level {
         type string;
         description "MD levels to which AIS messages are generated";
       }
       leaf cfm-ethernet-ais-priority {
         type uint32;
         description "VLAN priority used in the Ethernet AIS messages";
       }
     }
     container cfm-mep-database-interface {
       leaf cfm-interface-name {
         type string;
         description "Name of interface";
       }
       leaf cfm-interface-status {
         type string;
         description "Status of 802.1ag on the interface";
       }
       leaf cfm-interface-link-status {
         type string;
         description "Operational status of this interface";
       }
     }
     container cfm-local-mep {
     }
     container cfm-local-mep-defects {
       leaf cfm-defect-remote-mep-no-ccm {
         type string;
         description "Indicates whether remote MEPs are receiving continuity-check messages (CCMs)";
       }
       leaf cfm-defect-error-ccm {
         type string;
         description "Indicates whether erroneous continuity-check messages (CCMs) were received";
       }
       leaf cfm-defect-cross-connect-ccm {
         type string;
         description "Indicates whether cross-connect continuity-check messages (CCMs) were received";
       }
       leaf cfm-defect-rdi-in-some-mep {
         type string;
         description "Indicates whether any remote MEPs are sending continuity-check messages (CCMs) with the RDI bit set";
       }
       leaf cfm-defect-mac-status {
         type string;
         description "Indicates whether any remote MEP's associated MAC is reporting an error status via the Port Status or Interface Status TLVs";
       }
       leaf cfm-defect-ais {
         type string;
         description "Indicates whether local MEP generated or received an AIS message";
       }
     }
     container cfm-local-mep-statistics {
       leaf cfm-total-ccm-sent {
         type uint32;
         description "Number of continuity-check messages sent";
       }
       leaf cfm-out-of-sequence-ccm-received {
         type uint32;
         description "Number of continuity-check messages received out of sequence";
       }
       leaf cfm-lbm-sent {
         type uint32;
         description "Number of loopback messages sent";
       }
       leaf cfm-lbr-sent {
         type uint32;
         description "Number of loopback responses sent";
       }
       leaf cfm-lbr-received {
         type uint32;
         description "Number of valid in-order loopback responses received";
       }
       leaf cfm-lbr-received-out-of-order {
         type uint32;
         description "Number of valid out-of-order loopback responses received";
       }
       leaf cfm-lbr-bad-msdu {
         type uint32;
         description "Number of loopback responses received with corrupted data";
       }
       leaf cfm-total-ltm-sent {
         type uint32;
         description "Number of linktrace-request messages sent";
       }
       leaf cfm-total-ltm-received {
         type uint32;
         description "Number of linktrace-request messages received";
       }
       leaf cfm-total-ltr-sent {
         type uint32;
         description "Number of linktrace-response messages sent";
       }
       leaf cfm-total-ltr-received {
         type uint32;
         description "Number of linktrace-response messages received";
       }
       leaf cfm-next-ltm-sequence-number {
         type uint32;
         description "Sequence Number of the next LTM request";
       }
       leaf cfm-onedm-sent {
         type uint32;
         description "Number of one-way delay measurement request packets sent";
       }
       leaf cfm-onedm-received {
         type uint32;
         description "Number of valid one-way delay measurement request packets received";
       }
       leaf cfm-onedm-received-invalid {
         type uint32;
         description "Number of invalid one-way delay measurement request packets received";
       }
       leaf cfm-onedm-received-outofsync {
         type uint32;
         description "Number of out of sync one-way delay measurement request packets received";
       }
       leaf cfm-dmm-sent {
         type uint32;
         description "Number of two-way delay measurement request packets sent";
       }
       leaf cfm-dmm-received {
         type uint32;
         description "Number of valid two-way delay measurement request packets received";
       }
       leaf cfm-dmm-received-invalid {
         type uint32;
         description "Number of invalid two-way delay measurement request packets received";
       }
       leaf cfm-dmr-sent {
         type uint32;
         description "Number of two-way delay measurement response packets sent";
       }
       leaf cfm-dmr-received {
         type uint32;
         description "Number of valid two-way delay measurement response packets received";
       }
       leaf cfm-dmr-received-invalid {
         type uint32;
         description "Number of invalid two-way delay measurement response packets received";
       }
       leaf cfm-lmm-sent {
         type uint32;
         description "Number of loss measurement request message packets sent";
       }
       leaf cfm-lmm-received {
         type uint32;
         description "Number of valid loss measurement request message packets received";
       }
       leaf cfm-lmm-received-invalid {
         type uint32;
         description "Number of invalid loss measurement request message packets received";
       }
       leaf cfm-lmr-sent {
         type uint32;
         description "Number of loss measurement response packets sent";
       }
       leaf cfm-lmr-received {
         type uint32;
         description "Number of valid loss measurement response message packets received";
       }
       leaf cfm-lmr-received-invalid {
         type uint32;
         description "Number of invalid loss measurement response message packets received";
       }
       leaf cfm-slm-sent {
         type uint32;
         description "Number of synthetic loss measurement request message packets sent";
       }
       leaf cfm-slm-received {
         type uint32;
         description "Number of valid synthetic loss measurement request message packets received";
       }
       leaf cfm-slm-received-invalid {
         type uint32;
         description "Number of invalid synthetic loss measurement request message packets received";
       }
       leaf cfm-slr-sent {
         type uint32;
         description "Number of synthetic loss measurement response packets sent";
       }
       leaf cfm-slr-received {
         type uint32;
         description "Number of valid synthetic loss measurement response message packets received";
       }
       leaf cfm-slr-received-invalid {
         type uint32;
         description "Number of invalid synthetic loss measurement response message packets received";
       }
       leaf cfm-ais-sent {
         type uint32;
         description "Number of valid alarm indication signal messages generated";
       }
       leaf cfm-ais-received {
         type uint32;
         description "Number of valid alarm indication signal messages received";
       }
       leaf cfm-ais-received-invalid {
         type uint32;
         description "Number of invalid alarm indication signal messages received";
       }
     }
     container cfm-remote-meps {
       container brief {
         leaf cfm-remote-mep-count {
           type uint32;
           description "Number of remote MEP configured or learnt";
         }
         list cfm-remote-mep {
           leaf cfm-remote-mep-identifier {
             type uint32;
             description "Identifier of remote MEP";
           }
           leaf cfm-remote-mep-mac-address {
             type string;
             description "MAC address of remote MEP";
           }
           leaf cfm-remote-mep-state {
             type string;
             description "State of the remote MEP";
           }
           leaf cfm-remote-mep-interface {
             type string;
             description "Interface on which this remote MEP has been discovered";
           }
           container cfm-remote-mep-connection-protection-tlv {
             description "Connection Protection TLV information in the last recieved CCM from Remote MEP";
             leaf cfm-connection-protection-tlv-prefer-me {
               type string;
               description "To indicate switchover to protect path";
             }
             leaf cfm-connection-protection-tlv-protection-in-use {
               type string;
               description "To indicate protection path in use";
             }
             leaf cfm-connection-protection-tlv-frr-flag {
               type string;
               description "To indicate FRR active for the working path";
             }
           }
           container cfm-remote-mep-loss-threshold-tlv {
             description "Loss Threshold TLV information in the last Last received CCM from remote MEP";
             leaf cfm-loss-threshold-tlv-value {
               type uint32;
               description "Indicate Loss Threshold value";
             }
             leaf cfm-loss-threshold-tlv-flag {
               type uint32;
               description "To indicate ISSU info";
             }
           }
         }
       }
       container extensive {
         list cfm-remote-mep {
           leaf cfm-remote-mep-identifier {
             type uint32;
             description "Identifier of remote MEP";
           }
           leaf cfm-remote-mep-state {
             type string;
             description "State of the remote MEP";
           }
           leaf cfm-remote-mep-mac-address {
             type string;
             description "MAC address of remote MEP";
           }
           leaf cfm-remote-mep-type {
             type string;
             description "Type of the remote MEP";
           }
           leaf cfm-remote-mep-interface {
             type string;
             description "Interface on which this remote MEP has been discovered";
           }
           leaf cfm-remote-mep-last-flapped {
             type string;
             description "Last time when remote MEP flapped";
           }
           leaf cfm-remote-mep-last-dm-stats-cleared {
             type string;
             description "Last time when delay measurement statistics were cleared";
           }
           leaf cfm-remote-mep-last-lm-stats-cleared {
             type string;
             description "Last time when loss measurement statistics were cleared";
           }
           leaf cfm-remote-mep-last-slm-stats-cleared {
             type string;
             description "Last time when slm measurement statistics were cleared";
           }
           leaf cfm-remote-mep-continuity {
             type string;
             description "Display continuity measurement in percentage";
           }
           leaf cfm-remote-mep-admin-enable-time {
             type string;
             description "Total time in seconds for which remote mep is admin enabled";
           }
           leaf cfm-remote-mep-oper-down-time {
             type string;
             description "Total time in seconds for which remote mep was operationally down";
           }
           leaf cfm-remote-mep-loss-threshold {
             type uint32;
             description "Indicate Loss Threshold value used for this rmep";
           }
           leaf cfm-remote-mep-rdi {
             type string;
             description "Remote defect indication status of the remote MEP";
           }
           leaf cfm-remote-mep-port-status-tlv {
             type string;
             description "Port status TLV information in the received CCM from remote MEP";
           }
           leaf cfm-remote-mep-interface-status-tlv {
             type string;
             description "Interface status TLV information in the received CCM from remote MEP";
           }
           leaf cfm-remote-mep-chassis-mac-address {
             type string;
             description "MAC address of remote MEP";
           }
           leaf cfm-remote-management-address {
             type string;
             description "CFM remote management address";
           }
           leaf cfm-remote-sendid-tlv {
             type string;
             description "CFM Remote Sendid TLV Status";
           }
           leaf cfm-remote-sendid-chassis-subtype-tlv {
             type string;
             description "CFM Remote Sendid TLV Status";
           }
           container cfm-remote-mep-connection-protection-tlv {
             description "Connection Protection TLV information in the last recieved CCM from Remote MEP";
             leaf cfm-connection-protection-tlv-prefer-me {
               type string;
               description "To indicate switchover to protect path";
             }
             leaf cfm-connection-protection-tlv-protection-in-use {
               type string;
               description "To indicate protection path in use";
             }
             leaf cfm-connection-protection-tlv-frr-flag {
               type string;
               description "To indicate FRR active for the working path";
             }
           }
           container cfm-remote-mep-loss-threshold-tlv {
             description "Loss Threshold TLV information in the last Last received CCM from remote MEP";
             leaf cfm-loss-threshold-tlv-value {
               type uint32;
               description "Indicate Loss Threshold value";
             }
             leaf cfm-loss-threshold-tlv-flag {
               type uint32;
               description "To indicate ISSU info";
             }
           }
         }
         container cfm-remote-mep-ap {
           leaf cfm-action-profile-name {
             type string;
             description "Name of the action profile";
           }
           leaf cfm-ap-last-event {
             type string;
             description "Displays the last occurred event";
           }
           leaf cfm-ap-action-name {
             type string;
             description "Shows the action taken";
           }
           leaf cfm-ap-action-time {
             type string;
             description "Shows the time at which action was taken";
           }
           leaf cfm-ap-last-event-cleared-time {
             type string;
             description "Shows the time at which last event was cleared";
           }
         }
       }
     }
     container cfm-cross-connect-sessions {
       list cfm-cross-connect-session {
         leaf cfm-session-defect-type {
           type string;
           description "CCM session defect type";
         }
         leaf cfm-session-defect-description {
           type string;
           description "CCM session defect description";
         }
         leaf cfm-maintenance-domain-name {
           type string;
           description "Name of maintenance domain";
         }
         leaf cfm-maintenance-domain-name-format {
           type string;
           description "Format of maintenance domain name";
         }
         leaf cfm-level {
           type uint32;
           description "Maintenance-domain level";
         }
         leaf cfm-maintenance-association-name {
           type string;
           description "Name of maintenance association";
         }
         leaf cfm-maintenance-association-name-format {
           type string;
           description "Format of maintenance association name";
         }
         leaf cfm-mep-identifier {
           type uint32;
           description "Identifier of MEP";
         }
         leaf cfm-continuity-check-interval {
           type uint32;
           description "Continuity-check message interval";
         }
       }
     }
     container cfm-error-sessions {
       list cfm-error-session {
         leaf cfm-session-defect-type {
           type string;
           description "CCM session defect type";
         }
         leaf cfm-session-defect-description {
           type string;
           description "CCM session defect description";
         }
         leaf cfm-maintenance-domain-name {
           type string;
           description "Name of maintenance domain";
         }
         leaf cfm-maintenance-domain-name-format {
           type string;
           description "Format of maintenance domain name";
         }
         leaf cfm-level {
           type uint32;
           description "Maintenance-domain level";
         }
         leaf cfm-maintenance-association-name {
           type string;
           description "Name of maintenance association";
         }
         leaf cfm-maintenance-association-name-format {
           type string;
           description "Format of maintenance association name";
         }
         leaf cfm-mep-identifier {
           type uint32;
           description "Identifier of MEP";
         }
         leaf cfm-continuity-check-interval {
           type uint32;
           description "Continuity-check message interval";
         }
       }
     }
     container cfm-mep-statistics-mep-summary {
       leaf cfm-local-mep-identifier {
         type uint32;
         description "Identifier of local MEP";
       }
       leaf cfm-local-mep-mac-address {
         type string;
         description "MAC address of local MEP";
       }
       leaf cfm-remote-mep-count {
         type uint32;
         description "Number of remote MEP configured or learnt";
       }
     }
     container cfm-local-mep-packet-statistics {
       leaf cfm-total-ccm-sent {
         type uint32;
         description "Number of continuity-check messages sent";
       }
       leaf cfm-out-of-sequence-ccm-received {
         type uint32;
         description "Number of continuity-check messages received out of sequence";
       }
       leaf cfm-lbm-sent {
         type uint32;
         description "Number of loopback messages sent";
       }
       leaf cfm-lbr-sent {
         type uint32;
         description "Number of loopback responses sent";
       }
       leaf cfm-lbr-received {
         type uint32;
         description "Number of valid in-order loopback responses received";
       }
       leaf cfm-lbr-received-out-of-order {
         type uint32;
         description "Number of valid out-of-order loopback responses received";
       }
       leaf cfm-lbr-bad-msdu {
         type uint32;
         description "Number of loopback responses received with corrupted data";
       }
       leaf cfm-total-ltm-sent {
         type uint32;
         description "Number of linktrace-request messages sent";
       }
       leaf cfm-total-ltm-received {
         type uint32;
         description "Number of linktrace-request messages received";
       }
       leaf cfm-total-ltr-sent {
         type uint32;
         description "Number of linktrace-response messages sent";
       }
       leaf cfm-total-ltr-received {
         type uint32;
         description "Number of linktrace-response messages received";
       }
       leaf cfm-next-ltm-sequence-number {
         type uint32;
         description "Sequence Number of the next LTM request";
       }
       leaf cfm-onedm-sent {
         type uint32;
         description "Number of one-way delay measurement request packets sent";
       }
       leaf cfm-onedm-received {
         type uint32;
         description "Number of valid one-way delay measurement request packets received";
       }
       leaf cfm-onedm-received-invalid {
         type uint32;
         description "Number of invalid one-way delay measurement request packets received";
       }
       leaf cfm-onedm-received-outofsync {
         type uint32;
         description "Number of out of sync one-way delay measurement request packets received";
       }
       leaf cfm-dmm-sent {
         type uint32;
         description "Number of two-way delay measurement request packets sent";
       }
       leaf cfm-dmm-received {
         type uint32;
         description "Number of valid two-way delay measurement request packets received";
       }
       leaf cfm-dmm-received-invalid {
         type uint32;
         description "Number of invalid two-way delay measurement request packets received";
       }
       leaf cfm-dmr-sent {
         type uint32;
         description "Number of two-way delay measurement response packets sent";
       }
       leaf cfm-dmr-received {
         type uint32;
         description "Number of valid two-way delay measurement response packets received";
       }
       leaf cfm-dmr-received-invalid {
         type uint32;
         description "Number of invalid two-way delay measurement response packets received";
       }
       leaf cfm-lmm-sent {
         type uint32;
         description "Number of loss measurement request message packets sent";
       }
       leaf cfm-lmm-received {
         type uint32;
         description "Number of valid loss measurement request message packets received";
       }
       leaf cfm-lmm-received-invalid {
         type uint32;
         description "Number of invalid loss measurement request message packets received";
       }
       leaf cfm-lmr-sent {
         type uint32;
         description "Number of loss measurement response packets sent";
       }
       leaf cfm-lmr-received {
         type uint32;
         description "Number of valid loss measurement response message packets received";
       }
       leaf cfm-lmr-received-invalid {
         type uint32;
         description "Number of invalid loss measurement response message packets received";
       }
       leaf cfm-slm-sent {
         type uint32;
         description "Number of synthetic loss measurement request message packets sent";
       }
       leaf cfm-slm-received {
         type uint32;
         description "Number of valid synthetic loss measurement request message packets received";
       }
       leaf cfm-slm-received-invalid {
         type uint32;
         description "Number of invalid synthetic loss measurement request message packets received";
       }
       leaf cfm-slr-sent {
         type uint32;
         description "Number of synthetic loss measurement response packets sent";
       }
       leaf cfm-slr-received {
         type uint32;
         description "Number of valid synthetic loss measurement response message packets received";
       }
       leaf cfm-slr-received-invalid {
         type uint32;
         description "Number of invalid synthetic loss measurement response message packets received";
       }
       leaf cfm-ais-sent {
         type uint32;
         description "Number of valid alarm indication signal messages generated";
       }
       leaf cfm-ais-received {
         type uint32;
         description "Number of valid alarm indication signal messages received";
       }
       leaf cfm-ais-received-invalid {
         type uint32;
         description "Number of invalid alarm indication signal messages received";
       }
     }
     container cfm-remote-mep-brief-summary {
       leaf cfm-remote-mep-identifier {
         type uint32;
         description "Identifier of remote MEP";
       }
       leaf cfm-remote-mep-mac-address {
         type string;
         description "MAC address of remote MEP";
       }
     }
     container cfm-ethdm-delay-entry {
       leaf cfm-ethdm-delay-entry-index {
         type uint32;
         description "Delay entry index.";
       }
       leaf cfm-ethdm-oneway-delay {
         type uint32;
         description "One-way delay measured using ETH-DM.";
       }
       leaf cfm-ethdm-twoway-delay {
         type uint32;
         description "Two-way delay measured using ETH-DM.";
       }
     }
     container cfm-ethdm-oneway-delay-summary {
       leaf cfm-ethdm-average-oneway-delay {
         type uint32;
         description "Average one-way delay measured using ETH-DM.";
       }
       leaf cfm-ethdm-average-oneway-delay-variation {
         type uint32;
         description "Average variation of one-way delay between two samples of measurement.";
       }
       leaf cfm-ethdm-bestcase-oneway-delay {
         type uint32;
         description "Bestcase one-way delay measured using ETH-DM.";
       }
       leaf cfm-ethdm-worstcase-oneway-delay {
         type uint32;
         description "Worstcase one-way delay measured using ETH-DM.";
       }
     }
     container cfm-ethdm-twoway-delay-summary {
       leaf cfm-ethdm-average-twoway-delay {
         type uint32;
         description "Average two-way delay measured using ETH-DM.";
       }
       leaf cfm-ethdm-average-twoway-delay-variation {
         type uint32;
         description "Average variation of two-way delay between two samples of measurement.";
       }
       leaf cfm-ethdm-bestcase-twoway-delay {
         type uint32;
         description "Bestcase two-way delay measured using ETH-DM.";
       }
       leaf cfm-ethdm-worstcase-twoway-delay {
         type uint32;
         description "Worstcase two-way delay measured using ETH-DM.";
       }
     }
     container cfm-ethlm-cir-loss-entry {
       leaf cfm-ethlm-cir-loss-entry-index {
         type uint32;
         description "CIR Loss entry index.";
       }
       leaf cfm-ethlm-near-end-cir-frame-loss {
         type uint32;
         description "Near-end loss measured using ETH-LM.";
       }
       leaf cfm-ethlm-far-end-total-cir-tx {
         type uint32;
         description "Far-end total tx for current ETH-LM sample.";
       }
       leaf cfm-ethlm-near-end-total-cir-rx {
         type uint32;
         description "Near-end total rx for current ETH-LM sample.";
       }
       leaf cfm-ethlm-far-end-cir-frame-loss {
         type uint32;
         description "Far-end loss measured using ETH-LM.";
       }
       leaf cfm-ethlm-near-end-total-cir-tx {
         type uint32;
         description "Near-end total tx for current ETH-LM sample.";
       }
       leaf cfm-ethlm-far-end-total-cir-rx {
         type uint32;
         description "Far-end total rx for current ETH-LM sample.";
       }
     }
     container cfm-ethlm-eir-loss-entry {
       leaf cfm-ethlm-eir-loss-entry-index {
         type uint32;
         description "EIR Loss entry index.";
       }
       leaf cfm-ethlm-near-end-eir-frame-loss {
         type uint32;
         description "Near-end loss measured using ETH-LM.";
       }
       leaf cfm-ethlm-far-end-total-eir-tx {
         type uint32;
         description "Far-end total tx for current ETH-LM sample.";
       }
       leaf cfm-ethlm-near-end-total-eir-rx {
         type uint32;
         description "Near-end total rx for current ETH-LM sample.";
       }
       leaf cfm-ethlm-far-end-eir-frame-loss {
         type uint32;
         description "Far-end loss measured using ETH-LM.";
       }
       leaf cfm-ethlm-near-end-total-eir-tx {
         type uint32;
         description "Near-end total tx for current ETH-LM sample.";
       }
       leaf cfm-ethlm-far-end-total-eir-rx {
         type uint32;
         description "Far-end total rx for current ETH-LM sample.";
       }
     }
     container cfm-ethlm-cir-loss-summary {
       leaf cfm-ethlm-total-far-end-cir-tx {
         type uint32;
         description "Total far-end Tx measured using ETH-LM.";
       }
       leaf cfm-ethlm-total-near-end-cir-rx {
         type uint32;
         description "Total near-end Rx measured using ETH-LM.";
       }
       leaf cfm-ethlm-total-near-end-cir-loss {
         type uint32;
         description "Total near-end loss measured using ETH-LM.";
       }
       leaf cfm-ethlm-total-near-end-cir-loss-ratio {
         type string;
         description "Total near-end loss-ratio measured using ETH-LM.";
       }
       leaf cfm-ethlm-total-near-end-cir-tx {
         type uint32;
         description "Total near-end Tx measured using ETH-LM.";
       }
       leaf cfm-ethlm-total-far-end-cir-rx {
         type uint32;
         description "Total far-end Rx measured using ETH-LM.";
       }
       leaf cfm-ethlm-total-far-end-cir-loss {
         type uint32;
         description "Total far-end loss measured using ETH-LM.";
       }
       leaf cfm-ethlm-total-far-end-cir-loss-ratio {
         type string;
         description "Total far-end loss-ratio measured using ETH-LM.";
       }
       leaf cfm-ethlm-average-near-end-cir-loss {
         type string;
         description "Average near-end loss measured using ETH-LM.";
       }
       leaf cfm-ethlm-average-near-end-cir-loss-ratio {
         type string;
         description "Average near-end loss ratio measured using ETH-LM.";
       }
       leaf cfm-ethlm-average-far-end-cir-loss {
         type string;
         description "Average far-end loss measured using ETH-LM.";
       }
       leaf cfm-ethlm-average-far-end-cir-loss-ratio {
         type string;
         description "Average far-end loss ratio measured using ETH-LM.";
       }
       leaf cfm-ethlm-near-end-best-case-cir-loss {
         type string;
         description "Best case near-end loss measured using ETH-LM.";
       }
       leaf cfm-ethlm-near-end-best-case-cir-loss-ratio {
         type string;
         description "Best case near-end loss ratio measured using ETH-LM.";
       }
       leaf cfm-ethlm-near-end-worst-case-cir-loss {
         type string;
         description "Worst case near-end loss measured using ETH-LM.";
       }
       leaf cfm-ethlm-near-end-worst-case-cir-loss-ratio {
         type string;
         description "Worst case near-end loss ratio measured using ETH-LM.";
       }
       leaf cfm-ethlm-far-end-best-case-cir-loss {
         type string;
         description "Best case far-end loss measured using ETH-LM.";
       }
       leaf cfm-ethlm-far-end-best-case-cir-loss-ratio {
         type string;
         description "Best case far-end loss ratio measured using ETH-LM.";
       }
       leaf cfm-ethlm-far-end-worst-case-cir-loss {
         type string;
         description "Worst case far-end loss measured using ETH-LM.";
       }
       leaf cfm-ethlm-far-end-worst-case-cir-loss-ratio {
         type string;
         description "Worst case far-end loss ratio measured using ETH-LM.";
       }
     }
     container cfm-ethlm-eir-loss-summary {
       leaf cfm-ethlm-total-far-end-eir-tx {
         type uint32;
         description "Total far-end Tx measured using ETH-LM.";
       }
       leaf cfm-ethlm-total-near-end-eir-rx {
         type uint32;
         description "Total near-end Rx measured using ETH-LM.";
       }
       leaf cfm-ethlm-total-near-end-eir-loss {
         type uint32;
         description "Total near-end loss measured using ETH-LM.";
       }
       leaf cfm-ethlm-total-near-end-eir-loss-ratio {
         type string;
         description "Total near-end loss-ratio measured using ETH-LM.";
       }
       leaf cfm-ethlm-total-near-end-eir-tx {
         type uint32;
         description "Total near-end Tx measured using ETH-LM.";
       }
       leaf cfm-ethlm-total-far-end-eir-rx {
         type uint32;
         description "Total far-end Rx measured using ETH-LM.";
       }
       leaf cfm-ethlm-total-far-end-eir-loss {
         type uint32;
         description "Total far-end loss measured using ETH-LM.";
       }
       leaf cfm-ethlm-total-far-end-eir-loss-ratio {
         type string;
         description "Total far-end loss-ratio measured using ETH-LM.";
       }
       leaf cfm-ethlm-average-near-end-eir-loss {
         type string;
         description "Average near-end loss measured using ETH-LM.";
       }
       leaf cfm-ethlm-average-near-end-eir-loss-ratio {
         type string;
         description "Average near-end loss ratio measured using ETH-LM.";
       }
       leaf cfm-ethlm-average-far-end-eir-loss {
         type string;
         description "Average far-end loss measured using ETH-LM.";
       }
       leaf cfm-ethlm-average-far-end-eir-loss-ratio {
         type string;
         description "Average far-end loss ratio measured using ETH-LM.";
       }
       leaf cfm-ethlm-near-end-best-case-eir-loss {
         type string;
         description "Best case near-end loss measured using ETH-LM.";
       }
       leaf cfm-ethlm-near-end-best-case-eir-loss-ratio {
         type string;
         description "Best case near-end loss ratio measured using ETH-LM.";
       }
       leaf cfm-ethlm-near-end-worst-case-eir-loss {
         type string;
         description "Worst case near-end loss measured using ETH-LM.";
       }
       leaf cfm-ethlm-near-end-worst-case-eir-loss-ratio {
         type string;
         description "Worst case near-end loss ratio measured using ETH-LM.";
       }
       leaf cfm-ethlm-far-end-best-case-eir-loss {
         type string;
         description "Best case far-end loss measured using ETH-LM.";
       }
       leaf cfm-ethlm-far-end-best-case-eir-loss-ratio {
         type string;
         description "Best case far-end loss ratio measured using ETH-LM.";
       }
       leaf cfm-ethlm-far-end-worst-case-eir-loss {
         type string;
         description "Worst case far-end loss measured using ETH-LM.";
       }
       leaf cfm-ethlm-far-end-worst-case-eir-loss-ratio {
         type string;
         description "Worst case far-end loss ratio measured using ETH-LM.";
       }
     }
     container cfm-stats-ethslm-entry {
       leaf cfm-slm-txed {
         type uint32;
         description "Number of valid synthetic loss measurement request sent";
       }
       leaf cfm-slm-rxed {
         type uint32;
         description "Number of valid synthetic loss measurement response received";
       }
       leaf cfm-slm-tx-lastpkt-rcv {
         type uint32;
         description "TxFC1 value in the last valid synthetic loss measurement response received";
       }
       leaf cfm-slm-rx-lastpkt-rcv {
         type uint32;
         description "TxFCb value in the last valid synthetic loss measurement response received";
       }
       leaf cfm-slm-last-measured-near-end-slm-loss-stats {
         type uint32;
         description "Near end synthetic loss";
       }
       leaf cfm-slm-last-measured-near-end-slm-loss-stats-percent {
         type string;
         description "Near end synthetic loss in percentage";
       }
       leaf cfm-slm-last-measured-far-end-slm-loss-stats {
         type uint32;
         description "Far end synthetic loss";
       }
       leaf cfm-slm-last-measured-far-end-slm-loss-stats-percent {
         type string;
         description "Far end synthetic loss in percentage";
       }
     }
     container cfm-iter-mep-summary {
       leaf cfm-iterator-error-status {
         type string;
         description "Error reason for the iterator";
       }
       leaf cfm-maintenance-domain-name {
         type string;
         description "Name of maintenance domain";
       }
       leaf cfm-level {
         type uint32;
         description "Maintenance-domain level";
       }
       leaf cfm-maintenance-association-name {
         type string;
         description "Name of maintenance association";
       }
       leaf cfm-local-mep-identifier {
         type uint32;
         description "Identifier of local MEP";
       }
       leaf cfm-remote-mep-identifier {
         type uint32;
         description "Identifier of remote MEP";
       }
       leaf cfm-remote-mep-mac-address {
         type string;
         description "MAC address of remote MEP";
       }
     }
     container cfm-iter-info {
       leaf cfm-iterator-name {
         type string;
         description "Name of iterator";
       }
       leaf cfm-iterator-identifier {
         type uint32;
         description "Identifier of iterator";
       }
       leaf cfm-iterator-cycle-time {
         type uint32;
         description "Cycle time of iterator";
       }
       leaf cfm-iteration-period {
         type uint32;
         description "Period of iteration";
       }
       leaf cfm-iterator-status {
         type string;
         description "State of the iterator";
       }
       leaf cfm-iterator-forever-status {
         type string;
         description "For-ever running status of the iterator";
       }
       leaf cfm-iteration-current-count {
         type uint32;
         description "Current iteration count of iterator";
       }
       leaf cfm-iteration-remaining-count {
         type uint32;
         description "Remaining iteration count of iterator";
       }
       leaf cfm-iterator-counter-reset-time {
         type string;
         description "Shows the time at which iterator counters are resetted";
       }
       leaf cfm-iterator-counter-reset-reason {
         type string;
         description "Counter reset reason of iterator";
       }
     }
     container cfm-iter-ethdm-entry {
       leaf cfm-delay-weight {
         type uint32;
         description "Delay calculation weight of iterator";
       }
       leaf cfm-delay-variation-weight {
         type uint32;
         description "Delay variation calculation weight of iterator";
       }
       leaf cfm-dmm-sent {
         type uint32;
         description "Number of two-way delay measurement request packets sent";
       }
       leaf cfm-dmm-skipped-for-threshold-hit {
         type uint32;
         description "Number of delay measurement packets skipped due to threshold hit";
       }
       leaf cfm-dmm-skipped-for-threshold-hit-window {
         type uint32;
         description "Number of delay measurement packets skipped due to threshold hit window";
       }
       leaf cfm-dmr-received {
         type uint32;
         description "Number of valid two-way delay measurement response packets received";
       }
       leaf cfm-dmr-out-of-sequence {
         type uint32;
         description "Number of out of sequence delay measurement response packets received";
       }
       leaf cfm-dmr-fc-mismatch {
         type uint32;
         description "Number of forwarding-class mismatch delay measurement response packets received";
       }
       leaf cfm-dmr-invalid-time-stamp {
         type uint32;
         description "Number of invalid time stamps delay measurement response packets received";
       }
       leaf cfm-average-twoway-delay {
         type uint64;
         description "Average two-way delay measured using iterator";
       }
       leaf cfm-average-twoway-delay-variation {
         type uint64;
         description "Average variation of two-way delay measured using iterator";
       }
       leaf cfm-average-oneway-fwd-delay-variation {
         type uint64;
         description "Average variation of one-way forward delay measured using iterator";
       }
       leaf cfm-average-oneway-bkwd-delay-variation {
         type uint64;
         description "Average variation of one-way backward delay measured using iterator";
       }
       leaf cfm-weighted-average-twoway-delay {
         type uint64;
         description "Weighted average two-way delay measured using iterator";
       }
       leaf cfm-weighted-average-twoway-delay-variation {
         type uint64;
         description "Weighted average variation of two-way delay measured using iterator";
       }
       leaf cfm-weighted-average-oneway-fwd-delay-variation {
         type uint64;
         description "Weighted average variation of one-way forward delay measured using iterator";
       }
       leaf cfm-weighted-average-oneway-bkwd-delay-variation {
         type uint64;
         description "Weighted average variation of one-way backward delay measured using iterator";
       }
       leaf cfm-bestcase-twoway-delay {
         type uint64;
         description "Minimum of two-way delay measured using iterator";
       }
       leaf cfm-worstcase-twoway-delay {
         type uint64;
         description "Maximum of two-way delay measured using iterator";
       }
       leaf cfm-bestcase-oneway-fwd-delay {
         type uint64;
         description "Minimum of one-way forward delay measured using iterator";
       }
       leaf cfm-worstcase-oneway-fwd-delay {
         type uint64;
         description "Maximum of one-way forward delay measured using iterator";
       }
       leaf cfm-bestcase-oneway-bkwd-delay {
         type uint64;
         description "Mininmum of one-way backward delay measured using iterator";
       }
       leaf cfm-worstcase-oneway-bkwd-delay {
         type uint64;
         description "Maximum of one-way backward delay measured using iterator";
       }
       leaf cfm-weighted-average-bestcase-twoway-delay {
         type uint64;
         description "Weighted average minimum two-way delay measured using iterator";
       }
       leaf cfm-weighted-average-worstcase-twoway-delay {
         type uint64;
         description "Weighted average maximum two-way delay measured using iterator";
       }
       leaf cfm-weighted-average-bestcase-oneway-fwd-delay {
         type uint64;
         description "Weighted average minimum of one-way forward delay measured using iterator";
       }
       leaf cfm-weighted-average-worstcase-oneway-fwd-delay {
         type uint64;
         description "Weighted average maximum of one-way forward delay measured using iterator";
       }
       leaf cfm-weighted-average-bestcase-oneway-bkwd-delay {
         type uint64;
         description "Weighted average minimum of one-way backward delay measured using iterator";
       }
       leaf cfm-weighted-average-worstcase-oneway-bkwd-delay {
         type uint64;
         description "Weighted average maximum of one-way backward delay measured using iterator";
       }
     }
     container cfm-iter-ethlm-entry {
       leaf cfm-lmm-sent {
         type uint32;
         description "Number of loss measurement request message packets sent";
       }
       leaf cfm-lmm-skipped-for-threshold-hit {
         type uint32;
         description "Number of loss measurement packets skipped due to threshold hit";
       }
       leaf cfm-lmm-skipped-for-threshold-hit-window {
         type uint32;
         description "Number of loss measurement packets skipped due to threshold hit window";
       }
       leaf cfm-lmr-received {
         type uint32;
         description "Number of valid loss measurement response message packets received";
       }
       leaf cfm-lmr-out-of-seq {
         type uint32;
         description "Number of out of sequence loss measurement response message packets received";
       }
       leaf cfm-lmr-fc-mismatch {
         type uint32;
         description "Number of forwarding-class mismatch loss measurement response message packets received";
       }
       leaf cfm-accu-tx-near-end-cir-loss-stats {
         type uint32;
         description "Accumulated transmit statistics of near-end loss measured using iterator";
       }
       leaf cfm-accu-tx-far-end-cir-loss-stats {
         type uint32;
         description "Accumulated transmit statistics of far-end loss measured using iterator";
       }
       leaf cfm-accu-tx-near-end-eir-loss-stats {
         type uint32;
         description "Accumulated transmit statistics of near-end loss measured using iterator";
       }
       leaf cfm-accu-tx-far-end-eir-loss-stats {
         type uint32;
         description "Accumulated transmit statistics of far-end loss measured using iterator";
       }
       leaf cfm-accu-rx-near-end-cir-loss-stats {
         type uint32;
         description "Accumulated recieve statistics of near-end loss measured using iterator";
       }
       leaf cfm-accu-rx-far-end-cir-loss-stats {
         type uint32;
         description "Accumulated receive statistics of far-end loss measured using iterator";
       }
       leaf cfm-accu-rx-near-end-eir-loss-stats {
         type uint32;
         description "Accumulated receive statistics of near-end loss measured using iterator";
       }
       leaf cfm-accu-rx-far-end-eir-loss-stats {
         type uint32;
         description "Accumulated receive statistics of far-end loss measured using iterator";
       }
       leaf cfm-accu-loss-near-end-cir-loss-stats {
         type uint32;
         description "Accumulated statistics of near-end loss measured using iterator";
       }
       leaf cfm-accu-loss-near-end-cir-loss-stats-percent {
         type string;
         description "Accumulated statistics of near-end loss measured using iterator in percentage";
       }
       leaf cfm-accu-loss-far-end-cir-loss-stats {
         type uint32;
         description "Accumulated loss statistics of far-end loss measured using iterator";
       }
       leaf cfm-accu-loss-far-end-cir-loss-stats-percent {
         type string;
         description "Accumulated loss statistics of far-end loss measured using iterator in percentage";
       }
       leaf cfm-accu-loss-near-end-eir-loss-stats {
         type uint32;
         description "Accumulated loss statistics of near-end loss measured using iterator";
       }
       leaf cfm-accu-loss-near-end-eir-loss-stats-percent {
         type string;
         description "Accumulated loss statistics of near-end loss measured using iterator in percentage";
       }
       leaf cfm-accu-loss-far-end-eir-loss-stats {
         type uint32;
         description "Accumulated loss statistics of far-end loss measured using iterator";
       }
       leaf cfm-accu-loss-far-end-eir-loss-stats-percent {
         type string;
         description "Accumulated loss statistics of far-end loss measured using iterator in percentage";
       }
       leaf cfm-last-measured-near-end-cir-loss-stats {
         type uint32;
         description "Last measured statistics of near-end loss using iterator";
       }
       leaf cfm-last-measured-far-end-cir-loss-stats {
         type uint32;
         description "Last measured statistics of far-end loss using iterator";
       }
       leaf cfm-last-measured-near-end-eir-loss-stats {
         type uint32;
         description "Last measured statistics of near-end loss using iterator";
       }
       leaf cfm-last-measured-far-end-eir-loss-stats {
         type uint32;
         description "Last measured statistics of far-end loss using iterator";
       }
     }
     container cfm-iter-eth-sfl-entry {
       leaf sfl-measurement-packets-sent {
         type uint32;
         description "Number of statistical frame loss measurement packets sent";
       }
       leaf sfl-measurement-packets-skipped-for-threshold-hit {
         type uint32;
         description "Number of statistical frame loss measurement packets skipped due to threshold hit";
       }
       leaf sfl-measurement-packets-skipped-for-threshold-hit-window {
         type uint32;
         description "Number of statistical frame loss measurement packets skipped due to threshold hit window";
       }
       leaf sfl-measurement-packets-received {
         type uint32;
         description "Number of statistical frame loss measurement packets received";
       }
       leaf sfl-measurement-packets-out-of-sequence {
         type uint32;
         description "Number of statistical frame loss measurement out of sequence packets received";
       }
       leaf sfl-measurement-packets-fc-mismatch {
         type uint32;
         description "Number of statistical frame loss measurement forwarding-class mismatch packets received";
       }
       leaf sfl-measurement-cir-packets-sent {
         type uint32;
         description "Number of CIR statistical frame loss measurement packets sent";
       }
       leaf sfl-measurement-eir-packets-sent {
         type uint32;
         description "Number of EIR statistical frame loss measurement packets sent";
       }
       leaf sfl-measurement-cir-packets-received {
         type uint32;
         description "Number of CIR statistical frame loss measurement packets received";
       }
       leaf sfl-measurement-eir-packets-received {
         type uint32;
         description "Number of EIR statistical frame loss measurement packets received";
       }
       leaf sfl-measurement-cir-loss-count {
         type uint32;
         description "Number of CIR statistical frame loss measurement packets lost";
       }
       leaf sfl-measurement-cir-loss-percent {
         type uint32;
         description "Number of CIR statistical frame loss measurement packets lost percent";
       }
       leaf sfl-measurement-eir-loss-count {
         type uint32;
         description "Number of EIR statistical frame loss measurement packets lost";
       }
       leaf sfl-measurement-eir-loss-percent {
         type uint32;
         description "Number of EIR statistical frame loss measurement packets lost percent";
       }
       leaf sfl-measurement-loss-count {
         type uint32;
         description "Number of statistical frame loss measurement packets lost";
       }
       leaf sfl-measurement-loss-percent {
         type uint32;
         description "Number of statistical frame loss measurement packets lost percent";
       }
     }
     container cfm-iter-ethslm-entry {
       leaf cfm-slm-sent {
         type uint32;
         description "Number of synthetic loss measurement request message packets sent";
       }
       leaf cfm-slm-skipped-for-threshold-hit {
         type uint32;
         description "Number of synthetic loss measurement packets skipped due to threshold hit";
       }
       leaf cfm-slm-skipped-for-threshold-hit-window {
         type uint32;
         description "Number of synthetic loss measurement packets skipped due to threshold hit window";
       }
       leaf cfm-slr-received {
         type uint32;
         description "Number of valid synthetic loss measurement response message packets received";
       }
       leaf cfm-slr-out-of-seq {
         type uint32;
         description "Number of out of sequence synthetic loss measurement response message packets received";
       }
       leaf cfm-slm-txed {
         type uint32;
         description "Number of valid synthetic loss measurement request sent";
       }
       leaf cfm-slm-rxed {
         type uint32;
         description "Number of valid synthetic loss measurement response received";
       }
       leaf cfm-slm-tx-lastpkt-rcv {
         type uint32;
         description "TxFC1 value in the last valid synthetic loss measurement response received";
       }
       leaf cfm-slm-rx-lastpkt-rcv {
         type uint32;
         description "TxFCb value in the last valid synthetic loss measurement response received";
       }
       leaf cfm-slm-last-measured-near-end-slm-loss-stats {
         type uint32;
         description "Near end synthetic loss";
       }
       leaf cfm-slm-last-measured-near-end-slm-loss-stats-percent {
         type string;
         description "Near end synthetic loss in percentage";
       }
       leaf cfm-slm-last-measured-far-end-slm-loss-stats {
         type uint32;
         description "Far end synthetic loss";
       }
       leaf cfm-slm-last-measured-far-end-slm-loss-stats-percent {
         type string;
         description "Far end synthetic loss in percentage";
       }
     }
     container cfm-iter-pm-current-dm-entry {
       leaf cfm-pm-mi-index {
         type uint32;
         description "Measurement Interval Index";
       }
       leaf cfm-pm-mi-suspect-status {
         type string;
         description "Status flag information for the field";
       }
       leaf cfm-pm-mi-start-time {
         type string;
         description "Measurement Interval start time";
       }
       leaf cfm-pm-mi-elapsed-time {
         type string;
         description "Measurement Interval elapsed time";
       }
       leaf cfm-pm-twoway-frame-delay-min {
         type uint32;
         description "Minimum two way frame delay";
       }
       leaf cfm-pm-twoway-frame-delay-max {
         type uint32;
         description "Maximum two way frame delay";
       }
       leaf cfm-pm-twoway-frame-delay-avg {
         type uint32;
         description "Average two way frame delay";
       }
       leaf cfm-pm-forward-frame-delay-min {
         type uint32;
         description "Minimum forward frame delay";
       }
       leaf cfm-pm-forward-frame-delay-max {
         type uint32;
         description "Maximum forward frame delay";
       }
       leaf cfm-pm-forward-frame-delay-avg {
         type uint32;
         description "Average forward frame delay";
       }
       leaf cfm-pm-backward-frame-delay-min {
         type uint32;
         description "Minimum backward frame delay";
       }
       leaf cfm-pm-backward-frame-delay-max {
         type uint32;
         description "Maximum backward frame delay";
       }
       leaf cfm-pm-backward-frame-delay-avg {
         type uint32;
         description "Average backward frame delay";
       }
       leaf cfm-pm-twoway-frame-delay-variation-min {
         type uint32;
         description "Minimum two way inter frame delay variation";
       }
       leaf cfm-pm-twoway-frame-delay-variation-max {
         type uint32;
         description "Maximum two way inter frame delay variation";
       }
       leaf cfm-pm-twoway-frame-delay-variation-avg {
         type uint32;
         description "Average two way inter frame delay variation";
       }
       leaf cfm-pm-forward-frame-delay-variation-min {
         type uint32;
         description "Minimum forward inter frame delay variation";
       }
       leaf cfm-pm-forward-frame-delay-variation-max {
         type uint32;
         description "Maximum forward inter frame delay variation";
       }
       leaf cfm-pm-forward-frame-delay-variation-avg {
         type uint32;
         description "Average forward inter frame delay variation";
       }
       leaf cfm-pm-backward-frame-delay-variation-min {
         type uint32;
         description "Minimum backward inter frame delay variation";
       }
       leaf cfm-pm-backward-frame-delay-variation-max {
         type uint32;
         description "Maximum backward inter frame delay variation";
       }
       leaf cfm-pm-backward-frame-delay-variation-avg {
         type uint32;
         description "Average backward inter frame delay variation";
       }
       leaf cfm-pm-twoway-frame-delay-range-max {
         type uint32;
         description "Maximum two way frame delay range";
       }
       leaf cfm-pm-twoway-frame-delay-range-avg {
         type uint32;
         description "Average two way frame delay range";
       }
       leaf cfm-pm-forward-frame-delay-range-max {
         type uint32;
         description "Maximum forward frame delay range";
       }
       leaf cfm-pm-forward-frame-delay-range-avg {
         type uint32;
         description "Average forward frame delay range";
       }
       leaf cfm-pm-backward-frame-delay-range-max {
         type uint32;
         description "Maximum backward frame delay range";
       }
       leaf cfm-pm-backward-frame-delay-range-avg {
         type uint32;
         description "Average backward frame delay range";
       }
       leaf cfm-pm-soam-frame-tx {
         type uint32;
         description "SOAM(LMM/SLM/DMM) frames transmitted for performance measurement";
       }
       leaf cfm-pm-soam-frame-rx {
         type uint32;
         description "SOAM(LMR/SLR/DMR) frames received for performance measurement";
       }
     }
     container cfm-iter-pm-current-dm-bin-info {
       leaf cfm-pm-mi-index {
         type uint32;
         description "Measurement Interval Index";
       }
       list cfm-iter-pm-current-dm-bin-entry {
         leaf cfm-pm-bin-type {
           type string;
           description "Delay measurement bin type";
         }
         list cfm-iter-pm-current-dm-bin-entry-counter {
           leaf cfm-pm-bin-lower-threshold {
             type string;
             description "Lower threshold of this bin";
           }
           leaf cfm-pm-bin-upper-threshold {
             type string;
             description "Upper threshold of this bin";
           }
           leaf cfm-pm-bin-counter {
             type uint32;
             description "Number of measurements counted in this bin";
           }
         }
       }
     }
     container cfm-iter-pm-lm-entry {
       leaf cfm-lmm-skipped-for-threshold-hit {
         type uint32;
         description "Number of loss measurement packets skipped due to threshold hit";
       }
       leaf cfm-lmm-skipped-for-threshold-hit-window {
         type uint32;
         description "Number of loss measurement packets skipped due to threshold hit window";
       }
       leaf cfm-lmr-out-of-seq {
         type uint32;
         description "Number of out of sequence loss measurement response message packets received";
       }
       leaf cfm-lmr-fc-mismatch {
         type uint32;
         description "Number of forwarding-class mismatch loss measurement response message packets received";
       }
       leaf cfm-last-measured-far-end-cir-loss-stats {
         type uint32;
         description "Last measured statistics of far-end loss using iterator";
       }
       leaf cfm-last-measured-near-end-cir-loss-stats {
         type uint32;
         description "Last measured statistics of near-end loss using iterator";
       }
     }
     container cfm-iter-pm-slm-entry {
       container brief {
         container cfm-iter-pm-slm-entry-misc-details {
           leaf cfm-slm-skipped-for-threshold-hit {
             type uint32;
             description "Number of synthetic loss measurement packets skipped due to threshold hit";
           }
           leaf cfm-slm-skipped-for-threshold-hit-window {
             type uint32;
             description "Number of synthetic loss measurement packets skipped due to threshold hit window";
           }
           leaf cfm-slr-out-of-seq {
             type uint32;
             description "Number of out of sequence synthetic loss measurement response message packets received";
           }
           leaf cfm-slm-sample-size {
             type uint32;
             description "Number of SLM pdus considered as a sample for loss measurement";
           }
           leaf cfm-slm-txed {
             type uint32;
             description "Number of valid synthetic loss measurement request sent";
           }
           leaf cfm-slm-rxed {
             type uint32;
             description "Number of valid synthetic loss measurement response received";
           }
           leaf cfm-slm-tx-lastpkt-rcv {
             type uint32;
             description "TxFC1 value in the last valid synthetic loss measurement response received";
           }
           leaf cfm-slm-rx-lastpkt-rcv {
             type uint32;
             description "TxFCb value in the last valid synthetic loss measurement response received";
           }
           leaf cfm-slm-last-measured-far-end-slm-loss-stats-percent {
             type string;
             description "Far end synthetic loss in percentage";
           }
           leaf cfm-slm-last-measured-near-end-slm-loss-stats-percent {
             type string;
             description "Near end synthetic loss in percentage";
           }
           leaf cfm-pm-mi-num-calculations {
             type uint32;
             description "Number of PM calculations done in the measurement interval";
           }
         }
       }
       container detail {
         container cfm-iter-pm-slm-entry-misc-details {
           leaf cfm-slm-skipped-for-threshold-hit {
             type uint32;
             description "Number of synthetic loss measurement packets skipped due to threshold hit";
           }
           leaf cfm-slm-skipped-for-threshold-hit-window {
             type uint32;
             description "Number of synthetic loss measurement packets skipped due to threshold hit window";
           }
           leaf cfm-slr-out-of-seq {
             type uint32;
             description "Number of out of sequence synthetic loss measurement response message packets received";
           }
           leaf cfm-slm-sample-size {
             type uint32;
             description "Number of SLM pdus considered as a sample for loss measurement";
           }
           leaf cfm-slm-txed {
             type uint32;
             description "Number of valid synthetic loss measurement request sent";
           }
           leaf cfm-slm-rxed {
             type uint32;
             description "Number of valid synthetic loss measurement response received";
           }
           leaf cfm-slm-tx-lastpkt-rcv {
             type uint32;
             description "TxFC1 value in the last valid synthetic loss measurement response received";
           }
           leaf cfm-slm-rx-lastpkt-rcv {
             type uint32;
             description "TxFCb value in the last valid synthetic loss measurement response received";
           }
           leaf cfm-slm-last-measured-far-end-slm-loss-stats-percent {
             type string;
             description "Far end synthetic loss in percentage";
           }
           leaf cfm-slm-last-measured-near-end-slm-loss-stats-percent {
             type string;
             description "Near end synthetic loss in percentage";
           }
           leaf cfm-pm-mi-num-calculations {
             type uint32;
             description "Number of PM calculations done in the measurement interval";
           }
         }
         container cfm-iter-pm-slm-entry-current-mi-details {
           leaf cfm-pm-mi-num-calculations {
             type uint32;
             description "Number of PM calculations done in the measurement interval";
           }
           leaf cfm-slm-smpl-num-calc {
             type uint32;
             description "Number of loss calculations done in the measurement interval";
           }
           leaf cfm-lm-fe-num-calc-considered {
             type uint32;
             description "Number of far end loss calculations considered for loss measurement";
           }
           leaf cfm-lm-ne-num-calc-considered {
             type uint32;
             description "Number of near end loss calculations considered for loss measurement";
           }
           leaf cfm-lm-ai-num-calc {
             type uint32;
             description "Number of availability inidicators evaluated in measurement interval";
           }
           leaf cfm-lm-num-con-ai {
             type uint32;
             description "Number consecutive availability indicators got evaluated in sliding window";
           }
           leaf cfm-lm-fe-hloss-bitmap {
             type uint32;
             description "Far end high loss bitmap. Each bit indicates a availability indicator";
           }
           leaf cfm-lm-ne-hloss-bitmap {
             type uint32;
             description "Near end high loss bitmap. Each bit indicates a availability indicator";
           }
           leaf cfm-slm-base-txfcf {
             type uint32;
             description "Base TxFCf value for a measurement period";
           }
           leaf cfm-slm-last-txfcf {
             type uint32;
             description "Last TxFCf value for a measurement period";
           }
           leaf cfm-slm-base-txfcb {
             type uint32;
             description "Base TxFCb value for a measurement period";
           }
           leaf cfm-slm-last-txfcb {
             type uint32;
             description "Last TxFCb value for a measurement period";
           }
           leaf cfm-slm-base-rxfcb {
             type uint32;
             description "Base RxFCb value for a measurement period";
           }
           leaf cfm-slm-last-rxfcb {
             type uint32;
             description "Last RxFCb value for a measurement period";
           }
           leaf cfm-slm-far-end-loss-carry {
             type uint32;
             description "Previous unaccounted Loss in farward diretion";
           }
           leaf cfm-slm-near-end-loss-carry {
             type uint32;
             description "Previous unaccounted Loss in backward diretion";
           }
         }
       }
       container extensive {
         container cfm-iter-pm-slm-entry-misc-details {
           leaf cfm-slm-skipped-for-threshold-hit {
             type uint32;
             description "Number of synthetic loss measurement packets skipped due to threshold hit";
           }
           leaf cfm-slm-skipped-for-threshold-hit-window {
             type uint32;
             description "Number of synthetic loss measurement packets skipped due to threshold hit window";
           }
           leaf cfm-slr-out-of-seq {
             type uint32;
             description "Number of out of sequence synthetic loss measurement response message packets received";
           }
           leaf cfm-slm-sample-size {
             type uint32;
             description "Number of SLM pdus considered as a sample for loss measurement";
           }
           leaf cfm-slm-txed {
             type uint32;
             description "Number of valid synthetic loss measurement request sent";
           }
           leaf cfm-slm-rxed {
             type uint32;
             description "Number of valid synthetic loss measurement response received";
           }
           leaf cfm-slm-tx-lastpkt-rcv {
             type uint32;
             description "TxFC1 value in the last valid synthetic loss measurement response received";
           }
           leaf cfm-slm-rx-lastpkt-rcv {
             type uint32;
             description "TxFCb value in the last valid synthetic loss measurement response received";
           }
           leaf cfm-slm-last-measured-far-end-slm-loss-stats-percent {
             type string;
             description "Far end synthetic loss in percentage";
           }
           leaf cfm-slm-last-measured-near-end-slm-loss-stats-percent {
             type string;
             description "Near end synthetic loss in percentage";
           }
           leaf cfm-pm-mi-num-calculations {
             type uint32;
             description "Number of PM calculations done in the measurement interval";
           }
         }
         container cfm-iter-pm-slm-entry-current-mi-details {
           leaf cfm-pm-mi-num-calculations {
             type uint32;
             description "Number of PM calculations done in the measurement interval";
           }
           leaf cfm-slm-smpl-num-calc {
             type uint32;
             description "Number of loss calculations done in the measurement interval";
           }
           leaf cfm-lm-fe-num-calc-considered {
             type uint32;
             description "Number of far end loss calculations considered for loss measurement";
           }
           leaf cfm-lm-ne-num-calc-considered {
             type uint32;
             description "Number of near end loss calculations considered for loss measurement";
           }
           leaf cfm-lm-ai-num-calc {
             type uint32;
             description "Number of availability inidicators evaluated in measurement interval";
           }
           leaf cfm-lm-num-con-ai {
             type uint32;
             description "Number consecutive availability indicators got evaluated in sliding window";
           }
           leaf cfm-lm-fe-hloss-bitmap {
             type uint32;
             description "Far end high loss bitmap. Each bit indicates a availability indicator";
           }
           leaf cfm-lm-ne-hloss-bitmap {
             type uint32;
             description "Near end high loss bitmap. Each bit indicates a availability indicator";
           }
           leaf cfm-slm-base-txfcf {
             type uint32;
             description "Base TxFCf value for a measurement period";
           }
           leaf cfm-slm-last-txfcf {
             type uint32;
             description "Last TxFCf value for a measurement period";
           }
           leaf cfm-slm-base-txfcb {
             type uint32;
             description "Base TxFCb value for a measurement period";
           }
           leaf cfm-slm-last-txfcb {
             type uint32;
             description "Last TxFCb value for a measurement period";
           }
           leaf cfm-slm-base-rxfcb {
             type uint32;
             description "Base RxFCb value for a measurement period";
           }
           leaf cfm-slm-last-rxfcb {
             type uint32;
             description "Last RxFCb value for a measurement period";
           }
           leaf cfm-slm-far-end-loss-carry {
             type uint32;
             description "Previous unaccounted Loss in farward diretion";
           }
           leaf cfm-slm-near-end-loss-carry {
             type uint32;
             description "Previous unaccounted Loss in backward diretion";
           }
         }
         container cfm-iter-pm-slm-entry-last-mi-details {
           leaf cfm-pm-mi-closed {
             type uint32;
             description "Last measurement interval calculations are closed";
           }
           leaf cfm-pm-mi-index {
             type uint32;
             description "Measurement Interval Index";
           }
           leaf cfm-pm-forward-min-flr-percentage {
             type uint32;
             description "Minimum frame loss ratio percentage at far end";
           }
           leaf cfm-pm-forward-max-flr-percentage {
             type uint32;
             description "Maximum frame loss ratio percentage at far end";
           }
           leaf cfm-pm-forward-avg-flr-percentage {
             type uint32;
             description "Average frame loss ratio percentage at far end";
           }
           leaf cfm-pm-backward-min-flr-percentage {
             type uint32;
             description "Minimum frame loss ratio percentage at far end";
           }
           leaf cfm-pm-backward-max-flr-percentage {
             type uint32;
             description "Maximum frame loss ratio percentage at far end";
           }
           leaf cfm-pm-backward-avg-flr-percentage {
             type uint32;
             description "Average frame loss ratio percentage at far end";
           }
         }
       }
     }
     container cfm-iter-pm-current-lm-entry {
       leaf cfm-pm-mi-index {
         type uint32;
         description "Measurement Interval Index";
       }
       leaf cfm-pm-mi-suspect-status {
         type string;
         description "Status flag information for the field";
       }
       leaf cfm-pm-mi-start-time {
         type string;
         description "Measurement Interval start time";
       }
       leaf cfm-pm-mi-elapsed-time {
         type string;
         description "Measurement Interval elapsed time";
       }
       leaf cfm-pm-soam-frame-tx {
         type uint32;
         description "SOAM(LMM/SLM/DMM) frames transmitted for performance measurement";
       }
       leaf cfm-pm-soam-frame-rx {
         type uint32;
         description "SOAM(LMR/SLR/DMR) frames received for performance measurement";
       }
       leaf cfm-pm-mi-num-calculations {
         type uint32;
         description "Number of PM calculations done in the measurement interval";
       }
       leaf cfm-pm-forward-frame-tx {
         type uint32;
         description "Frame transmitted by near end for performance measurement";
       }
       leaf cfm-pm-forward-frame-rx {
         type uint32;
         description "Frame received by far end for performance measurement";
       }
       leaf cfm-pm-backward-frame-tx {
         type uint32;
         description "Frame transmitted by far end for performance measurement";
       }
       leaf cfm-pm-backward-frame-rx {
         type uint32;
         description "Frame received by near end for performance measurement";
       }
       leaf cfm-pm-forward-frame-loss {
         type uint32;
         description "Frame loss at far end";
       }
       leaf cfm-pm-backward-frame-loss {
         type uint32;
         description "Frame loss at near end";
       }
       leaf cfm-pm-forward-min-flr-percentage {
         type uint32;
         description "Minimum frame loss ratio percentage at far end";
       }
       leaf cfm-pm-forward-min-flr-time {
         type string;
         description "Time when minimum frame loss ratio occured at far end";
       }
       leaf cfm-pm-forward-max-flr-percentage {
         type uint32;
         description "Maximum frame loss ratio percentage at far end";
       }
       leaf cfm-pm-forward-max-flr-time {
         type string;
         description "Time when maximum frame loss ratio occured at far end";
       }
       leaf cfm-pm-forward-avg-flr-percentage {
         type uint32;
         description "Average frame loss ratio percentage at far end";
       }
       leaf cfm-pm-backward-min-flr-percentage {
         type uint32;
         description "Minimum frame loss ratio percentage at far end";
       }
       leaf cfm-pm-backward-min-flr-time {
         type string;
         description "Time when minimum frame loss ratio occured at near end";
       }
       leaf cfm-pm-backward-max-flr-percentage {
         type uint32;
         description "Maximum frame loss ratio percentage at far end";
       }
       leaf cfm-pm-backward-max-flr-time {
         type string;
         description "Time when maximum frame loss ratio occured at near end";
       }
       leaf cfm-pm-backward-avg-flr-percentage {
         type uint32;
         description "Average frame loss ratio percentage at far end";
       }
     }
     container cfm-iter-pm-current-avail-entry {
       leaf cfm-pm-mi-index {
         type uint32;
         description "Measurement Interval Index";
       }
       leaf cfm-pm-mi-suspect-status {
         type string;
         description "Status flag information for the field";
       }
       leaf cfm-pm-mi-start-time {
         type string;
         description "Measurement Interval start time";
       }
       leaf cfm-pm-mi-elapsed-time {
         type string;
         description "Measurement Interval elapsed time";
       }
       leaf cfm-pm-mi-num-calculations {
         type uint32;
         description "Number of PM calculations done in the measurement interval";
       }
       leaf cfm-pm-forward-high-loss {
         type uint32;
         description "Accumulative number of high loss intervals at far end";
       }
       leaf cfm-pm-backward-high-loss {
         type uint32;
         description "Accumulative number of high loss intervals at near end";
       }
       leaf cfm-pm-forward-consecutive-high-loss {
         type uint32;
         description "Accumulative number of consecutive high loss intervals at far end";
       }
       leaf cfm-pm-backward-consecutive-high-loss {
         type uint32;
         description "Accumulative number of consecutive high loss intervals at near end";
       }
       leaf cfm-pm-forward-available {
         type uint32;
         description "Number of availabilty indicators at far end";
       }
       leaf cfm-pm-backward-available {
         type uint32;
         description "Number of availabilty indicators at near end";
       }
       leaf cfm-pm-forward-unavailable {
         type uint32;
         description "Number of un-availabilty indicators at far end";
       }
       leaf cfm-pm-backward-unavailable {
         type uint32;
         description "Number of un-availabilty indicators at near end";
       }
       leaf cfm-pm-forward-min-flr-percentage {
         type uint32;
         description "Minimum frame loss ratio percentage at far end";
       }
       leaf cfm-pm-forward-min-flr-time {
         type string;
         description "Time when minimum frame loss ratio occured at far end";
       }
       leaf cfm-pm-forward-max-flr-percentage {
         type uint32;
         description "Maximum frame loss ratio percentage at far end";
       }
       leaf cfm-pm-forward-max-flr-time {
         type string;
         description "Time when maximum frame loss ratio occured at far end";
       }
       leaf cfm-pm-forward-avg-flr-percentage {
         type uint32;
         description "Average frame loss ratio percentage at far end";
       }
       leaf cfm-pm-backward-min-flr-percentage {
         type uint32;
         description "Minimum frame loss ratio percentage at far end";
       }
       leaf cfm-pm-backward-min-flr-time {
         type string;
         description "Time when minimum frame loss ratio occured at near end";
       }
       leaf cfm-pm-backward-max-flr-percentage {
         type uint32;
         description "Maximum frame loss ratio percentage at far end";
       }
       leaf cfm-pm-backward-max-flr-time {
         type string;
         description "Time when maximum frame loss ratio occured at near end";
       }
       leaf cfm-pm-backward-avg-flr-percentage {
         type uint32;
         description "Average frame loss ratio percentage at far end";
       }
       leaf cfm-pm-forward-avail-status {
         type string;
         description "Last known availability status in forward direction";
       }
       leaf cfm-pm-backward-avail-status {
         type string;
         description "Last known availability status in backward direction";
       }
       leaf cfm-pm-forward-avail-transition-time {
         type string;
         description "Time of last transition between available and unavailable in forward direction";
       }
       leaf cfm-pm-backward-avail-transition-time {
         type string;
         description "Time of last transition between available and unavailable in backward direction";
       }
     }
     container cfm-flap-trap-statistics {
       leaf cfm-flap-trap-total-flr-flaps {
         type uint32;
         description "Total number of FLR flaps";
       }
       leaf cfm-flap-trap-total-acc-flr-flaps {
         type uint32;
         description "Total numer of accumulated FLR flaps";
       }
       leaf cfm-flap-trap-total-blr-flaps {
         type uint32;
         description "Total number of BLR flaps";
       }
       leaf cfm-flap-trap-total-acc-blr-flaps {
         type uint32;
         description "Total numer of accumulated BLR flaps";
       }
     }
   }
 }
 grouping cfm-mep-database-block {
   list cfm-entry {
     container cfm-interface-entry {
       leaf cfm-interface-name {
         type string;
         description "Name of interface";
       }
       leaf cfm-interface-status {
         type string;
         description "Status of 802.1ag on the interface";
       }
       leaf cfm-interface-link-status {
         type string;
         description "Operational status of this interface";
       }
     }
     container cfm-interface-sessions {
       list cfm-interface-session {
         container cfm-interface-session-identifier {
           leaf cfm-maintenance-domain-name {
             type string;
             description "Name of maintenance domain";
           }
           leaf cfm-maintenance-domain-name-format {
             type string;
             description "Format of maintenance domain name";
           }
           leaf cfm-level {
             type uint32;
             description "Maintenance-domain level";
           }
           leaf cfm-maintenance-domain-index {
             type uint32;
             description "Index of MD";
           }
           leaf cfm-maintenance-association-name {
             type string;
             description "Name of maintenance association";
           }
           leaf cfm-maintenance-association-name-format {
             type string;
             description "Format of maintenance association name";
           }
           leaf cfm-maintenance-association-index {
             type uint32;
             description "Index of MA";
           }
         }
         container cfm-interface-continuity-check {
           leaf cfm-continuity-check-status {
             type string;
             description "Continuity-check protocol status";
           }
           leaf cfm-continuity-check-interval {
             type uint32;
             description "Continuity-check message interval";
           }
           leaf cfm-continuity-check-loss-threshold {
             type uint32;
             description "Maximum number of continuity-check messages that the endpoint can fail to acknowledge before it is marked as inoperative";
           }
         }
         container cfm-interface-ethernet-ais {
           leaf cfm-ethernet-ais-status {
             type string;
             description "Ethernet AIS message status";
           }
           leaf cfm-ethernet-ais-interval {
             type uint32;
             description "Ethernet AIS message interval";
           }
           leaf cfm-ethernet-ais-level {
             type string;
             description "MD levels to which AIS messages are generated";
           }
           leaf cfm-ethernet-ais-priority {
             type uint32;
             description "VLAN priority used in the Ethernet AIS messages";
           }
         }
         container cfm-interface-local-mep-tlv-info {
           leaf cfm-local-mep-interface-status-tlv {
             type string;
             description "Interface status TLV information in the last transmitted CCM from local MEP";
           }
           leaf cfm-local-mep-port-status-tlv {
             type string;
             description "Port status TLV information in the last transmitted CCM from local MEP";
           }
           leaf cfm-system-chassis-mac-address {
             type string;
             description "MAC address of remote MEP";
           }
           leaf cfm-management-address {
             type string;
             description "CFM Management address";
           }
           leaf cfm-sendid-tlv {
             type string;
             description "CFM Sendid TLV Status";
           }
           container cfm-local-mep-connection-protection-tlv {
             description "Connection Protection TLV information in the last transmitted CCM from local MEP";
             leaf cfm-connection-protection-tlv-status {
               type string;
               description "To indicate the status of connection protection TLV in last transmitted CCM";
             }
             leaf cfm-connection-protection-tlv-prefer-me {
               type string;
               description "To indicate switchover to protect path";
             }
             leaf cfm-connection-protection-tlv-protection-in-use {
               type string;
               description "To indicate protection path in use";
             }
             leaf cfm-connection-protection-tlv-frr-flag {
               type string;
               description "To indicate FRR active for the working path";
             }
           }
           container cfm-local-mep-loss-threshold-tlv {
             description "Loss Threshold TLV information in the last transmitted CCM from Local MEP";
             leaf cfm-loss-threshold-tlv-value {
               type uint32;
               description "Indicate Loss Threshold value";
             }
             leaf cfm-loss-threshold-tlv-flag {
               type uint32;
               description "To indicate ISSU info";
             }
           }
         }
         container cfm-interface-local-mep-info {
           leaf cfm-local-mep-identifier {
             type uint32;
             description "Identifier of local MEP";
           }
           leaf cfm-local-mep-direction {
             type string;
             description "Direction in which continuity-check messages are sent";
           }
           leaf cfm-local-mep-mac-address {
             type string;
             description "MAC address of local MEP";
           }
           leaf cfm-local-mep-status {
             type string;
             description "Status of maintenance association endpoint";
           }
           container cfm-local-mep-connection-protection-tlv {
             description "Connection Protection TLV information in the last transmitted CCM from local MEP";
             leaf cfm-connection-protection-tlv-status {
               type string;
               description "To indicate the status of connection protection TLV in last transmitted CCM";
             }
             leaf cfm-connection-protection-tlv-prefer-me {
               type string;
               description "To indicate switchover to protect path";
             }
             leaf cfm-connection-protection-tlv-protection-in-use {
               type string;
               description "To indicate protection path in use";
             }
             leaf cfm-connection-protection-tlv-frr-flag {
               type string;
               description "To indicate FRR active for the working path";
             }
           }
           container cfm-local-mep-loss-threshold-tlv {
             description "Loss Threshold TLV information in the last transmitted CCM from Local MEP";
             leaf cfm-loss-threshold-tlv-value {
               type uint32;
               description "Indicate Loss Threshold value";
             }
             leaf cfm-loss-threshold-tlv-flag {
               type uint32;
               description "To indicate ISSU info";
             }
           }
         }
         container cfm-interface-local-mep-defects {
           leaf cfm-defect-remote-mep-no-ccm {
             type string;
             description "Indicates whether remote MEPs are receiving continuity-check messages (CCMs)";
           }
           leaf cfm-defect-error-ccm {
             type string;
             description "Indicates whether erroneous continuity-check messages (CCMs) were received";
           }
           leaf cfm-defect-cross-connect-ccm {
             type string;
             description "Indicates whether cross-connect continuity-check messages (CCMs) were received";
           }
           leaf cfm-defect-rdi-in-some-mep {
             type string;
             description "Indicates whether any remote MEPs are sending continuity-check messages (CCMs) with the RDI bit set";
           }
           leaf cfm-defect-mac-status {
             type string;
             description "Indicates whether any remote MEP's associated MAC is reporting an error status via the Port Status or Interface Status TLVs";
           }
           leaf cfm-defect-ais {
             type string;
             description "Indicates whether local MEP generated or received an AIS message";
           }
         }
         container cfm-interface-local-mep-statistics {
           leaf cfm-total-ccm-sent {
             type uint32;
             description "Number of continuity-check messages sent";
           }
           leaf cfm-out-of-sequence-ccm-received {
             type uint32;
             description "Number of continuity-check messages received out of sequence";
           }
           leaf cfm-lbm-sent {
             type uint32;
             description "Number of loopback messages sent";
           }
           leaf cfm-lbr-sent {
             type uint32;
             description "Number of loopback responses sent";
           }
           leaf cfm-lbr-received {
             type uint32;
             description "Number of valid in-order loopback responses received";
           }
           leaf cfm-lbr-received-out-of-order {
             type uint32;
             description "Number of valid out-of-order loopback responses received";
           }
           leaf cfm-lbr-bad-msdu {
             type uint32;
             description "Number of loopback responses received with corrupted data";
           }
           leaf cfm-total-ltm-sent {
             type uint32;
             description "Number of linktrace-request messages sent";
           }
           leaf cfm-total-ltm-received {
             type uint32;
             description "Number of linktrace-request messages received";
           }
           leaf cfm-total-ltr-sent {
             type uint32;
             description "Number of linktrace-response messages sent";
           }
           leaf cfm-total-ltr-received {
             type uint32;
             description "Number of linktrace-response messages received";
           }
           leaf cfm-next-ltm-sequence-number {
             type uint32;
             description "Sequence Number of the next LTM request";
           }
           leaf cfm-onedm-sent {
             type uint32;
             description "Number of one-way delay measurement request packets sent";
           }
           leaf cfm-onedm-received {
             type uint32;
             description "Number of valid one-way delay measurement request packets received";
           }
           leaf cfm-onedm-received-invalid {
             type uint32;
             description "Number of invalid one-way delay measurement request packets received";
           }
           leaf cfm-onedm-received-outofsync {
             type uint32;
             description "Number of out of sync one-way delay measurement request packets received";
           }
           leaf cfm-dmm-sent {
             type uint32;
             description "Number of two-way delay measurement request packets sent";
           }
           leaf cfm-dmm-received {
             type uint32;
             description "Number of valid two-way delay measurement request packets received";
           }
           leaf cfm-dmm-received-invalid {
             type uint32;
             description "Number of invalid two-way delay measurement request packets received";
           }
           leaf cfm-dmr-sent {
             type uint32;
             description "Number of two-way delay measurement response packets sent";
           }
           leaf cfm-dmr-received {
             type uint32;
             description "Number of valid two-way delay measurement response packets received";
           }
           leaf cfm-dmr-received-invalid {
             type uint32;
             description "Number of invalid two-way delay measurement response packets received";
           }
           leaf cfm-lmm-sent {
             type uint32;
             description "Number of loss measurement request message packets sent";
           }
           leaf cfm-lmm-received {
             type uint32;
             description "Number of valid loss measurement request message packets received";
           }
           leaf cfm-lmm-received-invalid {
             type uint32;
             description "Number of invalid loss measurement request message packets received";
           }
           leaf cfm-lmr-sent {
             type uint32;
             description "Number of loss measurement response packets sent";
           }
           leaf cfm-lmr-received {
             type uint32;
             description "Number of valid loss measurement response message packets received";
           }
           leaf cfm-lmr-received-invalid {
             type uint32;
             description "Number of invalid loss measurement response message packets received";
           }
           leaf cfm-slm-received {
             type uint32;
             description "Number of valid synthetic loss measurement request message packets received";
           }
           leaf cfm-slm-sent {
             type uint32;
             description "Number of synthetic loss measurement request message packets sent";
           }
           leaf cfm-slm-received-invalid {
             type uint32;
             description "Number of invalid synthetic loss measurement request message packets received";
           }
           leaf cfm-slr-sent {
             type uint32;
             description "Number of synthetic loss measurement response packets sent";
           }
           leaf cfm-slr-received {
             type uint32;
             description "Number of valid synthetic loss measurement response message packets received";
           }
           leaf cfm-slr-received-invalid {
             type uint32;
             description "Number of invalid synthetic loss measurement response message packets received";
           }
           leaf cfm-ais-sent {
             type uint32;
             description "Number of valid alarm indication signal messages generated";
           }
           leaf cfm-ais-received {
             type uint32;
             description "Number of valid alarm indication signal messages received";
           }
           leaf cfm-ais-received-invalid {
             type uint32;
             description "Number of invalid alarm indication signal messages received";
           }
         }
         container cfm-interface-remote-meps {
           container summary {
             leaf cfm-remote-mep-count {
               type uint32;
               description "Number of remote MEP configured or learnt";
             }
             list cfm-remote-mep {
               leaf cfm-remote-mep-identifier {
                 type uint32;
                 description "Identifier of remote MEP";
               }
               leaf cfm-remote-mep-mac-address {
                 type string;
                 description "MAC address of remote MEP";
               }
               leaf cfm-remote-mep-state {
                 type string;
                 description "State of the remote MEP";
               }
               leaf cfm-remote-mep-interface {
                 type string;
                 description "Interface on which this remote MEP has been discovered";
               }
               container cfm-remote-mep-connection-protection-tlv {
                 description "Connection Protection TLV information in the last recieved CCM from Remote MEP";
                 leaf cfm-connection-protection-tlv-prefer-me {
                   type string;
                   description "To indicate switchover to protect path";
                 }
                 leaf cfm-connection-protection-tlv-protection-in-use {
                   type string;
                   description "To indicate protection path in use";
                 }
                 leaf cfm-connection-protection-tlv-frr-flag {
                   type string;
                   description "To indicate FRR active for the working path";
                 }
               }
               container cfm-remote-mep-loss-threshold-tlv {
                 description "Loss Threshold TLV information in the last Last received CCM from remote MEP";
                 leaf cfm-loss-threshold-tlv-value {
                   type uint32;
                   description "Indicate Loss Threshold value";
                 }
                 leaf cfm-loss-threshold-tlv-flag {
                   type uint32;
                   description "To indicate ISSU info";
                 }
               }
             }
           }
         }
       }
     }
     container cfm-mep-database-session {
       leaf cfm-maintenance-domain-name {
         type string;
         description "Name of maintenance domain";
       }
       leaf cfm-maintenance-domain-name-format {
         type string;
         description "Format of maintenance domain name";
       }
       leaf cfm-level {
         type uint32;
         description "Maintenance-domain level";
       }
       leaf cfm-maintenance-association-name {
         type string;
         description "Name of maintenance association";
       }
       leaf cfm-maintenance-association-name-format {
         type string;
         description "Format of maintenance association name";
       }
     }
     container cfm-mep-database-continuity-check {
       leaf cfm-continuity-check-status {
         type string;
         description "Continuity-check protocol status";
       }
       leaf cfm-continuity-check-interval {
         type uint32;
         description "Continuity-check message interval";
       }
       leaf cfm-continuity-check-loss-threshold {
         type uint32;
         description "Maximum number of continuity-check messages that the endpoint can fail to acknowledge before it is marked as inoperative";
       }
     }
     container cfm-mep-database-ethernet-ais {
       leaf cfm-ethernet-ais-status {
         type string;
         description "Ethernet AIS message status";
       }
       leaf cfm-ethernet-ais-interval {
         type uint32;
         description "Ethernet AIS message interval";
       }
       leaf cfm-ethernet-ais-level {
         type string;
         description "MD levels to which AIS messages are generated";
       }
       leaf cfm-ethernet-ais-priority {
         type uint32;
         description "VLAN priority used in the Ethernet AIS messages";
       }
     }
     container cfm-mep-database-interface {
       leaf cfm-interface-name {
         type string;
         description "Name of interface";
       }
       leaf cfm-interface-status {
         type string;
         description "Status of 802.1ag on the interface";
       }
       leaf cfm-interface-link-status {
         type string;
         description "Operational status of this interface";
       }
     }
     container cfm-local-mep {
       leaf cfm-local-mep-identifier {
         type uint32;
         description "Identifier of local MEP";
       }
       leaf cfm-local-mep-direction {
         type string;
         description "Direction in which continuity-check messages are sent";
       }
       leaf cfm-local-mep-mac-address {
         type string;
         description "MAC address of local MEP";
       }
       leaf cfm-local-mep-auto-discovery {
         type string;
         description "Indicates whether auto-discovery of remote MEPs are enabled";
       }
       leaf cfm-local-mep-priority {
         type uint32;
         description "VLAN priority used in the continuity-check and link-trace messages";
       }
       leaf cfm-local-mep-status {
         type string;
         description "Status of maintenance association endpoint";
       }
       leaf cfm-local-mep-interface-status-tlv {
         type string;
         description "Interface status TLV information in the last transmitted CCM from local MEP";
       }
       leaf cfm-local-mep-port-status-tlv {
         type string;
         description "Port status TLV information in the last transmitted CCM from local MEP";
       }
       leaf cfm-system-chassis-mac-address {
         type string;
         description "MAC address of remote MEP";
       }
       leaf cfm-management-address {
         type string;
         description "CFM Management address";
       }
       leaf cfm-sendid-tlv {
         type string;
         description "CFM Sendid TLV Status";
       }
       container cfm-local-mep-connection-protection-tlv {
         description "Connection Protection TLV information in the last transmitted CCM from local MEP";
         leaf cfm-connection-protection-tlv-status {
           type string;
           description "To indicate the status of connection protection TLV in last transmitted CCM";
         }
         leaf cfm-connection-protection-tlv-prefer-me {
           type string;
           description "To indicate switchover to protect path";
         }
         leaf cfm-connection-protection-tlv-protection-in-use {
           type string;
           description "To indicate protection path in use";
         }
         leaf cfm-connection-protection-tlv-frr-flag {
           type string;
           description "To indicate FRR active for the working path";
         }
       }
       container cfm-local-mep-loss-threshold-tlv {
         description "Loss Threshold TLV information in the last transmitted CCM from Local MEP";
         leaf cfm-loss-threshold-tlv-value {
           type uint32;
           description "Indicate Loss Threshold value";
         }
         leaf cfm-loss-threshold-tlv-flag {
           type uint32;
           description "To indicate ISSU info";
         }
       }
     }
     container cfm-local-mep-defects {
       leaf cfm-defect-remote-mep-no-ccm {
         type string;
         description "Indicates whether remote MEPs are receiving continuity-check messages (CCMs)";
       }
       leaf cfm-defect-error-ccm {
         type string;
         description "Indicates whether erroneous continuity-check messages (CCMs) were received";
       }
       leaf cfm-defect-cross-connect-ccm {
         type string;
         description "Indicates whether cross-connect continuity-check messages (CCMs) were received";
       }
       leaf cfm-defect-rdi-in-some-mep {
         type string;
         description "Indicates whether any remote MEPs are sending continuity-check messages (CCMs) with the RDI bit set";
       }
       leaf cfm-defect-mac-status {
         type string;
         description "Indicates whether any remote MEP's associated MAC is reporting an error status via the Port Status or Interface Status TLVs";
       }
       leaf cfm-defect-ais {
         type string;
         description "Indicates whether local MEP generated or received an AIS message";
       }
     }
     container cfm-local-mep-statistics {
       leaf cfm-total-ccm-sent {
         type uint32;
         description "Number of continuity-check messages sent";
       }
       leaf cfm-out-of-sequence-ccm-received {
         type uint32;
         description "Number of continuity-check messages received out of sequence";
       }
       leaf cfm-lbm-sent {
         type uint32;
         description "Number of loopback messages sent";
       }
       leaf cfm-lbr-sent {
         type uint32;
         description "Number of loopback responses sent";
       }
       leaf cfm-lbr-received {
         type uint32;
         description "Number of valid in-order loopback responses received";
       }
       leaf cfm-lbr-received-out-of-order {
         type uint32;
         description "Number of valid out-of-order loopback responses received";
       }
       leaf cfm-lbr-bad-msdu {
         type uint32;
         description "Number of loopback responses received with corrupted data";
       }
       leaf cfm-total-ltm-sent {
         type uint32;
         description "Number of linktrace-request messages sent";
       }
       leaf cfm-total-ltm-received {
         type uint32;
         description "Number of linktrace-request messages received";
       }
       leaf cfm-total-ltr-sent {
         type uint32;
         description "Number of linktrace-response messages sent";
       }
       leaf cfm-total-ltr-received {
         type uint32;
         description "Number of linktrace-response messages received";
       }
       leaf cfm-next-ltm-sequence-number {
         type uint32;
         description "Sequence Number of the next LTM request";
       }
       leaf cfm-onedm-sent {
         type uint32;
         description "Number of one-way delay measurement request packets sent";
       }
       leaf cfm-onedm-received {
         type uint32;
         description "Number of valid one-way delay measurement request packets received";
       }
       leaf cfm-onedm-received-invalid {
         type uint32;
         description "Number of invalid one-way delay measurement request packets received";
       }
       leaf cfm-onedm-received-outofsync {
         type uint32;
         description "Number of out of sync one-way delay measurement request packets received";
       }
       leaf cfm-dmm-sent {
         type uint32;
         description "Number of two-way delay measurement request packets sent";
       }
       leaf cfm-dmm-received {
         type uint32;
         description "Number of valid two-way delay measurement request packets received";
       }
       leaf cfm-dmm-received-invalid {
         type uint32;
         description "Number of invalid two-way delay measurement request packets received";
       }
       leaf cfm-dmr-sent {
         type uint32;
         description "Number of two-way delay measurement response packets sent";
       }
       leaf cfm-dmr-received {
         type uint32;
         description "Number of valid two-way delay measurement response packets received";
       }
       leaf cfm-dmr-received-invalid {
         type uint32;
         description "Number of invalid two-way delay measurement response packets received";
       }
       leaf cfm-lmm-sent {
         type uint32;
         description "Number of loss measurement request message packets sent";
       }
       leaf cfm-lmm-received {
         type uint32;
         description "Number of valid loss measurement request message packets received";
       }
       leaf cfm-lmm-received-invalid {
         type uint32;
         description "Number of invalid loss measurement request message packets received";
       }
       leaf cfm-lmr-sent {
         type uint32;
         description "Number of loss measurement response packets sent";
       }
       leaf cfm-lmr-received {
         type uint32;
         description "Number of valid loss measurement response message packets received";
       }
       leaf cfm-lmr-received-invalid {
         type uint32;
         description "Number of invalid loss measurement response message packets received";
       }
       leaf cfm-slm-sent {
         type uint32;
         description "Number of synthetic loss measurement request message packets sent";
       }
       leaf cfm-slm-received {
         type uint32;
         description "Number of valid synthetic loss measurement request message packets received";
       }
       leaf cfm-slm-received-invalid {
         type uint32;
         description "Number of invalid synthetic loss measurement request message packets received";
       }
       leaf cfm-slr-sent {
         type uint32;
         description "Number of synthetic loss measurement response packets sent";
       }
       leaf cfm-slr-received {
         type uint32;
         description "Number of valid synthetic loss measurement response message packets received";
       }
       leaf cfm-slr-received-invalid {
         type uint32;
         description "Number of invalid synthetic loss measurement response message packets received";
       }
       leaf cfm-ais-sent {
         type uint32;
         description "Number of valid alarm indication signal messages generated";
       }
       leaf cfm-ais-received {
         type uint32;
         description "Number of valid alarm indication signal messages received";
       }
       leaf cfm-ais-received-invalid {
         type uint32;
         description "Number of invalid alarm indication signal messages received";
       }
     }
     container cfm-remote-meps {
       container brief {
         leaf cfm-remote-mep-count {
           type uint32;
           description "Number of remote MEP configured or learnt";
         }
         list cfm-remote-mep {
           leaf cfm-remote-mep-identifier {
             type uint32;
             description "Identifier of remote MEP";
           }
           leaf cfm-remote-mep-mac-address {
             type string;
             description "MAC address of remote MEP";
           }
           leaf cfm-remote-mep-state {
             type string;
             description "State of the remote MEP";
           }
           leaf cfm-remote-mep-interface {
             type string;
             description "Interface on which this remote MEP has been discovered";
           }
           container cfm-remote-mep-connection-protection-tlv {
             description "Connection Protection TLV information in the last recieved CCM from Remote MEP";
             leaf cfm-connection-protection-tlv-prefer-me {
               type string;
               description "To indicate switchover to protect path";
             }
             leaf cfm-connection-protection-tlv-protection-in-use {
               type string;
               description "To indicate protection path in use";
             }
             leaf cfm-connection-protection-tlv-frr-flag {
               type string;
               description "To indicate FRR active for the working path";
             }
           }
           container cfm-remote-mep-loss-threshold-tlv {
             description "Loss Threshold TLV information in the last Last received CCM from remote MEP";
             leaf cfm-loss-threshold-tlv-value {
               type uint32;
               description "Indicate Loss Threshold value";
             }
             leaf cfm-loss-threshold-tlv-flag {
               type uint32;
               description "To indicate ISSU info";
             }
           }
         }
       }
       container extensive {
         list cfm-remote-mep {
           leaf cfm-remote-mep-identifier {
             type uint32;
             description "Identifier of remote MEP";
           }
           leaf cfm-remote-mep-state {
             type string;
             description "State of the remote MEP";
           }
           leaf cfm-remote-mep-mac-address {
             type string;
             description "MAC address of remote MEP";
           }
           leaf cfm-remote-mep-type {
             type string;
             description "Type of the remote MEP";
           }
           leaf cfm-remote-mep-interface {
             type string;
             description "Interface on which this remote MEP has been discovered";
           }
           leaf cfm-remote-mep-last-flapped {
             type string;
             description "Last time when remote MEP flapped";
           }
           leaf cfm-remote-mep-last-dm-stats-cleared {
             type string;
             description "Last time when delay measurement statistics were cleared";
           }
           leaf cfm-remote-mep-last-lm-stats-cleared {
             type string;
             description "Last time when loss measurement statistics were cleared";
           }
           leaf cfm-remote-mep-last-slm-stats-cleared {
             type string;
             description "Last time when slm measurement statistics were cleared";
           }
           leaf cfm-remote-mep-continuity {
             type string;
             description "Display continuity measurement in percentage";
           }
           leaf cfm-remote-mep-admin-enable-time {
             type string;
             description "Total time in seconds for which remote mep is admin enabled";
           }
           leaf cfm-remote-mep-oper-down-time {
             type string;
             description "Total time in seconds for which remote mep was operationally down";
           }
           leaf cfm-remote-mep-loss-threshold {
             type uint32;
             description "Indicate Loss Threshold value used for this rmep";
           }
           leaf cfm-remote-mep-rdi {
             type string;
             description "Remote defect indication status of the remote MEP";
           }
           leaf cfm-remote-mep-port-status-tlv {
             type string;
             description "Port status TLV information in the received CCM from remote MEP";
           }
           leaf cfm-remote-mep-interface-status-tlv {
             type string;
             description "Interface status TLV information in the received CCM from remote MEP";
           }
           leaf cfm-remote-mep-chassis-mac-address {
             type string;
             description "MAC address of remote MEP";
           }
           leaf cfm-remote-management-address {
             type string;
             description "CFM remote management address";
           }
           leaf cfm-remote-sendid-tlv {
             type string;
             description "CFM Remote Sendid TLV Status";
           }
           leaf cfm-remote-sendid-chassis-subtype-tlv {
             type string;
             description "CFM Remote Sendid TLV Status";
           }
           container cfm-remote-mep-connection-protection-tlv {
             description "Connection Protection TLV information in the last recieved CCM from Remote MEP";
             leaf cfm-connection-protection-tlv-prefer-me {
               type string;
               description "To indicate switchover to protect path";
             }
             leaf cfm-connection-protection-tlv-protection-in-use {
               type string;
               description "To indicate protection path in use";
             }
             leaf cfm-connection-protection-tlv-frr-flag {
               type string;
               description "To indicate FRR active for the working path";
             }
           }
           container cfm-remote-mep-loss-threshold-tlv {
             description "Loss Threshold TLV information in the last Last received CCM from remote MEP";
             leaf cfm-loss-threshold-tlv-value {
               type uint32;
               description "Indicate Loss Threshold value";
             }
             leaf cfm-loss-threshold-tlv-flag {
               type uint32;
               description "To indicate ISSU info";
             }
           }
         }
         container cfm-remote-mep-ap {
           leaf cfm-action-profile-name {
             type string;
             description "Name of the action profile";
           }
           leaf cfm-ap-last-event {
             type string;
             description "Displays the last occurred event";
           }
           leaf cfm-ap-action-name {
             type string;
             description "Shows the action taken";
           }
           leaf cfm-ap-action-time {
             type string;
             description "Shows the time at which action was taken";
           }
           leaf cfm-ap-last-event-cleared-time {
             type string;
             description "Shows the time at which last event was cleared";
           }
         }
       }
     }
     container cfm-cross-connect-sessions {
       leaf cfm-cross-connect-session-count {
         type uint32;
         description "Number of cross connect CCM sessions";
       }
       list cfm-cross-connect-session {
         leaf cfm-session-defect-type {
           type string;
           description "CCM session defect type";
         }
         leaf cfm-session-defect-description {
           type string;
           description "CCM session defect description";
         }
         leaf cfm-maintenance-domain-name {
           type string;
           description "Name of maintenance domain";
         }
         leaf cfm-maintenance-domain-name-format {
           type string;
           description "Format of maintenance domain name";
         }
         leaf cfm-level {
           type uint32;
           description "Maintenance-domain level";
         }
         leaf cfm-maintenance-association-name {
           type string;
           description "Name of maintenance association";
         }
         leaf cfm-maintenance-association-name-format {
           type string;
           description "Format of maintenance association name";
         }
         leaf cfm-mep-identifier {
           type uint32;
           description "Identifier of MEP";
         }
         leaf cfm-continuity-check-interval {
           type uint32;
           description "Continuity-check message interval";
         }
       }
     }
     container cfm-error-sessions {
       leaf cfm-error-session-count {
         type uint32;
         description "Number of error CCM sessions";
       }
       list cfm-error-session {
         leaf cfm-session-defect-type {
           type string;
           description "CCM session defect type";
         }
         leaf cfm-session-defect-description {
           type string;
           description "CCM session defect description";
         }
         leaf cfm-maintenance-domain-name {
           type string;
           description "Name of maintenance domain";
         }
         leaf cfm-maintenance-domain-name-format {
           type string;
           description "Format of maintenance domain name";
         }
         leaf cfm-level {
           type uint32;
           description "Maintenance-domain level";
         }
         leaf cfm-maintenance-association-name {
           type string;
           description "Name of maintenance association";
         }
         leaf cfm-maintenance-association-name-format {
           type string;
           description "Format of maintenance association name";
         }
         leaf cfm-mep-identifier {
           type uint32;
           description "Identifier of MEP";
         }
         leaf cfm-continuity-check-interval {
           type uint32;
           description "Continuity-check message interval";
         }
       }
     }
     container cfm-mep-statistics-mep-summary {
       leaf cfm-local-mep-identifier {
         type uint32;
         description "Identifier of local MEP";
       }
       leaf cfm-local-mep-mac-address {
         type string;
         description "MAC address of local MEP";
       }
       leaf cfm-remote-mep-count {
         type uint32;
         description "Number of remote MEP configured or learnt";
       }
     }
     container cfm-local-mep-packet-statistics {
       leaf cfm-total-ccm-sent {
         type uint32;
         description "Number of continuity-check messages sent";
       }
       leaf cfm-out-of-sequence-ccm-received {
         type uint32;
         description "Number of continuity-check messages received out of sequence";
       }
       leaf cfm-lbm-sent {
         type uint32;
         description "Number of loopback messages sent";
       }
       leaf cfm-lbr-sent {
         type uint32;
         description "Number of loopback responses sent";
       }
       leaf cfm-lbr-received {
         type uint32;
         description "Number of valid in-order loopback responses received";
       }
       leaf cfm-lbr-received-out-of-order {
         type uint32;
         description "Number of valid out-of-order loopback responses received";
       }
       leaf cfm-lbr-bad-msdu {
         type uint32;
         description "Number of loopback responses received with corrupted data";
       }
       leaf cfm-total-ltm-sent {
         type uint32;
         description "Number of linktrace-request messages sent";
       }
       leaf cfm-total-ltm-received {
         type uint32;
         description "Number of linktrace-request messages received";
       }
       leaf cfm-total-ltr-sent {
         type uint32;
         description "Number of linktrace-response messages sent";
       }
       leaf cfm-total-ltr-received {
         type uint32;
         description "Number of linktrace-response messages received";
       }
       leaf cfm-next-ltm-sequence-number {
         type uint32;
         description "Sequence Number of the next LTM request";
       }
       leaf cfm-onedm-sent {
         type uint32;
         description "Number of one-way delay measurement request packets sent";
       }
       leaf cfm-onedm-received {
         type uint32;
         description "Number of valid one-way delay measurement request packets received";
       }
       leaf cfm-onedm-received-invalid {
         type uint32;
         description "Number of invalid one-way delay measurement request packets received";
       }
       leaf cfm-onedm-received-outofsync {
         type uint32;
         description "Number of out of sync one-way delay measurement request packets received";
       }
       leaf cfm-dmm-sent {
         type uint32;
         description "Number of two-way delay measurement request packets sent";
       }
       leaf cfm-dmm-received {
         type uint32;
         description "Number of valid two-way delay measurement request packets received";
       }
       leaf cfm-dmm-received-invalid {
         type uint32;
         description "Number of invalid two-way delay measurement request packets received";
       }
       leaf cfm-dmr-sent {
         type uint32;
         description "Number of two-way delay measurement response packets sent";
       }
       leaf cfm-dmr-received {
         type uint32;
         description "Number of valid two-way delay measurement response packets received";
       }
       leaf cfm-dmr-received-invalid {
         type uint32;
         description "Number of invalid two-way delay measurement response packets received";
       }
       leaf cfm-lmm-sent {
         type uint32;
         description "Number of loss measurement request message packets sent";
       }
       leaf cfm-lmm-received {
         type uint32;
         description "Number of valid loss measurement request message packets received";
       }
       leaf cfm-lmm-received-invalid {
         type uint32;
         description "Number of invalid loss measurement request message packets received";
       }
       leaf cfm-lmr-sent {
         type uint32;
         description "Number of loss measurement response packets sent";
       }
       leaf cfm-lmr-received {
         type uint32;
         description "Number of valid loss measurement response message packets received";
       }
       leaf cfm-lmr-received-invalid {
         type uint32;
         description "Number of invalid loss measurement response message packets received";
       }
       leaf cfm-slm-sent {
         type uint32;
         description "Number of synthetic loss measurement request message packets sent";
       }
       leaf cfm-slm-received {
         type uint32;
         description "Number of valid synthetic loss measurement request message packets received";
       }
       leaf cfm-slm-received-invalid {
         type uint32;
         description "Number of invalid synthetic loss measurement request message packets received";
       }
       leaf cfm-slr-sent {
         type uint32;
         description "Number of synthetic loss measurement response packets sent";
       }
       leaf cfm-slr-received {
         type uint32;
         description "Number of valid synthetic loss measurement response message packets received";
       }
       leaf cfm-slr-received-invalid {
         type uint32;
         description "Number of invalid synthetic loss measurement response message packets received";
       }
       leaf cfm-ais-sent {
         type uint32;
         description "Number of valid alarm indication signal messages generated";
       }
       leaf cfm-ais-received {
         type uint32;
         description "Number of valid alarm indication signal messages received";
       }
       leaf cfm-ais-received-invalid {
         type uint32;
         description "Number of invalid alarm indication signal messages received";
       }
     }
     container cfm-remote-mep-brief-summary {
       leaf cfm-remote-mep-identifier {
         type uint32;
         description "Identifier of remote MEP";
       }
       leaf cfm-remote-mep-mac-address {
         type string;
         description "MAC address of remote MEP";
       }
     }
     container cfm-ethdm-delay-entry {
       leaf cfm-ethdm-delay-entry-index {
         type uint32;
         description "Delay entry index.";
       }
       leaf cfm-ethdm-oneway-delay {
         type uint32;
         description "One-way delay measured using ETH-DM.";
       }
       leaf cfm-ethdm-twoway-delay {
         type uint32;
         description "Two-way delay measured using ETH-DM.";
       }
     }
     container cfm-ethdm-oneway-delay-summary {
       leaf cfm-ethdm-average-oneway-delay {
         type uint32;
         description "Average one-way delay measured using ETH-DM.";
       }
       leaf cfm-ethdm-average-oneway-delay-variation {
         type uint32;
         description "Average variation of one-way delay between two samples of measurement.";
       }
       leaf cfm-ethdm-bestcase-oneway-delay {
         type uint32;
         description "Bestcase one-way delay measured using ETH-DM.";
       }
       leaf cfm-ethdm-worstcase-oneway-delay {
         type uint32;
         description "Worstcase one-way delay measured using ETH-DM.";
       }
     }
     container cfm-ethdm-twoway-delay-summary {
       leaf cfm-ethdm-average-twoway-delay {
         type uint32;
         description "Average two-way delay measured using ETH-DM.";
       }
       leaf cfm-ethdm-average-twoway-delay-variation {
         type uint32;
         description "Average variation of two-way delay between two samples of measurement.";
       }
       leaf cfm-ethdm-bestcase-twoway-delay {
         type uint32;
         description "Bestcase two-way delay measured using ETH-DM.";
       }
       leaf cfm-ethdm-worstcase-twoway-delay {
         type uint32;
         description "Worstcase two-way delay measured using ETH-DM.";
       }
     }
     container cfm-ethlm-cir-loss-entry {
       leaf cfm-ethlm-cir-loss-entry-index {
         type uint32;
         description "CIR Loss entry index.";
       }
       leaf cfm-ethlm-near-end-cir-frame-loss {
         type uint32;
         description "Near-end loss measured using ETH-LM.";
       }
       leaf cfm-ethlm-far-end-total-cir-tx {
         type uint32;
         description "Far-end total tx for current ETH-LM sample.";
       }
       leaf cfm-ethlm-near-end-total-cir-rx {
         type uint32;
         description "Near-end total rx for current ETH-LM sample.";
       }
       leaf cfm-ethlm-far-end-cir-frame-loss {
         type uint32;
         description "Far-end loss measured using ETH-LM.";
       }
       leaf cfm-ethlm-near-end-total-cir-tx {
         type uint32;
         description "Near-end total tx for current ETH-LM sample.";
       }
       leaf cfm-ethlm-far-end-total-cir-rx {
         type uint32;
         description "Far-end total rx for current ETH-LM sample.";
       }
     }
     container cfm-ethlm-eir-loss-entry {
       leaf cfm-ethlm-eir-loss-entry-index {
         type uint32;
         description "EIR Loss entry index.";
       }
       leaf cfm-ethlm-near-end-eir-frame-loss {
         type uint32;
         description "Near-end loss measured using ETH-LM.";
       }
       leaf cfm-ethlm-far-end-total-eir-tx {
         type uint32;
         description "Far-end total tx for current ETH-LM sample.";
       }
       leaf cfm-ethlm-near-end-total-eir-rx {
         type uint32;
         description "Near-end total rx for current ETH-LM sample.";
       }
       leaf cfm-ethlm-far-end-eir-frame-loss {
         type uint32;
         description "Far-end loss measured using ETH-LM.";
       }
       leaf cfm-ethlm-near-end-total-eir-tx {
         type uint32;
         description "Near-end total tx for current ETH-LM sample.";
       }
       leaf cfm-ethlm-far-end-total-eir-rx {
         type uint32;
         description "Far-end total rx for current ETH-LM sample.";
       }
     }
     container cfm-ethlm-cir-loss-summary {
       leaf cfm-ethlm-total-far-end-cir-tx {
         type uint32;
         description "Total far-end Tx measured using ETH-LM.";
       }
       leaf cfm-ethlm-total-near-end-cir-rx {
         type uint32;
         description "Total near-end Rx measured using ETH-LM.";
       }
       leaf cfm-ethlm-total-near-end-cir-loss {
         type uint32;
         description "Total near-end loss measured using ETH-LM.";
       }
       leaf cfm-ethlm-total-near-end-cir-loss-ratio {
         type string;
         description "Total near-end loss-ratio measured using ETH-LM.";
       }
       leaf cfm-ethlm-total-near-end-cir-tx {
         type uint32;
         description "Total near-end Tx measured using ETH-LM.";
       }
       leaf cfm-ethlm-total-far-end-cir-rx {
         type uint32;
         description "Total far-end Rx measured using ETH-LM.";
       }
       leaf cfm-ethlm-total-far-end-cir-loss {
         type uint32;
         description "Total far-end loss measured using ETH-LM.";
       }
       leaf cfm-ethlm-total-far-end-cir-loss-ratio {
         type string;
         description "Total far-end loss-ratio measured using ETH-LM.";
       }
       leaf cfm-ethlm-average-near-end-cir-loss {
         type string;
         description "Average near-end loss measured using ETH-LM.";
       }
       leaf cfm-ethlm-average-near-end-cir-loss-ratio {
         type string;
         description "Average near-end loss ratio measured using ETH-LM.";
       }
       leaf cfm-ethlm-average-far-end-cir-loss {
         type string;
         description "Average far-end loss measured using ETH-LM.";
       }
       leaf cfm-ethlm-average-far-end-cir-loss-ratio {
         type string;
         description "Average far-end loss ratio measured using ETH-LM.";
       }
       leaf cfm-ethlm-near-end-best-case-cir-loss {
         type string;
         description "Best case near-end loss measured using ETH-LM.";
       }
       leaf cfm-ethlm-near-end-best-case-cir-loss-ratio {
         type string;
         description "Best case near-end loss ratio measured using ETH-LM.";
       }
       leaf cfm-ethlm-near-end-worst-case-cir-loss {
         type string;
         description "Worst case near-end loss measured using ETH-LM.";
       }
       leaf cfm-ethlm-near-end-worst-case-cir-loss-ratio {
         type string;
         description "Worst case near-end loss ratio measured using ETH-LM.";
       }
       leaf cfm-ethlm-far-end-best-case-cir-loss {
         type string;
         description "Best case far-end loss measured using ETH-LM.";
       }
       leaf cfm-ethlm-far-end-best-case-cir-loss-ratio {
         type string;
         description "Best case far-end loss ratio measured using ETH-LM.";
       }
       leaf cfm-ethlm-far-end-worst-case-cir-loss {
         type string;
         description "Worst case far-end loss measured using ETH-LM.";
       }
       leaf cfm-ethlm-far-end-worst-case-cir-loss-ratio {
         type string;
         description "Worst case far-end loss ratio measured using ETH-LM.";
       }
     }
     container cfm-ethlm-eir-loss-summary {
       leaf cfm-ethlm-total-far-end-eir-tx {
         type uint32;
         description "Total far-end Tx measured using ETH-LM.";
       }
       leaf cfm-ethlm-total-near-end-eir-rx {
         type uint32;
         description "Total near-end Rx measured using ETH-LM.";
       }
       leaf cfm-ethlm-total-near-end-eir-loss {
         type uint32;
         description "Total near-end loss measured using ETH-LM.";
       }
       leaf cfm-ethlm-total-near-end-eir-loss-ratio {
         type string;
         description "Total near-end loss-ratio measured using ETH-LM.";
       }
       leaf cfm-ethlm-total-near-end-eir-tx {
         type uint32;
         description "Total near-end Tx measured using ETH-LM.";
       }
       leaf cfm-ethlm-total-far-end-eir-rx {
         type uint32;
         description "Total far-end Rx measured using ETH-LM.";
       }
       leaf cfm-ethlm-total-far-end-eir-loss {
         type uint32;
         description "Total far-end loss measured using ETH-LM.";
       }
       leaf cfm-ethlm-total-far-end-eir-loss-ratio {
         type string;
         description "Total far-end loss-ratio measured using ETH-LM.";
       }
       leaf cfm-ethlm-average-near-end-eir-loss {
         type string;
         description "Average near-end loss measured using ETH-LM.";
       }
       leaf cfm-ethlm-average-near-end-eir-loss-ratio {
         type string;
         description "Average near-end loss ratio measured using ETH-LM.";
       }
       leaf cfm-ethlm-average-far-end-eir-loss {
         type string;
         description "Average far-end loss measured using ETH-LM.";
       }
       leaf cfm-ethlm-average-far-end-eir-loss-ratio {
         type string;
         description "Average far-end loss ratio measured using ETH-LM.";
       }
       leaf cfm-ethlm-near-end-best-case-eir-loss {
         type string;
         description "Best case near-end loss measured using ETH-LM.";
       }
       leaf cfm-ethlm-near-end-best-case-eir-loss-ratio {
         type string;
         description "Best case near-end loss ratio measured using ETH-LM.";
       }
       leaf cfm-ethlm-near-end-worst-case-eir-loss {
         type string;
         description "Worst case near-end loss measured using ETH-LM.";
       }
       leaf cfm-ethlm-near-end-worst-case-eir-loss-ratio {
         type string;
         description "Worst case near-end loss ratio measured using ETH-LM.";
       }
       leaf cfm-ethlm-far-end-best-case-eir-loss {
         type string;
         description "Best case far-end loss measured using ETH-LM.";
       }
       leaf cfm-ethlm-far-end-best-case-eir-loss-ratio {
         type string;
         description "Best case far-end loss ratio measured using ETH-LM.";
       }
       leaf cfm-ethlm-far-end-worst-case-eir-loss {
         type string;
         description "Worst case far-end loss measured using ETH-LM.";
       }
       leaf cfm-ethlm-far-end-worst-case-eir-loss-ratio {
         type string;
         description "Worst case far-end loss ratio measured using ETH-LM.";
       }
     }
     container cfm-stats-ethslm-entry {
       leaf cfm-slm-txed {
         type uint32;
         description "Number of valid synthetic loss measurement request sent";
       }
       leaf cfm-slm-rxed {
         type uint32;
         description "Number of valid synthetic loss measurement response received";
       }
       leaf cfm-slm-tx-lastpkt-rcv {
         type uint32;
         description "TxFC1 value in the last valid synthetic loss measurement response received";
       }
       leaf cfm-slm-rx-lastpkt-rcv {
         type uint32;
         description "TxFCb value in the last valid synthetic loss measurement response received";
       }
       leaf cfm-slm-last-measured-near-end-slm-loss-stats {
         type uint32;
         description "Near end synthetic loss";
       }
       leaf cfm-slm-last-measured-near-end-slm-loss-stats-percent {
         type string;
         description "Near end synthetic loss in percentage";
       }
       leaf cfm-slm-last-measured-far-end-slm-loss-stats {
         type uint32;
         description "Far end synthetic loss";
       }
       leaf cfm-slm-last-measured-far-end-slm-loss-stats-percent {
         type string;
         description "Far end synthetic loss in percentage";
       }
     }
     container cfm-iter-mep-summary {
       leaf cfm-iterator-error-status {
         type string;
         description "Error reason for the iterator";
       }
       leaf cfm-maintenance-domain-name {
         type string;
         description "Name of maintenance domain";
       }
       leaf cfm-level {
         type uint32;
         description "Maintenance-domain level";
       }
       leaf cfm-maintenance-association-name {
         type string;
         description "Name of maintenance association";
       }
       leaf cfm-local-mep-identifier {
         type uint32;
         description "Identifier of local MEP";
       }
       leaf cfm-remote-mep-identifier {
         type uint32;
         description "Identifier of remote MEP";
       }
       leaf cfm-remote-mep-mac-address {
         type string;
         description "MAC address of remote MEP";
       }
     }
     container cfm-iter-info {
       leaf cfm-iterator-name {
         type string;
         description "Name of iterator";
       }
       leaf cfm-iterator-identifier {
         type uint32;
         description "Identifier of iterator";
       }
       leaf cfm-iterator-cycle-time {
         type uint32;
         description "Cycle time of iterator";
       }
       leaf cfm-iteration-period {
         type uint32;
         description "Period of iteration";
       }
       leaf cfm-iterator-status {
         type string;
         description "State of the iterator";
       }
       leaf cfm-iterator-forever-status {
         type string;
         description "For-ever running status of the iterator";
       }
       leaf cfm-iteration-current-count {
         type uint32;
         description "Current iteration count of iterator";
       }
       leaf cfm-iteration-remaining-count {
         type uint32;
         description "Remaining iteration count of iterator";
       }
       leaf cfm-iterator-counter-reset-time {
         type string;
         description "Shows the time at which iterator counters are resetted";
       }
       leaf cfm-iterator-counter-reset-reason {
         type string;
         description "Counter reset reason of iterator";
       }
     }
     container cfm-iter-ethdm-entry {
       leaf cfm-delay-weight {
         type uint32;
         description "Delay calculation weight of iterator";
       }
       leaf cfm-delay-variation-weight {
         type uint32;
         description "Delay variation calculation weight of iterator";
       }
       leaf cfm-dmm-sent {
         type uint32;
         description "Number of two-way delay measurement request packets sent";
       }
       leaf cfm-dmm-skipped-for-threshold-hit {
         type uint32;
         description "Number of delay measurement packets skipped due to threshold hit";
       }
       leaf cfm-dmm-skipped-for-threshold-hit-window {
         type uint32;
         description "Number of delay measurement packets skipped due to threshold hit window";
       }
       leaf cfm-dmr-received {
         type uint32;
         description "Number of valid two-way delay measurement response packets received";
       }
       leaf cfm-dmr-out-of-sequence {
         type uint32;
         description "Number of out of sequence delay measurement response packets received";
       }
       leaf cfm-dmr-fc-mismatch {
         type uint32;
         description "Number of forwarding-class mismatch delay measurement response packets received";
       }
       leaf cfm-dmr-invalid-time-stamp {
         type uint32;
         description "Number of invalid time stamps delay measurement response packets received";
       }
       leaf cfm-average-twoway-delay {
         type uint64;
         description "Average two-way delay measured using iterator";
       }
       leaf cfm-average-twoway-delay-variation {
         type uint64;
         description "Average variation of two-way delay measured using iterator";
       }
       leaf cfm-average-oneway-fwd-delay-variation {
         type uint64;
         description "Average variation of one-way forward delay measured using iterator";
       }
       leaf cfm-average-oneway-bkwd-delay-variation {
         type uint64;
         description "Average variation of one-way backward delay measured using iterator";
       }
       leaf cfm-weighted-average-twoway-delay {
         type uint64;
         description "Weighted average two-way delay measured using iterator";
       }
       leaf cfm-weighted-average-twoway-delay-variation {
         type uint64;
         description "Weighted average variation of two-way delay measured using iterator";
       }
       leaf cfm-weighted-average-oneway-fwd-delay-variation {
         type uint64;
         description "Weighted average variation of one-way forward delay measured using iterator";
       }
       leaf cfm-weighted-average-oneway-bkwd-delay-variation {
         type uint64;
         description "Weighted average variation of one-way backward delay measured using iterator";
       }
       leaf cfm-bestcase-twoway-delay {
         type uint64;
         description "Minimum of two-way delay measured using iterator";
       }
       leaf cfm-worstcase-twoway-delay {
         type uint64;
         description "Maximum of two-way delay measured using iterator";
       }
       leaf cfm-bestcase-oneway-fwd-delay {
         type uint64;
         description "Minimum of one-way forward delay measured using iterator";
       }
       leaf cfm-worstcase-oneway-fwd-delay {
         type uint64;
         description "Maximum of one-way forward delay measured using iterator";
       }
       leaf cfm-bestcase-oneway-bkwd-delay {
         type uint64;
         description "Mininmum of one-way backward delay measured using iterator";
       }
       leaf cfm-worstcase-oneway-bkwd-delay {
         type uint64;
         description "Maximum of one-way backward delay measured using iterator";
       }
       leaf cfm-weighted-average-bestcase-twoway-delay {
         type uint64;
         description "Weighted average minimum two-way delay measured using iterator";
       }
       leaf cfm-weighted-average-worstcase-twoway-delay {
         type uint64;
         description "Weighted average maximum two-way delay measured using iterator";
       }
       leaf cfm-weighted-average-bestcase-oneway-fwd-delay {
         type uint64;
         description "Weighted average minimum of one-way forward delay measured using iterator";
       }
       leaf cfm-weighted-average-worstcase-oneway-fwd-delay {
         type uint64;
         description "Weighted average maximum of one-way forward delay measured using iterator";
       }
       leaf cfm-weighted-average-bestcase-oneway-bkwd-delay {
         type uint64;
         description "Weighted average minimum of one-way backward delay measured using iterator";
       }
       leaf cfm-weighted-average-worstcase-oneway-bkwd-delay {
         type uint64;
         description "Weighted average maximum of one-way backward delay measured using iterator";
       }
     }
     container cfm-iter-ethlm-entry {
       leaf cfm-lmm-sent {
         type uint32;
         description "Number of loss measurement request message packets sent";
       }
       leaf cfm-lmm-skipped-for-threshold-hit {
         type uint32;
         description "Number of loss measurement packets skipped due to threshold hit";
       }
       leaf cfm-lmm-skipped-for-threshold-hit-window {
         type uint32;
         description "Number of loss measurement packets skipped due to threshold hit window";
       }
       leaf cfm-lmr-received {
         type uint32;
         description "Number of valid loss measurement response message packets received";
       }
       leaf cfm-lmr-out-of-seq {
         type uint32;
         description "Number of out of sequence loss measurement response message packets received";
       }
       leaf cfm-lmr-fc-mismatch {
         type uint32;
         description "Number of forwarding-class mismatch loss measurement response message packets received";
       }
       leaf cfm-accu-tx-near-end-cir-loss-stats {
         type uint32;
         description "Accumulated transmit statistics of near-end loss measured using iterator";
       }
       leaf cfm-accu-tx-far-end-cir-loss-stats {
         type uint32;
         description "Accumulated transmit statistics of far-end loss measured using iterator";
       }
       leaf cfm-accu-tx-near-end-eir-loss-stats {
         type uint32;
         description "Accumulated transmit statistics of near-end loss measured using iterator";
       }
       leaf cfm-accu-tx-far-end-eir-loss-stats {
         type uint32;
         description "Accumulated transmit statistics of far-end loss measured using iterator";
       }
       leaf cfm-accu-rx-near-end-cir-loss-stats {
         type uint32;
         description "Accumulated recieve statistics of near-end loss measured using iterator";
       }
       leaf cfm-accu-rx-far-end-cir-loss-stats {
         type uint32;
         description "Accumulated receive statistics of far-end loss measured using iterator";
       }
       leaf cfm-accu-rx-near-end-eir-loss-stats {
         type uint32;
         description "Accumulated receive statistics of near-end loss measured using iterator";
       }
       leaf cfm-accu-rx-far-end-eir-loss-stats {
         type uint32;
         description "Accumulated receive statistics of far-end loss measured using iterator";
       }
       leaf cfm-accu-loss-near-end-cir-loss-stats {
         type uint32;
         description "Accumulated statistics of near-end loss measured using iterator";
       }
       leaf cfm-accu-loss-near-end-cir-loss-stats-percent {
         type string;
         description "Accumulated statistics of near-end loss measured using iterator in percentage";
       }
       leaf cfm-accu-loss-far-end-cir-loss-stats {
         type uint32;
         description "Accumulated loss statistics of far-end loss measured using iterator";
       }
       leaf cfm-accu-loss-far-end-cir-loss-stats-percent {
         type string;
         description "Accumulated loss statistics of far-end loss measured using iterator in percentage";
       }
       leaf cfm-accu-loss-near-end-eir-loss-stats {
         type uint32;
         description "Accumulated loss statistics of near-end loss measured using iterator";
       }
       leaf cfm-accu-loss-near-end-eir-loss-stats-percent {
         type string;
         description "Accumulated loss statistics of near-end loss measured using iterator in percentage";
       }
       leaf cfm-accu-loss-far-end-eir-loss-stats {
         type uint32;
         description "Accumulated loss statistics of far-end loss measured using iterator";
       }
       leaf cfm-accu-loss-far-end-eir-loss-stats-percent {
         type string;
         description "Accumulated loss statistics of far-end loss measured using iterator in percentage";
       }
       leaf cfm-last-measured-near-end-cir-loss-stats {
         type uint32;
         description "Last measured statistics of near-end loss using iterator";
       }
       leaf cfm-last-measured-far-end-cir-loss-stats {
         type uint32;
         description "Last measured statistics of far-end loss using iterator";
       }
       leaf cfm-last-measured-near-end-eir-loss-stats {
         type uint32;
         description "Last measured statistics of near-end loss using iterator";
       }
       leaf cfm-last-measured-far-end-eir-loss-stats {
         type uint32;
         description "Last measured statistics of far-end loss using iterator";
       }
     }
     container cfm-iter-eth-sfl-entry {
       leaf sfl-measurement-packets-sent {
         type uint32;
         description "Number of statistical frame loss measurement packets sent";
       }
       leaf sfl-measurement-packets-skipped-for-threshold-hit {
         type uint32;
         description "Number of statistical frame loss measurement packets skipped due to threshold hit";
       }
       leaf sfl-measurement-packets-skipped-for-threshold-hit-window {
         type uint32;
         description "Number of statistical frame loss measurement packets skipped due to threshold hit window";
       }
       leaf sfl-measurement-packets-received {
         type uint32;
         description "Number of statistical frame loss measurement packets received";
       }
       leaf sfl-measurement-packets-out-of-sequence {
         type uint32;
         description "Number of statistical frame loss measurement out of sequence packets received";
       }
       leaf sfl-measurement-packets-fc-mismatch {
         type uint32;
         description "Number of statistical frame loss measurement forwarding-class mismatch packets received";
       }
       leaf sfl-measurement-cir-packets-sent {
         type uint32;
         description "Number of CIR statistical frame loss measurement packets sent";
       }
       leaf sfl-measurement-eir-packets-sent {
         type uint32;
         description "Number of EIR statistical frame loss measurement packets sent";
       }
       leaf sfl-measurement-cir-packets-received {
         type uint32;
         description "Number of CIR statistical frame loss measurement packets received";
       }
       leaf sfl-measurement-eir-packets-received {
         type uint32;
         description "Number of EIR statistical frame loss measurement packets received";
       }
       leaf sfl-measurement-cir-loss-count {
         type uint32;
         description "Number of CIR statistical frame loss measurement packets lost";
       }
       leaf sfl-measurement-cir-loss-percent {
         type uint32;
         description "Number of CIR statistical frame loss measurement packets lost percent";
       }
       leaf sfl-measurement-eir-loss-count {
         type uint32;
         description "Number of EIR statistical frame loss measurement packets lost";
       }
       leaf sfl-measurement-eir-loss-percent {
         type uint32;
         description "Number of EIR statistical frame loss measurement packets lost percent";
       }
       leaf sfl-measurement-loss-count {
         type uint32;
         description "Number of statistical frame loss measurement packets lost";
       }
       leaf sfl-measurement-loss-percent {
         type uint32;
         description "Number of statistical frame loss measurement packets lost percent";
       }
     }
     container cfm-iter-ethslm-entry {
       leaf cfm-slm-sent {
         type uint32;
         description "Number of synthetic loss measurement request message packets sent";
       }
       leaf cfm-slm-skipped-for-threshold-hit {
         type uint32;
         description "Number of synthetic loss measurement packets skipped due to threshold hit";
       }
       leaf cfm-slm-skipped-for-threshold-hit-window {
         type uint32;
         description "Number of synthetic loss measurement packets skipped due to threshold hit window";
       }
       leaf cfm-slr-received {
         type uint32;
         description "Number of valid synthetic loss measurement response message packets received";
       }
       leaf cfm-slr-out-of-seq {
         type uint32;
         description "Number of out of sequence synthetic loss measurement response message packets received";
       }
       leaf cfm-slm-txed {
         type uint32;
         description "Number of valid synthetic loss measurement request sent";
       }
       leaf cfm-slm-rxed {
         type uint32;
         description "Number of valid synthetic loss measurement response received";
       }
       leaf cfm-slm-tx-lastpkt-rcv {
         type uint32;
         description "TxFC1 value in the last valid synthetic loss measurement response received";
       }
       leaf cfm-slm-rx-lastpkt-rcv {
         type uint32;
         description "TxFCb value in the last valid synthetic loss measurement response received";
       }
       leaf cfm-slm-last-measured-near-end-slm-loss-stats {
         type uint32;
         description "Near end synthetic loss";
       }
       leaf cfm-slm-last-measured-near-end-slm-loss-stats-percent {
         type string;
         description "Near end synthetic loss in percentage";
       }
       leaf cfm-slm-last-measured-far-end-slm-loss-stats {
         type uint32;
         description "Far end synthetic loss";
       }
       leaf cfm-slm-last-measured-far-end-slm-loss-stats-percent {
         type string;
         description "Far end synthetic loss in percentage";
       }
     }
     container cfm-iter-pm-current-dm-entry {
       leaf cfm-pm-mi-index {
         type uint32;
         description "Measurement Interval Index";
       }
       leaf cfm-pm-mi-suspect-status {
         type string;
         description "Status flag information for the field";
       }
       leaf cfm-pm-mi-start-time {
         type string;
         description "Measurement Interval start time";
       }
       leaf cfm-pm-mi-elapsed-time {
         type string;
         description "Measurement Interval elapsed time";
       }
       leaf cfm-pm-twoway-frame-delay-min {
         type uint32;
         description "Minimum two way frame delay";
       }
       leaf cfm-pm-twoway-frame-delay-max {
         type uint32;
         description "Maximum two way frame delay";
       }
       leaf cfm-pm-twoway-frame-delay-avg {
         type uint32;
         description "Average two way frame delay";
       }
       leaf cfm-pm-forward-frame-delay-min {
         type uint32;
         description "Minimum forward frame delay";
       }
       leaf cfm-pm-forward-frame-delay-max {
         type uint32;
         description "Maximum forward frame delay";
       }
       leaf cfm-pm-forward-frame-delay-avg {
         type uint32;
         description "Average forward frame delay";
       }
       leaf cfm-pm-backward-frame-delay-min {
         type uint32;
         description "Minimum backward frame delay";
       }
       leaf cfm-pm-backward-frame-delay-max {
         type uint32;
         description "Maximum backward frame delay";
       }
       leaf cfm-pm-backward-frame-delay-avg {
         type uint32;
         description "Average backward frame delay";
       }
       leaf cfm-pm-twoway-frame-delay-variation-min {
         type uint32;
         description "Minimum two way inter frame delay variation";
       }
       leaf cfm-pm-twoway-frame-delay-variation-max {
         type uint32;
         description "Maximum two way inter frame delay variation";
       }
       leaf cfm-pm-twoway-frame-delay-variation-avg {
         type uint32;
         description "Average two way inter frame delay variation";
       }
       leaf cfm-pm-forward-frame-delay-variation-min {
         type uint32;
         description "Minimum forward inter frame delay variation";
       }
       leaf cfm-pm-forward-frame-delay-variation-max {
         type uint32;
         description "Maximum forward inter frame delay variation";
       }
       leaf cfm-pm-forward-frame-delay-variation-avg {
         type uint32;
         description "Average forward inter frame delay variation";
       }
       leaf cfm-pm-backward-frame-delay-variation-min {
         type uint32;
         description "Minimum backward inter frame delay variation";
       }
       leaf cfm-pm-backward-frame-delay-variation-max {
         type uint32;
         description "Maximum backward inter frame delay variation";
       }
       leaf cfm-pm-backward-frame-delay-variation-avg {
         type uint32;
         description "Average backward inter frame delay variation";
       }
       leaf cfm-pm-twoway-frame-delay-range-max {
         type uint32;
         description "Maximum two way frame delay range";
       }
       leaf cfm-pm-twoway-frame-delay-range-avg {
         type uint32;
         description "Average two way frame delay range";
       }
       leaf cfm-pm-forward-frame-delay-range-max {
         type uint32;
         description "Maximum forward frame delay range";
       }
       leaf cfm-pm-forward-frame-delay-range-avg {
         type uint32;
         description "Average forward frame delay range";
       }
       leaf cfm-pm-backward-frame-delay-range-max {
         type uint32;
         description "Maximum backward frame delay range";
       }
       leaf cfm-pm-backward-frame-delay-range-avg {
         type uint32;
         description "Average backward frame delay range";
       }
       leaf cfm-pm-soam-frame-tx {
         type uint32;
         description "SOAM(LMM/SLM/DMM) frames transmitted for performance measurement";
       }
       leaf cfm-pm-soam-frame-rx {
         type uint32;
         description "SOAM(LMR/SLR/DMR) frames received for performance measurement";
       }
     }
     container cfm-iter-pm-current-dm-bin-info {
       leaf cfm-pm-mi-index {
         type uint32;
         description "Measurement Interval Index";
       }
       list cfm-iter-pm-current-dm-bin-entry {
         leaf cfm-pm-bin-type {
           type string;
           description "Delay measurement bin type";
         }
         list cfm-iter-pm-current-dm-bin-entry-counter {
           leaf cfm-pm-bin-lower-threshold {
             type string;
             description "Lower threshold of this bin";
           }
           leaf cfm-pm-bin-upper-threshold {
             type string;
             description "Upper threshold of this bin";
           }
           leaf cfm-pm-bin-counter {
             type uint32;
             description "Number of measurements counted in this bin";
           }
         }
       }
     }
     container cfm-iter-pm-lm-entry {
       leaf cfm-lmm-skipped-for-threshold-hit {
         type uint32;
         description "Number of loss measurement packets skipped due to threshold hit";
       }
       leaf cfm-lmm-skipped-for-threshold-hit-window {
         type uint32;
         description "Number of loss measurement packets skipped due to threshold hit window";
       }
       leaf cfm-lmr-out-of-seq {
         type uint32;
         description "Number of out of sequence loss measurement response message packets received";
       }
       leaf cfm-lmr-fc-mismatch {
         type uint32;
         description "Number of forwarding-class mismatch loss measurement response message packets received";
       }
       leaf cfm-last-measured-far-end-cir-loss-stats {
         type uint32;
         description "Last measured statistics of far-end loss using iterator";
       }
       leaf cfm-last-measured-near-end-cir-loss-stats {
         type uint32;
         description "Last measured statistics of near-end loss using iterator";
       }
     }
     container cfm-iter-pm-slm-entry {
       container brief {
         container cfm-iter-pm-slm-entry-misc-details {
           leaf cfm-slm-skipped-for-threshold-hit {
             type uint32;
             description "Number of synthetic loss measurement packets skipped due to threshold hit";
           }
           leaf cfm-slm-skipped-for-threshold-hit-window {
             type uint32;
             description "Number of synthetic loss measurement packets skipped due to threshold hit window";
           }
           leaf cfm-slr-out-of-seq {
             type uint32;
             description "Number of out of sequence synthetic loss measurement response message packets received";
           }
           leaf cfm-slm-sample-size {
             type uint32;
             description "Number of SLM pdus considered as a sample for loss measurement";
           }
           leaf cfm-slm-txed {
             type uint32;
             description "Number of valid synthetic loss measurement request sent";
           }
           leaf cfm-slm-rxed {
             type uint32;
             description "Number of valid synthetic loss measurement response received";
           }
           leaf cfm-slm-tx-lastpkt-rcv {
             type uint32;
             description "TxFC1 value in the last valid synthetic loss measurement response received";
           }
           leaf cfm-slm-rx-lastpkt-rcv {
             type uint32;
             description "TxFCb value in the last valid synthetic loss measurement response received";
           }
           leaf cfm-slm-last-measured-far-end-slm-loss-stats-percent {
             type string;
             description "Far end synthetic loss in percentage";
           }
           leaf cfm-slm-last-measured-near-end-slm-loss-stats-percent {
             type string;
             description "Near end synthetic loss in percentage";
           }
           leaf cfm-pm-mi-num-calculations {
             type uint32;
             description "Number of PM calculations done in the measurement interval";
           }
         }
       }
       container detail {
         container cfm-iter-pm-slm-entry-misc-details {
           leaf cfm-slm-skipped-for-threshold-hit {
             type uint32;
             description "Number of synthetic loss measurement packets skipped due to threshold hit";
           }
           leaf cfm-slm-skipped-for-threshold-hit-window {
             type uint32;
             description "Number of synthetic loss measurement packets skipped due to threshold hit window";
           }
           leaf cfm-slr-out-of-seq {
             type uint32;
             description "Number of out of sequence synthetic loss measurement response message packets received";
           }
           leaf cfm-slm-sample-size {
             type uint32;
             description "Number of SLM pdus considered as a sample for loss measurement";
           }
           leaf cfm-slm-txed {
             type uint32;
             description "Number of valid synthetic loss measurement request sent";
           }
           leaf cfm-slm-rxed {
             type uint32;
             description "Number of valid synthetic loss measurement response received";
           }
           leaf cfm-slm-tx-lastpkt-rcv {
             type uint32;
             description "TxFC1 value in the last valid synthetic loss measurement response received";
           }
           leaf cfm-slm-rx-lastpkt-rcv {
             type uint32;
             description "TxFCb value in the last valid synthetic loss measurement response received";
           }
           leaf cfm-slm-last-measured-far-end-slm-loss-stats-percent {
             type string;
             description "Far end synthetic loss in percentage";
           }
           leaf cfm-slm-last-measured-near-end-slm-loss-stats-percent {
             type string;
             description "Near end synthetic loss in percentage";
           }
           leaf cfm-pm-mi-num-calculations {
             type uint32;
             description "Number of PM calculations done in the measurement interval";
           }
         }
         container cfm-iter-pm-slm-entry-current-mi-details {
           leaf cfm-pm-mi-num-calculations {
             type uint32;
             description "Number of PM calculations done in the measurement interval";
           }
           leaf cfm-slm-smpl-num-calc {
             type uint32;
             description "Number of loss calculations done in the measurement interval";
           }
           leaf cfm-lm-fe-num-calc-considered {
             type uint32;
             description "Number of far end loss calculations considered for loss measurement";
           }
           leaf cfm-lm-ne-num-calc-considered {
             type uint32;
             description "Number of near end loss calculations considered for loss measurement";
           }
           leaf cfm-lm-ai-num-calc {
             type uint32;
             description "Number of availability inidicators evaluated in measurement interval";
           }
           leaf cfm-lm-num-con-ai {
             type uint32;
             description "Number consecutive availability indicators got evaluated in sliding window";
           }
           leaf cfm-lm-fe-hloss-bitmap {
             type uint32;
             description "Far end high loss bitmap. Each bit indicates a availability indicator";
           }
           leaf cfm-lm-ne-hloss-bitmap {
             type uint32;
             description "Near end high loss bitmap. Each bit indicates a availability indicator";
           }
           leaf cfm-slm-base-txfcf {
             type uint32;
             description "Base TxFCf value for a measurement period";
           }
           leaf cfm-slm-last-txfcf {
             type uint32;
             description "Last TxFCf value for a measurement period";
           }
           leaf cfm-slm-base-txfcb {
             type uint32;
             description "Base TxFCb value for a measurement period";
           }
           leaf cfm-slm-last-txfcb {
             type uint32;
             description "Last TxFCb value for a measurement period";
           }
           leaf cfm-slm-base-rxfcb {
             type uint32;
             description "Base RxFCb value for a measurement period";
           }
           leaf cfm-slm-last-rxfcb {
             type uint32;
             description "Last RxFCb value for a measurement period";
           }
           leaf cfm-slm-far-end-loss-carry {
             type uint32;
             description "Previous unaccounted Loss in farward diretion";
           }
           leaf cfm-slm-near-end-loss-carry {
             type uint32;
             description "Previous unaccounted Loss in backward diretion";
           }
         }
       }
       container extensive {
         container cfm-iter-pm-slm-entry-misc-details {
           leaf cfm-slm-skipped-for-threshold-hit {
             type uint32;
             description "Number of synthetic loss measurement packets skipped due to threshold hit";
           }
           leaf cfm-slm-skipped-for-threshold-hit-window {
             type uint32;
             description "Number of synthetic loss measurement packets skipped due to threshold hit window";
           }
           leaf cfm-slr-out-of-seq {
             type uint32;
             description "Number of out of sequence synthetic loss measurement response message packets received";
           }
           leaf cfm-slm-sample-size {
             type uint32;
             description "Number of SLM pdus considered as a sample for loss measurement";
           }
           leaf cfm-slm-txed {
             type uint32;
             description "Number of valid synthetic loss measurement request sent";
           }
           leaf cfm-slm-rxed {
             type uint32;
             description "Number of valid synthetic loss measurement response received";
           }
           leaf cfm-slm-tx-lastpkt-rcv {
             type uint32;
             description "TxFC1 value in the last valid synthetic loss measurement response received";
           }
           leaf cfm-slm-rx-lastpkt-rcv {
             type uint32;
             description "TxFCb value in the last valid synthetic loss measurement response received";
           }
           leaf cfm-slm-last-measured-far-end-slm-loss-stats-percent {
             type string;
             description "Far end synthetic loss in percentage";
           }
           leaf cfm-slm-last-measured-near-end-slm-loss-stats-percent {
             type string;
             description "Near end synthetic loss in percentage";
           }
           leaf cfm-pm-mi-num-calculations {
             type uint32;
             description "Number of PM calculations done in the measurement interval";
           }
         }
         container cfm-iter-pm-slm-entry-current-mi-details {
           leaf cfm-pm-mi-num-calculations {
             type uint32;
             description "Number of PM calculations done in the measurement interval";
           }
           leaf cfm-slm-smpl-num-calc {
             type uint32;
             description "Number of loss calculations done in the measurement interval";
           }
           leaf cfm-lm-fe-num-calc-considered {
             type uint32;
             description "Number of far end loss calculations considered for loss measurement";
           }
           leaf cfm-lm-ne-num-calc-considered {
             type uint32;
             description "Number of near end loss calculations considered for loss measurement";
           }
           leaf cfm-lm-ai-num-calc {
             type uint32;
             description "Number of availability inidicators evaluated in measurement interval";
           }
           leaf cfm-lm-num-con-ai {
             type uint32;
             description "Number consecutive availability indicators got evaluated in sliding window";
           }
           leaf cfm-lm-fe-hloss-bitmap {
             type uint32;
             description "Far end high loss bitmap. Each bit indicates a availability indicator";
           }
           leaf cfm-lm-ne-hloss-bitmap {
             type uint32;
             description "Near end high loss bitmap. Each bit indicates a availability indicator";
           }
           leaf cfm-slm-base-txfcf {
             type uint32;
             description "Base TxFCf value for a measurement period";
           }
           leaf cfm-slm-last-txfcf {
             type uint32;
             description "Last TxFCf value for a measurement period";
           }
           leaf cfm-slm-base-txfcb {
             type uint32;
             description "Base TxFCb value for a measurement period";
           }
           leaf cfm-slm-last-txfcb {
             type uint32;
             description "Last TxFCb value for a measurement period";
           }
           leaf cfm-slm-base-rxfcb {
             type uint32;
             description "Base RxFCb value for a measurement period";
           }
           leaf cfm-slm-last-rxfcb {
             type uint32;
             description "Last RxFCb value for a measurement period";
           }
           leaf cfm-slm-far-end-loss-carry {
             type uint32;
             description "Previous unaccounted Loss in farward diretion";
           }
           leaf cfm-slm-near-end-loss-carry {
             type uint32;
             description "Previous unaccounted Loss in backward diretion";
           }
         }
         container cfm-iter-pm-slm-entry-last-mi-details {
           leaf cfm-pm-mi-closed {
             type uint32;
             description "Last measurement interval calculations are closed";
           }
           leaf cfm-pm-mi-index {
             type uint32;
             description "Measurement Interval Index";
           }
           leaf cfm-pm-forward-min-flr-percentage {
             type uint32;
             description "Minimum frame loss ratio percentage at far end";
           }
           leaf cfm-pm-forward-max-flr-percentage {
             type uint32;
             description "Maximum frame loss ratio percentage at far end";
           }
           leaf cfm-pm-forward-avg-flr-percentage {
             type uint32;
             description "Average frame loss ratio percentage at far end";
           }
           leaf cfm-pm-backward-min-flr-percentage {
             type uint32;
             description "Minimum frame loss ratio percentage at far end";
           }
           leaf cfm-pm-backward-max-flr-percentage {
             type uint32;
             description "Maximum frame loss ratio percentage at far end";
           }
           leaf cfm-pm-backward-avg-flr-percentage {
             type uint32;
             description "Average frame loss ratio percentage at far end";
           }
         }
       }
     }
     container cfm-iter-pm-current-lm-entry {
       leaf cfm-pm-mi-index {
         type uint32;
         description "Measurement Interval Index";
       }
       leaf cfm-pm-mi-suspect-status {
         type string;
         description "Status flag information for the field";
       }
       leaf cfm-pm-mi-start-time {
         type string;
         description "Measurement Interval start time";
       }
       leaf cfm-pm-mi-elapsed-time {
         type string;
         description "Measurement Interval elapsed time";
       }
       leaf cfm-pm-soam-frame-tx {
         type uint32;
         description "SOAM(LMM/SLM/DMM) frames transmitted for performance measurement";
       }
       leaf cfm-pm-soam-frame-rx {
         type uint32;
         description "SOAM(LMR/SLR/DMR) frames received for performance measurement";
       }
       leaf cfm-pm-mi-num-calculations {
         type uint32;
         description "Number of PM calculations done in the measurement interval";
       }
       leaf cfm-pm-forward-frame-tx {
         type uint32;
         description "Frame transmitted by near end for performance measurement";
       }
       leaf cfm-pm-forward-frame-rx {
         type uint32;
         description "Frame received by far end for performance measurement";
       }
       leaf cfm-pm-backward-frame-tx {
         type uint32;
         description "Frame transmitted by far end for performance measurement";
       }
       leaf cfm-pm-backward-frame-rx {
         type uint32;
         description "Frame received by near end for performance measurement";
       }
       leaf cfm-pm-forward-frame-loss {
         type uint32;
         description "Frame loss at far end";
       }
       leaf cfm-pm-backward-frame-loss {
         type uint32;
         description "Frame loss at near end";
       }
       leaf cfm-pm-forward-min-flr-percentage {
         type uint32;
         description "Minimum frame loss ratio percentage at far end";
       }
       leaf cfm-pm-forward-min-flr-time {
         type string;
         description "Time when minimum frame loss ratio occured at far end";
       }
       leaf cfm-pm-forward-max-flr-percentage {
         type uint32;
         description "Maximum frame loss ratio percentage at far end";
       }
       leaf cfm-pm-forward-max-flr-time {
         type string;
         description "Time when maximum frame loss ratio occured at far end";
       }
       leaf cfm-pm-forward-avg-flr-percentage {
         type uint32;
         description "Average frame loss ratio percentage at far end";
       }
       leaf cfm-pm-backward-min-flr-percentage {
         type uint32;
         description "Minimum frame loss ratio percentage at far end";
       }
       leaf cfm-pm-backward-min-flr-time {
         type string;
         description "Time when minimum frame loss ratio occured at near end";
       }
       leaf cfm-pm-backward-max-flr-percentage {
         type uint32;
         description "Maximum frame loss ratio percentage at far end";
       }
       leaf cfm-pm-backward-max-flr-time {
         type string;
         description "Time when maximum frame loss ratio occured at near end";
       }
       leaf cfm-pm-backward-avg-flr-percentage {
         type uint32;
         description "Average frame loss ratio percentage at far end";
       }
     }
     container cfm-iter-pm-current-avail-entry {
       leaf cfm-pm-mi-index {
         type uint32;
         description "Measurement Interval Index";
       }
       leaf cfm-pm-mi-suspect-status {
         type string;
         description "Status flag information for the field";
       }
       leaf cfm-pm-mi-start-time {
         type string;
         description "Measurement Interval start time";
       }
       leaf cfm-pm-mi-elapsed-time {
         type string;
         description "Measurement Interval elapsed time";
       }
       leaf cfm-pm-mi-num-calculations {
         type uint32;
         description "Number of PM calculations done in the measurement interval";
       }
       leaf cfm-pm-forward-high-loss {
         type uint32;
         description "Accumulative number of high loss intervals at far end";
       }
       leaf cfm-pm-backward-high-loss {
         type uint32;
         description "Accumulative number of high loss intervals at near end";
       }
       leaf cfm-pm-forward-consecutive-high-loss {
         type uint32;
         description "Accumulative number of consecutive high loss intervals at far end";
       }
       leaf cfm-pm-backward-consecutive-high-loss {
         type uint32;
         description "Accumulative number of consecutive high loss intervals at near end";
       }
       leaf cfm-pm-forward-available {
         type uint32;
         description "Number of availabilty indicators at far end";
       }
       leaf cfm-pm-backward-available {
         type uint32;
         description "Number of availabilty indicators at near end";
       }
       leaf cfm-pm-forward-unavailable {
         type uint32;
         description "Number of un-availabilty indicators at far end";
       }
       leaf cfm-pm-backward-unavailable {
         type uint32;
         description "Number of un-availabilty indicators at near end";
       }
       leaf cfm-pm-forward-min-flr-percentage {
         type uint32;
         description "Minimum frame loss ratio percentage at far end";
       }
       leaf cfm-pm-forward-min-flr-time {
         type string;
         description "Time when minimum frame loss ratio occured at far end";
       }
       leaf cfm-pm-forward-max-flr-percentage {
         type uint32;
         description "Maximum frame loss ratio percentage at far end";
       }
       leaf cfm-pm-forward-max-flr-time {
         type string;
         description "Time when maximum frame loss ratio occured at far end";
       }
       leaf cfm-pm-forward-avg-flr-percentage {
         type uint32;
         description "Average frame loss ratio percentage at far end";
       }
       leaf cfm-pm-backward-min-flr-percentage {
         type uint32;
         description "Minimum frame loss ratio percentage at far end";
       }
       leaf cfm-pm-backward-min-flr-time {
         type string;
         description "Time when minimum frame loss ratio occured at near end";
       }
       leaf cfm-pm-backward-max-flr-percentage {
         type uint32;
         description "Maximum frame loss ratio percentage at far end";
       }
       leaf cfm-pm-backward-max-flr-time {
         type string;
         description "Time when maximum frame loss ratio occured at near end";
       }
       leaf cfm-pm-backward-avg-flr-percentage {
         type uint32;
         description "Average frame loss ratio percentage at far end";
       }
       leaf cfm-pm-forward-avail-status {
         type string;
         description "Last known availability status in forward direction";
       }
       leaf cfm-pm-backward-avail-status {
         type string;
         description "Last known availability status in backward direction";
       }
       leaf cfm-pm-forward-avail-transition-time {
         type string;
         description "Time of last transition between available and unavailable in forward direction";
       }
       leaf cfm-pm-backward-avail-transition-time {
         type string;
         description "Time of last transition between available and unavailable in backward direction";
       }
     }
     container cfm-flap-trap-statistics {
       leaf cfm-flap-trap-total-flr-flaps {
         type uint32;
         description "Total number of FLR flaps";
       }
       leaf cfm-flap-trap-total-acc-flr-flaps {
         type uint32;
         description "Total numer of accumulated FLR flaps";
       }
       leaf cfm-flap-trap-total-blr-flaps {
         type uint32;
         description "Total number of BLR flaps";
       }
       leaf cfm-flap-trap-total-acc-blr-flaps {
         type uint32;
         description "Total numer of accumulated BLR flaps";
       }
     }
   }
 }
 grouping cfm-flood-instance-information-block {
   list brief {
     leaf cfm-instance-name {
       type string;
       description "Forwarding instance";
     }
     leaf cfm-num-active-customer-endpoint-iffs {
       type int32;
       description "Number of customer endpoints (or customer-facing) ports";
     }
     leaf cfm-num-active-vpn-endpoint-iffs {
       type int32;
       description "Number of VPN endpoints (or pseudowire/core-facing) ports";
     }
     list cfm-flood-maintenance-domain-level {
       leaf cfm-level {
         type uint32;
         description "Maintenance-domain level";
       }
       leaf cfm-local-mep-direction {
         type string;
         description "Direction in which continuity-check messages are sent";
       }
       leaf cfm-filter-action {
         type string;
         description "Action taken on receiving a CFM protocol packet";
       }
       leaf cfm-nexthop-type {
         type string;
       }
       leaf cfm-nexthop-index {
         type int32;
       }
       list detail {
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
       list extensive {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
     }
   }
   list detail {
     leaf cfm-instance-name {
       type string;
       description "Forwarding instance";
     }
     leaf cfm-num-active-customer-endpoint-iffs {
       type int32;
       description "Number of customer endpoints (or customer-facing) ports";
     }
     leaf cfm-num-active-vpn-endpoint-iffs {
       type int32;
       description "Number of VPN endpoints (or pseudowire/core-facing) ports";
     }
     list cfm-flood-maintenance-domain-level {
       leaf cfm-level {
         type uint32;
         description "Maintenance-domain level";
       }
       leaf cfm-local-mep-direction {
         type string;
         description "Direction in which continuity-check messages are sent";
       }
       leaf cfm-filter-action {
         type string;
         description "Action taken on receiving a CFM protocol packet";
       }
       leaf cfm-nexthop-type {
         type string;
       }
       leaf cfm-nexthop-index {
         type int32;
       }
       list brief {
       }
       list detail {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
       list extensive {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
     }
   }
   list extensive {
     leaf cfm-instance-name {
       type string;
       description "Forwarding instance";
     }
     leaf cfm-num-active-customer-endpoint-iffs {
       type int32;
       description "Number of customer endpoints (or customer-facing) ports";
     }
     leaf cfm-num-active-vpn-endpoint-iffs {
       type int32;
       description "Number of VPN endpoints (or pseudowire/core-facing) ports";
     }
     list cfm-flood-maintenance-domain-level {
       leaf cfm-level {
         type uint32;
         description "Maintenance-domain level";
       }
       leaf cfm-local-mep-direction {
         type string;
         description "Direction in which continuity-check messages are sent";
       }
       leaf cfm-filter-action {
         type string;
         description "Action taken on receiving a CFM protocol packet";
       }
       leaf cfm-nexthop-type {
         type string;
       }
       leaf cfm-nexthop-index {
         type int32;
       }
       list brief {
       }
       list detail {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
       list extensive {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
     }
   }
 }
 grouping cfm-flood-interface-information-block {
   list brief {
     leaf cfm-interface-name {
       type string;
       description "Name of interface";
     }
     leaf cfm-instance-name {
       type string;
       description "Forwarding instance";
     }
     list cfm-flood-maintenance-domain-level {
       leaf cfm-level {
         type uint32;
         description "Maintenance-domain level";
       }
       leaf cfm-local-mep-direction {
         type string;
         description "Direction in which continuity-check messages are sent";
       }
       leaf cfm-filter-action {
         type string;
         description "Action taken on receiving a CFM protocol packet";
       }
       leaf cfm-nexthop-type {
         type string;
       }
       leaf cfm-nexthop-index {
         type int32;
       }
       list detail {
         list cfm-flood-nexthop-components {
           leaf cfm-interface-type {
             type string;
           }
           leaf cfm-interface-nexthop-type {
             type string;
           }
           leaf cfm-interface-nexthop-index {
             type int32;
           }
         }
       }
       list extensive {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
     }
   }
   list detail {
     leaf cfm-interface-name {
       type string;
       description "Name of interface";
     }
     leaf cfm-instance-name {
       type string;
       description "Forwarding instance";
     }
     list cfm-flood-maintenance-domain-level {
       leaf cfm-level {
         type uint32;
         description "Maintenance-domain level";
       }
       leaf cfm-local-mep-direction {
         type string;
         description "Direction in which continuity-check messages are sent";
       }
       leaf cfm-filter-action {
         type string;
         description "Action taken on receiving a CFM protocol packet";
       }
       leaf cfm-nexthop-type {
         type string;
       }
       leaf cfm-nexthop-index {
         type int32;
       }
       list brief {
       }
       list detail {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
       list extensive {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
     }
   }
   list extensive {
     leaf cfm-interface-name {
       type string;
       description "Name of interface";
     }
     leaf cfm-instance-name {
       type string;
       description "Forwarding instance";
     }
     list cfm-flood-maintenance-domain-level {
       list brief {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
       }
       list detail {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
       list extensive {
         leaf cfm-level {
           type uint32;
           description "Maintenance-domain level";
         }
         leaf cfm-local-mep-direction {
           type string;
           description "Direction in which continuity-check messages are sent";
         }
         leaf cfm-filter-action {
           type string;
           description "Action taken on receiving a CFM protocol packet";
         }
         leaf cfm-nexthop-type {
           type string;
         }
         leaf cfm-nexthop-index {
           type int32;
         }
         list cfm-flood-nexthop-components {
           leaf cfm-interface-name {
             type string;
             description "Name of interface";
           }
           leaf cfm-interface-type {
             type string;
           }
           leaf cfm-interface-nexthop-type {
             type string;
           }
           leaf cfm-interface-nexthop-index {
             type int32;
           }
         }
       }
     }
   }
 }
 grouping cfm-linktrace-path-database-block {
   container cfm-ltm-request-snapshot {
     leaf cfm-ltm-target-mac-address {
       type string;
       description "MAC address of the target host in linktrace request";
     }
     leaf cfm-interface-name {
       type string;
       description "Name of interface";
     }
     leaf cfm-maintenance-domain-name {
       type string;
       description "Name of maintenance domain";
     }
     leaf cfm-level {
       type uint32;
       description "Maintenance-domain level";
     }
     leaf cfm-maintenance-association-name {
       type string;
       description "Name of maintenance association";
     }
     leaf cfm-local-mep-identifier {
       type uint32;
       description "Identifier of local MEP";
     }
   }
   list cfm-ltr-reply-entry {
     leaf cfm-ltm-transaction-identifier {
       type uint32;
       description "Identifier which uniquely identifies a linktrace request";
     }
     leaf cfm-ltr-request-hop-identifier {
       type uint32;
       description "Identifier showing the order in which linktrace replies are received";
     }
     leaf cfm-ltr-reply-ttl {
       type uint32;
       description "Time-to-live value received in linktrace reply";
     }
     leaf cfm-ltr-mep-mip-mac-address {
       type string;
       description "MAC address of the of the host sending the linktrace reply";
     }
     leaf cfm-ltr-next-hop-mac-address {
       type string;
       description "MAC address of the next-hop to which the linktrace request is forwarded";
     }
   }
 }
 grouping cfm-mip-information-block {
   list cfm-instance-mip-information {
     leaf cfm-instance-name {
       type string;
       description "Forwarding instance";
     }
     leaf cfm-maintenance-domain-mhf {
       type string;
       description "Maintenance domain mip half function value for bridge-domain";
     }
     leaf cfm-maintenance-association-mhf {
       type string;
       description "Maintenance association mip half function value for bridge-domain";
     }
     leaf cfm-default-maintenance-domain-mhf {
       type string;
       description "Default maintenance domain mip half function value for bridge-domain";
     }
     list cfm-interface-mip-information {
       leaf cfm-interface-name {
         type string;
         description "Name of interface";
       }
       leaf cfm-level {
         type uint32;
         description "Maintenance-domain level";
       }
     }
   }
 }
 grouping cfm-policer-block {
   leaf cfm-legend {
     type string;
   }
   container cfm-policer-sessions {
     list cfm-policer-session {
       container cfm-policer-maintenance-domain-entry {
         leaf cfm-maintenance-domain-name {
           type string;
           description "Name of maintenance domain";
         }
         leaf cfm-level {
           type uint32;
           description "Maintenance-domain level";
         }
       }
       container cfm-policer-maintenance-association-entries {
         list cfm-policer-maintenance-association-entry {
           leaf cfm-maintenance-association-name {
             type string;
             description "Name of maintenance association";
           }
           leaf cfm-policer-name {
             type string;
             description "Name of policer";
           }
           leaf cfm-policer-type {
             type string;
             description "Type of policer";
           }
           leaf cfm-policer-scope {
             type string;
             description "Scope of policer";
           }
           leaf cfm-policer-drop-count {
             type uint64;
             description "Policer drop count";
           }
         }
       }
     }
   }
 }
 grouping cfm-iterator-history-block {
   container cfm-iter-mep-summary {
     leaf cfm-iterator-error-status {
       type string;
       description "Error reason for the iterator";
     }
     leaf cfm-maintenance-domain-name {
       type string;
       description "Name of maintenance domain";
     }
     leaf cfm-level {
       type uint32;
       description "Maintenance-domain level";
     }
     leaf cfm-maintenance-association-name {
       type string;
       description "Name of maintenance association";
     }
     leaf cfm-local-mep-identifier {
       type uint32;
       description "Identifier of local MEP";
     }
     leaf cfm-remote-mep-identifier {
       type uint32;
       description "Identifier of remote MEP";
     }
     leaf cfm-remote-mep-mac-address {
       type string;
       description "MAC address of remote MEP";
     }
   }
   container cfm-iter-summary {
     leaf cfm-iterator-name {
       type string;
       description "Name of iterator";
     }
     leaf cfm-iterator-type {
       type string;
       description "Shows the type of the iterator counters";
     }
     leaf cfm-iterator-identifier {
       type uint32;
       description "Identifier of iterator";
     }
     leaf cfm-iterator-cycle-time {
       type uint32;
       description "Cycle time of iterator";
     }
     leaf cfm-iteration-period {
       type uint32;
       description "Period of iteration";
     }
     leaf cfm-iterator-forever-status {
       type string;
       description "For-ever running status of the iterator";
     }
   }
   list cfm-lm-history-record-entry {
     leaf cfm-iterator-name {
       type string;
       description "Name of iterator";
     }
     leaf cfm-iterator-type {
       type string;
       description "Shows the type of the iterator counters";
     }
     leaf cfm-iterator-status {
       type string;
       description "State of the iterator";
     }
     leaf cfm-iterator-counter-start-time {
       type string;
       description "Shows the time at which iterator counters are started";
     }
     leaf cfm-maintenance-domain-name {
       type string;
       description "Name of maintenance domain";
     }
     leaf cfm-maintenance-association-name {
       type string;
       description "Name of maintenance association";
     }
     leaf cfm-local-mep-identifier {
       type uint32;
       description "Identifier of local MEP";
     }
     leaf cfm-remote-mep-identifier {
       type uint32;
       description "Identifier of remote MEP";
     }
     leaf cfm-txfcf-entry {
       type uint32;
       description "5 minutes transmit statistics of near-end loss measured using iterator";
     }
     leaf cfm-txfcb-entry {
       type uint32;
       description "5 minutes transmit statistics of far-end loss measured using iterator";
     }
     leaf cfm-rxfcf-entry {
       type uint32;
       description "5 minutes receive statistics of near-end loss measured using iterator";
     }
     leaf cfm-rxfcb-entry {
       type uint32;
       description "5 minutes receive statistics of far-end loss measured using iterator";
     }
     leaf cfm-near-end-loss-entry {
       type uint32;
       description "5 minutes loss statistics of near-end loss measured using iterator";
     }
     leaf cfm-far-end-loss-entry {
       type uint32;
       description "5 minutes loss statistics of far-end loss measured using iterator";
     }
   }
   list cfm-dm-history-record-entry {
     leaf cfm-iterator-name {
       type string;
       description "Name of iterator";
     }
     leaf cfm-iterator-type {
       type string;
       description "Shows the type of the iterator counters";
     }
     leaf cfm-iterator-status {
       type string;
       description "State of the iterator";
     }
     leaf cfm-iterator-counter-start-time {
       type string;
       description "Shows the time at which iterator counters are started";
     }
     leaf cfm-maintenance-domain-name {
       type string;
       description "Name of maintenance domain";
     }
     leaf cfm-maintenance-association-name {
       type string;
       description "Name of maintenance association";
     }
     leaf cfm-local-mep-identifier {
       type uint32;
       description "Identifier of local MEP";
     }
     leaf cfm-remote-mep-identifier {
       type uint32;
       description "Identifier of remote MEP";
     }
     leaf cfm-weighted-average-twoway-delay {
       type uint64;
       description "Weighted average two-way delay measured using iterator";
     }
     leaf cfm-weighted-average-worstcase-twoway-delay {
       type uint64;
       description "Weighted average maximum two-way delay measured using iterator";
     }
     leaf cfm-weighted-average-bestcase-twoway-delay {
       type uint64;
       description "Weighted average minimum two-way delay measured using iterator";
     }
   }
   list cfm-slm-history-record-entry {
     leaf cfm-iterator-name {
       type string;
       description "Name of iterator";
     }
     leaf cfm-iterator-type {
       type string;
       description "Shows the type of the iterator counters";
     }
     leaf cfm-iterator-status {
       type string;
       description "State of the iterator";
     }
     leaf cfm-iterator-counter-start-time {
       type string;
       description "Shows the time at which iterator counters are started";
     }
     leaf cfm-maintenance-domain-name {
       type string;
       description "Name of maintenance domain";
     }
     leaf cfm-maintenance-association-name {
       type string;
       description "Name of maintenance association";
     }
     leaf cfm-local-mep-identifier {
       type uint32;
       description "Identifier of local MEP";
     }
     leaf cfm-remote-mep-identifier {
       type uint32;
       description "Identifier of remote MEP";
     }
     leaf cfm-slm-txed {
       type uint32;
       description "Number of valid synthetic loss measurement request sent";
     }
     leaf cfm-slm-rxed {
       type uint32;
       description "Number of valid synthetic loss measurement response received";
     }
     leaf cfm-slm-tx-lastpkt-rcv {
       type uint32;
       description "TxFC1 value in the last valid synthetic loss measurement response received";
     }
     leaf cfm-slm-rx-lastpkt-rcv {
       type uint32;
       description "TxFCb value in the last valid synthetic loss measurement response received";
     }
     leaf cfm-slm-last-measured-near-end-slm-loss-stats {
       type uint32;
       description "Near end synthetic loss";
     }
     leaf cfm-slm-last-measured-far-end-slm-loss-stats {
       type uint32;
       description "Far end synthetic loss";
     }
   }
   list cfm-sfl-history-record-entry {
     leaf cfm-iterator-name {
       type string;
       description "Name of iterator";
     }
     leaf cfm-iterator-type {
       type string;
       description "Shows the type of the iterator counters";
     }
     leaf cfm-iterator-status {
       type string;
       description "State of the iterator";
     }
     leaf cfm-iterator-counter-start-time {
       type string;
       description "Shows the time at which iterator counters are started";
     }
     leaf cfm-maintenance-domain-name {
       type string;
       description "Name of maintenance domain";
     }
     leaf cfm-maintenance-association-name {
       type string;
       description "Name of maintenance association";
     }
     leaf cfm-local-mep-identifier {
       type uint32;
       description "Identifier of local MEP";
     }
     leaf cfm-remote-mep-identifier {
       type uint32;
       description "Identifier of remote MEP";
     }
     leaf sfl-measurement-cir-packets-sent {
       type uint32;
       description "Number of CIR statistical frame loss measurement packets sent";
     }
     leaf sfl-measurement-cir-packets-received {
       type uint32;
       description "Number of CIR statistical frame loss measurement packets received";
     }
     leaf sfl-measurement-cir-loss-count {
       type uint32;
       description "Number of CIR statistical frame loss measurement packets lost";
     }
   }
   list cfm-pm-dm-history-record-entry {
     container cfm-iter-pm-history-dm-entry {
       leaf cfm-pm-history-record-number {
         type uint32;
         description "History Record Number";
       }
       leaf cfm-pm-mi-index {
         type uint32;
         description "Measurement Interval Index";
       }
       leaf cfm-pm-mi-suspect-status {
         type string;
         description "Status flag information for the field";
       }
       leaf cfm-pm-mi-start-time {
         type string;
         description "Measurement Interval start time";
       }
       leaf cfm-pm-mi-end-time {
         type string;
         description "Measurement Interval end time";
       }
       leaf cfm-pm-mi-elapsed-time {
         type string;
         description "Measurement Interval elapsed time";
       }
       leaf cfm-pm-twoway-frame-delay-min {
         type uint32;
         description "Minimum two way frame delay";
       }
       leaf cfm-pm-twoway-frame-delay-max {
         type uint32;
         description "Maximum two way frame delay";
       }
       leaf cfm-pm-twoway-frame-delay-avg {
         type uint32;
         description "Average two way frame delay";
       }
       leaf cfm-pm-forward-frame-delay-min {
         type uint32;
         description "Minimum forward frame delay";
       }
       leaf cfm-pm-forward-frame-delay-max {
         type uint32;
         description "Maximum forward frame delay";
       }
       leaf cfm-pm-forward-frame-delay-avg {
         type uint32;
         description "Average forward frame delay";
       }
       leaf cfm-pm-backward-frame-delay-min {
         type uint32;
         description "Minimum backward frame delay";
       }
       leaf cfm-pm-backward-frame-delay-max {
         type uint32;
         description "Maximum backward frame delay";
       }
       leaf cfm-pm-backward-frame-delay-avg {
         type uint32;
         description "Average backward frame delay";
       }
       leaf cfm-pm-twoway-frame-delay-variation-min {
         type uint32;
         description "Minimum two way inter frame delay variation";
       }
       leaf cfm-pm-twoway-frame-delay-variation-max {
         type uint32;
         description "Maximum two way inter frame delay variation";
       }
       leaf cfm-pm-twoway-frame-delay-variation-avg {
         type uint32;
         description "Average two way inter frame delay variation";
       }
       leaf cfm-pm-forward-frame-delay-variation-min {
         type uint32;
         description "Minimum forward inter frame delay variation";
       }
       leaf cfm-pm-forward-frame-delay-variation-max {
         type uint32;
         description "Maximum forward inter frame delay variation";
       }
       leaf cfm-pm-forward-frame-delay-variation-avg {
         type uint32;
         description "Average forward inter frame delay variation";
       }
       leaf cfm-pm-backward-frame-delay-variation-min {
         type uint32;
         description "Minimum backward inter frame delay variation";
       }
       leaf cfm-pm-backward-frame-delay-variation-max {
         type uint32;
         description "Maximum backward inter frame delay variation";
       }
       leaf cfm-pm-backward-frame-delay-variation-avg {
         type uint32;
         description "Average backward inter frame delay variation";
       }
       leaf cfm-pm-twoway-frame-delay-range-max {
         type uint32;
         description "Maximum two way frame delay range";
       }
       leaf cfm-pm-twoway-frame-delay-range-avg {
         type uint32;
         description "Average two way frame delay range";
       }
       leaf cfm-pm-forward-frame-delay-range-max {
         type uint32;
         description "Maximum forward frame delay range";
       }
       leaf cfm-pm-forward-frame-delay-range-avg {
         type uint32;
         description "Average forward frame delay range";
       }
       leaf cfm-pm-backward-frame-delay-range-max {
         type uint32;
         description "Maximum backward frame delay range";
       }
       leaf cfm-pm-backward-frame-delay-range-avg {
         type uint32;
         description "Average backward frame delay range";
       }
       leaf cfm-pm-soam-frame-tx {
         type uint32;
         description "SOAM(LMM/SLM/DMM) frames transmitted for performance measurement";
       }
       leaf cfm-pm-soam-frame-rx {
         type uint32;
         description "SOAM(LMR/SLR/DMR) frames received for performance measurement";
       }
     }
     container cfm-iter-pm-history-dm-bin-info {
       leaf cfm-pm-history-record-number {
         type uint32;
         description "History Record Number";
       }
       leaf cfm-pm-mi-index {
         type uint32;
         description "Measurement Interval Index";
       }
       list cfm-iter-pm-history-dm-bin-entry {
         leaf cfm-pm-bin-type {
           type string;
           description "Delay measurement bin type";
         }
         list cfm-iter-pm-history-dm-bin-entry-counter {
           leaf cfm-pm-bin-lower-threshold {
             type string;
             description "Lower threshold of this bin";
           }
           leaf cfm-pm-bin-upper-threshold {
             type string;
             description "Upper threshold of this bin";
           }
           leaf cfm-pm-bin-counter {
             type uint32;
             description "Number of measurements counted in this bin";
           }
         }
       }
     }
   }
   list cfm-iter-pm-history-lm-entry {
     leaf cfm-pm-history-record-number {
       type uint32;
       description "History Record Number";
     }
     leaf cfm-pm-mi-index {
       type uint32;
       description "Measurement Interval Index";
     }
     leaf cfm-pm-mi-suspect-status {
       type string;
       description "Status flag information for the field";
     }
     leaf cfm-pm-mi-start-time {
       type string;
       description "Measurement Interval start time";
     }
     leaf cfm-pm-mi-end-time {
       type string;
       description "Measurement Interval end time";
     }
     leaf cfm-pm-mi-elapsed-time {
       type string;
       description "Measurement Interval elapsed time";
     }
     leaf cfm-pm-soam-frame-tx {
       type uint32;
       description "SOAM(LMM/SLM/DMM) frames transmitted for performance measurement";
     }
     leaf cfm-pm-soam-frame-rx {
       type uint32;
       description "SOAM(LMR/SLR/DMR) frames received for performance measurement";
     }
     leaf cfm-pm-mi-num-calculations {
       type uint32;
       description "Number of PM calculations done in the measurement interval";
     }
     leaf cfm-pm-forward-frame-tx {
       type uint32;
       description "Frame transmitted by near end for performance measurement";
     }
     leaf cfm-pm-forward-frame-rx {
       type uint32;
       description "Frame received by far end for performance measurement";
     }
     leaf cfm-pm-backward-frame-tx {
       type uint32;
       description "Frame transmitted by far end for performance measurement";
     }
     leaf cfm-pm-backward-frame-rx {
       type uint32;
       description "Frame received by near end for performance measurement";
     }
     leaf cfm-pm-forward-frame-loss {
       type uint32;
       description "Frame loss at far end";
     }
     leaf cfm-pm-backward-frame-loss {
       type uint32;
       description "Frame loss at near end";
     }
     leaf cfm-pm-forward-min-flr-percentage {
       type uint32;
       description "Minimum frame loss ratio percentage at far end";
     }
     leaf cfm-pm-forward-min-flr-time {
       type string;
       description "Time when minimum frame loss ratio occured at far end";
     }
     leaf cfm-pm-forward-max-flr-percentage {
       type uint32;
       description "Maximum frame loss ratio percentage at far end";
     }
     leaf cfm-pm-forward-max-flr-time {
       type string;
       description "Time when maximum frame loss ratio occured at far end";
     }
     leaf cfm-pm-forward-avg-flr-percentage {
       type uint32;
       description "Average frame loss ratio percentage at far end";
     }
     leaf cfm-pm-backward-min-flr-percentage {
       type uint32;
       description "Minimum frame loss ratio percentage at far end";
     }
     leaf cfm-pm-backward-min-flr-time {
       type string;
       description "Time when minimum frame loss ratio occured at near end";
     }
     leaf cfm-pm-backward-max-flr-percentage {
       type uint32;
       description "Maximum frame loss ratio percentage at far end";
     }
     leaf cfm-pm-backward-max-flr-time {
       type string;
       description "Time when maximum frame loss ratio occured at near end";
     }
     leaf cfm-pm-backward-avg-flr-percentage {
       type uint32;
       description "Average frame loss ratio percentage at far end";
     }
   }
   list cfm-iter-pm-history-avail-entry {
     leaf cfm-pm-history-record-number {
       type uint32;
       description "History Record Number";
     }
     leaf cfm-pm-mi-index {
       type uint32;
       description "Measurement Interval Index";
     }
     leaf cfm-pm-mi-suspect-status {
       type string;
       description "Status flag information for the field";
     }
     leaf cfm-pm-mi-start-time {
       type string;
       description "Measurement Interval start time";
     }
     leaf cfm-pm-mi-end-time {
       type string;
       description "Measurement Interval end time";
     }
     leaf cfm-pm-mi-elapsed-time {
       type string;
       description "Measurement Interval elapsed time";
     }
     leaf cfm-pm-mi-num-calculations {
       type uint32;
       description "Number of PM calculations done in the measurement interval";
     }
     leaf cfm-pm-forward-high-loss {
       type uint32;
       description "Accumulative number of high loss intervals at far end";
     }
     leaf cfm-pm-backward-high-loss {
       type uint32;
       description "Accumulative number of high loss intervals at near end";
     }
     leaf cfm-pm-forward-consecutive-high-loss {
       type uint32;
       description "Accumulative number of consecutive high loss intervals at far end";
     }
     leaf cfm-pm-backward-consecutive-high-loss {
       type uint32;
       description "Accumulative number of consecutive high loss intervals at near end";
     }
     leaf cfm-pm-forward-available {
       type uint32;
       description "Number of availabilty indicators at far end";
     }
     leaf cfm-pm-backward-available {
       type uint32;
       description "Number of availabilty indicators at near end";
     }
     leaf cfm-pm-forward-unavailable {
       type uint32;
       description "Number of un-availabilty indicators at far end";
     }
     leaf cfm-pm-backward-unavailable {
       type uint32;
       description "Number of un-availabilty indicators at near end";
     }
     leaf cfm-pm-forward-min-flr-percentage {
       type uint32;
       description "Minimum frame loss ratio percentage at far end";
     }
     leaf cfm-pm-forward-min-flr-time {
       type string;
       description "Time when minimum frame loss ratio occured at far end";
     }
     leaf cfm-pm-forward-max-flr-percentage {
       type uint32;
       description "Maximum frame loss ratio percentage at far end";
     }
     leaf cfm-pm-forward-max-flr-time {
       type string;
       description "Time when maximum frame loss ratio occured at far end";
     }
     leaf cfm-pm-forward-avg-flr-percentage {
       type uint32;
       description "Average frame loss ratio percentage at far end";
     }
     leaf cfm-pm-backward-min-flr-percentage {
       type uint32;
       description "Minimum frame loss ratio percentage at far end";
     }
     leaf cfm-pm-backward-min-flr-time {
       type string;
       description "Time when minimum frame loss ratio occured at near end";
     }
     leaf cfm-pm-backward-max-flr-percentage {
       type uint32;
       description "Maximum frame loss ratio percentage at far end";
     }
     leaf cfm-pm-backward-max-flr-time {
       type string;
       description "Time when maximum frame loss ratio occured at near end";
     }
     leaf cfm-pm-backward-avg-flr-percentage {
       type uint32;
       description "Average frame loss ratio percentage at far end";
     }
   }
 }
 grouping elmi-evc-information-block {
   container elmi-evc-entry {
     leaf elmi-evc-id {
       type string;
       description "EVC identifier";
     }
     leaf elmi-evc-status {
       type string;
       description "EVC status";
     }
     leaf elmi-evc-type {
       type string;
       description "EVC type";
     }
     leaf elmi-evc-reference-id {
       type uint32;
       description "EVC reference ID";
     }
     leaf elmi-evc-configured-remote-uni-count {
       type uint32;
       description "UNI count configured";
     }
     leaf elmi-evc-active-uni-count {
       type uint32;
       description "Active UNI count";
     }
     leaf elmi-evc-async-status-msg-transmit-interval {
       type int32;
       description "Time interval between E-LMI async messages per EVC";
     }
     leaf elmi-evc-protocol {
       type string;
     }
     leaf elmi-cfm-maintenance-domain {
       type string;
       description "CFM maintenance domain name";
     }
     leaf elmi-cfm-maintenance-association {
       type string;
       description "CFM maintenance association name";
     }
     leaf elmi-vpls-routing-instance {
       type string;
       description "VPLS routing instance name";
     }
     leaf elmi-l2ckt-interface-name {
       type string;
       description "L2circuit interface name";
     }
     leaf elmi-l2vpn-interface-name {
       type string;
       description "L2vpn interface name";
     }
     container elmi-evc-uni {
       leaf elmi-uni-id {
         type string;
         description "UNI identifier";
       }
       leaf elmi-interface-name {
         type string;
         description "Name of interface";
       }
       leaf elmi-operational-state {
         type string;
         description "E-LMI operational state";
       }
     }
   }
 }
 grouping elmi-interface-information-block {
   container elmi-interface-entry {
     leaf elmi-interface-name {
       type string;
       description "Name of interface";
     }
     leaf elmi-interface-status {
       type string;
       description "Interface state";
     }
     leaf elmi-uni-id {
       type string;
       description "UNI identifier";
     }
     leaf elmi-evc-map-type {
       type string;
       description "EVC map type";
     }
     leaf elmi-polling-verification-timer {
       type string;
       description "Polling verification timer enabled/disabled";
     }
     leaf elmi-operational-state {
       type string;
       description "E-LMI operational state";
     }
     leaf elmi-untagged-vlan-id {
       type uint32;
       description "VLAN ID assigned for Priority/Untagged service frames";
     }
     leaf elmi-default-evc {
       type string;
       description "Default EVC to which unmapped CE VLAN IDs are mapped";
     }
     container elmi-uni-evc {
       leaf elmi-evc-id {
         type string;
         description "EVC identifier";
       }
       leaf elmi-evc-reference-id {
         type uint32;
         description "EVC reference ID";
       }
       leaf elmi-evc-status {
         type string;
         description "EVC status";
       }
       leaf elmi-ce-vlan-ids {
         type string;
         description "CE VLAN IDs mapped to this EVC";
       }
     }
   }
 }
 grouping elmi-interface-statistics-block {
   container elmi-interface-statistics-entry {
     leaf elmi-interface-name {
       type string;
       description "Name of interface";
     }
     leaf elmi-reliability-errors {
       type uint32;
       description "Number of polling verification timeouts";
     }
     leaf elmi-protocol-errors {
       type uint32;
       description "Number of protocol errors";
     }
     leaf elmi-check-messages-received {
       type uint32;
       description "Number of E-LMI check messages received";
     }
     leaf elmi-check-messages-sent {
       type uint32;
       description "Number of E-LMI check messages sent";
     }
     leaf elmi-full-status-messages-received {
       type uint32;
       description "Number of full status messages received";
     }
     leaf elmi-full-status-messages-sent {
       type uint32;
       description "Number of full status messages sent";
     }
     leaf elmi-full-status-continued-messages-received {
       type uint32;
       description "Number of full status continued messages received";
     }
     leaf elmi-full-status-continued-messages-sent {
       type uint32;
       description "Number of full status continued messages sent";
     }
     leaf elmi-async-evc-status-messages-sent {
       type uint32;
       description "Number of asynchronous EVC messages sent";
     }
   }
 }
 grouping fnp-interface-information-block {
   list fnp-interface-entry {
     leaf fnp-interface-name {
       type string;
       description "Name of interface";
     }
     leaf fnp-vlan-id {
       type int32;
       description "VLAN ID";
     }
     leaf fnp-interface-oper-state {
       type string;
       description "Current interface operational state";
     }
     leaf fnp-interface-state {
       type string;
       description "FNP controlled interface operational state";
     }
     leaf fnp-source-interface-name {
       type string;
       description "Name of the interface receiving FNP message";
     }
     leaf fnp-source-mac {
       type string;
       description "Source MAC address of the FNP message";
     }
   }
 }
 grouping fnp-status-information-block {
   leaf fnp-interval {
     type string;
     description "FNP message interval";
   }
   leaf fnp-loss-threshold {
     type uint32;
     description "FNP message loss threshold";
   }
   list fnp-enabled-interface-entry {
     leaf fnp-interface-name {
       type string;
       description "Name of interface";
     }
     leaf fnp-domain-id {
       type uint32;
       description "FNP domain identifier";
     }
     leaf fnp-stp-root-id {
       type string;
       description "STP root MAC address";
     }
     leaf fnp-num-messages {
       type uint32;
       description "Number of active FNP messages";
     }
   }
 }
 grouping fnp-messages-information-block {
   list fnp-interface-messages {
     list fnp-message-entry {
       leaf fnp-port-number {
         type uint32;
         description "Originating port number";
       }
       leaf fnp-time-since-last-message {
         type string;
         description "Time since last FNP message received";
       }
       leaf fnp-time-created {
         type string;
         description "Time message received";
       }
       leaf fnp-time-since-last-update {
         type string;
         description "Time since last updated FNP message received";
       }
       leaf fnp-total-messages-received {
         type uint32;
         description "Total FNP messages received";
       }
       leaf fnp-domain-id {
         type uint32;
         description "FNP domain identifier";
       }
       leaf fnp-stp-root-id {
         type string;
         description "STP root MAC address";
       }
       leaf fnp-trigger-reason {
         type string;
         description "FNP trigger reason";
       }
       leaf fnp-effected-vlans {
         type string;
         description "Effected VLANs";
       }
       list fnp-disabled-interface-entry {
         leaf fnp-disabled-interface-name {
           type string;
           description "Name of the disabled interface";
         }
         leaf fnp-vlan-id {
           type int32;
           description "VLAN ID";
         }
         leaf fnp-time-ifl-down {
           type string;
           description "IFL disable trigger time";
         }
         leaf fnp-time-ifl-down-event {
           type string;
           description "IFL down event receive time";
         }
       }
     }
   }
 }
 }
