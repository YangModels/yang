/*
 * Copyright (c) 2017 Juniper Networks, Inc.
 * All rights reserved.
 */
 module show-hfrr {
  namespace "http://yang.juniper.net/yang/1.1/jrpc/show-hfrr/junos-qfx/17.2R1.13";
  prefix show-hfrr;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-hfrr-information {
     description "Show HFRR profile information";
     input {
       container daemon-select {
         choice daemon-select_c {
           case logical-system {
             leaf logical-system {
               description "Name of logical system, or 'all'";
               type string {
                 junos:posix-pattern "^[a-zA-Z0-9_-]{1,63}$";
                 junos:pattern-message "Logical-system name is a string consisting of up to 63 letters, numbers, dashes and underscores";
               }
             }
           }
           case fabric {
             leaf fabric {
               description "Internal fabric state";
               type empty;
             }
           }
         }
       }
     }
     output {
       container hfrr-information {
         uses hfrr-information-block;
       }
     }
   }
 grouping hfrr-information-block {
   list hfrrp {
     leaf ptr {
       type int32;
       description "HFRR profile pointer";
     }
     leaf state {
       type string;
       description "HFRR profile Current state";
     }
     leaf inactive-reason {
       type string;
       description "HFRR profile Inactive reason (if any)";
     }
     leaf prefix-limit-timer-expiration {
       type uint32;
       description "HFRR prefix limit blackout timer expiration (in secs)";
     }
     leaf prefix-limit-hit-count {
       type uint32;
       description "Number of times prefix limit was hit for this profile.";
     }
     leaf prefix-limit-last-occurance {
       type string;
       description "Time at which prefix limit was hit the last time.";
     }
     leaf ifl-name {
       type string;
       description "HFRR profile protected IFL Name";
     }
     leaf ifl-handle {
       type int32;
       description "HFRR profile protected IFL Handle";
     }
     leaf rt-instance-name {
       type string;
       description "HFRR profile Routing Instance Name";
     }
     leaf rt-instance-handle {
       type int32;
       description "HFRR profile Routing Instance Handle";
     }
     leaf sync-bg-running {
       type string;
       description "HFRR profile Sync BG running currently";
     }
     leaf rts-filter-set {
       type string;
       description "HFRR profile RTS Filter Set";
     }
     leaf delete-bg-running {
       type string;
       description "HFRR profile Delete BG running currently";
     }
     leaf arp-prefix-limit {
       type int32;
       description "HFRR profile ARP prefix limit";
     }
     leaf blackout-timeout-scale-factor {
       type int32;
       description "HFRR profile blackout timeout scale factor (in mins)";
     }
     leaf num-arp-routes {
       type int32;
       description "HFRR profile No of ARP routes learnt";
     }
     leaf num-frr-routes {
       type int32;
       description "HFRR profile No of HFRR routes added currently";
     }
   }
 }
 }
