/*
 * Copyright (c) 2017 Juniper Networks, Inc.
 * All rights reserved.
 */
 module show-security {
  namespace "http://yang.juniper.net/yang/1.1/jrpc/show-security/junos-qfx/17.2R1.13";
  prefix show-security;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-security-alarm-information {
     description "Show active security alarm information";
     input {
       leaf alarm-id {
         description "Alarm ID filter";
         type uint32;
       }
       leaf-list alarm-type {
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type time;
       }
       leaf older-than {
         description "Alarms older than filter (YYYY-MM-DD.HH:MM:SS)";
         type time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf style {
         type enumeration {
           enum "detail" {
             description "Show detail alarm information";
           }
         }
       }
     }
     output {
       container security-alarm-information {
         uses security-alarm-information-block;
       }
     }
   }
   rpc get-security-log-information {
     description "Show auditable security log information";
     input {
       leaf destination-address {
         description "Destination address and optional prefix length";
         type ipprefix-optional;
       }
       leaf destination-port {
         description "Destination port";
         type uint32;
       }
       leaf event-id {
         description "Event ID filter";
         type string;
       }
       leaf interface-name {
         description "Name of interface";
         type string;
       }
       leaf older-than {
         description "Events older than filter (YYYY-MM-DD.HH:MM:SS)";
         type time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type time;
       }
       leaf result {
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type ipprefix-optional;
       }
       leaf source-port {
         description "Source port";
         type uint32;
       }
       leaf username {
         description "Username filter";
         type string;
       }
       leaf sort-by {
         description "Sort by selected field";
         default "time";
         type enumeration {
           enum "destination-address" {
             description "Sort by destination address";
           }
           enum "destination-port" {
             description "Sort by destination port";
           }
           enum "interface-name" {
             description "Sort by interface name";
           }
           enum "policy-name" {
             description "Sort by policy name";
           }
           enum "protocol" {
             description "Sort by protocol";
           }
           enum "source-address" {
             description "Sort by source address";
           }
           enum "source-port" {
             description "Sort by source port";
           }
           enum "time" {
             description "Sort by time of event arrival";
           }
           enum "username" {
             description "Sort by event user name ";
           }
         }
       }
       leaf direction {
         default "ascending";
         type enumeration {
           enum "ascending" {
             description "Sort in ascending order";
           }
           enum "descending" {
             description "Sort in descending order";
           }
         }
       }
       leaf style {
         type enumeration {
           enum "detail" {
             description "Show detail alarm information";
           }
         }
       }
     }
     output {
       container security-log-information {
         uses security-log-information-block;
       }
     }
   }
   rpc get-hakr-keychain-information {
     description "Show all protocols keychain";
     input {
       leaf verbosity {
         default "brief";
         type enumeration {
           enum "brief" {
             description "Display brief output (default)";
           }
           enum "detail" {
             description "Display detailed output";
           }
         }
       }
     }
     output {
       container hakr-keychain-information {
         uses hakr-keychain-information-block;
       }
     }
   }
   rpc get-pki-certificate-request {
     description "Show PKCS-10 certificate request information";
     input {
       leaf certificate-id {
         description "Certificate identifier";
         type string {
           junos:posix-pattern "^.{1,32}$";
           junos:pattern-message "Must be string of 32 characters or less";
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-ca-certificate {
     description "Show certificate-authority certificate information";
     input {
       container ca-cert-choice {
         choice ca-cert-choice_c {
           case ca-profile {
             leaf ca-profile {
               description "Certificate authority profile";
               type string {
                 junos:posix-pattern "^.{1,32}$";
                 junos:pattern-message "Must be string of 32 characters or less";
               }
             }
           }
           case ca-profile-group {
             leaf ca-profile-group {
               description "Show CA profile group";
               type string {
                 junos:posix-pattern "^.{1,32}$";
                 junos:pattern-message "Must be string of 32 characters or less";
               }
             }
           }
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-local-certificate {
     description "Show router certificate information";
     input {
       container certificate-choice {
         choice certificate-choice_c {
           case certificate-id {
             leaf certificate-id {
               description "Certificate identifier";
               type string {
                 junos:posix-pattern "^.{1,32}$";
                 junos:pattern-message "Must be string of 32 characters or less";
               }
             }
           }
           case system-generated {
             leaf system-generated {
               description "Autogenerated self-signed certificate";
               type empty;
             }
           }
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-crl {
     description "Show certificate revocation list information";
     input {
       leaf ca-profile {
         description "Certificate authority profile";
         type string {
           junos:posix-pattern "^.{1,32}$";
           junos:pattern-message "Must be string of 32 characters or less";
         }
       }
       leaf level {
         default "brief";
         type enumeration {
           enum "brief" {
             description "Display brief output";
           }
           enum "detail" {
             description "Display detailed output";
           }
         }
       }
     }
     output {
       container x509-pkid-crl-information-list {
         uses x509-pkid-crl-information-list-block;
       }
     }
   }
   rpc get-gvpn-security-associations-information {
     description "Show IPSec security association information";
     input {
       leaf level {
         default "brief";
         type enumeration {
           enum "brief" {
             description "Display brief output";
           }
           enum "detail" {
             description "Display detailed output";
           }
         }
       }
       leaf show-gvpn-index-ipsec-security-association {
         description "Index of security association";
         type uint32 {
           range "10001 .. 20000";
         }
       }
       leaf group-id {
         description "Group VPN identification number";
         type uint32 {
           range "1 .. 4294967295";
         }
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       container ipsec-security-associations-information {
         uses ipsec-security-associations-information-block;
       }
     }
   }
   rpc get-gvpn-ipsec-statistics-information {
     description "Show IPSec statistics";
     input {
       leaf fpc {
         description "FPC slot number";
         type uint32 {
           range "0 .. 63";
         }
       }
       leaf pic {
         description "PIC slot number";
         type uint32 {
           range "0 .. 3";
         }
       }
       leaf show-gvpn-index-ipsec-statistics {
         description "Index of Security Association";
         type uint32 {
           range "10001 .. 20000";
         }
       }
     }
     output {
       container usp-ipsec-total-statistics-information {
         uses usp-ipsec-total-statistics-information-block;
       }
     }
   }
   rpc get-gvpn-inactive-tunnels {
     description "Inactive-tunnels";
     input {
       leaf level {
         default "brief";
         type enumeration {
           enum "brief" {
             description "Display brief output";
           }
           enum "detail" {
             description "Display detailed output";
           }
         }
       }
       leaf group-id {
         description "Group VPN identification number";
         type uint32 {
           range "1 .. 4294967295";
         }
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       container ipsec-unestablished-tunnel-information {
         uses ipsec-unestablished-tunnel-information-block;
       }
     }
   }
   rpc get-gvpn-ike-security-associations-information {
     description "Show IKE security association information";
     input {
       leaf level {
         default "brief";
         type enumeration {
           enum "brief" {
             description "Show brief output (default)";
           }
           enum "detail" {
             description "Show detailed output";
           }
         }
       }
       leaf peer-address {
         description "IP address of the peer";
         type ipaddr;
       }
       leaf index {
         description "Index of security association";
         default "0";
         type uint32;
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       container ike-security-associations-information {
         uses ike-security-associations-information-block;
       }
     }
   }
   rpc get-gvpn-kek-security-associations-information {
     description "Show KEK security association information";
     input {
       leaf level {
         default "brief";
         type enumeration {
           enum "brief" {
             description "Show brief output (default)";
           }
           enum "detail" {
             description "Show detailed output";
           }
         }
       }
       leaf peer-address {
         description "IP address of the peer";
         type ipaddr;
       }
       leaf index {
         description "Index of security association";
         default "0";
         type uint32;
       }
       container groupchoice {
         description "Specify a group by name or ID";
         choice groupchoice_c {
           case group-id {
             leaf group-id {
               description "Group VPN identification number";
               type uint32 {
                 range "1 .. 4294967295";
               }
             }
           }
           case vpn {
             leaf vpn {
               description "Group VPN Name";
               type string {
                 length "1 .. 32";
               }
             }
           }
         }
       }
     }
     output {
       container gvpn-kek-security-associations-information {
         uses gvpn-kek-security-associations-information-block;
       }
     }
   }
   rpc get-mka-session-information {
     description "Show MKA sessions information";
     output {
       container mka-session-information {
         uses mka-session-information-block;
       }
     }
   }
   rpc get-mka-session-interface-information {
     description "Show MKA session on this interface";
     input {
       leaf interface-name {
         description "Show MKA session for this interface";
         default "all";
         type interface-name;
       }
     }
   }
   rpc get-mka-statistics {
     description "Show MKA statistics";
     output {
       container mka-statistics {
         uses mka-statistics-block;
       }
     }
   }
   rpc get-mka-interface-statistics {
     description "Show MKA statistics on this interface";
     input {
       leaf interface-name {
         description "Show MKA statistics for this interface";
         default "all";
         type interface-name;
       }
     }
   }
   rpc get-macsec-connection-information {
     description "Show MAC Security connections information";
     output {
       container macsec-connection-information {
         uses macsec-connection-information-block;
       }
     }
   }
   rpc get-macsec-connection-interface-information {
     description "Show MAC security connections on this interface";
     input {
       leaf interface-name {
         description "Show MAC security connections for this interface";
         default "all";
         type interface-name;
       }
     }
   }
   rpc get-macsec-statistics {
     description "Show MAC Security statistics";
     input {
       leaf verbosity_level {
         default "brief";
         type enumeration {
           enum "brief" {
             description "Display brief output (default)";
           }
           enum "detail" {
             description "Display detailed output";
           }
         }
       }
     }
     output {
       container macsec-statistics {
         uses macsec-statistics-block;
       }
     }
   }
   rpc get-macsec-interface-statistics {
     description "Show MAC security statistics on this interface";
     input {
       leaf verbosity_level {
         default "brief";
         type enumeration {
           enum "brief" {
             description "Display brief output (default)";
           }
           enum "detail" {
             description "Display detailed output";
           }
         }
       }
       leaf interface-name {
         description "Show MAC security statistics for this interface";
         default "all";
         type interface-name;
       }
     }
   }
 grouping security-alarm-information-block {
   container brief {
     description "Information about all active security alarms";
     list security-alarm {
       description "Detailed information about an active security alarm";
       leaf security-alarm-id {
         type string;
         description "Alarm ID";
       }
       leaf security-alarm-time {
         type string;
         description "Time of the alarm";
       }
       leaf security-alarm-message {
         type string;
         description "Full message of the alarm";
       }
     }
   }
   container detail {
     description "Information about all active security alarms";
     list security-alarm {
       description "Detailed information about an active security alarm";
       leaf security-alarm-id {
         type string;
         description "Alarm ID";
       }
       leaf security-alarm-type {
         type string;
         description "Alarm type";
       }
       leaf security-alarm-time {
         type string;
         description "Time of the alarm";
       }
       leaf security-alarm-message {
         type string;
         description "Full message of the alarm";
       }
       leaf severity {
         type string;
         description "Syslog message severity";
       }
       container process {
         description "Process that generated the event";
         leaf name {
           type string;
           description "Syslog message tag name";
         }
         leaf pid {
           type int32;
           description "PID of the process that generated the event";
         }
       }
     }
   }
 }
 grouping security-log-information-block {
   container brief {
     description "Information about all active security events";
     list security-event {
       description "Detailed information about a security event";
       leaf security-event-time {
         type string;
         description "Time of the event";
       }
       leaf security-event-message {
         type string;
         description "Full message of the event";
       }
     }
   }
   container detail {
     description "Information about all active security events";
     list security-event {
       description "Detailed information about a security event";
       leaf security-event-id {
         type string;
         description "Event ID";
       }
       leaf security-event-time {
         type string;
         description "Time of the event";
       }
       leaf security-event-message {
         type string;
         description "Full message of the event";
       }
       leaf severity {
         type string;
         description "Syslog message severity";
       }
       leaf security-event-result {
         type string;
         description "Result of this event (success or failure)";
       }
       leaf security-event-username {
         type string;
         description "Username associated with event";
       }
       leaf security-event-interface-name {
         type string;
         description "Interface name associated with event";
       }
       leaf security-event-protocol {
         type string;
         description "Protocol associated with event";
       }
       leaf security-event-policy-name {
         type string;
         description "Policy name associated with event";
       }
       leaf security-event-destination-address {
         type string;
         description "Destination address associated with event";
       }
       leaf security-event-destination-port {
         type int32;
         description "Destination port associated with event";
       }
       leaf security-event-source-address {
         type string;
         description "Source address associated with event";
       }
       leaf security-event-source-port {
         type int32;
         description "Source port associated with event";
       }
       container process {
         description "Process that generated the event";
         leaf name {
           type string;
           description "Syslog message tag name";
         }
         leaf pid {
           type int32;
           description "PID of the process that generated the event";
         }
       }
     }
   }
 }
 grouping hakr-keychain-information-block {
   container brief {
     list hakr-keychain {
       description "Information about Keychain";
       leaf hakr-keychain-name {
         type string;
         description "Keychain name";
       }
       leaf hakr-keychain-active-send-key {
         type int32;
         description "Transmit key ID";
       }
       leaf hakr-keychain-active-receive-key {
         type int32;
         description "Receive key ID";
       }
       leaf hakr-keychain-next-send-key {
         type string;
         description "Next transmit key";
       }
       leaf hakr-keychain-next-receive-key {
         type string;
         description "Next receive key";
       }
       leaf hakr-keychain-next-key-time {
         type string;
         description "Key transition time";
       }
       leaf hakr-keychain-tolerance {
         type int32;
         description "Clock skew tolerance";
       }
       list hakr-keys {
         description "Information about the clients";
         leaf hakr-key-id {
           type string;
           description "Authentication element identifier";
         }
         leaf hakr-key-algorithm {
           type string;
           description "Authentication algorithm";
         }
         leaf hakr-key-state {
           type string;
           description "Authentication key operational state";
         }
         leaf hakr-key-options {
           type string;
           description "Authentication key options";
         }
         leaf hakr-key-start-time {
           type string;
           description "Time since the current session began (hours:minutes:seconds)";
         }
         leaf hakr-key-mode {
           type string;
           description "Authentication key mode";
         }
       }
     }
     list hakr-keys {
       description "Information about the clients";
     }
   }
   container detail {
     list hakr-keychain {
       description "Information about Keychain";
       leaf hakr-keychain-name {
         type string;
         description "Keychain name";
       }
       leaf hakr-keychain-active-send-key {
         type int32;
         description "Transmit key ID";
       }
       leaf hakr-keychain-active-receive-key {
         type int32;
         description "Receive key ID";
       }
       leaf hakr-keychain-next-send-key {
         type string;
         description "Next transmit key";
       }
       leaf hakr-keychain-next-receive-key {
         type string;
         description "Next receive key";
       }
       leaf hakr-keychain-next-key-time {
         type string;
         description "Key transition time";
       }
       leaf hakr-keychain-tolerance {
         type int32;
         description "Clock skew tolerance";
       }
       leaf hakr-sa-clients {
         type string;
         description "Keychain clients ";
       }
       list hakr-keys {
         description "Information about the clients";
         leaf hakr-key-id {
           type string;
           description "Authentication element identifier";
         }
         leaf hakr-key-algorithm {
           type string;
           description "Authentication algorithm";
         }
         leaf hakr-key-state {
           type string;
           description "Authentication key operational state";
         }
         leaf hakr-key-options {
           type string;
           description "Authentication key options";
         }
         leaf hakr-key-start-time {
           type string;
           description "Time since the current session began (hours:minutes:seconds)";
         }
         leaf hakr-key-mode {
           type string;
           description "Authentication key mode";
         }
       }
     }
     list hakr-keys {
       description "Information about the clients";
       leaf hakr-key-id {
         type string;
         description "Authentication element identifier";
       }
       leaf hakr-key-algorithm {
         type string;
         description "Authentication algorithm";
       }
       leaf hakr-key-state {
         type string;
         description "Authentication key operational state";
       }
       leaf hakr-key-options {
         type string;
         description "Authentication key options";
       }
       leaf hakr-key-start-time {
         type string;
         description "Time since the current session began (hours:minutes:seconds)";
       }
       leaf hakr-key-mode {
         type string;
         description "Authentication key mode";
       }
     }
   }
 }
 grouping x509-pki-certificate-info-list-block {
   container x509-certificate-info {
     description "Detailed information about an X.509 certificate";
     container verbose {
       description "Detailed information about an X.509 certificate";
       leaf identifier {
         type string;
         description "Certificate identifier";
       }
       leaf signature-algorithm {
         type string;
         description "Algorithm used by the CA to sign the certificate";
       }
       container public-key {
         description "Information about an X.509 public key";
         leaf public-key-algorithm {
           type string;
           description "Algorithm used for creating the subject public key";
         }
         leaf public-key-length {
           type int32;
           description "Length of X.509 public";
         }
         leaf public-key-verification-status {
           type string;
           description "Verification status of X.509 public key";
         }
       }
       list fingerprint {
         description "Fingerprint";
       }
       container issuer {
         description "Identifies the CA that issued certificate";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
       container subject {
         description "Information about certificate owner";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
     }
     container brief {
       description "Detailed information about an X.509 certificate";
       leaf identifier {
         type string;
         description "Certificate identifier";
       }
       leaf certificate-type {
         type string;
         description "X.509 certificate type";
       }
       leaf status {
         type string;
       }
       container issue-info {
         leaf recipient {
           type string;
         }
         leaf issued-by {
           type string;
         }
       }
       container public-key {
         description "Information about an X.509 public key";
         leaf public-key-algorithm {
           type string;
           description "Algorithm used for creating the subject public key";
         }
         leaf public-key-length {
           type int32;
           description "Length of X.509 public";
         }
         leaf public-key-verification-status {
           type string;
           description "Verification status of X.509 public key";
         }
       }
       container validity {
         description "Information about validity period for X.509 certificate";
         leaf not-before {
           type string;
           description "Start date of validity period";
         }
         leaf not-after {
           type string;
           description "End date of validity period";
         }
       }
       container issuer {
         description "Identifies the CA that issued certificate";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
       container subject {
         description "Information about certificate owner";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
     }
     container detail {
       description "Detailed information about an X.509 certificate";
       leaf identifier {
         type string;
         description "Certificate identifier";
       }
       leaf certificate-type {
         type string;
         description "X.509 certificate type";
       }
       leaf status {
         type string;
       }
       leaf version {
         type string;
         description "Certificate version";
       }
       leaf signature-algorithm {
         type string;
         description "Algorithm used by the CA to sign the certificate";
       }
       list serial-number-list {
         description "Serial numbers of one or more X.509 certificate";
         leaf serial-number-x509 {
           type string;
           description "Serial number of an X.509 certificate";
         }
       }
       container public-key {
         description "Information about an X.509 public key";
         leaf public-key-algorithm {
           type string;
           description "Algorithm used for creating the subject public key";
         }
         leaf public-key-length {
           type int32;
           description "Length of X.509 public";
         }
         leaf public-key-verification-status {
           type string;
           description "Verification status of X.509 public key";
         }
       }
       list fingerprint {
         description "Fingerprint";
         leaf fingerprint-content {
           type string;
         }
         leaf fingerprint-hash-algorithm {
           type string;
         }
       }
       list public-key-contents-list {
         leaf key-contents {
           type string;
           description "Contents of an X.509 public key";
         }
       }
       list subject-string-list {
         leaf subject-string {
           type string;
           description "Cerificate's distinguished name";
         }
       }
       list alternate-subject-list {
         leaf alternate-subject {
           type string;
           description "Series of alternate subject in X.509 certificate";
         }
       }
       list key-usage-list {
         leaf key-usage {
           type string;
           description "Purpose for which X.509 key is used";
         }
       }
       list distribution-crl-list {
         description "Information about one or more distribution certificate revocation lists";
         leaf distribution-crl {
           type string;
           description "Information about a distribution CRL";
         }
       }
       list authority-information-access-ocsp-list {
         description "Information about one or more ocsp authority-information-access locations";
         leaf authority-information-access-ocsp {
           type string;
           description "Information about ocsp authority-information-access locations";
         }
       }
       list certificate-policy-list {
         description "Certificate policy identifiers";
         leaf certificate-policy {
           type string;
           description "List of certificate policy identifiers";
         }
       }
       container validity {
         description "Information about validity period for X.509 certificate";
         leaf not-before {
           type string;
           description "Start date of validity period";
         }
         leaf not-after {
           type string;
           description "End date of validity period";
         }
       }
       container auto-re-enrollment {
         leaf auto-re-enrollment-status {
           type string;
           description "Auto-re-enrollment information";
         }
         leaf auto-re-enrollment-next-trigger-time {
           type string;
           description "Auto-re-enrollment next trigger time";
         }
       }
       container issuer {
         description "Identifies the CA that issued certificate";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
       container subject {
         description "Information about certificate owner";
         container distinguished-name {
           leaf organization-name {
             type string;
             description "Organization";
           }
           leaf organizational-unit-name {
             type string;
             description "Organization unit";
           }
           leaf country-name {
             type string;
             description "Country name";
           }
           leaf state-or-province-name {
             type string;
             description "State";
           }
           leaf locality-name {
             type string;
             description "Locality";
           }
           leaf common-name {
             type string;
             description "Common name";
           }
           leaf email-address {
             type string;
             description "E-mail address";
           }
           leaf domain-component {
             type string;
             description "Domain component";
           }
           leaf dn-serial-number {
             type string;
             description "DN Serial number";
           }
         }
       }
     }
   }
 }
 grouping x509-pkid-crl-information-list-block {
   container pkid-x509-crl-information {
     description "Detailed information about X.509 certificate revocation list";
     container brief {
       description "Detailed information about X.509 certificate revocation list";
       leaf identifier {
         type string;
         description "Certificate identifier";
       }
       leaf crl-version {
         type string;
         description "CRL version";
       }
       leaf crl-number {
         type string;
         description "CRL sequence number";
       }
       leaf crl-issuer {
         type string;
         description "CRL issuer name";
       }
       container crl-validity {
         description "Information about validity period for X.509 certificate revocation list";
         leaf effective-date {
           type string;
           description "Effective date of CRL";
         }
         leaf next-update {
           type string;
           description "Next update of CRL";
         }
       }
     }
     container detail {
       description "Detailed information about X.509 certificate revocation list";
       leaf identifier {
         type string;
         description "Certificate identifier";
       }
       leaf crl-version {
         type string;
         description "CRL version";
       }
       leaf crl-number {
         type string;
         description "CRL sequence number";
       }
       leaf crl-issuer {
         type string;
         description "CRL issuer name";
       }
       list crl-revocation-list {
         leaf revoked-cert-serial-number {
           type string;
           description "Serial number of revoked certificate";
         }
         leaf crl-revocation-date {
           type string;
           description "Revocation date";
         }
       }
       container crl-validity {
         description "Information about validity period for X.509 certificate revocation list";
         leaf effective-date {
           type string;
           description "Effective date of CRL";
         }
         leaf next-update {
           type string;
           description "Next update of CRL";
         }
       }
     }
   }
 }
 grouping ipsec-security-associations-information-block {
   container brief {
     container ipsec-security-associations {
     }
     container ipsec-security-associations-block {
       container ipsec-security-associations {
         leaf sa-direction {
           type string;
           description "Direction of the security association";
         }
         leaf sa-tunnel-index {
           type int32;
           description "Tunnel index";
         }
         leaf sa-protocol {
           type string;
           description "IPSec security protocol";
         }
         leaf sa-esp-encryption-algorithm {
           type string;
           description "ESP Encryption Algorithm";
         }
         leaf sa-hmac-algorithm {
           type string;
           description "HMAC Authentication Algorithm";
         }
         leaf sa-spi {
           type string;
           description "Security Parameter Index";
         }
         leaf sa-hard-lifetime {
           type string;
           description "Remaining lifetime, in seconds or kilobytes, before hard lifetime expires";
         }
         leaf sa-lifesize-remaining {
           type string;
           description "Lifetime Remaining in Kilo Bytes";
         }
         leaf sa-vpn-monitoring-state {
           type string;
           description "VPN Monitoring State";
         }
         leaf sa-virtual-system {
           type string;
           description "Virtual System";
         }
         leaf sa-port {
           type int32;
           description "Port";
         }
         leaf sa-remote-gateway {
           type ipaddr;
           description "Remote gateway address";
         }
       }
     }
     container ipsec-gvpn-security-associations-block {
       container ipsec-security-associations {
         leaf sa-direction {
           type string;
           description "Direction of the security association";
         }
         leaf sa-tunnel-index {
           type int32;
           description "Tunnel index";
         }
         leaf sa-gvpn-server {
           type string;
           description "Group VPN Server Address";
         }
         leaf sa-port {
           type int32;
           description "Port";
         }
         leaf sa-protocol {
           type string;
           description "IPSec security protocol";
         }
         leaf sa-esp-encryption-algorithm {
           type string;
           description "ESP Encryption Algorithm";
         }
         leaf sa-hmac-algorithm {
           type string;
           description "HMAC Authentication Algorithm";
         }
         leaf sa-spi {
           type string;
           description "Security Parameter Index";
         }
         leaf sa-hard-lifetime {
           type string;
           description "Remaining lifetime, in seconds or kilobytes, before hard lifetime expires";
         }
         leaf sa-lifesize-remaining {
           type string;
           description "Lifetime Remaining in Kilo Bytes";
         }
         leaf sa-gvpn-groupid {
           type int32;
           description "Group VPN Group Id";
         }
         leaf sa-virtual-system {
           type string;
           description "Virtual System";
         }
       }
       container sa-child-tunnel-id-policy {
       }
     }
   }
   container detail {
     container ipsec-security-associations {
     }
     container ipsec-security-associations-block {
       leaf sa-tunnel-index {
         type int32;
         description "Tunnel index";
       }
       leaf sa-virtual-system {
         type string;
         description "Virtual System";
       }
       leaf sa-vpn-name {
         type string;
         description "VPN Name";
       }
       leaf sa-local-gateway {
         type ipaddr;
         description "Local gateway address";
       }
       leaf sa-remote-gateway {
         type ipaddr;
         description "Remote gateway address";
       }
       leaf sa-local-identity {
         type string;
         description "Local identity information";
       }
       leaf sa-remote-identity {
         type string;
         description "Remote identity information";
       }
       leaf sa-ike-version {
         type string;
         description "IKE version number used in negotiation";
       }
       container sa-df-bit-policy-name {
         leaf sa-df-bit {
           type string;
           description "Fragmentation bit";
         }
         leaf sa-policy-name {
           type string;
           description "Policy name";
         }
         leaf sa-bind-interface {
           type string;
           description "VPN bind-interface";
         }
       }
       container sa-dev-info {
         leaf sa-port {
           type int32;
           description "Port";
         }
         leaf sa-nego-num {
           type int32;
           description "SA nego num";
         }
         leaf sa-nego-fail {
           type int32;
           description "SA nego fail num";
         }
         leaf sa-del-num {
           type int32;
           description "SA defer delete count";
         }
         leaf sa-flag {
           type int32;
           description "SA flags";
         }
         leaf stats-name {
           type string;
         }
       }
       container ipsec-security-associations {
         leaf sa-direction {
           type string;
           description "Direction of the security association";
         }
         leaf sa-spi {
           type string;
           description "Security Parameter Index";
         }
         leaf sa-aux-spi {
           type string;
           description "Auxiliary Security Parameter Index";
         }
         leaf sa-mode {
           type string;
           description "Mode of the security association";
         }
         leaf sa-type {
           type string;
         }
         leaf sa-state {
           type string;
           description "Status of the SA";
         }
         leaf sa-vpn-monitoring-state {
           type string;
           description "VPN Monitoring State";
         }
         leaf sa-protocol {
           type string;
           description "IPSec security protocol";
         }
         leaf sa-authentication-algorithm {
           type string;
           description "Authentication algorithm";
         }
         leaf sa-encryption-algorithm {
           type string;
           description "Encryption algorithm";
         }
         leaf sa-soft-lifetime {
           type string;
           description "Remaining lifetime, in seconds or kilobytes, before soft lifetime expires";
         }
         leaf sa-hard-lifetime {
           type string;
           description "Remaining lifetime, in seconds or kilobytes, before hard lifetime expires";
         }
         leaf sa-lifesize-remaining {
           type string;
           description "Lifetime Remaining in Kilo Bytes";
         }
         leaf sa-anti-replay-service {
           type string;
           description "Anti-replay service";
         }
       }
       container sa-location {
         description "Location where SA is processed";
         leaf sa-fpc {
           type int32;
           description "FPC number";
         }
         leaf sa-pic {
           type int32;
           description "PIC number";
         }
         leaf sa-kmd-instance {
           type int32;
           description "KMD instance number";
         }
       }
     }
     container ipsec-gvpn-security-associations-block {
       leaf sa-virtual-system {
         type string;
         description "Virtual System";
       }
       leaf sa-vpn-name {
         type string;
         description "VPN Name";
       }
       leaf sa-local-gateway {
         type ipaddr;
         description "Local gateway address";
       }
       leaf sa-remote-gateway {
         type ipaddr;
         description "Remote gateway address";
       }
       leaf sa-local-identity {
         type string;
         description "Local identity information";
       }
       leaf sa-remote-identity {
         type string;
         description "Remote identity information";
       }
       leaf sa-gvpn-groupid {
         type int32;
         description "Group VPN Group Id";
       }
       leaf sa-match-dir {
         type string;
         description "Group VPN rule match direction";
       }
       leaf sa-tunnel-mtu {
         type int32;
         description "MTU of the IPSec Tunnel";
       }
       leaf sa-gvpn-vrf-name {
         type string;
         description "SA routing instance name";
       }
       container sa-df-bit-policy-name {
         leaf sa-df-bit {
           type string;
           description "Fragmentation bit";
         }
       }
       container ipsec-gvpn-sa-stats {
         leaf ipsec-sa-stats {
           type string;
           description "Ipsec SA stats";
         }
       }
       container ipsec-gvpn-sa-flags {
         leaf sa-rekey-needed {
           type string;
           description "SA rekey needed";
         }
       }
       container ipsec-security-associations {
         leaf sa-direction {
           type string;
           description "Direction of the security association";
         }
         leaf sa-spi {
           type string;
           description "Security Parameter Index";
         }
         leaf sa-aux-spi {
           type string;
           description "Auxiliary Security Parameter Index";
         }
         leaf sa-gvpn-groupid {
           type int32;
           description "Group VPN Group Id";
         }
         leaf sa-mode {
           type string;
           description "Mode of the security association";
         }
         leaf sa-type {
           type string;
         }
         leaf sa-state {
           type string;
           description "Status of the SA";
         }
         leaf sa-protocol {
           type string;
           description "IPSec security protocol";
         }
         leaf sa-hmac-algorithm {
           type string;
           description "HMAC Authentication Algorithm";
         }
         leaf sa-esp-encryption-algorithm {
           type string;
           description "ESP Encryption Algorithm";
         }
         leaf sa-soft-lifetime {
           type string;
           description "Remaining lifetime, in seconds or kilobytes, before soft lifetime expires";
         }
         leaf sa-hard-lifetime {
           type string;
           description "Remaining lifetime, in seconds or kilobytes, before hard lifetime expires";
         }
         leaf sa-activate-lifetime {
           type string;
           description "Activate time";
         }
         leaf sa-lifesize-remaining {
           type string;
           description "Lifetime Remaining in Kilo Bytes";
         }
         leaf sa-anti-replay-service {
           type string;
           description "Anti-replay service";
         }
       }
       container sa-child-tunnel-id-policy {
         leaf sa-tunnel-id {
           type int32;
           description "Tunnel id";
         }
         container sa-child-policy-list {
           leaf sa-policy-source-prefix {
             type string;
             description "Group VPN child sa policy source prefix";
           }
           leaf sa-policy-dest-prefix {
             type string;
             description "Group VPN child sa policy destination prefix";
           }
         }
       }
       container sa-location {
         description "Location where SA is processed";
         leaf sa-fpc {
           type int32;
           description "FPC number";
         }
         leaf sa-pic {
           type int32;
           description "PIC number";
         }
         leaf sa-kmd-instance {
           type int32;
           description "KMD instance number";
         }
       }
     }
   }
 }
 grouping usp-ipsec-total-statistics-information-block {
   leaf pic-name {
     type string;
     description "PIC name";
   }
   leaf service-set-name {
     type string;
     description "Service set name";
   }
   leaf local-gateway {
     type ipaddr;
     description "Local gateway address";
   }
   leaf remote-gateway {
     type ipaddr;
     description "Remote gateway address";
   }
   leaf tunnel-index {
     type int32;
     description "Tunnel index";
   }
   container esp-statistics {
     leaf esp-encrypted-bytes {
       type uint64;
       description "ESP encrypted bytes information";
     }
     leaf esp-decrypted-bytes {
       type uint64;
       description "ESP decrypted bytes information";
     }
     leaf esp-encrypted-packets {
       type uint64;
       description "ESP encrypted packets information";
     }
     leaf esp-decrypted-packets {
       type uint64;
       description "ESP decrypted packets information";
     }
   }
   container ah-statistics {
     leaf ah-input-bytes {
       type uint64;
       description "AH input bytes information";
     }
     leaf ah-output-bytes {
       type uint64;
       description "AH output bytes information";
     }
     leaf ah-input-packets {
       type uint64;
       description "AH input packets information";
     }
     leaf ah-output-packets {
       type uint64;
       description "AH output packets information";
     }
   }
   container d3p-statistics {
     leaf d3p-old-packets {
       type uint64;
       description "D3p packets information";
     }
     leaf d3p-new-packets {
       type uint64;
       description "D3p packets information";
     }
     leaf d3p-no-header-packets {
       type uint64;
       description "D3p packets information";
     }
     leaf d3p-unexpected-header-packets {
       type uint64;
       description "D3p packets information";
     }
   }
   container fail-open-statistics {
     leaf fail-open-packets-received {
       type uint64;
       description "Fail open packets information";
     }
     leaf fail-open-packets-sent {
       type uint64;
       description "Fail open packets information";
     }
   }
   container error-statistics {
     leaf ah-authentication-failures {
       type int32;
       description "AH authentication failures information";
     }
     leaf esp-authentication-failures {
       type int32;
       description "ESP authentication failures information";
     }
     leaf esp-decryption-failures {
       type int32;
       description "ESP decryption failures information";
     }
     leaf bad-headers {
       type int32;
       description "Bad header information";
     }
     leaf bad-trailers {
       type int32;
       description "Bad trailer information";
     }
     leaf replay-before-window-drops {
       type int32;
       description "Replay before window drop information";
     }
     leaf replay-pkts {
       type int32;
       description "Replayed pkt information";
     }
     leaf rule-lookup-fail {
       type int32;
       description "Rule lookup failure information";
     }
     leaf no-sa-errors {
       type int32;
       description "No SA error information";
     }
     leaf ip-integrity-errors {
       type int32;
       description "IP Integrity error information";
     }
     leaf exceeds-tunnel-mtu {
       type int32;
       description "Exceeds Tunnel MTU";
     }
     leaf flow-errors {
       type int32;
       description "Flow error information";
     }
     leaf misc-errors {
       type int32;
       description "Misc error information";
     }
   }
 }
 grouping ipsec-unestablished-tunnel-information-block {
   container brief {
     container ipsec-security-associations {
     }
     container ipsec-security-associations-block {
       container ipsec-security-associations {
         leaf sa-tunnel-index {
           type int32;
           description "Tunnel index";
         }
         leaf sa-port {
           type int32;
           description "Port";
         }
         leaf sa-nego-num {
           type int32;
           description "SA nego num";
         }
         leaf sa-nego-fail {
           type int32;
           description "SA nego fail num";
         }
         leaf sa-flag {
           type int32;
           description "SA flags";
         }
         leaf sa-remote-gateway {
           type ipaddr;
           description "Remote gateway address";
         }
         leaf stats-name {
           type string;
         }
       }
     }
     container ipsec-gvpn-inactive-tunnel-info-block {
       leaf sa-gvpn-server {
         type string;
         description "Group VPN Server Address";
       }
       leaf sa-port {
         type int32;
         description "Port";
       }
       leaf sa-gvpn-groupid {
         type int32;
         description "Group VPN Group Id";
       }
       leaf sa-virtual-system {
         type string;
         description "Virtual System";
       }
       leaf sa-down-reason {
         type string;
         description "Ipsec SA down reason";
       }
     }
   }
   container detail {
     container ipsec-security-associations {
     }
     container ipsec-security-associations-block {
       container ipsec-security-associations {
       }
     }
     container ipsec-gvpn-inactive-tunnel-info-block {
       leaf sa-virtual-system {
         type string;
         description "Virtual System";
       }
       leaf sa-vpn-name {
         type string;
         description "VPN Name";
       }
       leaf sa-local-gateway {
         type ipaddr;
         description "Local gateway address";
       }
       leaf sa-remote-gateway {
         type ipaddr;
         description "Remote gateway address";
       }
       leaf sa-local-identity {
         type string;
         description "Local identity information";
       }
       leaf sa-remote-identity {
         type string;
         description "Remote identity information";
       }
       leaf sa-gvpn-groupid {
         type int32;
         description "Group VPN Group Id";
       }
       leaf sa-match-dir {
         type string;
         description "Group VPN rule match direction";
       }
       leaf sa-tunnel-mtu {
         type int32;
         description "MTU of the IPSec Tunnel";
       }
       container sa-df-bit-policy-name {
         leaf sa-df-bit {
           type string;
           description "Fragmentation bit";
         }
       }
       container ipsec-gvpn-sa-stats {
         leaf ipsec-sa-stats {
           type string;
           description "Ipsec SA stats";
         }
       }
       container gvpn-sa-down-reason {
         leaf sa-down-reason {
           type string;
           description "Ipsec SA down reason";
         }
       }
     }
   }
 }
 grouping ike-security-associations-information-block {
   container brief {
     list ike-security-associations {
       description "Information about a single security association";
       leaf ike-sa-remote-address {
         type ipaddr;
         description "Remote address";
       }
       leaf ike-sa-state {
         type string;
         description "Status of the SA";
       }
       leaf ike-sa-initiator-cookie {
         type string;
         description "IKE SA initiator cookie";
       }
       leaf ike-sa-responder-cookie {
         type string;
         description "IKE SA responder cookie";
       }
       leaf ike-sa-exchange-type {
         type string;
         description "Exchange type";
       }
       container ike-sa-algorithms {
         description "Algorithms used with the SA information";
       }
       container ike-sa-traffic-statistics {
         description "Number of packets and bytes received and transmitted on the SA";
       }
     }
     container ike-security-associations-block {
       description "Information about a single security association block";
       list ike-security-associations {
         description "Information about a single security association";
         container ike-sa-algorithms {
           description "Algorithms used with the SA information";
         }
         container ike-sa-traffic-statistics {
           description "Number of packets and bytes received and transmitted on the SA";
         }
       }
     }
   }
   container detail {
     list ike-security-associations {
       description "Information about a single security association";
       container ike-sa-algorithms {
         description "Algorithms used with the SA information";
       }
       container ike-sa-traffic-statistics {
         description "Number of packets and bytes received and transmitted on the SA";
       }
     }
     container ike-security-associations-block {
       description "Information about a single security association block";
       leaf ike-sa-remote-address {
         type ipaddr;
         description "Remote address";
       }
       list ike-security-associations {
         description "Information about a single security association";
         leaf ike-sa-role {
           type string;
           description "Role of our end";
         }
         leaf ike-sa-state {
           type string;
           description "Status of the SA";
         }
         leaf ike-sa-initiator-cookie {
           type string;
           description "IKE SA initiator cookie";
         }
         leaf ike-sa-responder-cookie {
           type string;
           description "IKE SA responder cookie";
         }
         leaf ike-sa-exchange-type {
           type string;
           description "Exchange type";
         }
         leaf ike-sa-authentication-method {
           type string;
         }
         leaf ike-sa-local-gateway-interface {
           type string;
           description "Local gateway  interface";
         }
         leaf ike-sa-routing-instance {
           type string;
           description "Local-gateway routing instance";
         }
         leaf ike-sa-local-address {
           type ipaddr;
           description "Local address";
         }
         leaf ike-sa-local-port {
           type int32;
           description "Local port";
         }
         leaf ike-sa-remote-port {
           type int32;
           description "Remote port";
         }
         leaf ike-sa-lifetime {
           type string;
           description "Remaining lifetime before expiration, in seconds or kilobytes";
         }
         container ike-sa-algorithms {
           description "Algorithms used with the SA information";
           leaf ike-sa-authentication-algorithm {
             type string;
             description "Authentication algorithm";
           }
           leaf ike-sa-encryption-algorithm {
             type string;
             description "Encryption algorithm";
           }
           leaf ike-sa-prf-algorithm {
             type string;
             description "PRF algorithm";
           }
           leaf ike-sa-dhgroup {
             type string;
             description "DH group";
           }
         }
         container ike-sa-traffic-statistics {
           description "Number of packets and bytes received and transmitted on the SA";
           leaf ike-sa-input-bytes {
             type int32;
             description "Input bytes, including retransmissions";
           }
           leaf ike-sa-output-bytes {
             type int32;
             description "Output bytes, including retransmissions";
           }
           leaf ike-sa-input-packets {
             type int32;
             description "Input packets, including retransmissions";
           }
           leaf ike-sa-output-packets {
             type int32;
             description "Output packets, including retransmissions";
           }
         }
         container ike-sa-misc {
           description "Miscellaneous IKE SA information";
           leaf ike-sa-flags {
             type string;
             description "IKE SA flags";
           }
           leaf ike-sa-num-ipsec-sas-created {
             type int32;
             description "Number of IPSec SAs created using this SA";
           }
           leaf ike-sa-num-ipsec-sas-deleted {
             type int32;
             description "Number of IPSec SAs deleted using this SA";
           }
           leaf ike-sa-num-phase2-negotiations {
             type int32;
             description "Number of negotiations in progress on this SA";
           }
         }
         list ike-sa-phase2-information {
           description "Information about phase 2 negotiation";
           leaf ike-sa-phase2-type {
             type string;
             description "Type of phase 2 negotiation";
           }
           leaf ike-sa-role {
             type string;
             description "Role of our end";
           }
           leaf ike-sa-msg-id {
             type int32;
             description "Message ID of the quick mode negotiation";
           }
           leaf ike-sa-local-address {
             type ipaddr;
             description "Local address";
           }
           leaf ike-sa-local-port {
             type int32;
             description "Local port";
           }
           leaf ike-sa-remote-address {
             type ipaddr;
             description "Remote address";
           }
           leaf ike-sa-remote-port {
             type int32;
             description "Remote port";
           }
           leaf ike-sa-local-id {
             type string;
             description "Local end identity in phase 2";
           }
           leaf ike-sa-remote-id {
             type string;
             description "Remote end identity in phase 2";
           }
           leaf ike-sa-flags {
             type string;
             description "IKE SA flags";
           }
         }
       }
     }
   }
 }
 grouping gvpn-kek-security-associations-information-block {
   container brief {
     list ike-security-associations {
       description "Information about a single security association";
       container ike-sa-traffic-statistics {
         description "Number of packets and bytes received and transmitted on the SA";
       }
       container ike-sa-misc {
         description "Miscellaneous IKE SA information";
       }
       container ike-sa-payload-statistics {
         description "Statistics related to payload types received and transmitted on this SA";
       }
     }
     container kek-security-associations {
       leaf security-association-index {
         type uint32;
         description "Index";
       }
       leaf server-address {
         type ipaddr;
         description "Server address";
       }
       leaf life-remaining {
         type uint32;
         description "Remaining life";
       }
       leaf initiator-cookie {
         type string;
         description "Initiator cookie";
       }
       leaf responder-cookie {
         type string;
         description "Responder cookie";
       }
       leaf group-id {
         type uint32;
         description "Group Id";
       }
     }
     container kek-security-associations-block {
       list ike-security-associations {
         description "Information about a single security association";
         container ike-sa-traffic-statistics {
           description "Number of packets and bytes received and transmitted on the SA";
         }
         container ike-sa-misc {
           description "Miscellaneous IKE SA information";
         }
         container ike-sa-payload-statistics {
           description "Statistics related to payload types received and transmitted on this SA";
         }
       }
     }
   }
   container detail {
     list ike-security-associations {
       description "Information about a single security association";
       container ike-sa-traffic-statistics {
         description "Number of packets and bytes received and transmitted on the SA";
       }
       container ike-sa-misc {
         description "Miscellaneous IKE SA information";
       }
       container ike-sa-payload-statistics {
         description "Statistics related to payload types received and transmitted on this SA";
       }
     }
     container kek-security-associations-block {
       leaf security-association-index {
         type uint32;
         description "Index";
       }
       leaf group-id {
         type uint32;
         description "Group Id";
       }
       leaf group-vpn-name {
         type string;
         description "Group VPN Name";
       }
       leaf local-address {
         type ipaddr;
         description "Local address";
       }
       leaf server-address {
         type ipaddr;
         description "Server address";
       }
       leaf initiator-cookie {
         type string;
         description "Initiator cookie";
       }
       leaf responder-cookie {
         type string;
         description "Responder cookie";
       }
       leaf lifetime-remaining {
         type string;
         description "Remaining lifetime before expiration, in seconds";
       }
       leaf push-sequence-number {
         type uint32;
         description "Group key Push sequence number";
       }
       container ike-sa-location {
         description "Location where SA is processed";
         leaf ike-sa-fpc {
           type int32;
           description "FPC number";
         }
         leaf ike-sa-pic {
           type int32;
           description "PIC number";
         }
         leaf ike-sa-kmd-instance {
           type int32;
           description "KMD instance number";
         }
       }
       list ike-security-associations {
         description "Information about a single security association";
         leaf ike-sa-role {
           type string;
           description "Role of our end";
         }
         leaf ike-sa-state {
           type string;
           description "Status of the SA";
         }
         leaf ike-sa-initiator-cookie {
           type string;
           description "IKE SA initiator cookie";
         }
         leaf ike-sa-responder-cookie {
           type string;
           description "IKE SA responder cookie";
         }
         leaf ike-sa-authentication-method {
           type string;
         }
         leaf ike-sa-local-address {
           type ipaddr;
           description "Local address";
         }
         leaf ike-sa-local-port {
           type int32;
           description "Local port";
         }
         leaf ike-sa-remote-address {
           type ipaddr;
           description "Remote address";
         }
         leaf ike-sa-remote-port {
           type int32;
           description "Remote port";
         }
         leaf ike-sa-lifetime {
           type string;
           description "Remaining lifetime before expiration, in seconds or kilobytes";
         }
         container ike-sa-algorithms {
           description "Algorithms used with the SA information";
           leaf ike-sa-authentication-algorithm {
             type string;
             description "Authentication algorithm";
           }
           leaf ike-sa-sig-key-length {
             type uint32;
             description "Signature Key Length";
           }
           leaf ike-sa-encryption-algorithm {
             type string;
             description "Encryption algorithm";
           }
         }
         container ike-sa-traffic-statistics {
           description "Number of packets and bytes received and transmitted on the SA";
           leaf ike-sa-input-bytes {
             type int32;
             description "Input bytes, including retransmissions";
           }
           leaf ike-sa-output-bytes {
             type int32;
             description "Output bytes, including retransmissions";
           }
           leaf ike-sa-input-packets {
             type int32;
             description "Input packets, including retransmissions";
           }
           leaf ike-sa-output-packets {
             type int32;
             description "Output packets, including retransmissions";
           }
         }
         container ike-sa-misc {
           description "Miscellaneous IKE SA information";
         }
         container ike-sa-payload-statistics {
           description "Statistics related to payload types received and transmitted on this SA";
         }
         list ike-sa-phase2-information {
           description "Information about phase 2 negotiation";
           leaf ike-sa-phase2-type {
             type string;
             description "Type of phase 2 negotiation";
           }
           leaf ike-sa-role {
             type string;
             description "Role of our end";
           }
           leaf ike-sa-msg-id {
             type int32;
             description "Message ID of the quick mode negotiation";
           }
           leaf ike-sa-local-address {
             type ipaddr;
             description "Local address";
           }
           leaf ike-sa-local-port {
             type int32;
             description "Local port";
           }
           leaf ike-sa-remote-address {
             type ipaddr;
             description "Remote address";
           }
           leaf ike-sa-remote-port {
             type int32;
             description "Remote port";
           }
           leaf ike-sa-local-id {
             type string;
             description "Local end identity in phase 2";
           }
           leaf ike-sa-remote-id {
             type string;
             description "Remote end identity in phase 2";
           }
         }
         container kek-sa-misc {
           description "Miscellaneous KEK SA information";
           leaf kek-sa-sequence-number {
             type uint32;
             description "Sequence Number";
           }
         }
         container kek-sa-group-info {
           description "KEK SA group information";
           leaf group-id {
             type uint32;
             description "Group Id";
           }
           leaf kek-sa-group-name {
             type string;
             description "Group Name";
           }
           leaf kek-sa-group-server-version {
             type uint32;
             description "Server Version Number";
           }
           leaf kek-sa-group-heartbeat-interval {
             type uint32;
             description "Server Heartbeat Interval";
           }
           leaf kek-sa-group-heartbeat-threshold {
             type uint32;
             description "Member Heartbeat Threshold";
           }
           leaf kek-sa-group-heartbeat-timeout-left {
             type uint32;
             description "Number of seconds till heartbeat timeout";
           }
           leaf kek-sa-group-activation-delay {
             type uint32;
             description "Server Activation Delay";
           }
           leaf kek-sa-group-multicast-group {
             type string;
             description "Server Multicast Group";
           }
           leaf kek-sa-group-replay-window {
             type uint32;
             description "Server Replay Window";
           }
         }
         container kek-sa-server-info {
           description "KEK SA server information";
           leaf kek-sa-server-retrans-period {
             type uint32;
             description "Server Retransmission Period";
           }
           leaf kek-sa-server-retrans-number {
             type uint32;
             description "Number of retransimissions";
           }
           leaf kek-sa-server-lifetime-secs {
             type uint32;
             description "Lifetime seconds";
           }
           leaf kek-sa-server-certificate {
             type string;
             description "Certificate";
           }
         }
       }
       container gvpn-kek-security-association-statistics {
         leaf kek-security-association-statistics {
           type string;
           description "KEK SA statistics";
         }
       }
     }
   }
 }
 grouping mka-session-information-block {
   leaf interface-name {
     type string;
   }
   leaf member-identifier {
     type string;
     description "MKA member identifier";
   }
   leaf cak-name {
     type string;
     description "Connectivity association key name";
   }
   leaf transmit-interval {
     type uint32;
     description "MKA periodic transmit interval in milliseconds";
   }
   leaf sci {
     type string;
     description "MKA outbound secure channel identifier";
   }
   leaf message-number {
     type uint32;
     description "MKA message number last transmitted";
   }
   leaf key-number {
     type uint32;
     description "MKA key number being used";
   }
   leaf key-server {
     type string;
     description "MKA key server status";
   }
   leaf key-server-priority {
     type uint32;
     description "MKA key server priority";
   }
   leaf latest-sak-association-number {
     type uint32;
     description "MKA latest security association key's association number";
   }
   leaf latest-sak-key-identifier {
     type string;
     description "MKA latest security association key's key identifier";
   }
   container session-previous-sak {
     leaf previous-sak-association-number {
       type uint32;
       description "MKA previous security association key's association number";
     }
     leaf previous-sak-key-identifier {
       type string;
       description "MKA previous security association key's key identifier";
     }
   }
   list session-peer-list {
     leaf peer-index {
       type uint32;
       description "MKA peer index number";
     }
     leaf member-identifier {
       type string;
       description "MKA member identifier";
     }
     leaf peer-status {
       type string;
       description "MKA peer status";
     }
     leaf message-number {
       type uint32;
       description "MKA message number last transmitted";
     }
     leaf hold-time {
       type uint32;
       description "MKA peer time to expiry in milli seconds";
     }
     leaf sci {
       type string;
       description "MKA outbound secure channel identifier";
     }
     leaf lowest-acceptable-packet-number {
       type uint32;
       description "MKA lowest acceptable packet number from peer";
     }
   }
 }
 grouping mka-statistics-block {
   leaf interface-name {
     type string;
   }
   leaf received-packets {
     type uint32;
     description "Number of MKA packets received";
   }
   leaf sent-packets {
     type uint32;
     description "Number of MKA packets sent";
   }
   leaf version-error {
     type uint32;
     description "Number of MKA packets with version mismatch";
   }
   leaf cak-error {
     type uint32;
     description "Number of MKA packets with CAK invalid or mismatch";
   }
   leaf integrity-check-value-mismatch {
     type uint32;
     description "Number of MKA packets with integrity check value mismatch";
   }
   leaf duplicate-message-identifier {
     type uint32;
     description "Number of MKA packets with duplicate message identifier";
   }
   leaf duplicate-message-number {
     type uint32;
     description "Number of MKA packets with duplicate message number";
   }
   leaf duplicate-address {
     type uint32;
     description "Number of MKA packets with duplicate address";
   }
   leaf invalid-destination {
     type uint32;
     description "Number of MKA packets with invalid destination";
   }
   leaf format-error {
     type uint32;
     description "Number of MKA packets with format errors";
   }
   leaf old-message-number {
     type uint32;
     description "Number of MKA packets with old or replayed message number";
   }
 }
 grouping macsec-connection-information-block {
   leaf connectivity-association-name {
     type string;
     description "Connectivity association name";
   }
   leaf cipher-suite {
     type string;
     description "Cipher suite name";
   }
   leaf encryption {
     type string;
     description "MAC security encryption status";
   }
   leaf offset {
     type uint32;
     description "MAC security offset";
   }
   leaf include-sci {
     type string;
     description "MAC security SCI inclusion status";
   }
   leaf replay-protect {
     type string;
     description "MAC replay protect status";
   }
   leaf replay-protect-window {
     type uint32;
     description "MAC security replay protect window size";
   }
   list outbound-secure-channel {
     leaf sci {
       type string;
       description "MKA outbound secure channel identifier";
     }
     leaf outgoing-packet-number {
       type uint64;
       description "MAC security outgoing packet number";
     }
     list outbound-secure-association {
       leaf association-number {
         type uint32;
         description "MAC security association number";
       }
       leaf association-number-status {
         type string;
         description "MAC security association number status";
       }
       leaf create-time {
         type string;
         description "MAC security association number creation time";
       }
     }
   }
   list inbound-secure-channel {
     leaf sci {
       type string;
       description "MKA outbound secure channel identifier";
     }
     list inbound-secure-association {
       leaf association-number {
         type uint32;
         description "MAC security association number";
       }
       leaf association-number-status {
         type string;
         description "MAC security association number status";
       }
       leaf create-time {
         type string;
         description "MAC security association number creation time";
       }
     }
   }
 }
 grouping macsec-statistics-block {
   leaf interface-name {
     type string;
   }
   list secure-channel-sent {
     leaf encrypted-packets {
       type uint64;
       description "Macsec encrypted packets sent";
     }
     leaf encrypted-bytes {
       type uint64;
       description "Macsec encrypted bytes sent";
     }
     leaf protected-packets {
       type uint64;
       description "Macsec packets sent with only integrity protection";
     }
     leaf protected-bytes {
       type uint64;
       description "Macsec bytes sent with only integrity protection";
     }
   }
   list secure-association-sent {
     leaf encrypted-packets {
       type uint64;
       description "Macsec encrypted packets sent";
     }
     leaf encrypted-bytes {
       type uint64;
       description "Macsec encrypted bytes sent";
     }
     leaf protected-packets {
       type uint64;
       description "Macsec packets sent with only integrity protection";
     }
     leaf protected-bytes {
       type uint64;
       description "Macsec bytes sent with only integrity protection";
     }
   }
   list secure-channel-received {
     leaf ok-packets {
       type uint64;
       description "Macsec packets accepted";
     }
     leaf decrypted-packets {
       type uint64;
       description "Macsec received packets decrypted";
     }
     leaf decrypted-bytes {
       type uint64;
       description "Macsec received bytes decrypted";
     }
     leaf validated-packets {
       type uint64;
       description "Macsec received packets validated";
     }
     leaf validated-bytes {
       type uint64;
       description "Macsec received bytes validated";
     }
   }
   list secure-association-received {
     leaf ok-packets {
       type uint64;
       description "Macsec packets accepted";
     }
     leaf decrypted-packets {
       type uint64;
       description "Macsec received packets decrypted";
     }
     leaf decrypted-bytes {
       type uint64;
       description "Macsec received bytes decrypted";
     }
     leaf validated-packets {
       type uint64;
       description "Macsec received packets validated";
     }
     leaf validated-bytes {
       type uint64;
       description "Macsec received bytes validated";
     }
   }
   list macsec-error-information {
     list secure-channel-sent-errors {
       leaf untagged-packets {
         type uint64;
         description "Macsec untagged packets";
       }
       leaf toolong-packets {
         type uint64;
         description "Macsec too long packets transmitted on a secure channel";
       }
     }
     list secure-channel-received-errors {
       leaf control-packets {
         type uint64;
         description "Macsec control packets received on a secure channel";
       }
       leaf tagged-miss-packets {
         type uint64;
         description "Macsec tagged miss packets received on a secure channel";
       }
       leaf untagged-hit-packets {
         type uint64;
         description "Macsec untagged hit packets received on a secure channel";
       }
       leaf untagged-packets {
         type uint64;
         description "Macsec untagged packets";
       }
       leaf notag-packets {
         type uint64;
         description "Macsec no tag packets received on a secure channel";
       }
       leaf badtag-packets {
         type uint64;
         description "Macsec bad tag packets received on a secure channel";
       }
       leaf unknown-sci-packets {
         type uint64;
         description "Macsec unknown sci packets received on a secure channel";
       }
       leaf no-sci-packets {
         type uint64;
         description "Macsec no sci packets received on a secure channel";
       }
       leaf control-pass-packets {
         type uint64;
         description "Macsec allowed control packets received on a secure channel";
       }
       leaf control-fail-packets {
         type uint64;
         description "Macsec dropped control packets received on a secure channel";
       }
       leaf uncontrol-pass-packets {
         type uint64;
         description "Macsec allowed uncontrol packets received on a secure channel";
       }
       leaf uncontrol-fail-packets {
         type uint64;
         description "Macsec dropped uncontrol packets received on a secure channel";
       }
     }
     list secure-channel-received-extended {
       leaf hit-dropped-packets {
         type uint64;
         description "Macsec hit dropped packets received on a security channel";
       }
       leaf invalid-packets {
         type uint64;
         description "Macsec invalid packets accepted on a security channel";
       }
       leaf late-packets {
         type uint64;
         description "Macsec late packets dropped on a security channel";
       }
       leaf delayed-packets {
         type uint64;
         description "Macsec delayed packets accepted on a security channel";
       }
       leaf unchecked-packets {
         type uint64;
         description "Macsec unchecked packets accepted on a security channel";
       }
       leaf notvalid-packets {
         type uint64;
         description "Macsec not valid packets dropped on a security channel";
       }
       leaf notusing-sa-packets {
         type uint64;
         description "Macsec not using sa packets received on a security channel";
       }
       leaf unused-sa-packets {
         type uint64;
         description "Macsec unused sa packets received on a security channel";
       }
     }
   }
 }
 }
