/*
 * Copyright (c) 2017 Juniper Networks, Inc.
 * All rights reserved.
 */
 module show-analytics {
  namespace "http://yang.juniper.net/yang/1.1/jrpc/show-analytics/junos-qfx/17.2R1.13";
  prefix show-analytics;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-analytics-information {
     description "Show Analytics information";
     output {
       container analytics {
         uses analytics-block;
       }
     }
   }
   rpc get-analytics-queue-statistics {
     description "Show queue statistics";
   }
   rpc get-analytics-queue-statistics-interface {
     description "Show queue-statistics for an interface";
     input {
       leaf interface-name {
         description "Interface name";
         type string;
         mandatory true;
       }
     }
   }
   rpc get-analytics-traffic-statistics {
     description "Show traffic statistics";
   }
   rpc get-analytics-traffic-statistics-interface {
     description "Show traffic-statistics for an interface";
     input {
       leaf interface-name {
         description "Interface name";
         type string;
         mandatory true;
       }
     }
   }
   rpc get-analytics-status {
     description "Show analytics status";
   }
   rpc get-analytics-status-global {
     description "Show analytics global status";
   }
   rpc get-analytics-status-interface {
     description "Show analytics status for an interface";
     input {
       leaf interface-name {
         description "Interface name";
         type string;
         mandatory true;
       }
     }
   }
   rpc get-analytics-configuration {
     description "Show analytics configuration";
   }
   rpc get-analytics-configuration-global {
     description "Show analytics global configuration";
   }
   rpc get-analytics-configuration-interface {
     description "Show analytics configuration for an interface";
     input {
       leaf interface-name {
         description "Interface name";
         type string;
         mandatory true;
       }
     }
   }
   rpc get-analytics-collector {
     description "Show collector status";
   }
 grouping analytics-block {
   container analytics-current-time {
     leaf an-timeval {
       type string;
       description "Time value";
     }
   }
   container analytics-interface-summary {
     leaf an-interface-name {
       type string;
       description "Interface name";
     }
     leaf an-ts-status {
       type string;
       description "Traffic statistics status";
     }
     leaf an-qs-status {
       type string;
       description "Queue statistics status";
     }
     leaf an-depth-threshold-high {
       type string;
       description "Depth threshold high";
     }
     leaf an-depth-threshold-low {
       type string;
       description "Depth threshold low";
     }
     leaf an-latency-threshold-high {
       type string;
       description "Latency threshold high";
     }
     leaf an-latency-threshold-low {
       type string;
       description "Latency threshold low";
     }
   }
   container analytics-interface {
     leaf an-interface-name {
       type string;
       description "Interface name";
     }
     leaf an-ts-status {
       type string;
       description "Traffic statistics status";
     }
     leaf an-ts-interval {
       type uint32;
       description "Traffic statistics interval";
     }
     leaf an-qs-status {
       type string;
       description "Queue statistics status";
     }
     leaf an-qs-interval {
       type uint32;
       description "Queue statistics interval";
     }
     leaf an-depth-threshold-high {
       type string;
       description "Depth threshold high";
     }
     leaf an-depth-threshold-low {
       type string;
       description "Depth threshold low";
     }
     leaf an-latency-threshold-high {
       type string;
       description "Latency threshold high";
     }
     leaf an-latency-threshold-low {
       type string;
       description "Latency threshold low";
     }
   }
   container analytics-global {
     leaf an-ts-status {
       type string;
       description "Traffic statistics status";
     }
     leaf an-ts-interval {
       type uint32;
       description "Traffic statistics interval";
     }
     leaf an-qs-status {
       type string;
       description "Queue statistics status";
     }
     leaf an-qs-interval {
       type uint32;
       description "Queue statistics interval";
     }
     leaf an-depth-threshold-high {
       type string;
       description "Depth threshold high";
     }
     leaf an-depth-threshold-low {
       type string;
       description "Depth threshold low";
     }
     leaf an-latency-threshold-high {
       type string;
       description "Latency threshold high";
     }
     leaf an-latency-threshold-low {
       type string;
       description "Latency threshold low";
     }
   }
   container analytics-status {
   }
   container analytics-configuration {
   }
   container analytics-queue-statistics {
     leaf an-timeval {
       type string;
       description "Time value";
     }
     leaf an-interface-name {
       type string;
       description "Interface name";
     }
     leaf an-queue-depth {
       type uint32;
     }
     leaf an-latency {
       type uint32;
     }
     container analytics-queue-statistics-summary {
       leaf an-queue-depth-1sec {
         type uint32;
       }
       leaf an-queue-depth-5sec {
         type uint32;
       }
       leaf an-queue-depth-60sec {
         type uint32;
       }
       leaf an-queue-depth-5min {
         type uint32;
       }
       leaf an-queue-depth-1hr {
         type uint32;
       }
     }
   }
   container analytics-traffic-statistics {
     leaf an-timeval {
       type string;
       description "Time value";
     }
     leaf an-interface-name {
       type string;
       description "Interface name";
     }
     leaf an-rx-total-bytes {
       type uint32;
     }
     leaf an-tx-total-bytes {
       type uint32;
     }
     leaf an-rx-total-packets {
       type uint32;
     }
     leaf an-tx-total-packets {
       type uint32;
     }
     leaf an-rx-unicast-packets {
       type uint32;
     }
     leaf an-tx-unicast-packets {
       type uint32;
     }
     leaf an-rx-multicast-packets {
       type uint32;
     }
     leaf an-tx-multicast-packets {
       type uint32;
     }
     leaf an-rx-broadcast-packets {
       type uint32;
     }
     leaf an-tx-broadcast-packets {
       type uint32;
     }
     leaf an-rx-bytes-per-second {
       type uint32;
     }
     leaf an-tx-bytes-per-second {
       type uint32;
     }
     leaf an-rx-bits-per-second {
       type uint32;
     }
     leaf an-tx-bits-per-second {
       type uint32;
     }
     leaf an-rx-packets-per-second {
       type uint32;
     }
     leaf an-tx-packets-per-second {
       type uint32;
     }
     leaf an-rx-crc-errors {
       type uint32;
     }
     leaf an-tx-crc-errors {
       type uint32;
     }
     leaf an-rx-packets-dropped {
       type uint32;
     }
     leaf an-tx-packets-dropped {
       type uint32;
     }
   }
   container analytics-collector {
     leaf an-server-address {
       type ipaddr;
     }
     leaf an-server-port {
       type uint32;
     }
     leaf an-server-transport {
       type uint32;
     }
     leaf an-stream-format {
       type string;
     }
     leaf an-connection-state {
       type string;
     }
     leaf an-msg-sent {
       type uint32;
     }
   }
 }
 }
