/*
 * Copyright (c) 2017 Juniper Networks, Inc.
 * All rights reserved.
 */
 module show-path-computation-client {
  namespace "http://yang.juniper.net/yang/1.1/jrpc/show-path-computation-client/junos-qfx/17.2R1.13";
  prefix show-path-computation-client;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-path-computation-client-statistics {
     description "Get path computation client statistics";
     input {
       leaf count {
         type enumeration {
           enum "all" {
             description "Show statistics of all available PCEs";
           }
         }
       }
       leaf verbosity_level {
         default "brief";
         type enumeration {
           enum "brief" {
             description "Display brief output (default)";
           }
           enum "detail" {
             description "Display detailed output";
           }
         }
       }
     }
     output {
       container path-computation-client-statistics {
         uses path-computation-client-statistics-block;
       }
     }
   }
   rpc get-path-computation-client-active-pce {
     description "Show information about current active PCE";
     input {
       leaf verbosity_level {
         default "brief";
         type enumeration {
           enum "brief" {
             description "Display brief output (default)";
           }
           enum "detail" {
             description "Display detailed output";
           }
         }
       }
     }
     output {
       container path-computation-client-statistics {
         uses path-computation-client-statistics-block;
       }
     }
   }
   rpc get-path-computation-client-lsp {
     description "Show information about known Labels Switched Paths";
     output {
       container path-computation-client-lsp {
         uses path-computation-client-lsp-block;
       }
     }
   }
   rpc get-path-computation-client-lsp-retry-pending {
     description "Show information about LSPs for which delegation will be re-tried";
   }
   rpc get-path-computation-client-status {
     description "Show status of Path Computation Client";
     output {
       container path-computation-client-status {
         uses path-computation-client-status-block;
       }
     }
   }
 grouping path-computation-client-statistics-block {
   list pce-statistics-response {
     leaf pce-id {
       type string;
       description "PCE IP/NAME1";
     }
     container pce-statistics-common {
       leaf pce-ip {
         type ipaddr;
         description "IP address of PCE";
       }
       leaf local-ip {
         type ipaddr;
         description "Local IP address";
       }
       leaf pce-priority {
         type int32;
         description "Priority";
       }
       leaf pce-connection {
         type string;
         description "Connection state (e.g. connecting/connected, disconnected)";
       }
       leaf pce-status {
         type string;
         description "A small but friendly message";
       }
       leaf pce-session-type {
         type string;
         description "A small but friendly message";
       }
       leaf pce-session-state {
         type string;
         description "A small but friendly message";
       }
       leaf lsp-provisioning {
         type string;
         description "LSP provisioning ability";
       }
       leaf pcupdate-empty-ero-action {
         type string;
         description "Action to be taken on empty ero in pcupdate";
       }
       leaf p2mp-lsp-reporting {
         type string;
         description "P2MP LSP reporting ability";
       }
       leaf p2mp-lsp-update {
         type string;
         description "P2MP LSP updating ability";
       }
       leaf p2mp-lsp-init {
         type string;
         description "P2MP LSP initiating ability";
       }
       leaf lsp-cleanup-timer {
         type uint32;
         description "Negotiated LSP cleanup timer";
       }
       leaf pce-mastership {
         type string;
         description "PCE-mastership (main or backup)";
       }
       leaf pce-max-unknown-msgs {
         type int32;
         description "A small but friendly message";
       }
       leaf keepalives-received {
         type int32;
         description "Keepalives received total";
       }
       leaf keepalives-sent {
         type int32;
         description "Keepalives sent total";
       }
       leaf dead-timer {
         type int32;
         description "DeadTimer value (0 meaning disconnection from PCE)";
       }
       leaf active-state-current {
         type int32;
         description "Elapsed time as main PCE current session";
       }
       leaf active-state-total {
         type int32;
         description "Elapsed time as main PCE total";
       }
       leaf unknown-ratio {
         type int32;
         description "Current unknown messages per minute ratio";
       }
       leaf session-failures {
         type int32;
         description "Active state duration";
       }
       leaf corrupted-messages {
         type int32;
         description "Active state duration";
       }
       leaf delegation-timeout-set {
         type int32;
         description "Delegation timeout set";
       }
       leaf delegation-timeout {
         type int32;
         description "Delegation timeout";
       }
       leaf delegation-failures {
         type int32;
         description "Delegation failures counter";
       }
       leaf connection-active {
         type int32;
         description "Time of PCE connection active";
       }
       leaf connection-down {
         type int32;
         description "Time of PCE connection down";
       }
     }
     container pce-statistics-counters {
       list pce-counter {
         leaf counter-name {
           type string;
           description "Counter name";
         }
         leaf count-total {
           type int32;
           description "Total count";
         }
         leaf count-5min {
           type int32;
           description "Last 5 minutes";
         }
         leaf count-hour {
           type int32;
           description "Last hour";
         }
       }
     }
     container pce-statistics-timers {
       list pce-timer {
         leaf timer-name {
           type string;
           description "Timer name";
         }
         leaf timer-keepalive {
           type int32;
           description "Keepalive timer";
         }
         leaf timer-dead {
           type int32;
           description "Dead timer";
         }
         leaf timer-lsp-cleanup {
           type uint32;
           description "LSP cleanup timer";
         }
       }
     }
     container pce-statistics-errors {
       list pce-error {
         leaf pce-error-name {
           type string;
         }
         list pce-error-entry {
           leaf pce-error-type {
             type int32;
           }
           leaf pce-error-value {
             type int32;
           }
           leaf pce-error-count {
             type int32;
           }
         }
       }
     }
     container pce-statistics-pcupdate-empty-ero-action {
       leaf stats-send-err {
         type int32;
         description "Sent err in response to Pcupdate containing empty-ero";
       }
       leaf stats-tear-down-path {
         type int32;
         description "Teared down path in response to Pcupdate containing empty-ero";
       }
       leaf stats-routing-decision {
         type int32;
         description "Path decision is taken by MPLS component in response to Pcupdate containing empty-ero";
       }
       leaf stats-routing-decision_failed {
         type int32;
         description "Path decision is taken by MPLS component in response to Pcupdate containing empty-ero, but operation failed";
       }
     }
   }
   container pccd-error-response {
     leaf pccd-error-message {
       type string;
       description "Operation error message";
     }
   }
 }
 grouping path-computation-client-lsp-block {
   list pcc-lsp-entry {
     leaf lsp-name {
       type string;
     }
     leaf lsp-status {
       type string;
     }
     leaf lsp-id {
       type int32;
     }
     leaf lsp-type {
       type string;
     }
     leaf lsp-controller {
       type string;
     }
     leaf lsp-setup-type {
       type string;
     }
     leaf template-name {
       type string;
     }
   }
 }
 grouping path-computation-client-status-block {
   container pcc-status-sessions {
     list pcc-status-sessions-entry {
       leaf session-name {
         type string;
       }
       leaf session-type {
         type string;
       }
       leaf session-provisioning {
         type string;
       }
       leaf session-status {
         type string;
       }
     }
     container pccd-error-response {
       leaf pccd-error-message {
         type string;
         description "Operation error message";
       }
     }
   }
   container pcc-status-lsp {
     list pcc-status-lsp-entry {
       leaf lsp-total {
         type uint32;
       }
       leaf lsp-static {
         type uint32;
       }
       leaf lsp-external {
         type uint32;
       }
       leaf lsp-provisioned-counter {
         type uint32;
       }
       leaf lsp-provisioned-limit {
         type uint32;
       }
       leaf lsp-orphan {
         type uint32;
       }
     }
     container pccd-error-response {
       leaf pccd-error-message {
         type string;
         description "Operation error message";
       }
     }
   }
   container pcc-status-pce {
     list pcc-status-pce-entry {
       leaf pce-name {
         type string;
       }
       leaf pce-delegated {
         type uint32;
       }
       leaf pce-provisioned {
         type uint32;
       }
       leaf pce-auth-keychain {
         type string;
       }
       leaf pce-auth-algorithm {
         type string;
       }
       leaf pce-auth-key {
         type string;
       }
     }
     container pccd-error-response {
       leaf pccd-error-message {
         type string;
         description "Operation error message";
       }
     }
   }
 }
 }
