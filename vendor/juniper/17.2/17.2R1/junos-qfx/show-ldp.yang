/*
 * Copyright (c) 2017 Juniper Networks, Inc.
 * All rights reserved.
 */
 module show-ldp {
  namespace "http://yang.juniper.net/yang/1.1/jrpc/show-ldp/junos-qfx/17.2R1.13";
  prefix show-ldp;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ldp-overview-information {
     description "Show LDP overview information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of LDP routing instance";
         type string;
       }
     }
     output {
       container ldp-overview-information {
         uses ldp-overview-information-block;
       }
     }
   }
   rpc get-ldp-interface-information {
     description "Show LDP interface status";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
       leaf interface-name {
         description "Name of interface";
         type string;
       }
     }
     output {
       container ldp-interface-information {
         uses ldp-interface-information-block;
       }
     }
   }
   rpc get-ldp-neighbor-information {
     description "Show LDP neighbor status";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
       leaf neighbor {
         description "IP address of the neighbor";
         type ipaddr;
       }
       leaf neighbor-type {
         type enumeration {
           enum "auto-targeted" {
             description "Auto targeted neighbors";
           }
           enum "auto-discovery" {
             description "Auto discovery neighbors";
           }
           enum "link-protection" {
             description "Link protection neighbors";
           }
           enum "session-protection" {
             description "Session protection neighbors";
           }
         }
       }
     }
     output {
       container ldp-neighbor-information {
         uses ldp-neighbor-information-block;
       }
     }
   }
   rpc get-ldp-session-information {
     description "Show LDP session status";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
       leaf destination {
         description "IP address of session destination";
         type ipaddr;
       }
       leaf session-type {
         type enumeration {
           enum "auto-targeted" {
             description "Auto targeted sessions";
           }
           enum "auto-discovery" {
             description "Auto discovery sessions";
           }
           enum "link-protection" {
             description "Link protection sessions";
           }
           enum "session-protection" {
             description "Session protection sessions";
           }
         }
       }
     }
     output {
       container ldp-session-information {
         uses ldp-session-information-block;
       }
     }
   }
   rpc get-ldp-route-information {
     description "Show LDP internal topology table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
       leaf destination {
         description "IP address and optional prefix length of destination";
         type ipprefix;
       }
       leaf ldp-route-type {
         description "Type of the shadow route ";
         default "route-only";
         type enumeration {
           enum "route-only" {
             description "Display shadow routes";
           }
           enum "fec-only" {
             description "Display LDP FECs";
           }
           enum "fec-and-route" {
             description "Display both shadow route and FECs";
           }
         }
       }
       leaf ldp-family {
         type enumeration {
           enum "inet" {
             description "Display IPv4 routes";
           }
           enum "inet6" {
             description "Display IPv6 routes";
           }
         }
       }
     }
     output {
       container ldp-route-information {
         uses ldp-route-information-block;
       }
     }
   }
   rpc get-ldp-path-information {
     description "Show LDP path table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
       leaf destination {
         description "IP address and optional prefix length of destination";
         type ipprefix;
       }
     }
     output {
       container ldp-path-information {
         uses ldp-path-information-block;
       }
     }
   }
   rpc get-ldp-database-information {
     description "Show LDP label database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "summary" {
             description "Display summary output";
           }
           enum "brief" {
             description "Display brief output (default)";
           }
           enum "detail" {
             description "Display detailed output";
           }
           enum "extensive" {
             description "Display extensive output";
           }
         }
       }
       leaf instance {
         description "Name of LDP routing instance";
         type string;
       }
       leaf session {
         description "IP address of session destination";
         type ipaddr;
       }
       leaf fec-type {
         type enumeration {
           enum "inet" {
             description "Display IPv4 bindings";
           }
           enum "inet6" {
             description "Display IPv6 bindings";
           }
           enum "l2circuit" {
             description "Display Layer 2 circuit bindings";
           }
           enum "p2mp" {
             description "Display P2MP bindings";
           }
         }
       }
     }
     output {
       container ldp-database-information {
         uses ldp-database-information-block;
       }
     }
   }
   rpc get-ldp-database-label-requests-information {
     description "Display Label Requests state";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
       leaf session {
         description "IP address of session destination";
         type ipaddr;
       }
       leaf fec-type {
         type enumeration {
           enum "inet" {
             description "Display IPv4 bindings";
           }
           enum "l2circuit" {
             description "Display Layer 2 circuit bindings";
           }
           enum "p2mp" {
             description "Display P2MP bindings";
           }
         }
       }
     }
   }
   rpc get-ldp-statistics-information {
     description "Show LDP statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of LDP routing instance";
         type string;
       }
     }
     output {
       container ldp-statistics-information {
         uses ldp-statistics-information-block;
       }
     }
   }
   rpc get-ldp-traffic-statistics-information {
     description "Show packet statistics for LDP label-switched paths";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of LDP routing instance";
         type string;
       }
       leaf fec-type {
         type enumeration {
           enum "inet" {
             description "Display statistics for INET FECs";
           }
           enum "p2mp" {
             description "Display statistics for P2MP FECs";
           }
         }
       }
     }
     output {
       container ldp-traffic-statistics-information {
         uses ldp-traffic-statistics-information-block;
       }
     }
   }
   rpc get-ldp-fec-filters-information {
     description "Show filters for forwarding equivalence classes";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of LDP routing instance";
         type string;
       }
       leaf fec {
         description "Forwarding equivalence class";
         type ipprefix;
       }
     }
     output {
       container ldp-fec-filters-information {
         uses ldp-fec-filters-information-block;
       }
     }
   }
   rpc get-ldp-rib-groups-information {
     description "Show LDP rib-groups";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of LDP routing instance";
         type string;
       }
     }
     output {
       container ldp-rib-groups-information {
         uses ldp-rib-groups-information-block;
       }
     }
   }
   rpc get-ldp-oam-information {
     description "Show LDP OAM information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf fec {
         description "IP address and optional prefix length of FEC";
         type ipprefix;
       }
       leaf instance {
         description "Name of LDP routing instance";
         type string;
       }
     }
     output {
       container ldp-oam-information {
         uses ldp-oam-information-block;
       }
     }
   }
   rpc get-ldp-p2mp-path-information {
     description "Show LDP p2mp path table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
     }
     output {
       container ldp-p2mp-path-information {
         uses ldp-p2mp-path-information-block;
       }
     }
   }
   rpc get-ldp-p2mp-tunnel-information {
     description "Show LDP p2mp tunnel table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
     }
     output {
       container ldp-p2mp-tunnel-information {
         uses ldp-p2mp-tunnel-information-block;
       }
     }
   }
   rpc get-ldp-p2mp-fec-information {
     description "Show LDP p2mp fec table";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of LDP routing instance";
         type string;
       }
     }
     output {
       container ldp-p2mp-fec-information {
         uses ldp-p2mp-fec-information-block;
       }
     }
   }
 grouping ldp-overview-information-block {
   list ldp-overview {
     leaf ldp-instance-name {
       type string;
       description "Name of LDP instance";
     }
     leaf ldp-reference-count {
       type int32;
     }
     leaf ldp-router-id {
       type ipaddr;
       description "LDP Router ID";
     }
     leaf ldp-inet-lsr-id {
       type ipaddr;
       description "LDP dual-transport LSR ID for IPv4";
     }
     leaf ldp-inet6-lsr-id {
       type ipaddr;
       description "LDP dual-transport LSR ID for IPv6";
     }
     leaf ldp-inet {
       type string;
       description "LDP address family inet";
     }
     leaf ldp-inet6 {
       type string;
       description "LDP address family inet6";
     }
     leaf ldp-transport-preference {
       type string;
     }
     leaf ldp-message-id {
       type uint32;
       description "Message id";
     }
     leaf ldp-configuration-sequence {
       type uint32;
       description "Configuration sequence";
     }
     leaf ldp-advertised-configuration-sequence {
       type uint32;
       description "Advertised configuration sequence";
     }
     leaf ldp-no-scaling-optimize {
       type string;
       description "Disable scaling optimization";
     }
     leaf ldp-deaggregate {
       type string;
       description "LDP deaggregate";
     }
     leaf ldp-explicit-null {
       type string;
       description "Explicit null";
     }
     leaf ldp-ipv6-tunneling {
       type string;
       description "IPv6 tunneling";
     }
     leaf ldp-strict-targeted-hellos {
       type string;
       description "Strict targeted hellos";
     }
     leaf ldp-upstream-label-assignment {
       type string;
       description "Upstream label assignment";
     }
     leaf ldp-loopback-if-added {
       type string;
       description "Loopback if added";
     }
     leaf ldp-route-preference {
       type uint32;
       description "Route preference";
     }
     leaf ldp-p2mp-max-branches {
       type uint32;
       description "P2MP max branches";
     }
     leaf ldp-unicast-transit-lsp-chaining {
       type string;
       description "Use chain nexthops for LDP unicast transit LSPs";
     }
     leaf ldp-p2mp-transit-lsp-chaining {
       type string;
       description "Use chain nexthops for LDP P2MP transit LSPs";
     }
     leaf ldp-transit-lsp-route-stats {
       type string;
       description "Use route statistics for LDP transit LSP statistics";
     }
     leaf ldp-route-acknowledgement {
       type string;
       description "Use LDP route acknowledgemet";
     }
     leaf ldp-mtu-discovery {
       type string;
       description "Use LDP mtu discovery";
     }
     leaf ldp-ingress-route-sessionid-count {
       type uint32;
       description "Ingress route session id count";
     }
     list ldp-instance-capability {
       description "LDP capability";
       leaf ldp-capability {
         type string;
         description "LDP capability";
       }
     }
     list ldp-instance-egress-fec-capability {
       description "LDP egress FEC capability";
       leaf ldp-egress-fec-capability {
         type string;
         description "LDP egress FEC capability";
       }
     }
     container ldp-longest-match-overview {
       description "Longest Match support";
       leaf ldp-longest-match {
         type string;
       }
       leaf ldp-longest-match-policy {
         type string;
       }
     }
     list ldp-session-count {
       description "LDP sessions";
       leaf ldp-session-operational {
         type uint32;
         description "Operational session count";
       }
       leaf ldp-session-nonexistent {
         type uint32;
         description "Nonexistent session count";
       }
       leaf ldp-session-connecting {
         type uint32;
         description "Connecting session count";
       }
       leaf ldp-session-initialized {
         type uint32;
         description "Initialized session count";
       }
       leaf ldp-session-openrec {
         type uint32;
         description "OpenRec session count";
       }
       leaf ldp-session-opensent {
         type uint32;
         description "OpenSent session count";
       }
       leaf ldp-session-closing {
         type uint32;
         description "Closing session count";
       }
       leaf ldp-retention-mode {
         type string;
         description "LDP retention mode";
       }
       leaf ldp-control-mode {
         type string;
         description "LDP control mode";
       }
     }
     list ldp-dod-session-count {
       description "LDP sessions";
       leaf ldp-session-operational {
         type uint32;
         description "Operational session count";
       }
       leaf ldp-session-nonexistent {
         type uint32;
         description "Nonexistent session count";
       }
       leaf ldp-session-connecting {
         type uint32;
         description "Connecting session count";
       }
       leaf ldp-session-initialized {
         type uint32;
         description "Initialized session count";
       }
       leaf ldp-session-openrec {
         type uint32;
         description "OpenRec session count";
       }
       leaf ldp-session-opensent {
         type uint32;
         description "OpenSent session count";
       }
       leaf ldp-session-closing {
         type uint32;
         description "Closing session count";
       }
       leaf ldp-retention-mode {
         type string;
         description "LDP retention mode";
       }
       leaf ldp-control-mode {
         type string;
         description "LDP control mode";
       }
     }
     list ldp-auto-targeted-session {
       description "LDP auto targeted sessions";
       leaf ldp-auto-targeted-session-enabled {
         type string;
         description "Use auto targerted sessions";
       }
       leaf ldp-auto-targeted-max-sessions {
         type uint32;
         description "Max sessions";
       }
       leaf ldp-auto-targeted-session-count {
         type uint32;
         description "Session count";
       }
       leaf ldp-auto-targeted-teardown-delay {
         type uint32;
         description "Teardown delay";
       }
     }
     list ldp-p2mp {
       description "LDP P2MP";
       leaf ldp-p2mp-recursive-route-enabled {
         type string;
         description "Use recursive route for mldp signaling";
       }
     }
     list ldp-timer-overview {
       description "LDP timer overview";
       leaf ldp-instance-keepalive-interval {
         type uint32;
         description "Keepalive interval";
       }
       leaf ldp-instance-keepalive-timeout {
         type uint32;
         description "Keepalive timeout";
       }
       leaf ldp-instance-link-hello-interval {
         type uint32;
         description "Link hello interval";
       }
       leaf ldp-instance-link-hello-hold-time {
         type uint32;
         description "Link hello hold time";
       }
       leaf ldp-instance-targeted-hello-interval {
         type uint32;
         description "Targeted hello interval";
       }
       leaf ldp-instance-targeted-hello-hold-time {
         type uint32;
         description "Targeted hello hold time";
       }
       leaf ldp-instance-label-withdraw-delay {
         type uint32;
         description "Label withdraw delay";
       }
       leaf ldp-instance-make-before-break-timeout {
         type uint32;
         description "Make before break timeout";
       }
       leaf ldp-instance-make-before-break-switchover-delay {
         type uint32;
         description "Make before break switchover delay";
       }
       leaf ldp-instance-link-protection-timeout {
         type uint32;
         description "Link protection timeout";
       }
     }
     list ldp-gr-overview {
       description "LDP GR overview";
       leaf ldp-gr-restart {
         type string;
         description "Restart";
       }
       leaf ldp-gr-helper {
         type string;
         description "Helper";
       }
       leaf ldp-gr-restarting {
         type string;
         description "Restart in progress";
       }
       leaf ldp-gr-reconnect-time {
         type uint32;
         description "Reconnect time";
       }
       leaf ldp-gr-max-neighbor-reconnect-time {
         type uint32;
         description "Max neighbor reconnect time";
       }
       leaf ldp-gr-recovery-time {
         type uint32;
         description "Recovery time";
       }
       leaf ldp-gr-max-neighbor-recovery-time {
         type uint32;
         description "Max neighbor recovery time";
       }
     }
     list ldp-te-overview {
       description "LDP TE overview";
       leaf ldp-te-bgp-igp {
         type string;
         description "Bgp igp";
       }
       leaf ldp-te-both-ribs {
         type string;
         description "Both ribs";
       }
       leaf ldp-te-mpls-forwarding {
         type string;
         description "Mpls forwarding";
       }
     }
     list ldp-igp-overview {
       description "LDP igp overview";
       leaf ldp-tracking-igp-metric {
         type string;
         description "Tracking igp metric";
       }
       leaf ldp-igp-sync-session-up-delay {
         type uint32;
         description "Sync session up delay";
       }
     }
     list ldp-session-protect-overview {
       description "LDP session protect overview";
       leaf ldp-session-protect {
         type string;
         description "Session protect";
       }
       leaf ldp-session-protect-timeout {
         type uint32;
         description "Session protect timeout";
       }
     }
     list ldp-interface-address {
       description "LDP interface addresses advertised";
       leaf interface-address {
         type ipaddr;
       }
     }
     list ldp-label-allocation {
       description "Lable allocation";
       leaf ldp-label-current-allocs {
         type uint32;
         description "Current number of LDP labels allocated";
       }
       leaf ldp-label-total-allocs {
         type uint32;
         description "Total number of LDP labels allocated";
       }
       leaf ldp-label-total-frees {
         type uint32;
         description "Total number of LDP labels freed";
       }
       leaf ldp-label-alloc-failure {
         type uint32;
         description "Total number of LDP label allocation failure";
       }
       leaf ldp-global-label-current-allocs {
         type uint32;
         description "Current number of labels allocated by all protocols";
       }
     }
     list ldp-job-overview {
       description "LDP job overview";
       leaf ldp-read-job-time-quantum {
         type uint32;
         description "Read job time quantum";
       }
       leaf ldp-write-job-time-quantum {
         type uint32;
         description "Write job time quantum";
       }
       leaf ldp-read-job-loop-quantum {
         type uint32;
         description "Read job loop quantum";
       }
       leaf ldp-write-job-loop-quantum {
         type uint32;
         description "Write job loop quantum";
       }
       leaf ldp-inbound-read-job-time-quantum {
         type uint32;
         description "Backup inbound read job time quantum";
       }
       leaf ldp-outbound-read-job-time-quantum {
         type uint32;
         description "Backup outbound read job time quantum";
       }
       leaf ldp-inbound-read-job-loop-quantum {
         type uint32;
         description "Backup inbound read job loop quantum";
       }
       leaf ldp-outbound-read-job-loop-quantum {
         type uint32;
         description "Backup outbound read job loop quantum";
       }
     }
   }
 }
 grouping ldp-interface-information-block {
   list ldp-interface {
     leaf interface-name {
       type string;
       description "Name of interface";
     }
     leaf ldp-interface-local-address {
       type ipaddr;
     }
     leaf ldp-label-space-id {
       type string;
     }
     leaf ldp-neighbor-count {
       type int32;
     }
     leaf ldp-next-hello {
       type int32;
     }
     leaf ldp-hello-interval {
       type int32;
     }
     leaf ldp-holdtime {
       type int32;
     }
     leaf ldp-transport-address {
       type ipaddr;
     }
     leaf ldp-local-hello-interval {
       type int32;
       description "The locally configured hello interval";
     }
     leaf ldp-interface-index {
       type uint32;
     }
     leaf ldp-block-time {
       type int32;
     }
     leaf ldp-hello-sent {
       type uint32;
       description "Number of hellos sent on this interface";
     }
     leaf ldp-hello-received {
       type uint32;
       description "Number of hellos received on this interface";
     }
     container ldp-if-link-protection {
       description "If link protection";
       leaf ldp-link-protection {
         type string;
         description "Link Protection";
       }
     }
   }
 }
 grouping ldp-neighbor-information-block {
   list ldp-neighbor {
     leaf ldp-neighbor-address {
       type ipaddr;
     }
     leaf interface-name {
       type string;
       description "Name of interface";
     }
     leaf ldp-label-space-id {
       type string;
     }
     leaf ldp-remaining-time {
       type int32;
     }
     leaf ldp-transport-address {
       type ipaddr;
     }
     leaf ldp-transport-preference {
       type string;
     }
     leaf ldp-config-sequence {
       type uint32;
     }
     leaf ldp-up-time {
       type int32;
     }
     leaf ldp-reference-count {
       type int32;
     }
     leaf ldp-auto-discovered-reference-count {
       type int32;
     }
     leaf ldp-holdtime {
       type int32;
     }
     leaf ldp-proposed-local-holdtime {
       type int32;
       description "The local value of the hold time";
     }
     leaf ldp-proposed-peer-holdtime {
       type int32;
       description "The peer's proposed value of the hold time";
     }
     leaf ldp-hello-interval {
       type int32;
     }
     container ldp-neighbor-hello-flags {
       description "LDP neighbor hello flags";
       leaf ldp-neighbor-hello-flag {
         type string;
         description "LDP neighbor hello flag";
       }
     }
     container ldp-neighbor-types {
       description "LDP neighbor types";
       leaf ldp-neighbor-type {
         type string;
         description "LDP neighbor type";
       }
     }
   }
 }
 grouping ldp-session-information-block {
   container brief {
     list ldp-session {
       leaf ldp-neighbor-address {
         type ipaddr;
       }
       leaf ldp-session-state {
         type string;
       }
       leaf ldp-connection-state {
         type string;
       }
       leaf ldp-remaining-time {
         type int32;
       }
       leaf ldp-session-adv-mode {
         type string;
       }
     }
   }
   container detail {
     list ldp-session {
       leaf ldp-neighbor-address {
         type ipaddr;
       }
       leaf ldp-session-state {
         type string;
       }
       leaf ldp-connection-state {
         type string;
       }
       leaf ldp-remaining-time {
         type int32;
       }
       leaf ldp-session-id {
         type string;
       }
       leaf ldp-retry-time {
         type int32;
       }
       leaf ldp-keepalive-time {
         type int32;
       }
       leaf ldp-session-role {
         type string;
       }
       leaf ldp-session-max-pdu {
         type int32;
       }
       leaf ldp-holdtime {
         type int32;
       }
       leaf ldp-neighbor-count {
         type int32;
       }
       leaf ldp-keepalive-interval {
         type int32;
       }
       leaf ldp-retry-interval {
         type int32;
       }
       leaf ldp-local-address {
         type ipaddr;
       }
       leaf ldp-remote-address {
         type ipaddr;
       }
       leaf ldp-up-time {
         type int32;
       }
       leaf ldp-last-down-time {
         type int32;
       }
       leaf ldp-down-reason {
         type string;
       }
       leaf ldp-session-flap-count {
         type uint32;
         description "Number of times the LDP session has gone down and then come back up";
       }
       leaf ldp-session-deleted {
         type empty;
       }
       leaf ldp-session-close-pending {
         type empty;
       }
       leaf ldp-session-queue-depth {
         type int32;
       }
       leaf ldp-session-read-pending {
         type empty;
       }
       leaf ldp-session-write-pending {
         type empty;
       }
       leaf ldp-session-receive-buffer-bytes {
         type int32;
       }
       leaf ldp-session-transmit-buffer-bytes {
         type int32;
       }
       leaf ldp-session-no-connection {
         type empty;
       }
       leaf ldp-session-authentication {
         type string;
       }
       leaf ldp-graceful-restart-state {
         type string;
       }
       leaf ldp-restart-complete-time {
         type int32;
       }
       leaf ldp-helper-mode-state {
         type string;
         description "Helping neighbor during graceful restart";
       }
       leaf ldp-helper-mode-time {
         type int32;
         description "Time left for session re-establishment or label recovery";
       }
       leaf ldp-graceful-restart-local {
         type string;
       }
       leaf ldp-local-helper-mode {
         type string;
       }
       leaf ldp-local-reconnect-time {
         type int32;
       }
       leaf ldp-graceful-restart-remote {
         type string;
       }
       leaf ldp-remote-helper-mode {
         type string;
       }
       leaf ldp-remote-reconnect-time {
         type int32;
       }
       leaf ldp-local-maximum-reconnect {
         type int32;
       }
       leaf ldp-local-maximum-recovery {
         type int32;
       }
       leaf ldp-local-label-adv-mode {
         type string;
       }
       leaf ldp-remote-label-adv-mode {
         type string;
       }
       leaf ldp-neg-label-adv-mode {
         type string;
       }
       leaf ldp-mtu-discovery {
         type string;
         description "Use LDP mtu discovery";
       }
       leaf ldp-label-request-status-code {
         type string;
         description "Status of label request from downstream session";
       }
       leaf ldp-session-nsr-state {
         type string;
         description "Synchronization state of nonstop routing for the session";
       }
       container ldp-neighbor-types {
         description "LDP neighbor types";
         leaf ldp-neighbor-type {
           type string;
           description "LDP neighbor type";
         }
       }
       container ldp-session-capabilities-advertised {
         description "Capabilities advertised to peer";
         leaf ldp-capability {
           type string;
           description "LDP capability";
         }
       }
       container ldp-session-capabilities-received {
         description "Capabilities received from peer";
         leaf ldp-capability {
           type string;
           description "LDP capability";
         }
       }
       container ldp-session-protection {
         description "LDP session protection information";
         leaf ldp-session-protection-state {
           type string;
           description "LDP session protection state";
         }
         leaf ldp-session-protection-remaining-time {
           type int32;
           description "Time after which session protection will cease to be active";
         }
       }
       container ldp-session-flags {
         description "LDP session flags";
         leaf ldp-session-flag {
           type string;
           description "LDP session flag";
         }
       }
       list ldp-session-address {
         leaf interface-name {
           type string;
           description "Name of interface";
         }
         leaf interface-address {
           type ipaddr;
         }
         leaf ldp-session-address-stale {
           type empty;
         }
       }
       list ldp-session-statistics {
         leaf ldp-message-type {
           type string;
         }
         leaf ldp-messages-sent {
           type uint32;
         }
         leaf ldp-messages-received {
           type uint32;
         }
         leaf ldp-messages-sent-5seconds {
           type uint32;
         }
         leaf ldp-messages-received-5seconds {
           type uint32;
         }
       }
     }
   }
 }
 grouping ldp-route-information-block {
   list ldp-route {
     leaf ldp-prefix {
       type string;
     }
     leaf ldp-label {
       type int32;
     }
     leaf ldp-no-label {
       type empty;
     }
     leaf ldp-topology-entry {
       type int32;
     }
     leaf ldp-ingress-route-status {
       type string;
       description "Status about whether the ingress route is present or not";
     }
     leaf ldp-ingress-route-last-modified-time {
       type int32;
       description "Time since the ingress route was modified";
     }
     leaf ldp-ingress-route-session-id {
       type uint32;
       description "Ingress route session id";
     }
     leaf ldp-ingress-route-session-id-version {
       type uint32;
       description "Version";
     }
     leaf ldp-merged-next-hop {
       type empty;
       description "Both active and non-active next hop will be merged together";
     }
     leaf ldp-inet0-data {
       type int32;
     }
     leaf ldp-reference-count {
       type int32;
     }
     leaf ldp-fec-nexthop-route {
       type string;
       description "Nexthop route for longest match FEC";
     }
     leaf ldp-fec-events {
       type string;
       description "LDP FEC pending events";
     }
     leaf ldp-p2mp-ref-count {
       type int32;
     }
     list ldp-nexthop {
       leaf interface-name {
         type string;
         description "Name of interface";
       }
       leaf lsp-name {
         type string;
         description "Tunneled into an RSVP LSP";
       }
       leaf nh-table {
         type string;
         description "Indirect pointing to another table";
       }
       leaf lsp-no-ldp-tunneling {
         type empty;
         description "LDP tunneling is not configured on LSP";
       }
       leaf interface-address {
         type ipaddr;
       }
       leaf ldp-session-id {
         type string;
       }
       leaf ldp-label-request-state {
         type string;
       }
       leaf ldp-label-request-status-code {
         type string;
         description "Status of label request from downstream session";
       }
       leaf ldp-route-backoff-time {
         type int32;
         description "Time since label request backoff timer started";
       }
     }
     container ldp-route-types {
       description "Route types";
       leaf ldp-route-type {
         type string;
         description "LDP Route type";
       }
     }
     container ldp-route-flags {
       description "LDP Route flags";
       leaf ldp-route-flag {
         type string;
         description "LDP Route flag";
       }
     }
     list ldp-oam-bfd-session {
       description "LDP OAM state information";
       leaf ldp-oam-destination-address {
         type ipaddr;
       }
       leaf ldp-oam-bfd-session-state {
         type string;
       }
       leaf ldp-oam-lsp-ping-state {
         type string;
       }
       leaf ldp-oam-nexthop-address {
         type ipaddr;
       }
       leaf ldp-oam-interface-name {
         type string;
       }
       leaf ldp-oam-nexthop-lsp {
         type string;
       }
     }
     container ldp-fec-history {
       description "Log over time of Fec related events";
       leaf ldp-fec-hist-sequence-number {
         type int32;
       }
       leaf ldp-fec-hist-time {
         type string;
       }
       leaf ldp-fec-hist-log {
         type string;
       }
       leaf ldp-fec-hist-more-info {
         type string;
       }
     }
   }
 }
 grouping ldp-path-information-block {
   list ldp-path {
     leaf ldp-outlib-session {
       type string;
     }
     leaf ldp-outlib-label {
       type int32;
     }
     leaf ldp-ingress-label {
       type empty;
     }
     leaf ldp-inlib-session {
       type string;
     }
     leaf ldp-inlib-label {
       type int32;
     }
     leaf ldp-egress-label {
       type empty;
     }
     leaf ldp-reference-count {
       type int32;
     }
     leaf ldp-route-transit {
       type empty;
     }
     leaf ldp-global-label {
       type int32;
     }
     leaf ldp-merged-next-hop {
       type empty;
       description "Both active and non-active next hop will be merged together";
     }
     list ldp-path-route {
       leaf ldp-prefix {
         type string;
       }
       leaf ldp-route-ingress {
         type empty;
       }
     }
   }
 }
 grouping ldp-database-information-block {
   list ldp-database {
     leaf ldp-database-type {
       type string;
     }
     leaf ldp-session-id {
       type string;
     }
     leaf ldp-label-received {
       type uint32;
       description "Labels received";
     }
     leaf ldp-label-advertised {
       type uint32;
       description "Labels advertised";
     }
     container ldp-database-summary {
     }
     list ldp-binding {
       leaf ldp-label {
         type int32;
       }
       leaf ldp-prefix {
         type string;
       }
       leaf ldp-binding-filtered {
         type empty;
       }
       leaf ldp-binding-mbbreqrecvd {
         type empty;
       }
       leaf ldp-binding-mbbreqsent {
         type empty;
       }
       leaf ldp-binding-stale {
         type empty;
       }
       leaf ldp-binding-mtu {
         type int32;
       }
       leaf ldp-binding-cell-bundle-size {
         type int32;
       }
       leaf ldp-binding-requested-vlan-id {
         type int32;
       }
       leaf ldp-binding-bitrate {
         type int32;
       }
       leaf ldp-binding-payload-size {
         type int32;
       }
       leaf ldp-binding-pw-flow-label-tx {
         type int32;
       }
       leaf ldp-binding-pw-flow-label-rx {
         type int32;
       }
       leaf ldp-binding-pw-status-code {
         type int32;
       }
       leaf ldp-binding-l2protec-context-id {
         type ipaddr;
       }
       leaf ldp-binding-l2protec-ctrl-word {
         type string;
       }
       leaf ldp-binding-state {
         type string;
       }
       leaf ldp-binding-age {
         type string;
       }
       leaf ldp-binding-queued {
         type empty;
       }
       leaf ldp-binding-not-yet-sent {
         type empty;
       }
       leaf ldp-binding-delete-scheduled {
         type string;
       }
       leaf ldp-binding-elc {
         type string;
       }
       container ldp-binding-standby {
         description "Standby binding information";
         leaf ldp-binding-standby-map-count {
           type int32;
           description "Count of outstanding map messages received";
         }
         leaf ldp-binding-standby-rel-count {
           type int32;
           description "Count of outstanding release messages received";
         }
       }
       container ldp-l2circuit-vccv-cc-type {
         description "VCCV connectivity channel types supported by peer";
         leaf mpls-type-control-word {
           type string;
           description "Indicates that pwe3 control word type is supported";
         }
         leaf mpls-type-router-alert {
           type string;
           description "Indicates that mpls router alert label is supported";
         }
         leaf mpls-type-pw-label {
           type string;
           description "Indicates that pseudowire label with ttl=1 is supported";
         }
       }
       container ldp-l2circuit-vccv-cv-type {
         description "VCCV connectivity verification types supported by peer";
         leaf mpls-type-icmp-ping {
           type string;
           description "Indicates that ICMP ping is supported";
         }
         leaf mpls-type-lsp-ping {
           type string;
           description "Indicates that LSP ping is supported";
         }
         leaf mpls-type-bfd-pw-ach-fd {
           type string;
           description "Indicates that PW-ACH-encapsulated BFD for PW Fault Detection is supported";
         }
         leaf mpls-type-bfd-pw-ach-fd-fss {
           type string;
           description "Indicates that PW-ACH-encapsulated BFD for PW Fault Detection and AC/PW Fault Status Signaling is supported";
         }
         leaf mpls-type-bfd-ip-udp-fd {
           type string;
           description "Indicates that IP/UDP-encapsulated BFD for PW Fault Detection is supported";
         }
         leaf mpls-type-bfd-ip-udp-fd-fss {
           type string;
           description "Indicates that IP/UDP-encapsulated BFD for PW Fault Detection and AC/PW Fault Status Signaling is supported";
         }
       }
     }
     list ldp-label-request {
       leaf ldp-prefix {
         type string;
       }
       leaf ldp-label-request-state {
         type string;
       }
       leaf ldp-label-request-filtered {
         type empty;
       }
       leaf ldp-label-request-stale {
         type empty;
       }
       leaf ldp-label-request-status-code {
         type string;
         description "Status of label request from downstream session";
       }
       leaf ldp-route-backoff-time {
         type int32;
         description "Time since label request backoff timer started";
       }
       leaf ldp-label-request-age {
         type string;
       }
     }
   }
 }
 grouping ldp-statistics-information-block {
   container ldp-statistics {
     list ldp-message-statistics {
       leaf ldp-message-type {
         type string;
       }
       leaf ldp-messages-sent {
         type uint32;
       }
       leaf ldp-messages-received {
         type uint32;
       }
       leaf ldp-messages-sent-5seconds {
         type uint32;
       }
       leaf ldp-messages-received-5seconds {
         type uint32;
       }
     }
     list ldp-event-statistics {
       leaf ldp-event-type {
         type string;
       }
       leaf ldp-event-count {
         type uint32;
       }
       leaf ldp-event-count-5seconds {
         type uint32;
       }
     }
   }
 }
 grouping ldp-traffic-statistics-information-block {
   container ldp-traffic-statistics {
     leaf ldp-prefix {
       type string;
     }
     leaf ldp-traffic-type {
       type string;
       description "Type of traffic: ingress or transit";
     }
     leaf ldp-traffic-error {
       type string;
       description "Error encountered when querying the statistics";
     }
     leaf ldp-traffic-statistics-packet-count {
       type int32;
       description "Number of packets";
     }
     leaf ldp-traffic-statistics-byte-count {
       type int32;
       description "Number of bytes";
     }
     leaf ldp-traffic-multiple-fec {
       type string;
       description "Multiple FECs sharing the same label";
     }
   }
   container ldp-p2mp-traffic-statistics {
     leaf ldp-prefix {
       type string;
     }
     leaf ldp-label {
       type int32;
     }
     leaf ldp-p2mp-label-primary {
       type string;
       description "Indicates if p2mp label is primary for this fec";
     }
     leaf ldp-traffic-branch-nexthop-addr {
       type string;
       description "Branch nexthop address of p2mp lsp";
     }
     leaf ldp-traffic-branch-nexthop-interface {
       type string;
       description "Branch nexthop interface of p2mp lsp";
     }
     leaf ldp-traffic-error {
       type string;
       description "Error encountered when querying the statistics";
     }
     leaf ldp-traffic-statistics-packet-count {
       type int32;
       description "Number of packets";
     }
     leaf ldp-traffic-statistics-byte-count {
       type int32;
       description "Number of bytes";
     }
     leaf ldp-traffic-multiple-fec {
       type string;
       description "Multiple FECs sharing the same label";
     }
   }
   container ldp-traffic-statistics-error {
     leaf ldp-traffic-error {
       type string;
       description "Error encountered when querying the statistics";
     }
   }
 }
 grouping ldp-fec-filters-information-block {
   list ldp-fec-filter {
     leaf ldp-prefix {
       type string;
     }
     leaf ldp-ingress-filter {
       type string;
       description "Ingress firewall filter name";
     }
     leaf ldp-ingress-filterid {
       type int32;
       description "Ingress firewall filter index";
     }
     leaf ldp-transit-filter {
       type string;
       description "Transit firewall filter name";
     }
     leaf ldp-transit-filterid {
       type int32;
       description "Transit firewall filter index";
     }
   }
 }
 grouping ldp-rib-groups-information-block {
   list ldp-rib-group {
     leaf ldp-rib-group-name {
       type string;
       description "Rib group name";
     }
   }
 }
 grouping ldp-oam-information-block {
   list ldp-oam-status {
     leaf ldp-oam-prefix {
       type string;
     }
     leaf ldp-oam-time {
       type string;
     }
     list ldp-oam-path {
       leaf ldp-oam-destination-address {
         type ipaddr;
       }
       leaf ldp-oam-nexthop-address {
         type ipaddr;
       }
       leaf ldp-oam-interface-name {
         type string;
       }
       leaf ldp-oam-nexthop-lsp {
         type string;
       }
       leaf ldp-oam-bfd-session-state {
         type string;
       }
       leaf ldp-oam-lsp-ping-state {
         type string;
       }
       leaf ldp-oam-path-address {
         type ipaddr;
       }
     }
   }
 }
 grouping ldp-p2mp-path-information-block {
   list ldp-p2mp-path {
     leaf ldp-p2mp-path-type {
       type string;
       description "Type of p2mp path";
     }
     leaf ldp-p2mp-outlib-session {
       type string;
       description "Output session";
     }
     leaf ldp-p2mp-outlib-label {
       type int32;
       description "Label advertised on output session";
     }
     leaf ldp-p2mp-label-primary {
       type string;
       description "Indicates if p2mp label is primary for this fec";
     }
     leaf ldp-p2mp-egress-label {
       type int32;
       description "Application specified label";
     }
     leaf ldp-p2mp-path-address {
       type int32;
       description "Address of the p2mp path object";
     }
     leaf ldp-reference-count {
       type int32;
     }
     leaf ldp-p2mp-path-transit-route {
       type empty;
       description "Indicates if transit route is installed";
     }
     list ldp-p2mp-inlib-label {
       leaf ldp-label-session {
         type string;
         description "Input session";
       }
       leaf ldp-label {
         type int32;
       }
     }
     list ldp-egress-nh {
       leaf ldp-egress-nh-type {
         type string;
         description "Type of egress nexthop";
       }
       leaf interface-name {
         type string;
         description "Name of interface";
       }
     }
     list ldp-rpf-nh {
       leaf ldp-rpf-nh-type {
         type string;
         description "Type of RPF nexthop";
       }
       leaf interface-name {
         type string;
         description "Name of interface";
       }
       leaf ldp-rpf-nexthop-address {
         type ipaddr;
       }
       leaf ldp-label {
         type int32;
       }
       leaf ldp-rpf-weight {
         type int32;
       }
     }
     list ldp-p2mp-path-fec {
       leaf ldp-prefix {
         type string;
       }
       leaf ldp-prefix-active {
         type string;
         description "Indicates if p2mp path is active for this fec";
       }
       leaf ldp-prefix-mbb-timer {
         type int32;
         description "Make before break timer";
       }
       leaf ldp-prefix-mbb-timer-type {
         type string;
         description "Make before break timer type";
       }
     }
   }
 }
 grouping ldp-p2mp-tunnel-information-block {
   list ldp-p2mp-tunnel {
     description "P2MP tunnel entry";
     leaf ldp-instance-id {
       type int32;
       description "Routing instance identifier";
     }
     leaf ldp-p2mp-tunnel-type {
       type string;
       description "P2MP tunnel type";
     }
     leaf ldp-p2mp-tunnel-name {
       type string;
       description "P2MP tunnel name";
     }
     leaf ldp-prefix {
       type string;
     }
     leaf ldp-p2mp-tunnel-selfid {
       type uint32;
       description "P2MP tunnel self ID";
     }
     leaf ldp-reference-count {
       type int32;
     }
   }
 }
 grouping ldp-p2mp-fec-information-block {
   list ldp-p2mp-fec {
     leaf ldp-prefix {
       type string;
     }
     leaf ldp-p2mp-fec-mofrr {
       type string;
       description "Indicates if MoFRR enabled for this fec";
     }
     leaf ldp-p2mp-fec-type {
       type string;
       description "Type of p2mp fec";
     }
     leaf ldp-prefix-active {
       type string;
       description "Indicates if p2mp path is active for this fec";
     }
     leaf ldp-p2mp-fec-outlib-label {
       type int32;
       description "Label advertised on output session";
     }
     leaf ldp-reference-count {
       type int32;
     }
   }
 }
 }
