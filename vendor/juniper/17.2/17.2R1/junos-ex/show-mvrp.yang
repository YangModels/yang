/*
 * Copyright (c) 2017 Juniper Networks, Inc.
 * All rights reserved.
 */
 module show-mvrp {
  namespace "http://yang.juniper.net/yang/1.1/jrpc/show-mvrp/junos-ex/17.2R1.13";
  prefix show-mvrp;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-mvrp-information {
     description "Show MVRP Protocol information";
     input {
       leaf logical-system {
         description "Name of logical system";
         type string {
           junos:posix-pattern "^[a-zA-Z0-9_-]{1,63}$";
           junos:pattern-message "Logical-system name is a string consisting of up to 63 letters, numbers, dashes and underscores";
         }
       }
       leaf routing-instance {
         description "Name of routing instance";
         type string;
       }
     }
     output {
       container mvrp-information {
         uses mvrp-information-block;
       }
     }
   }
   rpc get-mvrp-interface-information {
     description "Show MVRP interface information";
     input {
       leaf logical-system {
         description "Name of logical system";
         type string {
           junos:posix-pattern "^[a-zA-Z0-9_-]{1,63}$";
           junos:pattern-message "Logical-system name is a string consisting of up to 63 letters, numbers, dashes and underscores";
         }
       }
       leaf routing-instance {
         description "Name of routing instance";
         type string;
       }
       leaf interface {
         description "Name of interface";
         type string;
       }
     }
     output {
       container mvrp-interface-information {
         uses mvrp-interface-information-block;
       }
     }
   }
   rpc get-mvrp-registration-state {
     description "Show MVRP registration state ";
     input {
       leaf logical-system {
         description "Name of logical system";
         type string {
           junos:posix-pattern "^[a-zA-Z0-9_-]{1,63}$";
           junos:pattern-message "Logical-system name is a string consisting of up to 63 letters, numbers, dashes and underscores";
         }
       }
       leaf routing-instance {
         description "Name of routing instance";
         type string;
       }
       leaf interface {
         description "Name of interface";
         type string;
       }
       leaf vlan {
         description "VLAN ID";
         type int32 {
           range "1 .. 4094";
         }
       }
     }
     output {
       container mvrp-registration-information {
         uses mvrp-registration-information-block;
       }
     }
   }
   rpc get-mvrp-applicant-information {
     description "Show MVRP applicant state ";
     input {
       leaf logical-system {
         description "Name of logical system";
         type string {
           junos:posix-pattern "^[a-zA-Z0-9_-]{1,63}$";
           junos:pattern-message "Logical-system name is a string consisting of up to 63 letters, numbers, dashes and underscores";
         }
       }
       leaf routing-instance {
         description "Name of routing instance";
         type string;
       }
       leaf interface {
         description "Name of interface";
         type string;
       }
       leaf vlan {
         description "VLAN ID";
         type int32 {
           range "1 .. 4094";
         }
       }
     }
   }
   rpc get-mvrp-interface-statistics {
     description "Show MVRP interface statistics";
     input {
       leaf logical-system {
         description "Name of logical system";
         type string {
           junos:posix-pattern "^[a-zA-Z0-9_-]{1,63}$";
           junos:pattern-message "Logical-system name is a string consisting of up to 63 letters, numbers, dashes and underscores";
         }
       }
       leaf routing-instance {
         description "Name of routing instance";
         type string;
       }
       leaf interface {
         description "Name of interface";
         type string;
       }
     }
     output {
       container mvrp-interface-statistics {
         uses mvrp-interface-statistics-block;
       }
     }
   }
   rpc get-mvrp-dynamic-vlan-memberships {
     description "Show MVRP dynamic VLAN memberships";
     input {
       leaf logical-system {
         description "Name of logical system";
         type string {
           junos:posix-pattern "^[a-zA-Z0-9_-]{1,63}$";
           junos:pattern-message "Logical-system name is a string consisting of up to 63 letters, numbers, dashes and underscores";
         }
       }
       leaf routing-instance {
         description "Name of routing instance";
         type string;
       }
       leaf vlan {
         description "VLAN ID";
         type int32 {
           range "1 .. 4094";
         }
       }
       leaf interface {
         description "Name of interface";
         type string;
       }
     }
     output {
       container mvrp-vlan-information {
         uses mvrp-vlan-information-block;
       }
     }
   }
 grouping mvrp-information-block {
   container mvrp-information-entry {
     leaf mvrp-dynamic-vlan {
       type string;
       description "MVRP dynamic VLAN creation";
     }
     leaf mvrp-bpdu-mac-address {
       type string;
       description "MVRP BPDU destination MAC address";
     }
     list mvrp-interface-timers {
       leaf mvrp-interface-name {
         type string;
         description "Name of interface";
       }
       leaf mvrp-timer-join {
         type uint32;
         description "Join timer";
       }
       leaf mvrp-timer-leave {
         type uint32;
         description "Leave timer";
       }
       leaf mvrp-timer-leaveall {
         type uint32;
         description "LeaveAll timer";
       }
     }
   }
 }
 grouping mvrp-interface-information-block {
   list mvrp-interface-instance {
     container mvrp-interface-entry {
       leaf mvrp-interface-name {
         type string;
         description "Name of interface";
       }
       leaf mvrp-interface-status {
         type string;
         description "MVRP interface operational status";
       }
       leaf mvrp-interface-registration-mode {
         type string;
         description "MVRP interface registration mode";
       }
       leaf mvrp-interface-applicant-mode {
         type string;
         description "MVRP interface applicant mode";
       }
     }
   }
 }
 grouping mvrp-registration-information-block {
   list mvrp-registration-instance {
     list mvrp-registration-vlan-entry {
       description "Registration state information";
       leaf mvrp-vlan-id {
         type int32;
         description "VLAN ID";
       }
       list mvrp-registration-interface-entry {
         leaf mvrp-interface-name {
           type string;
           description "Name of interface";
         }
         leaf mvrp-registration-state {
           type string;
           description "Registration state";
         }
         leaf mvrp-registration-forced-state {
           type string;
           description "Forced state";
         }
         leaf mvrp-registration-manage-state {
           type string;
           description "Management state";
         }
         leaf mvrp-registration-stp-state {
           type string;
           description "STP state";
         }
       }
     }
   }
 }
 grouping mvrp-interface-statistics-block {
   list mvrp-statistics-instance {
     list mvrp-statistics-interface-entry {
       description "Statistics information";
       leaf mvrp-interface-name {
         type string;
         description "Name of interface";
       }
       leaf mvrp-statistics-vlan-registered {
         type int32;
         description "MAC Registered";
       }
       leaf mvrp-statistics-sent-pdu {
         type int32;
         description "Number of Sent MVRP PDUs";
       }
       leaf mvrp-statistics-received-pdu {
         type int32;
         description "Number of Received MVRP PDUs without error";
       }
       leaf mvrp-statistics-error-pdu {
         type int32;
         description "Number of Received MVRP PDUs with error";
       }
       leaf mvrp-join-empty-transmit {
         type int32;
         description "Join Empty transmitted";
       }
       leaf mvrp-leaveall-transmit {
         type int32;
         description "Leave All Transmitted";
       }
       leaf mvrp-join-in-transmit {
         type int32;
         description "Join In Transmitted";
       }
       leaf mvrp-empty-transmit {
         type int32;
         description "Empty Transmitted";
       }
       leaf mvrp-leave-transmit {
         type int32;
         description "Leave Transmitted";
       }
       leaf mvrp-in-transmit {
         type int32;
         description "In transmitted";
       }
       leaf mvrp-new-transmit {
         type int32;
         description "New Transmitted";
       }
       leaf mvrp-join-in-received {
         type int32;
         description "Join In Received";
       }
       leaf mvrp-leave-all-received {
         type int32;
         description "Leave All received";
       }
       leaf mvrp-leave-received {
         type int32;
         description "Leave Received";
       }
       leaf mvrp-in-received {
         type int32;
         description "In Received";
       }
       leaf mvrp-empty-received {
         type int32;
         description "Empty Received";
       }
       leaf mvrp-join-empty-received {
         type int32;
         description "Join Empty Received";
       }
       leaf mvrp-new-received {
         type int32;
         description "New Received";
       }
     }
   }
 }
 grouping mvrp-vlan-information-block {
   list mvrp-vlan-instance {
     list mvrp-vlan-entry {
       description "Dynamic vlan information";
       leaf mvrp-vlan-id {
         type int32;
         description "VLAN ID";
       }
       leaf mvrp-static-vlan {
         type empty;
         description "Statically configured vlan";
       }
       list mvrp-vlan-interface-entry {
         leaf mvrp-interface-name {
           type string;
           description "Name of interface";
         }
         leaf mvrp-fixed-registration {
           type empty;
           description "Fixed registration vlan";
         }
       }
     }
   }
 }
 }
