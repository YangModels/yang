/*
 * Copyright (c) 2017 Juniper Networks, Inc.
 * All rights reserved.
 */
 module show-sflow {
  namespace "http://yang.juniper.net/yang/1.1/jrpc/show-sflow/junos-ex/17.2R1.13";
  prefix show-sflow;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-sflow-information {
     description "Show sFlow information";
     output {
       container sflow {
         uses sflow-block;
       }
     }
   }
   rpc get-sflow-collector {
     description "Show sFlow collectors";
     output {
       container sflow {
         uses sflow-block;
       }
     }
   }
   rpc get-sflow-interface {
     description "Show sFlow interfaces";
     output {
       container sflow {
         uses sflow-block;
       }
     }
   }
 grouping sflow-block {
   list sflow-information {
     leaf sflow-global-status {
       type string;
       description "SFLOW Global status";
     }
     leaf sflow-status {
       type string;
       description "SFLOW status";
     }
     leaf sflow-sample-rate-egress {
       type int32;
       description "SFLOW egress sample rate";
     }
     leaf sflow-sample-rate-ingress {
       type int32;
       description "SFLOW ingress sample rate";
     }
     leaf sflow-sample-limit {
       type int32;
       description "SFLOW sampling limit";
     }
     leaf sflow-polling-interval {
       type int32;
       description "SFLOW polling interval";
     }
     leaf sflow-agent-id {
       type ipaddr;
       description "SFLOW agent ID";
     }
     leaf sflow-agent-id6 {
       type ipaddr;
       description "SFLOW agent ID IPv6";
     }
     leaf sflow-source-ip {
       type ipaddr;
       description "SFLOW datagram source IP";
     }
     leaf sflow-source-ip6 {
       type ipaddr;
       description "SFLOW datagram source IPv6";
     }
   }
   list sflow-collector {
     leaf remote-collector-interface-address {
       type ipaddr;
       description "SFLOW remote collector IP address";
     }
     leaf collector-udp-port {
       type int32;
       description "SFLOW collector UDP port";
     }
     leaf collector-number-of-samples {
       type int32;
       description "SFLOW collector number of samples";
     }
   }
   list sflow-interface {
     leaf interface-name {
       type string;
       description "SFLOW interface name";
     }
     leaf interface-status-egress {
       type string;
       description "SFLOW interface egress status";
     }
     leaf interface-status-ingress {
       type string;
       description "SFLOW interface ingress status";
     }
     leaf interface-sample-rate-egress {
       type int32;
       description "SFLOW Inteface egress sampling rate";
     }
     leaf interface-sample-rate-ingress {
       type int32;
       description "SFLOW Inteface ingress sampling rate";
     }
     leaf interface-adapt-sample-rate-egress {
       type int32;
       description "SFLOW Inteface adapted egress sampling rate";
     }
     leaf interface-adapt-sample-rate-ingress {
       type int32;
       description "SFLOW Inteface adapted ingress sampling rate";
     }
     leaf interface-polling-interval {
       type int32;
       description "SFLOW Inteface polling interval";
     }
   }
 }
 }
