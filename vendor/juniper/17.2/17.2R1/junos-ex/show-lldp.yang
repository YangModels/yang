/*
 * Copyright (c) 2017 Juniper Networks, Inc.
 * All rights reserved.
 */
 module show-lldp {
  namespace "http://yang.juniper.net/yang/1.1/jrpc/show-lldp/junos-ex/17.2R1.13";
  prefix show-lldp;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-lldp-information {
     description "Show Link Layer Discovery Protocol information";
   }
   rpc get-lldp-information-detail {
     description "Show detailed LLDP information";
   }
   rpc get-lldp-neighbors-information {
     description "Show LLDP neighbor information";
     output {
       container lldp-neighbors-information {
         uses lldp-neighbors-information-block;
       }
     }
   }
   rpc get-lldp-interface-neighbors {
     description "Show LLDP neighbors on this interface";
     input {
       leaf interface-device {
         description "Name of interface";
         type interface-device;
       }
     }
     output {
       container lldp-neighbors-information {
         uses lldp-neighbors-information-block;
       }
     }
   }
   rpc get-lldp-statistics-information {
     description "Show LLDP statistics";
   }
   rpc get-lldp-interface-statistics {
     description "Show LLDP statistics for this interface";
     input {
       leaf interface-device {
         description "Show LLDP statistics for this interface";
         type interface-device;
       }
     }
     output {
       container lldp-statistics {
         uses lldp-statistics-block;
       }
     }
   }
   rpc get-lldp-local-info {
     description "Show LLDP information of local device";
     output {
       container lldp-local-info {
         uses lldp-local-info-block;
       }
     }
   }
   rpc get-lldp-remote-global-statistics {
     description "Show LLDP remote global statistics information";
     output {
       container lldp-remote-global-statistics {
         uses lldp-remote-global-statistics-block;
       }
     }
   }
 grouping lldp-neighbors-information-block {
   container detail {
     list lldp-neighbor-information {
       leaf lldp-index {
         type uint32;
         description "LLDP index";
       }
       leaf lldp-ttl {
         type uint32;
         description "How long until the neighbor record expired";
       }
       leaf lldp-timemark {
         type string;
         description "When neighbor information was received";
       }
       leaf lldp-age {
         type string;
         description "Age of record";
       }
       leaf lldp-local-interface {
         type string;
         description "Interface on which neighbor information was received";
       }
       leaf lldp-local-parent-interface-name {
         type string;
         description "Parent interface of local interface on which neighbor informationwas received";
       }
       leaf lldp-local-port-id {
         type string;
         description "Port on which neighbor information was received";
       }
       leaf lldp-local-port-ageout-count {
         type uint32;
         description "Number of age-outs that occured on a given port";
       }
       leaf lldp-remote-chassis-id-subtype {
         type string;
         description "LLDP remote chassis ID subtype";
       }
       leaf lldp-remote-chassis-id {
         type string;
         description "LLDP remote chassis ID";
       }
       leaf lldp-remote-port-id-subtype {
         type string;
         description "LLDP remote port ID subtype";
       }
       leaf lldp-remote-port-id {
         type string;
         description "LLDP remote port ID";
       }
       leaf lldp-remote-port-description {
         type string;
         description "LLDP remote port ID";
       }
       leaf lldp-remote-system-name {
         type string;
         description "Administratively assigned host name of remote neighbor";
       }
       leaf lldp-remote-system-capabilities-supported {
         type string;
       }
       leaf lldp-remote-system-capabilities-enabled {
         type string;
       }
       leaf lldp-remote-management-address-type {
         type uint32;
         description "Management address for use by SNMP manager query";
       }
       leaf lldp-remote-management-address {
         type string;
         description "Management address for use by SNMP manager query";
       }
       leaf lldp-remote-management-address-port-id {
         type uint32;
         description "Port ID of Management address for use by SNMP manager query";
       }
       leaf lldp-remote-management-address-interface-subtype {
         type uint32;
         description "Enumeration value that identifies the interface numbering method used for defining the interface number associated with the remote system";
       }
       leaf lldp-remote-management-addr-oid {
         type string;
         description "LLDP OID value advertised by the remote system";
       }
       leaf lldp-remote-oui-802-3 {
         type string;
         description "Organizationally Unique Identifier globally unique assigned  number of IEEE 802.3 information received from the remote system";
       }
       leaf lldp-remote-oui-802-1 {
         type string;
         description "Organizationally Unique Identifier globally unique assigned  number of IEEE 802.1 information received from the remote system";
       }
       leaf lldp-remote-org-def-info-oui {
         type string;
         description "Organizationally Unique Identifier globally unique assignednumber of the information received from the remote system";
       }
       leaf lldp-remote-oui-juniper {
         type uint32;
         description "Juniper specific information received from the remote system";
       }
       leaf lldp-remote-oui-tia {
         type string;
         description "Organizationally Unique Identifier globally unique assigned  number of TIA TR-41 committee information received from the remote system";
       }
       leaf lldp-remote-subtype {
         type uint32;
         description "Subtype of the organizationally defined information received from the remote system";
       }
       leaf lldp-remote-subtype-vlan {
         type uint32;
         description "Subtype of the IEEE 802.1 VLAN name organizationally definedinformation received from the remote system";
       }
       leaf lldp-remote-subtype-port-vid {
         type uint32;
         description "Subtype of the IEEE 802.1 VLAN id organizationally definedinformation received from the remote system";
       }
       leaf lldp-remote-subtype-port-protocol-vid {
         type uint32;
         description "Subtype of the IEEE 802.1 VLAN id organizationally definedinformation received from the remote system";
       }
       leaf lldp-remote-subtype-protocol-id {
         type uint32;
         description "Subtype of the IEEE 802.1 VLAN id organizationally definedinformation received from the remote system";
       }
       leaf lldp-remote-subtype-mac {
         type uint32;
         description "Subtype of the IEEE 802.3 MAC/PHY configuration/statusorganizationally defined information received from the remote system";
       }
       leaf lldp-remote-subtype-lag {
         type uint32;
         description "Subtype of the IEEE 802.3 Link Aggregation organizationallydefined information received from the remote system";
       }
       leaf lldp-remote-subtype-mdi-power {
         type uint32;
         description "Subtype of the IEEE 802.3 MDI Power organizationallydefined information received from the remote system";
       }
       leaf lldp-remote-subtype-serial {
         type uint32;
         description "Subtype of the Juniper specific information received from the remote system";
       }
       leaf lldp-remote-subtype-vcp {
         type uint32;
         description "Subtype of the Juniper specific information received from the remote system";
       }
       leaf lldp-remote-subtype-mtu {
         type uint32;
         description "Subtype of the IEEE 802.3 Maximum Frame Size organizationallydefined information received from the remote system";
       }
       leaf lldp-remote-index {
         type uint32;
         description "Value used by agent to identify a particular unrecognized organizationally defined information";
       }
       leaf lldp-remote-value {
         type string;
         description "Value used to identify the organizationally defined information of the remote system";
       }
       leaf lldp-remote-subtype-vlan-id {
         type uint32;
         description "IEEE 802.1 VLAN name subtype VLAN ID value of theorganizationally defined information received from the remote system";
       }
       leaf lldp-remote-subtype-vlan-name {
         type string;
         description "IEEE 802.1 VLAN name subtype VLAN name value of theorganizationally defined information received from the remote system";
       }
       leaf lldp-remote-subtype-mac-autonegotiation {
         type string;
         description "IEEE 802.3 MAC/PHY configuration/status subtype autonegotiationsupport/status value of organizationally defined information receivedfrom the remote system";
       }
       leaf lldp-remote-subtype-mac-pmd {
         type uint32;
         description "IEEE 802.3 MAC/PHY configuration/status subtype PMDautonegotiation advertised capability value of organizationally definedinformation received from the remote system";
       }
       leaf lldp-remote-subtype-mac-mau {
         type uint32;
         description "IEEE 802.3 MAC/PHY configuration/status subtype operational MAUtype value of organizationally defined information received from theremote system";
       }
       leaf lldp-remote-subtype-power-support {
         type string;
         description "Subtype of the IEEE 802.3 MDI Power support organizationallydefined information received from the remote system";
       }
       leaf lldp-remote-subtype-power-pair {
         type string;
         description "Subtype of the IEEE 802.3 MDI Power pair organizationallyeefined information received from the remote system";
       }
       leaf lldp-remote-subtype-power-class {
         type string;
         description "Subtype of the IEEE 802.3 MDI Power class organizationallydefined information received from the remote system";
       }
       leaf lldp-remote-subtype-slot-serial {
         type string;
         description "Juniper specific ifl slot serial information receivedfrom the remote system";
       }
       leaf lldp-remote-subtype-vcp-info {
         type string;
         description "Juniper specific ifl vcp information receivedfrom the remote system";
       }
       leaf lldp-remote-subtype-juniper-mode-change {
         type string;
         description "Juniper specific ifl slot serial information receivedfrom the remote system";
       }
       leaf lldp-remote-subtype-juniper-mode-change-error {
         type string;
         description "Juniper specific ifl slot serial information receivedfrom the remote system";
       }
       leaf lldp-remote-subtype-juniper-mode-change-ip-address {
         type string;
         description "Juniper specific ifl slot serial information receivedfrom the remote system";
       }
       leaf lldp-remote-subtype-juniper-mode-change-image-name {
         type string;
         description "Juniper specific ifl slot serial information receivedfrom the remote system";
       }
       leaf lldp-remote-subtype-juniper-mode-change-ftp-login {
         type string;
         description "Juniper specific ifl slot serial information receivedfrom the remote system";
       }
       leaf lldp-remote-subtype-juniper-mode-change-image-md5 {
         type string;
         description "Juniper specific ifl slot serial information receivedfrom the remote system";
       }
       leaf lldp-remote-subtype-lag-status {
         type uint32;
         description "IEEE 802.3 Link Aggregation subtype status value oforganizationally defined information received from the remote system";
       }
       leaf lldp-remote-subtype-lag-portid {
         type uint32;
         description "IEEE 802.3 Link Aggregation subtype aggregated port ID value oforganizationally defined information received from the remote system";
       }
       leaf lldp-remote-subtype-mtu-size {
         type uint32;
         description "IEEE 802.3 Maximum Frame Size subtype frame size value oforganizationally defined information received from the remote system";
       }
       leaf lldp-remote-unknown-tlv-type {
         type uint32;
         description "Type extracted from the TLV";
       }
       leaf lldp-remote-unknown-tlv-info {
         type string;
         description "Value extracted from the value field of TLV";
       }
       leaf lldp-med-remote-system-class {
         type string;
         description "LLDP remote MED system class";
       }
       leaf lldp-med-remote-application-attributes {
         type string;
         description "Application which MED runs and its configuration parameters";
       }
       leaf lldp-remote-subtype-med-capabilities {
         type string;
         description "Organizationally Unique Identifier globally unique assigned  number of TIA TR-41 committee information received from the remote system";
       }
       leaf lldp-remote-subtype-med-cap-status {
         type string;
         description "Organizationally Unique Identifier globally unique assigned  number of TIA TR-41 committee information received from the remote system";
       }
       leaf lldp-remote-subtype-med-class-type {
         type string;
         description "Organizationally Unique Identifier globally unique assigned  number of TIA TR-41 committee information received from the remote system";
       }
       leaf lldp-remote-subtype-policy-type {
         type string;
         description "Organizationally Unique Identifier globally unique assigned  number of TIA TR-41 committee information received from the remote system";
       }
       leaf lldp-remote-subtype-nw-app-type {
         type string;
         description "Organizationally Unique Identifier globally unique assigned  number of TIA TR-41 committee information received from the remote system";
       }
       leaf lldp-remote-subtype-nw-policy-info {
         type string;
         description "Organizationally Unique Identifier globally unique assigned  number of TIA TR-41 committee information received from the remote system";
       }
       leaf lldp-remote-subtype-loc-id-type {
         type string;
         description "Organizationally Unique Identifier globally unique assigned  number of TIA TR-41 committee information received from the remote system";
       }
       leaf lldp-remote-subtype-loc-data-format {
         type string;
         description "Organizationally Unique Identifier globally unique assigned  number of TIA TR-41 committee information received from the remote system";
       }
       leaf lldp-remote-subtype-loc-lci-len {
         type string;
         description "Organizationally Unique Identifier globally unique assigned  number of TIA TR-41 committee information received from the remote system";
       }
       leaf lldp-remote-subtype-ext-power-vi-mdi {
         type string;
         description "Organizationally Unique Identifier globally unique assigned  number of TIA TR-41 committee information received from the remote system";
       }
       leaf lldp-remote-subtype-med-power-type {
         type string;
         description "Organizationally Unique Identifier globally unique assigned  number of TIA TR-41 committee information received from the remote system";
       }
       leaf lldp-remote-subtype-med-power-source {
         type string;
         description "Organizationally Unique Identifier globally unique assigned  number of TIA TR-41 committee information received from the remote system";
       }
       leaf lldp-remote-subtype-med-power-priority {
         type string;
         description "Organizationally Unique Identifier globally unique assigned  number of TIA TR-41 committee information received from the remote system";
       }
       leaf lldp-remote-subtype-med-power-value {
         type string;
         description "Organizationally Unique Identifier globally unique assigned  number of TIA TR-41 committee information received from the remote system";
       }
       leaf lldp-remote-subtype-port-protocol-vid-status {
         type string;
         description "IEEE 802.1 VLAN name subtype VLAN name value of theorganizationally defined information received from the remote system";
       }
       leaf lldp-remote-subtype-port-protocol-vid-id {
         type string;
         description "IEEE 802.1 VLAN name subtype VLAN name value of theorganizationally defined information received from the remote system";
       }
       leaf lldp-remote-subtype-protocol-id-length {
         type string;
         description "IEEE 802.1 VLAN name subtype VLAN name value of theorganizationally defined information received from the remote system";
       }
       leaf lldp-remote-inventory-hardware-revision {
         type string;
       }
       leaf lldp-remote-inventory-firmware-revision {
         type string;
       }
       leaf lldp-remote-inventory-software-revision {
         type string;
       }
       leaf lldp-remote-inventory-serial-number {
         type string;
       }
       leaf lldp-remote-inventory-manufacturer-name {
         type string;
       }
       leaf lldp-remote-inventory-model-name {
         type string;
       }
       leaf lldp-remote-inventory-asset-id {
         type string;
       }
       list lldp-system-description {
       }
     }
   }
   container brief {
     list lldp-neighbor-information {
       leaf lldp-local-port-id {
         type string;
         description "Port on which neighbor information was received";
       }
       leaf lldp-local-parent-interface-name {
         type string;
         description "Parent interface of local interface on which neighbor informationwas received";
       }
       leaf lldp-remote-chassis-id {
         type string;
         description "LLDP remote chassis ID";
       }
       leaf lldp-remote-port-id {
         type string;
         description "LLDP remote port ID";
       }
       leaf lldp-remote-port-description {
         type string;
         description "LLDP remote port ID";
       }
       leaf lldp-remote-system-name {
         type string;
         description "Administratively assigned host name of remote neighbor";
       }
     }
   }
 }
 grouping lldp-statistics-block {
   list lldp-interface-statistics {
     description "Interface statistics";
     leaf lldp-statistics-interface-name {
       type string;
     }
     leaf lldp-parent-intf-name {
       type string;
       description "Parent interface for which statistics are shown";
     }
     leaf lldp-receive-packet-count {
       type uint32;
     }
     leaf lldp-receive-packet-unknown-tlvs {
       type uint32;
       description "Number of received LLDP packets with unknown TLVs";
     }
     leaf lldp-receive-packet-error-count {
       type uint32;
     }
     leaf lldp-receive-tlv-discard-count {
       type uint32;
     }
     leaf lldp-transmit-packet-count {
       type uint32;
     }
     leaf lldp-transmit-packet-error-count {
       type uint32;
     }
   }
 }
 grouping lldp-local-info-block {
   leaf lldp-local-chassis-id {
     type string;
   }
   leaf lldp-local-system-name {
     type string;
   }
   leaf lldp-local-system-description {
     type string;
   }
   leaf lldp-local-system-capabilities-supported {
     type string;
     description "LLDP local system capabilities supported";
   }
   leaf lldp-local-system-capabilities-enabled {
     type string;
     description "LLDP local system capabilities enabled";
   }
   leaf lldp-local-management-address-interface-name {
     type string;
     description "LLDP local management interaface name";
   }
   leaf lldp-local-management-address-subtype {
     type uint32;
     description "LLDP local management interface address subtype ";
   }
   leaf lldp-local-management-address-address {
     type string;
     description "LLDP local management interface address ";
   }
   leaf lldp-local-management-address-interface-number-subtype {
     type uint32;
     description "LLDP local management interface number subtype";
   }
   leaf lldp-local-management-address-interface-number {
     type uint32;
     description "LLDP local management address interface number";
   }
   leaf lldp-local-redundancy-group-name {
     type string;
   }
   leaf lldp-local-redundancy-group-address {
     type string;
   }
   list lldp-local-interface-info {
     leaf lldp-local-interface-name {
       type string;
     }
     leaf lldp-parent-local-interface-name {
       type string;
       description "Parent interface name of local interface";
     }
     leaf lldp-local-interface-id {
       type uint32;
     }
     leaf lldp-local-interface-description {
       type string;
     }
     leaf lldp-local-interface-status {
       type string;
       description "Interface status";
     }
   }
 }
 grouping lldp-remote-global-statistics-block {
   container brief {
     leaf lldp-last-change-time {
       type uint32;
       description "LLDP last change time";
     }
     leaf lldp-inserts {
       type uint32;
       description "LLDP inserts";
     }
     leaf lldp-deletes {
       type uint32;
       description "LLDP deletes";
     }
     leaf lldp-drops {
       type uint32;
       description "LLDP drops";
     }
     leaf lldp-ageouts {
       type uint32;
       description "LLDP ageouts";
     }
   }
 }
 }
