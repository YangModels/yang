/*
 * Copyright (c) 2017 Juniper Networks, Inc.
 * All rights reserved.
 */
 module show-spring-traffic-engineering {
  namespace "http://yang.juniper.net/yang/1.1/jrpc/show-spring-traffic-engineering/junos-ex/17.2R1.13";
  prefix show-spring-traffic-engineering;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-spring-te-overview-information {
     description "Show overview of ingress SPRING Traffic Engineering";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container spring-te-overview-information {
         uses spring-te-overview-information-block;
       }
     }
   }
   rpc get-spring-te-lsp-information {
     description "Show SPRING Traffic Engineered ingress LSPs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf regex {
         description "Regular expression for LSP names to match";
         type string;
       }
     }
     output {
       container spring-te-lsp-information {
         uses spring-te-lsp-information-block;
       }
     }
   }
 grouping spring-te-overview-information-block {
   container spring-te-overview {
     description "Overview of SPRING Traffic-Engineering";
     leaf ste-preference {
       type uint32;
     }
     leaf ste-num-lsps {
       type uint32;
     }
     leaf ste-num-lsps-up {
       type uint32;
     }
     leaf ste-num-lsps-down {
       type uint32;
     }
     container ste-ext-ctrlrs {
       leaf ste-ext-ctrlr {
         type string;
       }
     }
   }
 }
 grouping spring-te-lsp-information-block {
   container spring-te-lsp {
     description "SPRING Traffic-Engineered LSP";
     container brief {
       description "SPRING Traffic-Engineered LSP";
       leaf stl-dest-address {
         type ipaddr;
       }
       leaf stl-lsp-state {
         type string;
       }
       leaf stl-lsp-name {
         type string;
       }
       container stl-sr-ero-list {
         leaf stl-sr-ero-num-eros {
           type uint32;
         }
         list stl-sr-ero {
           leaf stl-sr-ero-index {
             type uint32;
           }
           leaf stl-sr-ero-hop-type {
             type string;
           }
           leaf stl-sr-ero-nai-type {
             type string;
           }
           leaf stl-sr-ero-ip-node-id {
             type ipaddr;
           }
           leaf stl-sr-ero-local-intf-id {
             type ipaddr;
           }
           leaf stl-sr-ero-remote-intf-id {
             type ipaddr;
           }
           leaf stl-sr-ero-unnum-local-router-id {
             type ipaddr;
           }
           leaf stl-sr-ero-unnum-local-id {
             type uint32;
           }
           leaf stl-sr-ero-unnum-remote-router-id {
             type ipaddr;
           }
           leaf stl-sr-ero-unnum-remote-id {
             type uint32;
           }
           leaf stl-sr-ero-sid-type {
             type string;
           }
           leaf stl-sr-ero-sid-value {
             type uint32;
           }
           leaf stl-sr-ero-sid-ttl {
             type uint32;
           }
           leaf stl-sr-ero-sid-exp {
             type uint32;
           }
         }
       }
     }
     container detail {
       description "SPRING Traffic-Engineered LSP";
       leaf stl-lsp-name {
         type string;
       }
       leaf stl-dest-address {
         type ipaddr;
       }
       leaf stl-lsp-state {
         type string;
       }
       leaf stl-out-if {
         type string;
       }
       container stl-sr-ero-list {
         leaf stl-sr-ero-num-eros {
           type uint32;
         }
         list stl-sr-ero {
           leaf stl-sr-ero-index {
             type uint32;
           }
           leaf stl-sr-ero-hop-type {
             type string;
           }
           leaf stl-sr-ero-nai-type {
             type string;
           }
           leaf stl-sr-ero-ip-node-id {
             type ipaddr;
           }
           leaf stl-sr-ero-local-intf-id {
             type ipaddr;
           }
           leaf stl-sr-ero-remote-intf-id {
             type ipaddr;
           }
           leaf stl-sr-ero-unnum-local-router-id {
             type ipaddr;
           }
           leaf stl-sr-ero-unnum-local-id {
             type uint32;
           }
           leaf stl-sr-ero-unnum-remote-router-id {
             type ipaddr;
           }
           leaf stl-sr-ero-unnum-remote-id {
             type uint32;
           }
           leaf stl-sr-ero-sid-type {
             type string;
           }
           leaf stl-sr-ero-sid-value {
             type uint32;
           }
           leaf stl-sr-ero-sid-ttl {
             type uint32;
           }
           leaf stl-sr-ero-sid-exp {
             type uint32;
           }
         }
       }
     }
   }
   container spring-te-lsp-counts {
     leaf stl-total {
       type uint32;
     }
     leaf stl-up {
       type uint32;
     }
     leaf stl-down {
       type uint32;
     }
   }
 }
 }
