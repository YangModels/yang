/*
 * Copyright (c) 2017 Juniper Networks, Inc.
 * All rights reserved.
 */
 module show-version {
  namespace "http://yang.juniper.net/yang/1.1/jrpc/show-version/junos-ex/17.2R1.13";
  prefix show-version;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-software-information {
     description "Show software process revision levels";
     input {
       leaf level {
         type enumeration {
           enum "brief" {
             description "Display brief output";
           }
           enum "detail" {
             description "Display detailed output";
           }
         }
       }
     }
     output {
       container software-information {
         uses software-information-block;
       }
     }
   }
   rpc get-fpc-version {
     description "Show software version on FPC";
     input {
       leaf fpc-slot {
         description "FPC slot number";
         type uint32 {
           range "0 .. 63";
         }
       }
     }
     output {
       container fpc-version {
         uses fpc-version-block;
       }
     }
   }
   rpc get-software-rollback-information {
     description "Show version of previous set of packages";
     output {
       container rollback-information {
         uses rollback-information-block;
       }
     }
   }
 grouping software-information-block {
   leaf host-name {
     type string;
     description "Hostname of router";
   }
   leaf product-model {
     type string;
     description "Hardware model name";
   }
   leaf junos-version {
     type string;
     description "Junos Version";
   }
   leaf junos-edition {
     type string;
     description "Junos Edition";
   }
   list package-information {
     leaf comment {
       type string;
     }
   }
   list version-information {
     leaf component {
       type string;
     }
     leaf release {
       type string;
       description "Release name";
     }
     leaf builder {
       type string;
     }
     leaf build-date {
       type string;
       description "Build date";
     }
     leaf build-machine {
       type string;
     }
     leaf build-directory {
       type string;
     }
   }
   container haiku {
     leaf content {
       type string;
     }
   }
 }
 grouping fpc-version-block {
   leaf fpc-slot {
     type int32;
   }
 }
 grouping rollback-information-block {
   container load-configuration-results {
     leaf load-success {
       type empty;
       description "Load completed with no errors";
     }
     leaf load-error-count {
       type int32;
       description "Number of errors during load";
     }
     leaf diff-error-count {
       type int32;
       description "Number of errors";
     }
   }
   container configuration-information {
     leaf configuration-output {
       type string;
     }
     leaf json-output {
       type string;
     }
     container file-destination {
       leaf source-filename {
         type string;
       }
       leaf alias-filename {
         type string;
       }
       leaf export-data-type {
         type string;
         description "Type of data being exported";
       }
     }
     container configuration-detail {
       leaf indent {
         type int32;
       }
       container configuration-detail-line {
         leaf detail-name {
           type string;
         }
         leaf detail-value {
           type string;
         }
         leaf detail-message {
           type string;
         }
       }
     }
   }
 }
 }
