/*
 * Copyright (c) 2017 Juniper Networks, Inc.
 * All rights reserved.
 */
 module show-pim {
  namespace "http://yang.juniper.net/yang/1.1/jrpc/show-pim/junos-ex/17.2R1.13";
  prefix show-pim;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-pim-bootstrap-information {
     description "Show PIM bootstrap routers";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
     }
     output {
       container pim-bootstrap-information {
         uses pim-bootstrap-information-block;
       }
     }
   }
   rpc get-pim-bidir-df-election-information {
     description "Show PIM bidirectional DF election information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "detail";
         type enumeration {
           enum "brief" {
             description "Display brief output (default)";
           }
           enum "detail" {
             description "Display detailed output";
           }
         }
       }
       leaf family {
         description "Address family";
         default "inet";
         type enumeration {
           enum "inet" {
             description "Display IPv4 DF election information";
           }
           enum "inet6" {
             description "Display IPv6 DF election information";
           }
         }
       }
       leaf rpa {
         description "Rendezvous Point Address";
         type ipaddr;
       }
     }
     output {
       container pim-bidir-df-election-information {
         uses pim-bidir-df-election-information-block;
       }
     }
   }
   rpc get-pim-bidir-df-election-interface-information {
     description "Show PIM bidirectional DF election interface information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf interface-name {
         description "Name of interface";
         type string;
       }
       leaf family {
         description "Address family";
         default "inet";
         type enumeration {
           enum "inet" {
             description "Display IPv4 DF election interface information";
           }
           enum "inet6" {
             description "Display IPv6 DF election interface information";
           }
         }
       }
     }
     output {
       container pim-bidir-df-election-interface-information {
         uses pim-bidir-df-election-interface-information-block;
       }
     }
   }
   rpc get-pim-interfaces-information {
     description "Show PIM interfaces";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface-name {
         description "Name of interface";
         type string;
       }
       leaf instance {
         description "Name of instance";
         type string;
       }
       leaf family {
         description "Address family";
         default "inet";
         type enumeration {
           enum "inet" {
             description "Display IPv4 interfaces";
           }
           enum "inet6" {
             description "Display IPv6 interfaces";
           }
         }
       }
     }
     output {
       container pim-interfaces-information {
         uses pim-interfaces-information-block;
       }
     }
   }
   rpc get-pim-join-information {
     description "Show PIM join/prune state";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "summary" {
             description "Display summary output";
           }
           enum "brief" {
             description "Display brief output (default)";
           }
           enum "detail" {
             description "Display detailed output";
           }
           enum "extensive" {
             description "Display extensive output";
           }
         }
       }
       leaf group {
         description "IP address and optional prefix length of group";
         type ipprefix;
       }
       leaf exact {
         description "Show only group that matches exactly";
         type empty;
       }
       leaf source {
         description "IP address and optional prefix length of source";
         type ipprefix;
       }
       leaf rp {
         description "IP address and optional prefix length of rendezvous point";
         type ipprefix;
       }
       leaf sparse {
         description "Show only PIM sparse-mode entries (including SSM)";
         type empty;
       }
       leaf dense {
         description "Show only PIM dense-mode entries";
         type empty;
       }
       leaf bidirectional {
         description "Show only bidirectional PIM entries";
         type empty;
       }
       leaf star-g {
         description "Show only *,G entries";
         type empty;
       }
       leaf sg {
         description "Show only S,G entries";
         type empty;
       }
       leaf resolve-mvpn-neighbor {
         description "Display BGP-MVPN neighbor";
         type empty;
       }
       leaf downstream-count {
         description "Display downstream count instead of list";
         type empty;
       }
       leaf family {
         description "Address family";
         default "inet";
         type enumeration {
           enum "inet" {
             description "Display IPv4 join/prune state";
           }
           enum "inet6" {
             description "Display IPv6 join/prune state";
           }
         }
       }
     }
     output {
       container pim-join-information {
         uses pim-join-information-block;
       }
     }
   }
   rpc get-pim-mvpn-information {
     description "Show PIM MVPN instances";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container pim-mvpn-information {
         uses pim-mvpn-information-block;
       }
     }
   }
   rpc get-pim-neighbors-information {
     description "Show PIM neighbors";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "brief" {
             description "Display brief output (default)";
           }
           enum "detail" {
             description "Display detailed output";
           }
         }
       }
       leaf family {
         description "Address family";
         default "inet";
         type enumeration {
           enum "inet" {
             description "Display IPv4 neighbors";
           }
           enum "inet6" {
             description "Display IPv6 neighbors";
           }
         }
       }
     }
     output {
       container pim-neighbors-information {
         uses pim-neighbors-information-block;
       }
     }
   }
   rpc get-pim-rps-information {
     description "Show PIM rendezvous points";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "brief" {
             description "Display brief output (default)";
           }
           enum "detail" {
             description "Display detailed output";
           }
           enum "extensive" {
             description "Display extensive output";
           }
         }
       }
       leaf group-address {
         description "IP address of group";
         type ipaddr;
       }
       leaf family {
         description "Address family";
         default "inet";
         type enumeration {
           enum "inet" {
             description "Display IPv4 rendezvous points";
           }
           enum "inet6" {
             description "Display IPv6 rendezvous points";
           }
         }
       }
     }
     output {
       container pim-rps-information {
         uses pim-rps-information-block;
       }
     }
   }
   rpc get-pim-source-information {
     description "Show the PIM source RPF state";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf verbosity_level {
         default "brief";
         type enumeration {
           enum "brief" {
             description "Display brief output (default)";
           }
           enum "detail" {
             description "Display detailed output";
           }
         }
       }
       leaf resolve-mvpn-neighbor {
         description "Display BGP-MVPN neighbor";
         type empty;
       }
       leaf source {
         description "IP address and optional prefix length of source RPFs";
         type ipprefix;
       }
       leaf family {
         description "Address family";
         default "inet";
         type enumeration {
           enum "inet" {
             description "Display IPv4 PIM source RPF state";
           }
           enum "inet6" {
             description "Display IPv6 PIM source RPF state";
           }
         }
       }
     }
     output {
       container pim-source-information {
         uses pim-source-information-block;
       }
     }
   }
   rpc get-pim-statistics-information {
     description "Show PIM statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of instance";
         type string;
       }
       leaf interface {
         description "Name of interface";
         type string;
       }
       leaf family {
         description "Address family";
         default "inet";
         type enumeration {
           enum "inet" {
             description "Display IPv4 PIM statistics";
           }
           enum "inet6" {
             description "Display IPv6 PIM statistics";
           }
         }
       }
     }
     output {
       container pim-statistics-information {
         uses pim-statistics-information-block;
       }
     }
   }
   rpc get-pim-mdt-information {
     description "Show state of PIM multicast data tunnels";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf direction {
         type enumeration {
           enum "outgoing" {
             description "Display outgoing multicast data tunnels";
           }
           enum "incoming" {
             description "Display incoming multicast data tunnels";
           }
         }
       }
       leaf level {
         default "brief";
         type enumeration {
           enum "brief" {
             description "Display brief output (default)";
           }
           enum "detail" {
             description "Display detailed output";
           }
           enum "extensive" {
             description "Display extensive output";
           }
         }
       }
       leaf range {
         description "IP address and optional prefix length of group";
         type ipprefix;
       }
       leaf instance {
         description "Name of PIM instance";
         type string;
         mandatory true;
       }
     }
     output {
       container pim-mdt-information {
         uses pim-mdt-information-block;
       }
     }
   }
   rpc get-pim-data-mdt-limit {
     description "Show received PIM data MDT limit";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of PIM instance";
         type string;
         mandatory true;
       }
     }
     output {
       container pim-data-mdt-limit {
         uses pim-data-mdt-limit-block;
       }
     }
   }
   rpc get-pim-data-mdt-join-information {
     description "Show received PIM data-mdt-joins";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of PIM instance";
         type string;
         mandatory true;
       }
     }
     output {
       container pim-data-mdt-join-information {
         uses pim-data-mdt-join-information-block;
       }
     }
   }
   rpc get-pim-snooping-interfaces-information {
     description "Show PIM snooping interfaces";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf interface {
         description "Name of interface";
         type string;
       }
       leaf vlan-id {
         description "VLAN ID for a learning domain";
         type uint32 {
           range "0 .. 4094";
         }
       }
       leaf instance {
         description "Name of routing-instance";
         type string;
       }
     }
     output {
       container pim-interfaces-information {
         uses pim-interfaces-information-block;
       }
     }
   }
   rpc get-pim-snooping-join-information {
     description "Show PIM snooping join";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf group {
         description "IP address range for group";
         type ipv4prefix;
       }
       leaf vlan-id {
         description "VLAN ID for a learning domain";
         type uint32 {
           range "0 .. 4094";
         }
       }
       leaf instance {
         description "Name of routing-instance";
         type string;
       }
     }
     output {
       container pim-join-information {
         uses pim-join-information-block;
       }
     }
   }
   rpc get-pim-snooping-neighbors-information {
     description "Show PIM snooping neighbors";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf interface {
         description "Name of interface";
         type string;
       }
       leaf vlan-id {
         description "VLAN ID for a learning domain";
         type uint32 {
           range "0 .. 4094";
         }
       }
       leaf instance {
         description "Name of routing-instance";
         type string;
       }
     }
     output {
       container pim-neighbors-information {
         uses pim-neighbors-information-block;
       }
     }
   }
   rpc get-pim-snooping-statistics-information {
     description "Show PIM snooping statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf interface {
         description "Name of interface";
         type string;
       }
       leaf vlan-id {
         description "VLAN ID for a learning domain";
         type uint32 {
           range "0 .. 4094";
         }
       }
       leaf instance {
         description "Name of routing-instance";
         type string;
       }
     }
     output {
       container pim-statistics-information {
         uses pim-statistics-information-block;
       }
     }
   }
 grouping pim-bootstrap-information-block {
   leaf pim-instance {
     type string;
     description "Name of the PIM instance";
   }
   list bootstrap-family {
     leaf address {
       type ipaddr;
     }
     leaf bootstrap-priority {
       type int32;
       description "Priority of bootstrap router";
     }
     leaf local-address {
       type ipaddr;
     }
     leaf local-priority {
       type int32;
       description "Local priority";
     }
     leaf bootstrap-state {
       type string;
     }
     leaf bootstrap-timeout {
       type int32;
       description "Bootstrap router timeout";
     }
   }
 }
 grouping pim-bidir-df-election-information-block {
   list bidir-df-election-family {
     leaf pim-instance {
       type string;
       description "Name of the PIM instance";
     }
     leaf address-family {
       type string;
     }
     container bidir-df-election-rpa-list {
       list bidir-df-election-rp {
         leaf rpa {
           type ipaddr;
         }
         container bidir-df-election-group-ranges {
           leaf group-range {
             type ipprefix;
           }
         }
         container bidir-df-election-interface-list {
           list bidir-df-election-interface {
             leaf pim-interface-name {
               type string;
               description "Name of PIM interface";
             }
             leaf df-state {
               type string;
               description "PIM-BIDIR DF election state";
             }
             leaf df {
               type ipaddr;
             }
           }
         }
       }
     }
   }
 }
 grouping pim-bidir-df-election-interface-information-block {
   list bidir-df-election-interface-family {
     leaf pim-instance {
       type string;
       description "Name of the PIM instance";
     }
     leaf address-family {
       type string;
     }
     list bidir-df-election-interface-interface-list {
       leaf pim-interface-name {
         type string;
         description "Name of PIM interface";
       }
       leaf robustness-count {
         type int32;
       }
       leaf offer-period {
         type int32;
       }
       leaf backoff-period {
         type int32;
       }
       list bidir-df-election-interface-rpa-list {
         leaf rpa {
           type ipaddr;
         }
         leaf df-state {
           type string;
           description "PIM-BIDIR DF election state";
         }
         leaf df {
           type ipaddr;
         }
       }
     }
   }
 }
 grouping pim-interfaces-information-block {
   leaf pim-instance {
     type string;
     description "Name of the PIM instance";
   }
   list terse {
     list pim-interface {
       leaf pim-interface-name {
         type string;
         description "Name of PIM interface";
       }
       leaf status {
         type string;
         description "Status of PIM interface";
       }
       leaf ip-protocol-version {
         type int32;
         description "IP protocol version of PIM interface";
       }
       leaf protocol-version {
         type int32;
         description "PIM protocol version of PIM interface";
       }
       leaf neighbor-count {
         type int32;
         description "Number of neighbors on PIM interface";
       }
       leaf interface-join-sg-count {
         type int32;
         description "Number of (s,g) joins sent on the interface";
       }
       leaf interface-join-tsg-count {
         type int32;
         description "Number of (*,g) joins sent on the interface";
       }
       leaf designated-router-address {
         type ipaddr;
         description "Designated router address of PIM interface";
       }
       container pim-interface-mode-abbreviation {
         description "Mode of PIM interface";
         leaf pim-interface-mode-s {
           type empty;
         }
         leaf pim-interface-mode-d {
           type empty;
         }
         leaf pim-interface-mode-b {
           type empty;
         }
       }
       container interface-state {
         description "State of PIM interface";
         leaf interface-state-dr {
           type empty;
         }
         leaf interface-state-not-dr {
           type empty;
         }
         leaf interface-state-ddr-dr {
           type empty;
         }
         leaf interface-state-ddr-bdr {
           type empty;
         }
         leaf interface-state-distributed-dr {
           type empty;
         }
         leaf interface-state-p2p {
           type empty;
         }
         leaf interface-state-p2mp {
           type empty;
         }
         leaf interface-state-bidir-active {
           type empty;
         }
         leaf interface-state-bidir-not-capable {
           type empty;
         }
       }
       list pim-neighbor {
         leaf pim-interface-name {
           type string;
           description "Name of PIM interface";
         }
         leaf pim-pktcache-count {
           type int32;
           description "Number of packets cached from this unknown neighbor";
         }
         leaf pim-pktcache-time-remaining {
           type int32;
           description "Time remaining before this unknown neighbor times out";
         }
         leaf pim-neighbor-address {
           type ipaddr;
           description "PIM neighbor address";
         }
       }
     }
   }
   list rpf-loads {
     list pim-interface {
       leaf pim-interface-name {
         type string;
         description "Name of PIM interface";
       }
       leaf status {
         type string;
         description "Status of PIM interface";
       }
       leaf ip-protocol-version {
         type int32;
         description "IP protocol version of PIM interface";
       }
       leaf protocol-version {
         type int32;
         description "PIM protocol version of PIM interface";
       }
       leaf neighbor-count {
         type int32;
         description "Number of neighbors on PIM interface";
       }
       leaf interface-active-join-sg-count {
         type int32;
         description "Number of active path (s,g) joins sent on the interface";
       }
       leaf interface-mofrr-backup-join-sg-count {
         type int32;
         description "Number of mofrr backup path (s,g) joins sent on the interface";
       }
       leaf interface-standby-join-sg-count {
         type int32;
         description "Number of standby path (s,g) joins sent on the interface";
       }
       leaf interface-ephemeral-join-sg-count {
         type int32;
         description "Number of ephemeral (s,g) joins on the interface";
       }
       leaf interface-static-join-sg-count {
         type int32;
         description "Number of static (s,g) joins on the interface";
       }
       leaf interface-active-join-tsg-count {
         type int32;
         description "Number of active path (*,g) joins sent on the interface";
       }
       leaf interface-standby-join-tsg-count {
         type int32;
         description "Number of standby path (*,g) joins sent on the interface";
       }
       leaf interface-ephemeral-join-tsg-count {
         type int32;
         description "Number of ephemeral (*,g) joins on the interface";
       }
       leaf interface-static-join-tsg-count {
         type int32;
         description "Number of static (*,g) joins on the interface";
       }
       leaf designated-router-address {
         type ipaddr;
         description "Designated router address of PIM interface";
       }
       container pim-interface-mode-abbreviation {
         description "Mode of PIM interface";
         leaf pim-interface-mode-s {
           type empty;
         }
         leaf pim-interface-mode-d {
           type empty;
         }
         leaf pim-interface-mode-b {
           type empty;
         }
       }
       container interface-state {
         description "State of PIM interface";
         leaf interface-state-dr {
           type empty;
         }
         leaf interface-state-not-dr {
           type empty;
         }
         leaf interface-state-ddr-dr {
           type empty;
         }
         leaf interface-state-ddr-bdr {
           type empty;
         }
         leaf interface-state-distributed-dr {
           type empty;
         }
         leaf interface-state-p2p {
           type empty;
         }
         leaf interface-state-bidir-active {
           type empty;
         }
         leaf interface-state-bidir-not-capable {
           type empty;
         }
       }
       list pim-neighbor {
         leaf pim-interface-name {
           type string;
           description "Name of PIM interface";
         }
         leaf pim-pktcache-count {
           type int32;
           description "Number of packets cached from this unknown neighbor";
         }
         leaf pim-pktcache-time-remaining {
           type int32;
           description "Time remaining before this unknown neighbor times out";
         }
         leaf pim-neighbor-address {
           type ipaddr;
           description "PIM neighbor address";
         }
       }
     }
   }
 }
 grouping pim-join-information-block {
   list join-family {
     list summary {
       leaf pim-instance {
         type string;
         description "Name of the PIM instance";
       }
       leaf address-family {
         type string;
       }
       list join-summaries {
         container join-summary {
           leaf multicast-route-type {
             type string;
           }
           leaf multicast-route-count {
             type int32;
           }
         }
       }
       list join-group {
         list dense {
           leaf multicast-group-address {
             type ipaddr;
             description "Group address";
           }
           leaf multicast-source-address {
             type ipaddr;
             description "Source address";
           }
           leaf upstream-interface-name {
             type string;
             description "Upstream interface";
           }
           leaf pim-interface-state {
             type string;
             description "State of PIM interface";
           }
           leaf upstream-neighbor {
             type ipaddr;
             description "IP Address of Upstream Neighbor";
           }
           leaf upstream-neighbor-rpf-origin {
             type string;
             description "Reverse-path forwarding origin of upstream neighbor";
           }
           leaf uptime {
             type string;
           }
           leaf downstream-interface-count {
             type int32;
           }
           leaf downstream-neighbor-count {
             type int32;
           }
           container pim-group-flags {
             leaf sparse {
               type empty;
             }
             leaf bidir {
               type empty;
               description "Bidirectional flag";
             }
             leaf delete {
               type empty;
             }
             leaf rptree {
               type empty;
             }
             leaf wildcard {
               type empty;
             }
             leaf spt {
               type empty;
             }
           }
           list dense-event {
             container dense-receive-prune {
               leaf pim-interface-name {
                 type string;
                 description "Name of PIM interface";
               }
               leaf dense-timeout {
                 type int32;
               }
             }
             container dense-send-prune {
               leaf pim-interface-name {
                 type string;
                 description "Name of PIM interface";
               }
               leaf dense-timeout {
                 type int32;
               }
             }
             container dense-join {
               leaf pim-interface-name {
                 type string;
                 description "Name of PIM interface";
               }
               leaf dense-timeout {
                 type int32;
               }
             }
             container dense-graft {
               leaf pim-interface-name {
                 type string;
                 description "Name of PIM interface";
               }
               leaf dense-timeout {
                 type int32;
               }
             }
           }
           container downstream-interfaces {
             leaf dummy {
               type empty;
             }
             list downstream-interface {
               description "Downstream/Outgoing interface list";
               leaf pim-interface-name {
                 type string;
                 description "Name of PIM interface";
               }
               leaf pruned-timeout {
                 type int32;
                 description "PIM-DM pruned timeout";
               }
               leaf pim-interface-state {
                 type string;
                 description "State of PIM interface";
               }
               list downstream-neighbor {
               }
             }
           }
           list downstream-interface {
             description "Downstream/Outgoing interface list";
             list downstream-neighbor {
             }
           }
         }
         list sparse {
           leaf multicast-group-address {
             type ipaddr;
             description "Group address";
           }
           leaf multicast-source-address {
             type ipaddr;
             description "Source address";
           }
           leaf rendezvous-point-address {
             type ipaddr;
             description "Address of rendezvous point";
           }
           leaf upstream-protocol-name {
             type string;
             description "Upstream protocol";
           }
           leaf upstream-interface-name {
             type string;
             description "Upstream interface";
           }
           leaf pim-interface-state {
             type string;
             description "State of PIM interface";
           }
           leaf upstream-neighbor {
             type ipaddr;
             description "IP Address of Upstream Neighbor";
           }
           leaf upstream-neighbor-rpf-origin {
             type string;
             description "Reverse-path forwarding origin of upstream neighbor";
           }
           leaf keepalive-timeout {
             type int32;
           }
           leaf no-keepalive-timeout {
             type empty;
           }
           leaf uptime {
             type string;
           }
           leaf downstream-interface-count {
             type int32;
           }
           leaf downstream-neighbor-count {
             type int32;
           }
           container pim-group-flags {
             leaf bidir {
               type empty;
               description "Bidirectional flag";
             }
             leaf dense {
               type empty;
             }
             leaf delete {
               type empty;
             }
             leaf rptree {
               type empty;
             }
             leaf wildcard {
               type empty;
             }
             leaf spt {
               type empty;
             }
           }
           container active-upstream-path {
             leaf upstream-protocol-name {
               type string;
               description "Upstream protocol";
             }
             leaf upstream-interface-name {
               type string;
               description "Upstream interface";
             }
             leaf pim-interface-state {
               type string;
               description "State of PIM interface";
             }
             leaf upstream-neighbor {
               type ipaddr;
               description "IP Address of Upstream Neighbor";
             }
             leaf upstream-neighbor-rpf-origin {
               type string;
               description "Reverse-path forwarding origin of upstream neighbor";
             }
           }
           container mofrr-backup-upstream-path {
             leaf upstream-protocol-name {
               type string;
               description "Upstream protocol";
             }
             leaf upstream-interface-name {
               type string;
               description "Upstream interface";
             }
             leaf pim-interface-state {
               type string;
               description "State of PIM interface";
             }
             leaf upstream-neighbor {
               type ipaddr;
               description "IP Address of Upstream Neighbor";
             }
             leaf upstream-neighbor-rpf-origin {
               type string;
               description "Reverse-path forwarding origin of upstream neighbor";
             }
           }
           container standby-upstream-path {
             leaf upstream-protocol-name {
               type string;
               description "Upstream protocol";
             }
             leaf upstream-interface-name {
               type string;
               description "Upstream interface";
             }
             leaf pim-interface-state {
               type string;
               description "State of PIM interface";
             }
             leaf upstream-neighbor {
               type ipaddr;
               description "IP Address of Upstream Neighbor";
             }
             leaf upstream-neighbor-rpf-origin {
               type string;
               description "Reverse-path forwarding origin of upstream neighbor";
             }
           }
           list dense-event {
           }
           container upstream-state-flags {
             leaf none {
               type empty;
             }
             leaf local-source {
               type empty;
             }
             leaf local-rp {
               type empty;
             }
             leaf join-to-rp {
               type empty;
             }
             leaf join-to-source {
               type empty;
             }
             leaf prune-to-rp {
               type empty;
             }
             leaf no-prune-to-rp {
               type empty;
             }
             leaf prune-to-source {
               type empty;
             }
           }
           container downstream-interfaces {
             leaf dummy {
               type empty;
             }
             list downstream-interface {
               description "Downstream/Outgoing interface list";
               leaf pim-interface-name {
                 type string;
                 description "Name of PIM interface";
               }
               leaf pim-interface-state {
                 type string;
                 description "State of PIM interface";
               }
               leaf register-rp {
                 type ipaddr;
               }
               leaf register-interface-name {
                 type string;
               }
               list downstream-neighbor {
                 leaf neighbor-address {
                   type ipaddr;
                   description "IP address of this neighbor";
                 }
                 leaf neighbor-state {
                   type string;
                 }
                 leaf terse-sparse {
                   type empty;
                 }
                 leaf terse-rpt {
                   type empty;
                 }
                 leaf terse-wc {
                   type empty;
                 }
                 leaf neighbor-timeout {
                   type int32;
                 }
                 leaf downstream-if-uptime {
                   type string;
                   description "Time since first join received on this interface";
                 }
                 container downstream-last-jp {
                   leaf downstream-last-jp-oper {
                     type string;
                   }
                   leaf downstream-last-jp-time {
                     type string;
                   }
                 }
               }
               container downstream-assert-neighbor {
                 description "Information about the neighbor that won the assert";
                 leaf neighbor-address {
                   type ipaddr;
                   description "IP address of this neighbor";
                 }
                 leaf neighbor-assert-metric {
                   type int32;
                   description "Metric of the assert winner for reaching a source or RP";
                 }
                 leaf neighbor-assert-preference {
                   type int32;
                   description "Preference of the assert winner for reaching a source or RP";
                 }
                 leaf neighbor-assert-timeout {
                   type int32;
                   description "Time remaining before assert winner timer expires";
                 }
               }
             }
           }
           list downstream-interface {
             description "Downstream/Outgoing interface list";
             list downstream-neighbor {
             }
           }
         }
         list bidir {
           leaf multicast-group-address {
             type ipaddr;
             description "Group address";
           }
           leaf bidir-group-prefix-length {
             type uint32;
             description "Bidirectional group prefix length";
           }
           leaf multicast-source-address {
             type ipaddr;
             description "Source address";
           }
           leaf rendezvous-point-address {
             type ipaddr;
             description "Address of rendezvous point";
           }
           leaf upstream-protocol-name {
             type string;
             description "Upstream protocol";
           }
           leaf upstream-interface-name {
             type string;
             description "Upstream interface";
           }
           leaf pim-interface-state {
             type string;
             description "State of PIM interface";
           }
           leaf upstream-neighbor {
             type ipaddr;
             description "IP Address of Upstream Neighbor";
           }
           leaf upstream-neighbor-rpf-origin {
             type string;
             description "Reverse-path forwarding origin of upstream neighbor";
           }
           leaf keepalive-timeout {
             type int32;
           }
           leaf no-keepalive-timeout {
             type empty;
           }
           leaf downstream-interface-count {
             type int32;
           }
           leaf downstream-neighbor-count {
             type int32;
           }
           container pim-group-flags {
             leaf sparse {
               type empty;
             }
             leaf dense {
               type empty;
             }
             leaf delete {
               type empty;
             }
             leaf rptree {
               type empty;
             }
             leaf wildcard {
               type empty;
             }
             leaf spt {
               type empty;
             }
           }
           list dense-event {
           }
           container upstream-state-flags {
             leaf none {
               type empty;
             }
             leaf local-source {
               type empty;
             }
             leaf local-rp {
               type empty;
             }
             leaf join-to-rp {
               type empty;
             }
             leaf join-to-source {
               type empty;
             }
             leaf prune-to-rp {
               type empty;
             }
             leaf no-prune-to-rp {
               type empty;
             }
             leaf prune-to-source {
               type empty;
             }
           }
           list accepting-interface {
             description "Accepting interface list";
             leaf pim-interface-name {
               type string;
               description "Name of PIM interface";
             }
             leaf df-state {
               type string;
               description "PIM-BIDIR DF election state";
             }
           }
           container downstream-interfaces {
             leaf dummy {
               type empty;
             }
             list downstream-interface {
               description "Downstream/Outgoing interface list";
               leaf pim-interface-name {
                 type string;
                 description "Name of PIM interface";
               }
               leaf pim-interface-state {
                 type string;
                 description "State of PIM interface";
               }
               list downstream-neighbor {
                 leaf neighbor-address {
                   type ipaddr;
                   description "IP address of this neighbor";
                 }
                 leaf neighbor-state {
                   type string;
                 }
                 leaf terse-bidir {
                   type empty;
                   description "Bidirectional flag";
                 }
                 leaf terse-rpt {
                   type empty;
                 }
                 leaf terse-wc {
                   type empty;
                 }
                 leaf neighbor-timeout {
                   type int32;
                 }
               }
             }
           }
           list downstream-interface {
             description "Downstream/Outgoing interface list";
             list downstream-neighbor {
             }
           }
         }
       }
     }
     list brief {
       leaf pim-instance {
         type string;
         description "Name of the PIM instance";
       }
       leaf address-family {
         type string;
       }
       list join-summaries {
         container join-summary {
           leaf multicast-route-type {
             type string;
           }
           leaf multicast-route-count {
             type int32;
           }
         }
       }
       list join-group {
         list dense {
           leaf multicast-group-address {
             type ipaddr;
             description "Group address";
           }
           leaf multicast-source-address {
             type ipaddr;
             description "Source address";
           }
           leaf upstream-interface-name {
             type string;
             description "Upstream interface";
           }
           leaf pim-interface-state {
             type string;
             description "State of PIM interface";
           }
           leaf upstream-neighbor {
             type ipaddr;
             description "IP Address of Upstream Neighbor";
           }
           leaf upstream-neighbor-rpf-origin {
             type string;
             description "Reverse-path forwarding origin of upstream neighbor";
           }
           leaf uptime {
             type string;
           }
           leaf downstream-interface-count {
             type int32;
           }
           leaf downstream-neighbor-count {
             type int32;
           }
           container pim-group-flags {
             leaf sparse {
               type empty;
             }
             leaf bidir {
               type empty;
               description "Bidirectional flag";
             }
             leaf delete {
               type empty;
             }
             leaf rptree {
               type empty;
             }
             leaf wildcard {
               type empty;
             }
             leaf spt {
               type empty;
             }
           }
           list dense-event {
             container dense-receive-prune {
               leaf pim-interface-name {
                 type string;
                 description "Name of PIM interface";
               }
               leaf dense-timeout {
                 type int32;
               }
             }
             container dense-send-prune {
               leaf pim-interface-name {
                 type string;
                 description "Name of PIM interface";
               }
               leaf dense-timeout {
                 type int32;
               }
             }
             container dense-join {
               leaf pim-interface-name {
                 type string;
                 description "Name of PIM interface";
               }
               leaf dense-timeout {
                 type int32;
               }
             }
             container dense-graft {
               leaf pim-interface-name {
                 type string;
                 description "Name of PIM interface";
               }
               leaf dense-timeout {
                 type int32;
               }
             }
           }
           container downstream-interfaces {
             leaf dummy {
               type empty;
             }
             list downstream-interface {
               description "Downstream/Outgoing interface list";
               leaf pim-interface-name {
                 type string;
                 description "Name of PIM interface";
               }
               leaf pruned-timeout {
                 type int32;
                 description "PIM-DM pruned timeout";
               }
               leaf pim-interface-state {
                 type string;
                 description "State of PIM interface";
               }
               list downstream-neighbor {
               }
             }
           }
           list downstream-interface {
             description "Downstream/Outgoing interface list";
             list downstream-neighbor {
             }
           }
         }
         list sparse {
           leaf multicast-group-address {
             type ipaddr;
             description "Group address";
           }
           leaf multicast-source-address {
             type ipaddr;
             description "Source address";
           }
           leaf rendezvous-point-address {
             type ipaddr;
             description "Address of rendezvous point";
           }
           leaf upstream-protocol-name {
             type string;
             description "Upstream protocol";
           }
           leaf upstream-interface-name {
             type string;
             description "Upstream interface";
           }
           leaf pim-interface-state {
             type string;
             description "State of PIM interface";
           }
           leaf upstream-neighbor {
             type ipaddr;
             description "IP Address of Upstream Neighbor";
           }
           leaf upstream-neighbor-rpf-origin {
             type string;
             description "Reverse-path forwarding origin of upstream neighbor";
           }
           leaf keepalive-timeout {
             type int32;
           }
           leaf no-keepalive-timeout {
             type empty;
           }
           leaf uptime {
             type string;
           }
           leaf downstream-interface-count {
             type int32;
           }
           leaf downstream-neighbor-count {
             type int32;
           }
           container pim-group-flags {
             leaf bidir {
               type empty;
               description "Bidirectional flag";
             }
             leaf dense {
               type empty;
             }
             leaf delete {
               type empty;
             }
             leaf rptree {
               type empty;
             }
             leaf wildcard {
               type empty;
             }
             leaf spt {
               type empty;
             }
           }
           container active-upstream-path {
             leaf upstream-protocol-name {
               type string;
               description "Upstream protocol";
             }
             leaf upstream-interface-name {
               type string;
               description "Upstream interface";
             }
             leaf pim-interface-state {
               type string;
               description "State of PIM interface";
             }
             leaf upstream-neighbor {
               type ipaddr;
               description "IP Address of Upstream Neighbor";
             }
             leaf upstream-neighbor-rpf-origin {
               type string;
               description "Reverse-path forwarding origin of upstream neighbor";
             }
           }
           container mofrr-backup-upstream-path {
             leaf upstream-protocol-name {
               type string;
               description "Upstream protocol";
             }
             leaf upstream-interface-name {
               type string;
               description "Upstream interface";
             }
             leaf pim-interface-state {
               type string;
               description "State of PIM interface";
             }
             leaf upstream-neighbor {
               type ipaddr;
               description "IP Address of Upstream Neighbor";
             }
             leaf upstream-neighbor-rpf-origin {
               type string;
               description "Reverse-path forwarding origin of upstream neighbor";
             }
           }
           container standby-upstream-path {
             leaf upstream-protocol-name {
               type string;
               description "Upstream protocol";
             }
             leaf upstream-interface-name {
               type string;
               description "Upstream interface";
             }
             leaf pim-interface-state {
               type string;
               description "State of PIM interface";
             }
             leaf upstream-neighbor {
               type ipaddr;
               description "IP Address of Upstream Neighbor";
             }
             leaf upstream-neighbor-rpf-origin {
               type string;
               description "Reverse-path forwarding origin of upstream neighbor";
             }
           }
           list dense-event {
           }
           container upstream-state-flags {
             leaf none {
               type empty;
             }
             leaf local-source {
               type empty;
             }
             leaf local-rp {
               type empty;
             }
             leaf join-to-rp {
               type empty;
             }
             leaf join-to-source {
               type empty;
             }
             leaf prune-to-rp {
               type empty;
             }
             leaf no-prune-to-rp {
               type empty;
             }
             leaf prune-to-source {
               type empty;
             }
           }
           container downstream-interfaces {
             leaf dummy {
               type empty;
             }
             list downstream-interface {
               description "Downstream/Outgoing interface list";
               leaf pim-interface-name {
                 type string;
                 description "Name of PIM interface";
               }
               leaf pim-interface-state {
                 type string;
                 description "State of PIM interface";
               }
               leaf register-rp {
                 type ipaddr;
               }
               leaf register-interface-name {
                 type string;
               }
               list downstream-neighbor {
                 leaf neighbor-address {
                   type ipaddr;
                   description "IP address of this neighbor";
                 }
                 leaf neighbor-state {
                   type string;
                 }
                 leaf terse-sparse {
                   type empty;
                 }
                 leaf terse-rpt {
                   type empty;
                 }
                 leaf terse-wc {
                   type empty;
                 }
                 leaf neighbor-timeout {
                   type int32;
                 }
                 leaf downstream-if-uptime {
                   type string;
                   description "Time since first join received on this interface";
                 }
                 container downstream-last-jp {
                   leaf downstream-last-jp-oper {
                     type string;
                   }
                   leaf downstream-last-jp-time {
                     type string;
                   }
                 }
               }
               container downstream-assert-neighbor {
                 description "Information about the neighbor that won the assert";
                 leaf neighbor-address {
                   type ipaddr;
                   description "IP address of this neighbor";
                 }
                 leaf neighbor-assert-metric {
                   type int32;
                   description "Metric of the assert winner for reaching a source or RP";
                 }
                 leaf neighbor-assert-preference {
                   type int32;
                   description "Preference of the assert winner for reaching a source or RP";
                 }
                 leaf neighbor-assert-timeout {
                   type int32;
                   description "Time remaining before assert winner timer expires";
                 }
               }
             }
           }
           list downstream-interface {
             description "Downstream/Outgoing interface list";
             list downstream-neighbor {
             }
           }
         }
         list bidir {
           leaf multicast-group-address {
             type ipaddr;
             description "Group address";
           }
           leaf bidir-group-prefix-length {
             type uint32;
             description "Bidirectional group prefix length";
           }
           leaf multicast-source-address {
             type ipaddr;
             description "Source address";
           }
           leaf rendezvous-point-address {
             type ipaddr;
             description "Address of rendezvous point";
           }
           leaf upstream-protocol-name {
             type string;
             description "Upstream protocol";
           }
           leaf upstream-interface-name {
             type string;
             description "Upstream interface";
           }
           leaf pim-interface-state {
             type string;
             description "State of PIM interface";
           }
           leaf upstream-neighbor {
             type ipaddr;
             description "IP Address of Upstream Neighbor";
           }
           leaf upstream-neighbor-rpf-origin {
             type string;
             description "Reverse-path forwarding origin of upstream neighbor";
           }
           leaf keepalive-timeout {
             type int32;
           }
           leaf no-keepalive-timeout {
             type empty;
           }
           leaf downstream-interface-count {
             type int32;
           }
           leaf downstream-neighbor-count {
             type int32;
           }
           container pim-group-flags {
             leaf sparse {
               type empty;
             }
             leaf dense {
               type empty;
             }
             leaf delete {
               type empty;
             }
             leaf rptree {
               type empty;
             }
             leaf wildcard {
               type empty;
             }
             leaf spt {
               type empty;
             }
           }
           list dense-event {
           }
           container upstream-state-flags {
             leaf none {
               type empty;
             }
             leaf local-source {
               type empty;
             }
             leaf local-rp {
               type empty;
             }
             leaf join-to-rp {
               type empty;
             }
             leaf join-to-source {
               type empty;
             }
             leaf prune-to-rp {
               type empty;
             }
             leaf no-prune-to-rp {
               type empty;
             }
             leaf prune-to-source {
               type empty;
             }
           }
           list accepting-interface {
             description "Accepting interface list";
             leaf pim-interface-name {
               type string;
               description "Name of PIM interface";
             }
             leaf df-state {
               type string;
               description "PIM-BIDIR DF election state";
             }
           }
           container downstream-interfaces {
             leaf dummy {
               type empty;
             }
             list downstream-interface {
               description "Downstream/Outgoing interface list";
               leaf pim-interface-name {
                 type string;
                 description "Name of PIM interface";
               }
               leaf pim-interface-state {
                 type string;
                 description "State of PIM interface";
               }
               list downstream-neighbor {
                 leaf neighbor-address {
                   type ipaddr;
                   description "IP address of this neighbor";
                 }
                 leaf neighbor-state {
                   type string;
                 }
                 leaf terse-bidir {
                   type empty;
                   description "Bidirectional flag";
                 }
                 leaf terse-rpt {
                   type empty;
                 }
                 leaf terse-wc {
                   type empty;
                 }
                 leaf neighbor-timeout {
                   type int32;
                 }
               }
             }
           }
           list downstream-interface {
             description "Downstream/Outgoing interface list";
             list downstream-neighbor {
             }
           }
         }
       }
     }
   }
 }
 grouping pim-mvpn-information-block {
   leaf pim-mvpn-instance-name {
     type string;
   }
   leaf address-family {
     type string;
   }
   leaf pim-mvpn-address {
     type ipaddr;
   }
   leaf pim-mvpn-mode {
     type string;
     description "MVPN control protocol";
   }
   leaf pim-mvpn-tunnel {
     type string;
     description "MVPN Tunnel Type";
   }
 }
 grouping pim-neighbors-information-block {
   list basic {
     leaf pim-instance {
       type string;
       description "Name of the PIM instance";
     }
     container neighbor-option-banner {
       leaf banner-first {
         type empty;
       }
       leaf banner-second {
         type empty;
       }
       leaf banner-third {
         type empty;
       }
     }
     list pim-interface {
       list pim-neighbor {
         leaf pim-interface-name {
           type string;
           description "Name of PIM interface";
         }
         leaf ip-protocol-version {
           type int32;
           description "IP protocol version of PIM interface";
         }
         leaf protocol-version {
           type int32;
           description "PIM protocol version of PIM interface";
         }
         leaf pim-interface-mode {
           type string;
           description "Mode of PIM interface";
         }
         leaf pim-neighbor-uptime {
           type string;
           description "PIM neighbor uptime";
         }
         leaf pim-neighbor-address {
           type ipaddr;
           description "PIM neighbor address";
         }
         container pim-neighbor-flags {
           leaf pim-neighbor-hold-time-flag {
             type empty;
           }
           leaf pim-neighbor-priority-flag {
             type empty;
           }
           leaf pim-neighbor-lan-prune-flag {
             type empty;
           }
           leaf pim-neighbor-generation-id-flag {
             type empty;
           }
           leaf pim-neighbor-bidirectional-flag {
             type empty;
           }
           leaf pim-neighbor-t-bit-flag {
             type empty;
           }
         }
       }
     }
   }
   list rpf-loads {
     leaf pim-instance {
       type string;
       description "Name of the PIM instance";
     }
     list pim-interface {
       list pim-neighbor {
         leaf pim-interface-name {
           type string;
           description "Name of PIM interface";
         }
         leaf ip-protocol-version {
           type int32;
           description "IP protocol version of PIM interface";
         }
         leaf protocol-version {
           type int32;
           description "PIM protocol version of PIM interface";
         }
         leaf pim-interface-mode {
           type string;
           description "Mode of PIM interface";
         }
         leaf pim-neighbor-uptime {
           type string;
           description "PIM neighbor uptime";
         }
         leaf pim-neighbor-address {
           type ipaddr;
           description "PIM neighbor address";
         }
         leaf pim-neighbor-active-join-sg-count {
           type int32;
           description "Number of active path (s,g) joins sent to the neighbor";
         }
         leaf pim-neighbor-mofrr-backup-join-sg-count {
           type int32;
           description "Number of mofrr backup path (s,g) joins sent to the neighbor";
         }
         leaf pim-neighbor-standby-join-sg-count {
           type int32;
           description "Number of standby path (s,g) joins sent to the neighbor";
         }
         leaf pim-neighbor-ephemeral-join-sg-count {
           type int32;
           description "Number of ephemeral (s,g) joins on the neighbor";
         }
         leaf pim-neighbor-static-join-sg-count {
           type int32;
           description "Number of static (s,g) joins on the neighbor";
         }
         leaf pim-neighbor-active-join-tsg-count {
           type int32;
           description "Number of active path (*,g) joins sent to the neighbor";
         }
         leaf pim-neighbor-standby-join-tsg-count {
           type int32;
           description "Number of standby path (*,g) joins sent to the neighbor";
         }
         leaf pim-neighbor-ephemeral-join-tsg-count {
           type int32;
           description "Number of ephemeral (*,g) joins on the neighbor";
         }
         leaf pim-neighbor-static-join-tsg-count {
           type int32;
           description "Number of static (*,g) joins on the neighbor";
         }
         container pim-neighbor-flags {
           leaf pim-neighbor-hold-time-flag {
             type empty;
           }
           leaf pim-neighbor-priority-flag {
             type empty;
           }
           leaf pim-neighbor-lan-prune-flag {
             type empty;
           }
           leaf pim-neighbor-generation-id-flag {
             type empty;
           }
           leaf pim-neighbor-bidirectional-flag {
             type empty;
           }
           leaf pim-neighbor-t-bit-flag {
             type empty;
           }
         }
       }
     }
   }
   list detail {
     leaf pim-instance {
       type string;
       description "Name of the PIM instance";
     }
     list pim-interface {
       leaf pim-interface-name {
         type string;
         description "Name of PIM interface";
       }
       list pim-neighbor {
         leaf pim-neighbor-address {
           type ipaddr;
           description "PIM neighbor address";
         }
         leaf ip-protocol-version {
           type int32;
           description "IP protocol version of PIM interface";
         }
         leaf protocol-version {
           type int32;
           description "PIM protocol version of PIM interface";
         }
         leaf pim-interface-mode {
           type string;
           description "Mode of PIM interface";
         }
         leaf pim-neighbor-join-sg-count {
           type int32;
           description "Number of (s,g) joins sent to the neighbor";
         }
         leaf pim-neighbor-join-tsg-count {
           type int32;
           description "Number of (*,g) joins sent to the neighbor";
         }
         leaf pim-neighbor-nexthop-id {
           type int32;
           description "PIM neighbor nexthop id";
         }
         leaf pim-neighbor-p2mp-hello-tx-timeout {
           type int32;
           description "PIM P2MP Hello TX Timeout";
         }
         leaf pim-neighbor-secondary-address {
           type ipaddr;
           description "PIM neighbor secondary address";
         }
         leaf hello-holdtime {
           type int32;
         }
         leaf hello-holdtime-remaining {
           type int32;
         }
         leaf hello-default-holdtime {
           type int32;
           description "PIM neighbor default holdtime";
         }
         leaf hello-default-holdtime-remaining {
           type int32;
           description "PIM neighbor timeout from default holdtime";
         }
         leaf hello-dr-priority {
           type int32;
         }
         leaf hello-generation-id {
           type int32;
         }
         leaf hello-lanprune-delay {
           type int32;
         }
         leaf hello-override-interval {
           type int32;
         }
         leaf hello-nbr-t-bit {
           type empty;
         }
         container pim-neighbor-flags {
           leaf pim-neighbor-bidirectional-flag {
             type empty;
           }
         }
         list pim-neighbor-bfd {
           leaf configuration-state {
             type string;
             description "State (enabled or disabled) of Bidirectional Forwarding Detection for a PIM neighbor";
           }
           leaf operational-state {
             type string;
             description "Operational state of Bidirectional Forwarding Detection session for a PIM neighbor";
           }
         }
         list pim-neighbor-join {
           leaf multicast-group-address {
             type ipaddr;
             description "Group address";
           }
           leaf multicast-source-address {
             type ipaddr;
             description "Source address";
           }
           leaf join-timeout {
             type int32;
           }
         }
         list pim-neighbor-assert {
           leaf multicast-group-address {
             type ipaddr;
             description "Group address";
           }
           leaf multicast-source-address {
             type ipaddr;
             description "Source address";
           }
           leaf assert-state {
             type string;
           }
           leaf pim-neighbor-address {
             type ipaddr;
             description "PIM neighbor address";
           }
           leaf assert-timeout {
             type int32;
           }
         }
       }
     }
   }
 }
 grouping pim-rps-information-block {
   leaf pim-instance {
     type string;
     description "Name of the PIM instance";
   }
   list rp-family {
     leaf address-family {
       type string;
     }
     list rendezvous-point {
       list basic-ipv4 {
         leaf rendezvous-point-address {
           type ipaddr;
           description "Address of rendezvous point";
         }
         leaf rp-flag-static {
           type empty;
         }
         leaf rp-flag-embedded-rp {
           type empty;
         }
         leaf rp-flag-autorp {
           type empty;
         }
         leaf rp-flag-bootstrap {
           type empty;
         }
         leaf rp-flag-sparse {
           type empty;
         }
         leaf rp-flag-bidirectional {
           type empty;
         }
         leaf rendezvous-point-holdtime {
           type int32;
         }
         leaf rendezvous-point-timeout {
           type string;
         }
         leaf rendezvous-point-active-groups {
           type int32;
         }
         list rendezvous-point-group-prefixes {
           leaf multicast-group-prefix {
             type ipaddr;
             description "Group prefix";
           }
           leaf rp-group-state {
             type string;
           }
         }
         container rendezvous-point-active-group-prefixes {
         }
       }
       list basic-ipv6 {
         leaf rendezvous-point-address {
           type ipaddr;
           description "Address of rendezvous point";
         }
         leaf rp-flag-static {
           type empty;
         }
         leaf rp-flag-embedded-rp {
           type empty;
         }
         leaf rp-flag-autorp {
           type empty;
         }
         leaf rp-flag-bootstrap {
           type empty;
         }
         leaf rp-flag-sparse {
           type empty;
         }
         leaf rp-flag-bidirectional {
           type empty;
         }
         leaf rendezvous-point-holdtime {
           type int32;
         }
         leaf rendezvous-point-timeout {
           type string;
         }
         leaf rendezvous-point-active-groups {
           type int32;
         }
         list rendezvous-point-group-prefixes {
           leaf multicast-group-prefix {
             type ipaddr;
             description "Group prefix";
           }
           leaf rp-group-state {
             type string;
           }
         }
         container rendezvous-point-active-group-prefixes {
         }
       }
       list fancy {
         leaf rendezvous-point-address {
           type ipaddr;
           description "Address of rendezvous point";
         }
         leaf rp-flag-static {
           type empty;
         }
         leaf rp-flag-embedded-rp {
           type empty;
         }
         leaf rendezvous-point-from-address {
           type ipaddr;
         }
         leaf rp-flag-autorp {
           type empty;
         }
         leaf rp-flag-bootstrap {
           type empty;
         }
         leaf rendezvous-point-static-override {
           type string;
         }
         leaf rp-flag-sparse {
           type empty;
         }
         leaf rp-flag-bidirectional {
           type empty;
         }
         leaf rendezvous-point-time-active {
           type string;
         }
         leaf rendezvous-point-refcount {
           type int32;
         }
         leaf rendezvous-point-holdtime {
           type int32;
         }
         leaf rendezvous-point-holdtime-remaining {
           type int32;
         }
         leaf rp-interface-device-index {
           type int32;
         }
         leaf rp-interface-device-subunit {
           type int32;
         }
         leaf pim-interface-name {
           type string;
           description "Name of PIM interface";
         }
         leaf rendezvous-point-anycast-pim-local-address {
           type ipaddr;
           description "Local address for replicating register messages to anycast RPs";
         }
         list rendezvous-point-group-prefixes {
           leaf multicast-group-prefix {
             type ipaddr;
             description "Group prefix";
           }
           leaf rp-group-timeout {
             type string;
             description "Time remaining for RP group prefix";
           }
           leaf rp-group-state {
             type string;
           }
         }
         container rendezvous-point-active-group-prefixes {
           leaf rendezvous-point-active-groups {
             type int32;
           }
           list rendezvous-point-active-group-prefix {
             leaf multicast-group-address {
               type ipaddr;
               description "Group address";
             }
           }
         }
         list rendezvous-point-register-state {
           leaf multicast-group-address {
             type ipaddr;
             description "Group address";
           }
           leaf multicast-source-address {
             type ipaddr;
             description "Source address";
           }
           leaf first-hop-address {
             type ipaddr;
           }
           leaf rendezvous-point-address {
             type ipaddr;
             description "Address of rendezvous point";
           }
           leaf pim-register-state {
             type string;
           }
           leaf pim-register-timeout {
             type int32;
           }
         }
         list rendezvous-point-anycast-pim-rpset {
           description "IPv4 address of one or more remote anycast RPs";
           leaf multicast-group-address {
             type ipaddr;
             description "Group address";
           }
         }
         list rendezvous-point-anycast-register-state {
           description "Anycast register state";
           leaf multicast-group-address {
             type ipaddr;
             description "Group address";
           }
           leaf multicast-source-address {
             type ipaddr;
             description "Source address";
           }
           leaf pim-anycast-register-state-origin {
             type string;
             description "Origin of anycast register state";
           }
         }
       }
     }
   }
   container rendezvous-point-address-info {
     leaf pim-instance {
       type string;
       description "Name of the PIM instance";
     }
     leaf rendezvous-point-address {
       type ipaddr;
       description "Address of rendezvous point";
     }
     leaf rendezvous-point-embedded-rp-address {
       type empty;
     }
     leaf rendezvous-point-no-address {
       type ipaddr;
     }
     leaf rendezvous-point-dm-address {
       type ipaddr;
     }
     leaf rendezvous-point-ssm-address {
       type ipaddr;
     }
     leaf rendezvous-point-asm-override-ssm-address {
       type ipaddr;
     }
     list rendezvous-point-trees {
       leaf multicast-group-prefix {
         type ipaddr;
         description "Group prefix";
       }
       list rendezvous-point-addresses {
         leaf rendezvous-point-mode-bidir {
           type empty;
         }
         leaf rendezvous-point-hash {
           type int32;
         }
       }
     }
   }
 }
 grouping pim-source-information-block {
   list source-family {
     leaf pim-instance {
       type string;
       description "Name of the PIM instance";
     }
     leaf address-family {
       type string;
     }
     list pim-source {
       leaf multicast-source-address {
         type ipaddr;
         description "Source address";
       }
       leaf route-prefix {
         type ipaddr;
       }
       leaf upstream-protocol-name {
         type string;
         description "Upstream protocol";
       }
       leaf upstream-interface-name {
         type string;
         description "Upstream interface";
       }
       leaf upstream-neighbor {
         type ipaddr;
         description "IP Address of Upstream Neighbor";
       }
       list upstream-group {
         leaf multicast-group-address {
           type ipaddr;
           description "Group address";
         }
       }
     }
   }
 }
 grouping pim-statistics-information-block {
   list statistics-family {
     leaf pim-instance {
       type string;
       description "Name of the PIM instance";
     }
     leaf address-family {
       type string;
     }
     list pim-statistics-interface {
       leaf pim-interface-name {
         type string;
         description "Name of PIM interface";
       }
       list pim-statistic {
         leaf statistic-name {
           type string;
         }
         leaf received-count {
           type int32;
         }
         leaf sent-count {
           type int32;
         }
         leaf error-count {
           type int32;
           description "Total number of errors encountered";
         }
       }
     }
   }
   container pim-statistics-all {
     container pim-statistics-global {
       list pim-statistic {
         leaf statistic-name {
           type string;
         }
         leaf received-count {
           type int32;
         }
         leaf sent-count {
           type int32;
         }
         leaf error-count {
           type int32;
           description "Total number of errors encountered";
         }
       }
     }
     container pim-statistics-other {
       list pim-other-statistic {
         leaf statistic-name {
           type string;
         }
         leaf statistic-count {
           type int32;
         }
       }
     }
   }
   container everything {
     container pim-statistics-global {
       list pim-statistic {
         leaf statistic-name {
           type string;
         }
         leaf received-count {
           type int32;
         }
         leaf sent-count {
           type int32;
         }
         leaf error-count {
           type int32;
           description "Total number of errors encountered";
         }
       }
     }
     container pim-statistics-other {
       list pim-other-statistic {
         leaf statistic-name {
           type string;
         }
         leaf statistic-count {
           type int32;
         }
       }
     }
   }
 }
 grouping pim-mdt-information-block {
   container basic {
     list mdt-active-tunnel {
       leaf mdt-customer-group-address {
         type ipaddr;
       }
       leaf mdt-customer-source-address {
         type ipaddr;
       }
       leaf mdt-provider-group-address {
         type ipaddr;
       }
       leaf mdt-tunnel-interface-name {
         type string;
       }
     }
   }
   container extensive {
     list mdt-active-tunnel {
       leaf mdt-customer-group-address {
         type ipaddr;
       }
       leaf mdt-customer-source-address {
         type ipaddr;
       }
       leaf mdt-provider-group-address {
         type ipaddr;
       }
       leaf mdt-tunnel-interface-name {
         type string;
       }
       leaf mdt-forwarding-rate-kilobits {
         type int32;
       }
       leaf mdt-forwarding-rate-kilobytes {
         type int32;
       }
       leaf mdt-configured-threshold-rate {
         type int32;
       }
       leaf mdt-tunnel-uptime {
         type string;
       }
     }
   }
 }
 grouping pim-data-mdt-limit-block {
   list pim-data-mdt-limit-params {
     leaf pim-data-mdt-limit-name {
       type string;
       description "PIM Data MDT limit ";
     }
     leaf pim-data-mdt-limit-value {
       type uint32;
       description "PIM Data MDT limit value";
     }
   }
 }
 grouping pim-data-mdt-join-information-block {
   leaf pim-data-mdt-csource-address {
     type ipaddr;
   }
   leaf pim-data-mdt-cgroup-address {
     type ipaddr;
   }
   leaf pim-data-mdt-psource-address {
     type ipaddr;
   }
   leaf pim-data-mdt-pgroup-address {
     type ipaddr;
   }
   leaf pim-data-mdt-timeout {
     type int32;
   }
 }
 }
