/*
 * Copyright (c) 2017 Juniper Networks, Inc.
 * All rights reserved.
 */
 module show-snmp {
  namespace "http://yang.juniper.net/yang/1.1/jrpc/show-snmp/junos-ex/17.2R1.13";
  prefix show-snmp;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-snmp-object {
     description "Get SNMP object value";
     input {
       leaf format {
         default "decimal";
         type enumeration {
           enum "decimal" {
             description "Decimal format (default)";
           }
           enum "ascii" {
             description "Convert string indices to 'ascii-keys' representation";
           }
         }
       }
       leaf snmp-object-name {
         type string {
           junos:posix-pattern "^(([.]?1|[a-zA-Z][a-zA-Z0-9]*)([.]([a-zA-Z]|[0-9]+))*([ ]|$))+$";
           junos:pattern-message "Must be an OID of the form 1.x.y.z... or objname[.x.y.z] where x, y, & z are either numbers or a single letter";
         }
         mandatory true;
       }
     }
     output {
       container snmp-object-information {
         uses snmp-object-information-block;
       }
     }
   }
   rpc next-snmp-object {
     description "Get next SNMP object value";
     input {
       leaf format {
         default "decimal";
         type enumeration {
           enum "decimal" {
             description "Decimal format (default)";
           }
           enum "ascii" {
             description "Convert string indices to 'ascii-keys' representation";
           }
         }
       }
       leaf snmp-object-name {
         type string {
           junos:posix-pattern "^(([.]?1|[a-zA-Z][a-zA-Z0-9]*)([.]([a-zA-Z]|[0-9]+))*([ ]|$))+$";
           junos:pattern-message "Must be an OID of the form 1.x.y.z... or objname[.x.y.z] where x, y, & z are either numbers or a single letter";
         }
         mandatory true;
       }
     }
     output {
       container snmp-object-information {
         uses snmp-object-information-block;
       }
     }
   }
   rpc walk-snmp-object {
     description "Walk SNMP object values";
     input {
       leaf format {
         default "decimal";
         type enumeration {
           enum "decimal" {
             description "Decimal format (default)";
           }
           enum "ascii" {
             description "Convert string indices to 'ascii-keys' representation";
           }
         }
       }
       leaf snmp-object-name {
         description "Requested SNMP object names";
         type string {
           junos:posix-pattern "^(([.]?1|[a-zA-Z][a-zA-Z0-9]*)([.]([a-zA-Z]|[0-9]+))*([ ]|$))+$";
           junos:pattern-message "Must be an OID of the form 1.x.y.z... or objname[.x.y.z] where x, y, & z are either numbers or a single letter";
         }
         mandatory true;
       }
     }
     output {
       container snmp-object-information {
         uses snmp-object-information-block;
       }
     }
   }
   rpc get-snmp-information {
     description "Show SNMP statistics";
     output {
       container snmp-statistics {
         uses snmp-statistics-block;
       }
     }
   }
   rpc get-snmp-subagent-statistics {
     description "Show statistics for all SNMP subagents";
     output {
       container snmp-subagent-statistics {
         uses snmp-subagent-statistics-block;
       }
     }
   }
   rpc get-snmp-stats-response-statistics-information {
     description "Show mib2d's statistics for the stats responses from kernel/PFE";
     output {
       container snmp-stats-response-statistics {
         uses snmp-stats-response-statistics-block;
       }
     }
   }
   rpc get-rmon-information {
     description "Show remote monitoring information";
     output {
       container rmon-information {
         uses rmon-information-block;
       }
     }
   }
   rpc get-rmon-history-information {
     description "Show RMON history";
     input {
       leaf index {
         type int32;
       }
       leaf sample-index {
         type int32;
       }
     }
     output {
       container rmon-history-information {
         uses rmon-history-information-block;
       }
     }
   }
   rpc get-rmon-alarm-information {
     description "Show RMON alarms";
     input {
       leaf level {
         default "brief";
         type enumeration {
           enum "brief" {
             description "Display brief output (default)";
           }
           enum "detail" {
             description "Display detailed output";
           }
         }
       }
     }
     output {
       container rmon-alarm-information {
         uses rmon-alarm-information-block;
       }
     }
   }
   rpc get-rmon-event-information {
     description "Show RMON events";
     input {
       leaf level {
         default "brief";
         type enumeration {
           enum "brief" {
             description "Display brief output (default)";
           }
           enum "detail" {
             description "Display detailed output";
           }
         }
       }
     }
     output {
       container rmon-event-information {
         uses rmon-event-information-block;
       }
     }
   }
   rpc get-rmon-log-information {
     description "Show rmon monitoring logs";
     output {
       container rmon-log-information {
         uses rmon-log-information-block;
       }
     }
   }
   rpc get-health-monitor-information {
     description "Show health-monitoring information";
     output {
       container health-monitor-information {
         uses health-monitor-information-block;
       }
     }
   }
   rpc get-health-monitor-alarm-information {
     description "Show health-monitor alarms";
     input {
       leaf level {
         default "brief";
         type enumeration {
           enum "brief" {
             description "Display brief output (default)";
           }
           enum "detail" {
             description "Display detailed output";
           }
         }
       }
     }
     output {
       container rmon-alarm-information {
         uses rmon-alarm-information-block;
       }
     }
   }
   rpc get-health-monitor-log-information {
     description "Show health-monitoring logs";
     output {
       container rmon-log-information {
         uses rmon-log-information-block;
       }
     }
   }
   rpc get-snmp-v3-information {
     description "Show SNMP version 3 information";
     output {
       container snmp-v3-information {
         uses snmp-v3-information-block;
       }
     }
   }
   rpc get-snmp-v3-general-information {
     description "Show general SNMPv3 information";
     output {
       container snmp-v3-general-information {
         uses snmp-v3-general-information-block;
       }
     }
   }
   rpc get-snmp-v3-group-information {
     description "Show SNMPv3 security-to-group information";
     output {
       container snmp-v3-group-information {
         uses snmp-v3-group-information-block;
       }
     }
   }
   rpc get-snmp-v3-usm-user-information {
     description "Show SNMPv3 user information";
     output {
       container snmp-v3-usm-user-information {
         uses snmp-v3-usm-user-information-block;
       }
     }
   }
   rpc get-snmp-v3-access-information {
     description "Show SNMPv3 access information";
     input {
       leaf level {
         default "brief";
         type enumeration {
           enum "brief" {
             description "Display brief output (default)";
           }
           enum "detail" {
             description "Display detailed output";
           }
         }
       }
     }
     output {
       container snmp-v3-access-information {
         uses snmp-v3-access-information-block;
       }
     }
   }
   rpc get-snmp-v3-community-information {
     description "Show SNMPv3 community information";
     output {
       container snmp-v3-community-information {
         uses snmp-v3-community-information-block;
       }
     }
   }
   rpc get-snmp-v3-target-information {
     description "Show SNMPv3 target information";
     output {
       container snmp-v3-target-information {
         uses snmp-v3-target-information-block;
       }
     }
   }
   rpc get-snmp-v3-target-address-information {
     description "Show SNMPv3 target address information";
     output {
       container snmp-v3-target-address-information {
         uses snmp-v3-target-address-information-block;
       }
     }
   }
   rpc get-snmp-v3-target-parameters-information {
     description "Show SNMPv3 target parameters information";
     output {
       container snmp-v3-target-parameters-information {
         uses snmp-v3-target-parameters-information-block;
       }
     }
   }
   rpc get-snmp-v3-notify-information {
     description "Show SNMPv3 notify information";
     output {
       container snmp-v3-notify-information {
         uses snmp-v3-notify-information-block;
       }
     }
   }
   rpc get-snmp-v3-notify-filter-information {
     description "Show SNMPv3 notify filter information";
     output {
       container snmp-v3-notify-filter-information {
         uses snmp-v3-notify-filter-information-block;
       }
     }
   }
   rpc get-snmp-inform-statistics {
     description "Show SNMP Inform request statistics";
     output {
       container snmp-inform-statistics {
         uses snmp-inform-statistics-block;
       }
     }
   }
   rpc get-snmp-proxy-information {
     description "Show SNMP Proxy information";
     output {
       container snmp-proxy-information {
         uses snmp-proxy-information-block;
       }
     }
   }
 grouping snmp-object-information-block {
   list snmp-object {
     leaf name {
       type string;
       description "SNMP object name";
     }
     leaf object-value {
       type string;
       description "SNMP object value";
     }
     leaf error {
       type string;
       description "SNMP object error";
     }
     list index {
     }
   }
   container snmp-request-error {
     leaf snmp-req-error-value {
       type string;
       description "SNMP request error";
     }
   }
 }
 grouping snmp-statistics-block {
   container snmp-input-statistics {
     leaf packets {
       type int32;
     }
     leaf bad-versions {
       type int32;
     }
     leaf bad-community-names {
       type int32;
     }
     leaf bad-community-uses {
       type int32;
     }
     leaf asn-parse-errors {
       type int32;
     }
     leaf too-bigs {
       type int32;
     }
     leaf no-such-names {
       type int32;
     }
     leaf bad-values {
       type int32;
     }
     leaf read-onlys {
       type int32;
     }
     leaf general-errors {
       type int32;
     }
     leaf total-request-varbinds {
       type int32;
     }
     leaf total-set-varbinds {
       type int32;
     }
     leaf get-requests {
       type int32;
     }
     leaf get-nexts {
       type int32;
     }
     leaf set-requests {
       type int32;
     }
     leaf get-responses {
       type int32;
     }
     leaf traps {
       type int32;
     }
     leaf silent-drops {
       type int32;
     }
     leaf proxy-drops {
       type int32;
     }
     leaf commit-pending-drops {
       type int32;
     }
     leaf throttle-drops {
       type int32;
     }
     leaf duplicate-request-drops {
       type int32;
       description "Number of duplicate requests that were dropped";
     }
   }
   container snmp-v3-input-statistics {
     leaf unknown-secmodels {
       type int32;
     }
     leaf invalid-msgs {
       type int32;
     }
     leaf unknown-pduhandlers {
       type int32;
     }
     leaf unavail-contexts {
       type int32;
     }
     leaf unknown-contexts {
       type int32;
     }
     leaf unsupported-seclevels {
       type int32;
     }
     leaf not-in-timewindows {
       type int32;
     }
     leaf unknown-usernames {
       type int32;
     }
     leaf unknown-eids {
       type int32;
     }
     leaf wrong-digests {
       type int32;
     }
     leaf decrypt-errors {
       type int32;
     }
   }
   container snmp-output-statistics {
     leaf packets {
       type int32;
     }
     leaf too-bigs {
       type int32;
     }
     leaf no-such-names {
       type int32;
     }
     leaf bad-values {
       type int32;
     }
     leaf general-errors {
       type int32;
     }
     leaf get-requests {
       type int32;
     }
     leaf get-nexts {
       type int32;
     }
     leaf set-requests {
       type int32;
     }
     leaf get-responses {
       type int32;
     }
     leaf traps {
       type int32;
     }
   }
   container snmp-performance-statistics {
     leaf average-response-time {
       type string;
       description "Average response time in ms for processing SNMP PDU";
     }
     leaf one-minute-request-throughput {
       type int32;
       description "Throughput of request diaptaching in last minute";
     }
     leaf five-minute-request-throughput {
       type int32;
       description "Throughput of request dispatching in last five minutes";
     }
     leaf fifteen-minute-request-throughput {
       type int32;
       description "Throughput of request dispatching in last fifteen minutes";
     }
     leaf one-minute-response-throughput {
       type int32;
       description "Throughput of response dispatching in last minute";
     }
     leaf five-minute-response-throughput {
       type int32;
       description "Throughput of response dispatching in last five minutes";
     }
     leaf fifteen-minute-response-throughput {
       type int32;
       description "Throughput of response dispatching in last fifteen minutes";
     }
   }
   container sub-agent-control-blocks {
     leaf total {
       type int32;
     }
     leaf currently-active {
       type int32;
     }
     leaf max-active {
       type int32;
     }
     leaf not-found {
       type int32;
     }
     leaf timed-out {
       type int32;
     }
     leaf max-latency {
       type int32;
     }
   }
   container sub-agent-registration {
     leaf group-registers {
       type int32;
     }
     leaf group-deregisters {
       type int32;
     }
     leaf group-removes {
       type int32;
     }
   }
   container sec-sub-agent-control-blocks {
     leaf sec-total {
       type int32;
     }
     leaf sec-currently-active {
       type int32;
     }
     leaf sec-max-active {
       type int32;
     }
     leaf sec-sa-max-latency {
       type int32;
     }
     leaf sec-max-latency {
       type int32;
     }
   }
   container trap-queue-stats {
     leaf current-queued {
       type int32;
     }
     leaf total-queued {
       type int32;
     }
     leaf total-discards {
       type int32;
     }
     leaf total-overflows {
       type int32;
     }
   }
   container trap-throttle-stats {
     leaf current-throttled {
       type int32;
     }
     leaf total-throttles {
       type int32;
     }
   }
   container snmp-set-stats {
     leaf nvs-commit-pending {
       type int32;
       description "Set requests failed because of a pending commit";
     }
     leaf nvs-conflock-failures {
       type int32;
       description "Set requests failed because of configuration lock conflict";
     }
     leaf nvs-rpc-mgd-failures {
       type int32;
       description "Set requests failed because of a management daemon rpc error";
     }
     leaf nvs-journal-write-failures {
       type int32;
       description "Set requests failed because of journal write error";
     }
     leaf nvs-mgd-connect-failures {
       type int32;
       description "Set requests failed because snmpd could not connect to mgd";
     }
     leaf nvs-commit-failures {
       type int32;
       description "Set requests failed because of a general commit error";
     }
   }
 }
 grouping snmp-subagent-statistics-block {
   container subagent-statistics {
     leaf subagent {
       type string;
       description "Subagent identifier";
     }
     leaf subagent-request-pdus {
       type uint32;
       description "Number of request PDUs handled by subagent";
     }
     leaf subagent-response-pdus {
       type uint32;
       description "Number of response PDUs handled by subagent";
     }
     leaf subagent-request-variables {
       type uint32;
       description "Number of request variables handled by subagent";
     }
     leaf subagent-response-variables {
       type uint32;
       description "Number of request variables handled by subagent";
     }
     leaf subagent-average-response-time {
       type string;
       description "Average response time of subagent";
     }
     leaf subagent-maximum-response-time {
       type string;
       description "Maximum response time of subagent";
     }
   }
 }
 grouping snmp-stats-response-statistics-block {
   list stats-average-response-time-statistics {
     leaf stats-type {
       type string;
       description "Stats type";
     }
     leaf stats-type-count {
       type uint64;
       description "Stats count for a stats type";
     }
     leaf stats-average-response-time {
       type string;
       description "Average response time for a stats type";
     }
   }
   list bucket-statistics {
     leaf bucket-type {
       type string;
       description "Bucket type";
     }
     leaf bucket-stats-response-count {
       type uint64;
       description "Stats count for a bucket";
     }
   }
   list bad-responses {
     leaf bad-responses-response-time {
       type string;
       description "Response time of a stats request";
     }
     leaf bad-responses-request-timestamp {
       type int32;
       description "Timestamp of stats request";
     }
     leaf bad-responses-stats-type {
       type string;
       description "Stats type";
     }
     leaf bad-responses-key {
       type string;
       description "Key for a stats request";
     }
   }
 }
 grouping rmon-information-block {
   container rmon-alarm-information {
     container verbose {
       list rmon-alarm {
         leaf alarm-index {
           type int32;
           description "Alarm instance identifier";
         }
         leaf var-name {
           type string;
           description "Monitored variable name";
         }
         leaf var-oid {
           type string;
           description "Monitored variable OID";
         }
         leaf sample-type {
           type string;
           description "Method of sampling the monitored variable";
         }
         leaf startup {
           type string;
           description "Alarm that might be sent when entry is activated";
         }
         leaf alarm-owner {
           type string;
           description "Name of owner of this entry";
         }
         leaf alarm-creator {
           type string;
           description "Method by which entry was created";
         }
         leaf alarm-subtag {
           type string;
           description "Additional tag added to system logs for this entry";
         }
         leaf alarm-state {
           type string;
           description "Current state of the entry";
         }
         leaf alarm-interval {
           type int32;
           description "Interval between samples, in seconds";
         }
         leaf rising-threshold {
           type int32;
           description "Rising alarm threshold";
         }
         leaf falling-threshold {
           type int32;
           description "Falling alarm threshold";
         }
         leaf rising-event-index {
           type int32;
           description "Event generated when a rising alarm is sent";
         }
         leaf falling-event-index {
           type int32;
           description "Event generated when a falling alarm is sent";
         }
         leaf alarm-value {
           type int32;
           description "Most recently monitored value";
         }
         container rmon-alarm-instance-information {
           description "Information about one or more alarm instances";
           list rmon-alarm-instance {
             description "Information about an alarm instance";
             leaf inst-var-name {
               type string;
               description "Monitored variable name";
             }
             leaf inst-description {
               type string;
               description "Monitored variable description";
             }
             leaf inst-value {
               type int32;
               description "Most recently monitored value";
             }
             leaf inst-state {
               type string;
               description "Current state of the alarm instance";
             }
           }
         }
       }
     }
     container verbose-hm-extn {
       list rmon-alarm {
         leaf alarm-index {
           type int32;
           description "Alarm instance identifier";
         }
         leaf var-name {
           type string;
           description "Monitored variable name";
         }
         leaf var-oid {
           type string;
           description "Monitored variable OID";
         }
         leaf sample-type {
           type string;
           description "Method of sampling the monitored variable";
         }
         leaf startup {
           type string;
           description "Alarm that might be sent when entry is activated";
         }
         leaf alarm-owner {
           type string;
           description "Name of owner of this entry";
         }
         leaf alarm-creator {
           type string;
           description "Method by which entry was created";
         }
         leaf alarm-subtag {
           type string;
           description "Additional tag added to system logs for this entry";
         }
         leaf alarm-state {
           type string;
           description "Current state of the entry";
         }
         leaf alarm-interval {
           type int32;
           description "Interval between samples, in seconds";
         }
         leaf moderate-threshold {
           type int32;
           description "Moderate alarm threshold";
         }
         leaf high-threshold {
           type int32;
           description "High alarm threshold";
         }
         leaf critical-threshold {
           type int32;
           description "Critical alarm threshold";
         }
         leaf rising-threshold {
           type int32;
           description "Rising alarm threshold";
         }
         leaf falling-threshold {
           type int32;
           description "Falling alarm threshold";
         }
         leaf rising-event-index {
           type int32;
           description "Event generated when a rising alarm is sent";
         }
         leaf falling-event-index {
           type int32;
           description "Event generated when a falling alarm is sent";
         }
         leaf alarm-value {
           type int32;
           description "Most recently monitored value";
         }
         container rmon-alarm-instance-information {
           description "Information about one or more alarm instances";
           list rmon-alarm-instance {
             description "Information about an alarm instance";
             leaf inst-var-name {
               type string;
               description "Monitored variable name";
             }
             leaf inst-description {
               type string;
               description "Monitored variable description";
             }
             leaf inst-value {
               type int32;
               description "Most recently monitored value";
             }
             leaf inst-state {
               type string;
               description "Current state of the alarm instance";
             }
           }
         }
       }
     }
     container brief {
       list rmon-alarm {
         leaf alarm-index {
           type int32;
           description "Alarm instance identifier";
         }
         leaf alarm-owner {
           type string;
           description "Name of owner of this entry";
         }
         container rmon-alarm-instance-information {
           description "Information about one or more alarm instances";
           list rmon-alarm-instance {
             description "Information about an alarm instance";
             leaf inst-var-name {
               type string;
               description "Monitored variable name";
             }
             leaf inst-description {
               type string;
               description "Monitored variable description";
             }
             leaf inst-value {
               type int32;
               description "Most recently monitored value";
             }
             leaf inst-state {
               type string;
               description "Current state of the alarm instance";
             }
           }
         }
       }
     }
   }
   container rmon-event-information {
     container verbose {
       list rmon-event {
         leaf event-index {
           type int32;
           description "Event instance identifier";
         }
         leaf event-descr {
           type string;
           description "Comment describing the event entry";
         }
         leaf event-type {
           type string;
           description "Type of notification made about this event";
         }
         leaf community {
           type string;
           description "Trap group to which trap is sent";
         }
         leaf last-time-sent {
           type string;
           description "Time this event was last generated";
         }
         leaf event-owner {
           type string;
           description "Name of owner of the event";
         }
         leaf event-creator {
           type string;
           description "Method by which the entry was created";
         }
         leaf event-state {
           type string;
           description "Current state of the entry";
         }
       }
     }
     container brief {
       list rmon-event {
         leaf event-index {
           type int32;
           description "Event instance identifier";
         }
         leaf event-type {
           type string;
           description "Type of notification made about this event";
         }
         leaf last-time-sent {
           type string;
           description "Time this event was last generated";
         }
       }
     }
   }
   container rmon-history-information {
     list rmon-history {
       leaf history-index {
         type int32;
         description "History instance identifier";
       }
       leaf history-interface {
         type string;
         description "Comment describing the RMON interface";
       }
       leaf history-requested-buckets {
         type int32;
         description "Requested buckets for the RMON interface";
       }
       leaf history-interval {
         type int32;
         description "Interval for statistics collection on the RMON interface";
       }
       leaf history-owner {
         type string;
         description "Owner for RMON history";
       }
       leaf history-status {
         type string;
         description "Status of RMON history";
       }
     }
     list history-sample {
       leaf history-sample-index {
         type int32;
         description "History sample instance identifier";
       }
       leaf history-sample-start-time {
         type string;
         description "History sample collection start time ";
       }
       leaf history-sample-drop-events {
         type uint64;
         description "Sample drop events";
       }
       leaf history-sample-octect {
         type uint64;
         description "Octets";
       }
       leaf history-sample-packets {
         type uint64;
         description "Packets";
       }
       leaf history-sample-broadcast-packets {
         type uint64;
         description "Number of broadcast packets";
       }
       leaf history-sample-multicast-packets {
         type uint64;
         description "Number of multicast packets";
       }
       leaf history-sample-crc-errors {
         type uint64;
         description "Crc errors";
       }
       leaf history-sample-undersize-packets {
         type uint64;
         description "Number of undersize packets";
       }
       leaf history-sample-oversize-packets {
         type uint64;
         description "Number of oversize packets";
       }
       leaf history-sample-fragments {
         type uint64;
         description "Number of fragment";
       }
       leaf history-sample-jabbers {
         type uint64;
         description "Number of jabbers";
       }
       leaf history-sample-collisions {
         type uint64;
         description "Number of collisions";
       }
       leaf history-sample-utilization {
         type uint64;
         description "Utilization ";
       }
     }
   }
 }
 grouping rmon-history-information-block {
   list rmon-history {
     leaf history-index {
       type int32;
       description "History instance identifier";
     }
     leaf history-interface {
       type string;
       description "Comment describing the RMON interface";
     }
     leaf history-requested-buckets {
       type int32;
       description "Requested buckets for the RMON interface";
     }
     leaf history-interval {
       type int32;
       description "Interval for statistics collection on the RMON interface";
     }
     leaf history-owner {
       type string;
       description "Owner for RMON history";
     }
     leaf history-status {
       type string;
       description "Status of RMON history";
     }
   }
   list history-sample {
     leaf history-sample-index {
       type int32;
       description "History sample instance identifier";
     }
     leaf history-sample-start-time {
       type string;
       description "History sample collection start time ";
     }
     leaf history-sample-drop-events {
       type uint64;
       description "Sample drop events";
     }
     leaf history-sample-octect {
       type uint64;
       description "Octets";
     }
     leaf history-sample-packets {
       type uint64;
       description "Packets";
     }
     leaf history-sample-broadcast-packets {
       type uint64;
       description "Number of broadcast packets";
     }
     leaf history-sample-multicast-packets {
       type uint64;
       description "Number of multicast packets";
     }
     leaf history-sample-crc-errors {
       type uint64;
       description "Crc errors";
     }
     leaf history-sample-undersize-packets {
       type uint64;
       description "Number of undersize packets";
     }
     leaf history-sample-oversize-packets {
       type uint64;
       description "Number of oversize packets";
     }
     leaf history-sample-fragments {
       type uint64;
       description "Number of fragment";
     }
     leaf history-sample-jabbers {
       type uint64;
       description "Number of jabbers";
     }
     leaf history-sample-collisions {
       type uint64;
       description "Number of collisions";
     }
     leaf history-sample-utilization {
       type uint64;
       description "Utilization ";
     }
   }
 }
 grouping rmon-alarm-information-block {
   container verbose {
     list rmon-alarm {
       leaf alarm-index {
         type int32;
         description "Alarm instance identifier";
       }
       leaf var-name {
         type string;
         description "Monitored variable name";
       }
       leaf var-oid {
         type string;
         description "Monitored variable OID";
       }
       leaf sample-type {
         type string;
         description "Method of sampling the monitored variable";
       }
       leaf startup {
         type string;
         description "Alarm that might be sent when entry is activated";
       }
       leaf alarm-owner {
         type string;
         description "Name of owner of this entry";
       }
       leaf alarm-creator {
         type string;
         description "Method by which entry was created";
       }
       leaf alarm-subtag {
         type string;
         description "Additional tag added to system logs for this entry";
       }
       leaf alarm-state {
         type string;
         description "Current state of the entry";
       }
       leaf alarm-interval {
         type int32;
         description "Interval between samples, in seconds";
       }
       leaf rising-threshold {
         type int32;
         description "Rising alarm threshold";
       }
       leaf falling-threshold {
         type int32;
         description "Falling alarm threshold";
       }
       leaf rising-event-index {
         type int32;
         description "Event generated when a rising alarm is sent";
       }
       leaf falling-event-index {
         type int32;
         description "Event generated when a falling alarm is sent";
       }
       leaf alarm-value {
         type int32;
         description "Most recently monitored value";
       }
       container rmon-alarm-instance-information {
         description "Information about one or more alarm instances";
         list rmon-alarm-instance {
           description "Information about an alarm instance";
           leaf inst-var-name {
             type string;
             description "Monitored variable name";
           }
           leaf inst-description {
             type string;
             description "Monitored variable description";
           }
           leaf inst-value {
             type int32;
             description "Most recently monitored value";
           }
           leaf inst-state {
             type string;
             description "Current state of the alarm instance";
           }
         }
       }
     }
   }
   container verbose-hm-extn {
     list rmon-alarm {
       leaf alarm-index {
         type int32;
         description "Alarm instance identifier";
       }
       leaf var-name {
         type string;
         description "Monitored variable name";
       }
       leaf var-oid {
         type string;
         description "Monitored variable OID";
       }
       leaf sample-type {
         type string;
         description "Method of sampling the monitored variable";
       }
       leaf startup {
         type string;
         description "Alarm that might be sent when entry is activated";
       }
       leaf alarm-owner {
         type string;
         description "Name of owner of this entry";
       }
       leaf alarm-creator {
         type string;
         description "Method by which entry was created";
       }
       leaf alarm-subtag {
         type string;
         description "Additional tag added to system logs for this entry";
       }
       leaf alarm-state {
         type string;
         description "Current state of the entry";
       }
       leaf alarm-interval {
         type int32;
         description "Interval between samples, in seconds";
       }
       leaf moderate-threshold {
         type int32;
         description "Moderate alarm threshold";
       }
       leaf high-threshold {
         type int32;
         description "High alarm threshold";
       }
       leaf critical-threshold {
         type int32;
         description "Critical alarm threshold";
       }
       leaf rising-threshold {
         type int32;
         description "Rising alarm threshold";
       }
       leaf falling-threshold {
         type int32;
         description "Falling alarm threshold";
       }
       leaf rising-event-index {
         type int32;
         description "Event generated when a rising alarm is sent";
       }
       leaf falling-event-index {
         type int32;
         description "Event generated when a falling alarm is sent";
       }
       leaf alarm-value {
         type int32;
         description "Most recently monitored value";
       }
       container rmon-alarm-instance-information {
         description "Information about one or more alarm instances";
         list rmon-alarm-instance {
           description "Information about an alarm instance";
           leaf inst-var-name {
             type string;
             description "Monitored variable name";
           }
           leaf inst-description {
             type string;
             description "Monitored variable description";
           }
           leaf inst-value {
             type int32;
             description "Most recently monitored value";
           }
           leaf inst-state {
             type string;
             description "Current state of the alarm instance";
           }
         }
       }
     }
   }
   container brief {
     list rmon-alarm {
       leaf alarm-index {
         type int32;
         description "Alarm instance identifier";
       }
       leaf alarm-owner {
         type string;
         description "Name of owner of this entry";
       }
       container rmon-alarm-instance-information {
         description "Information about one or more alarm instances";
         list rmon-alarm-instance {
           description "Information about an alarm instance";
           leaf inst-var-name {
             type string;
             description "Monitored variable name";
           }
           leaf inst-description {
             type string;
             description "Monitored variable description";
           }
           leaf inst-value {
             type int32;
             description "Most recently monitored value";
           }
           leaf inst-state {
             type string;
             description "Current state of the alarm instance";
           }
         }
       }
     }
   }
 }
 grouping rmon-event-information-block {
   container verbose {
     list rmon-event {
       leaf event-index {
         type int32;
         description "Event instance identifier";
       }
       leaf event-descr {
         type string;
         description "Comment describing the event entry";
       }
       leaf event-type {
         type string;
         description "Type of notification made about this event";
       }
       leaf community {
         type string;
         description "Trap group to which trap is sent";
       }
       leaf last-time-sent {
         type string;
         description "Time this event was last generated";
       }
       leaf event-owner {
         type string;
         description "Name of owner of the event";
       }
       leaf event-creator {
         type string;
         description "Method by which the entry was created";
       }
       leaf event-state {
         type string;
         description "Current state of the entry";
       }
     }
   }
   container brief {
     list rmon-event {
       leaf event-index {
         type int32;
         description "Event instance identifier";
       }
       leaf event-type {
         type string;
         description "Type of notification made about this event";
       }
       leaf last-time-sent {
         type string;
         description "Time this event was last generated";
       }
     }
   }
 }
 grouping rmon-log-information-block {
   list rmon-log {
     leaf rmon-log-event-index {
       type int32;
       description "Event instance identifier";
     }
     leaf rmon-log-descr {
       type string;
       description "Log description";
     }
     leaf rmon-log-time {
       type string;
       description "Time this event was last generated";
     }
   }
 }
 grouping health-monitor-information-block {
   container rmon-alarm-information {
     container verbose {
       list rmon-alarm {
         leaf alarm-index {
           type int32;
           description "Alarm instance identifier";
         }
         leaf var-name {
           type string;
           description "Monitored variable name";
         }
         leaf var-oid {
           type string;
           description "Monitored variable OID";
         }
         leaf sample-type {
           type string;
           description "Method of sampling the monitored variable";
         }
         leaf startup {
           type string;
           description "Alarm that might be sent when entry is activated";
         }
         leaf alarm-owner {
           type string;
           description "Name of owner of this entry";
         }
         leaf alarm-creator {
           type string;
           description "Method by which entry was created";
         }
         leaf alarm-subtag {
           type string;
           description "Additional tag added to system logs for this entry";
         }
         leaf alarm-state {
           type string;
           description "Current state of the entry";
         }
         leaf alarm-interval {
           type int32;
           description "Interval between samples, in seconds";
         }
         leaf rising-threshold {
           type int32;
           description "Rising alarm threshold";
         }
         leaf falling-threshold {
           type int32;
           description "Falling alarm threshold";
         }
         leaf rising-event-index {
           type int32;
           description "Event generated when a rising alarm is sent";
         }
         leaf falling-event-index {
           type int32;
           description "Event generated when a falling alarm is sent";
         }
         leaf alarm-value {
           type int32;
           description "Most recently monitored value";
         }
         container rmon-alarm-instance-information {
           description "Information about one or more alarm instances";
           list rmon-alarm-instance {
             description "Information about an alarm instance";
             leaf inst-var-name {
               type string;
               description "Monitored variable name";
             }
             leaf inst-description {
               type string;
               description "Monitored variable description";
             }
             leaf inst-value {
               type int32;
               description "Most recently monitored value";
             }
             leaf inst-state {
               type string;
               description "Current state of the alarm instance";
             }
           }
         }
       }
     }
     container verbose-hm-extn {
       list rmon-alarm {
         leaf alarm-index {
           type int32;
           description "Alarm instance identifier";
         }
         leaf var-name {
           type string;
           description "Monitored variable name";
         }
         leaf var-oid {
           type string;
           description "Monitored variable OID";
         }
         leaf sample-type {
           type string;
           description "Method of sampling the monitored variable";
         }
         leaf startup {
           type string;
           description "Alarm that might be sent when entry is activated";
         }
         leaf alarm-owner {
           type string;
           description "Name of owner of this entry";
         }
         leaf alarm-creator {
           type string;
           description "Method by which entry was created";
         }
         leaf alarm-subtag {
           type string;
           description "Additional tag added to system logs for this entry";
         }
         leaf alarm-state {
           type string;
           description "Current state of the entry";
         }
         leaf alarm-interval {
           type int32;
           description "Interval between samples, in seconds";
         }
         leaf moderate-threshold {
           type int32;
           description "Moderate alarm threshold";
         }
         leaf high-threshold {
           type int32;
           description "High alarm threshold";
         }
         leaf critical-threshold {
           type int32;
           description "Critical alarm threshold";
         }
         leaf rising-threshold {
           type int32;
           description "Rising alarm threshold";
         }
         leaf falling-threshold {
           type int32;
           description "Falling alarm threshold";
         }
         leaf rising-event-index {
           type int32;
           description "Event generated when a rising alarm is sent";
         }
         leaf falling-event-index {
           type int32;
           description "Event generated when a falling alarm is sent";
         }
         leaf alarm-value {
           type int32;
           description "Most recently monitored value";
         }
         container rmon-alarm-instance-information {
           description "Information about one or more alarm instances";
           list rmon-alarm-instance {
             description "Information about an alarm instance";
             leaf inst-var-name {
               type string;
               description "Monitored variable name";
             }
             leaf inst-description {
               type string;
               description "Monitored variable description";
             }
             leaf inst-value {
               type int32;
               description "Most recently monitored value";
             }
             leaf inst-state {
               type string;
               description "Current state of the alarm instance";
             }
           }
         }
       }
     }
     container brief {
       list rmon-alarm {
         leaf alarm-index {
           type int32;
           description "Alarm instance identifier";
         }
         leaf alarm-owner {
           type string;
           description "Name of owner of this entry";
         }
         container rmon-alarm-instance-information {
           description "Information about one or more alarm instances";
           list rmon-alarm-instance {
             description "Information about an alarm instance";
             leaf inst-var-name {
               type string;
               description "Monitored variable name";
             }
             leaf inst-description {
               type string;
               description "Monitored variable description";
             }
             leaf inst-value {
               type int32;
               description "Most recently monitored value";
             }
             leaf inst-state {
               type string;
               description "Current state of the alarm instance";
             }
           }
         }
       }
     }
   }
   container rmon-log-information {
     list rmon-log {
       leaf rmon-log-event-index {
         type int32;
         description "Event instance identifier";
       }
       leaf rmon-log-descr {
         type string;
         description "Log description";
       }
       leaf rmon-log-time {
         type string;
         description "Time this event was last generated";
       }
     }
   }
   container rmon-history-information {
     list rmon-history {
       leaf history-index {
         type int32;
         description "History instance identifier";
       }
       leaf history-interface {
         type string;
         description "Comment describing the RMON interface";
       }
       leaf history-requested-buckets {
         type int32;
         description "Requested buckets for the RMON interface";
       }
       leaf history-interval {
         type int32;
         description "Interval for statistics collection on the RMON interface";
       }
       leaf history-owner {
         type string;
         description "Owner for RMON history";
       }
       leaf history-status {
         type string;
         description "Status of RMON history";
       }
     }
     list history-sample {
       leaf history-sample-index {
         type int32;
         description "History sample instance identifier";
       }
       leaf history-sample-start-time {
         type string;
         description "History sample collection start time ";
       }
       leaf history-sample-drop-events {
         type uint64;
         description "Sample drop events";
       }
       leaf history-sample-octect {
         type uint64;
         description "Octets";
       }
       leaf history-sample-packets {
         type uint64;
         description "Packets";
       }
       leaf history-sample-broadcast-packets {
         type uint64;
         description "Number of broadcast packets";
       }
       leaf history-sample-multicast-packets {
         type uint64;
         description "Number of multicast packets";
       }
       leaf history-sample-crc-errors {
         type uint64;
         description "Crc errors";
       }
       leaf history-sample-undersize-packets {
         type uint64;
         description "Number of undersize packets";
       }
       leaf history-sample-oversize-packets {
         type uint64;
         description "Number of oversize packets";
       }
       leaf history-sample-fragments {
         type uint64;
         description "Number of fragment";
       }
       leaf history-sample-jabbers {
         type uint64;
         description "Number of jabbers";
       }
       leaf history-sample-collisions {
         type uint64;
         description "Number of collisions";
       }
       leaf history-sample-utilization {
         type uint64;
         description "Utilization ";
       }
     }
   }
   container terse {
     description "Health monitor configuration information about one or more health monitors";
     list slb-hm-information {
       leaf slb-hm-rulename {
         type string;
         description "Health monitor rule name";
       }
       leaf slb-hm-protocol {
         type string;
         description "Health monitor protocol";
       }
       leaf slb-hm-port {
         type string;
         description "Health monitor port number";
       }
       leaf slb-hm-rs-count {
         type uint32;
         description "Number of real server";
       }
       leaf slb-hm-rsg-count {
         type uint32;
         description "Number of real server group";
       }
     }
   }
   container detail {
     description "Health monitor configuration information about one or more health monitors";
     list slb-hm-information {
       leaf slb-hm-rulename {
         type string;
         description "Health monitor rule name";
       }
       leaf slb-hm-protocol {
         type string;
         description "Health monitor protocol";
       }
       leaf slb-hm-http-request {
         type string;
         description "Health monitor HTTP request definition";
       }
       leaf slb-hm-http-response {
         type string;
         description "Health monitor HTTP response-check definition";
       }
       leaf slb-hm-port {
         type string;
         description "Health monitor port number";
       }
       leaf slb-hm-timeout {
         type uint32;
         description "Health monitor timeout value, in seconds";
       }
       leaf slb-hm-itvl-down {
         type uint32;
         description "Health monitor probe interval when server is down";
       }
       leaf slb-hm-itvl-up {
         type uint32;
         description "Health monitor probe interval when server is up";
       }
       leaf slb-hm-max-retry {
         type uint32;
         description "Health monitor maximum retry count";
       }
       leaf slb-hm-rs-count {
         type uint32;
         description "Number of real server";
       }
       leaf slb-hm-rsg-count {
         type uint32;
         description "Number of real server group";
       }
       leaf slb-rs-servername {
         type string;
         description "Real server name";
       }
       leaf slb-rs-hm-state {
         type string;
         description "Real server health monitor state";
       }
       leaf slb-spu-slot {
         type uint32;
         description "SPU slot number";
       }
       leaf slb-spu-pic {
         type uint32;
         description "SPU PIC number";
       }
       leaf slb-rsg-servername {
         type string;
         description "Real server group name";
       }
       leaf slb-rsg-rs-count {
         type string;
         description "Real server number under this real server group";
       }
     }
   }
 }
 grouping snmp-v3-information-block {
   container snmp-v3-general-information {
     list snmp-v3-engine-information {
       leaf engine-id {
         type string;
         description "Engine ID";
       }
       leaf engine-boots {
         type int32;
         description "Number of times this engine has booted";
       }
       leaf engine-time {
         type int32;
         description "Number of seconds since this engine has booted";
       }
       leaf max-msg-size {
         type int32;
         description "Maximum message size allowed by this engine";
       }
     }
   }
   container snmp-v3-usm-user-information {
     container snmp-v3-usm-user-engine-id {
       leaf user-engine-id {
         type string;
         description "Engine ID";
       }
     }
     list snmp-v3-usm-user {
       leaf user-name {
         type string;
         description "User name";
       }
       leaf auth-type {
         type string;
         description "Type of authentication required by this user";
       }
       leaf priv-type {
         type string;
         description "Type of encryption required by this user";
       }
       leaf storage-type {
         type string;
         description "Type of storage for this entry";
       }
       leaf row-status {
         type string;
         description "Status for this entry";
       }
     }
   }
   container snmp-v3-group-information {
     list snmp-v3-group {
       leaf group-name {
         type string;
         description "Group name";
       }
       leaf security-model {
         type string;
         description "Security model";
       }
       leaf security-name {
         type string;
         description "Security name";
       }
       leaf storage-type {
         type string;
         description "Type of storage for this entry";
       }
       leaf row-status {
         type string;
         description "Status for this entry";
       }
     }
   }
   container snmp-v3-access-information {
     container brief {
       list snmp-v3-access {
         leaf group-name {
           type string;
           description "Group name";
         }
         leaf context-prefix {
           type string;
           description "Context prefix";
         }
         leaf security-model {
           type string;
           description "Security model";
         }
         leaf security-level {
           type string;
           description "Security level";
         }
         leaf read-view {
           type string;
           description "MIB view allowed for read access";
         }
         leaf write-view {
           type string;
           description "MIB view allowed for write access";
         }
         leaf notify-view {
           type string;
           description "MIB view allowed for notifications";
         }
         leaf row-status {
           type string;
           description "Status for this entry";
         }
       }
     }
     container verbose {
       list snmp-v3-access {
         leaf group-name {
           type string;
           description "Group name";
         }
         leaf context-prefix {
           type string;
           description "Context prefix";
         }
         leaf security-model {
           type string;
           description "Security model";
         }
         leaf security-level {
           type string;
           description "Security level";
         }
         leaf context-match {
           type string;
         }
         leaf read-view {
           type string;
           description "MIB view allowed for read access";
         }
         leaf write-view {
           type string;
           description "MIB view allowed for write access";
         }
         leaf notify-view {
           type string;
           description "MIB view allowed for notifications";
         }
         leaf storage-type {
           type string;
           description "Type of storage for this entry";
         }
         leaf row-status {
           type string;
           description "Status for this entry";
         }
       }
     }
   }
   container snmp-v3-target-information {
     container snmp-v3-target-address-information {
       description "SNMPv3 target address information";
       list snmp-v3-target_address {
         description "SNMPv3 target address";
         leaf target-address-name {
           type string;
           description "Target address name in target address table";
         }
         leaf address {
           type string;
           description "Target address";
         }
         leaf port {
           type string;
           description "Target port number";
         }
         leaf target-parameters-name {
           type string;
           description "Target parameters name";
         }
         leaf storage-type {
           type string;
           description "Type of storage for this entry";
         }
         leaf row-status {
           type string;
           description "Status for this entry";
         }
       }
     }
     container snmp-v3-target-parameters-information {
       description "SNMPv3 target parameters information";
       list snmp-v3-target_parameters {
         description "SNMPv3 target parameters";
         leaf target-parameters-name {
           type string;
           description "Target parameters name";
         }
         leaf security-name {
           type string;
           description "Security name";
         }
         leaf security-model {
           type string;
           description "Security model";
         }
         leaf security-level {
           type string;
           description "Security level";
         }
         leaf notify-filter-name {
           type string;
           description "Notify filter name in the notify filter table";
         }
         leaf storage-type {
           type string;
           description "Type of storage for this entry";
         }
         leaf row-status {
           type string;
           description "Status for this entry";
         }
       }
     }
   }
   container snmp-v3-notify-information {
     description "SNMPv3 notify information";
     list snmp-v3-notify {
       description "SNMPv3 notify";
       leaf notify-name {
         type string;
         description "Notify name";
       }
       leaf notify-tag {
         type string;
         description "Notify tag used to identify all acceptable targets";
       }
       leaf notify-type {
         type string;
       }
       leaf storage-type {
         type string;
         description "Type of storage for this entry";
       }
       leaf row-status {
         type string;
         description "Status for this entry";
       }
     }
   }
   container snmp-v3-notify-filter-information {
     description "SNMPv3 notify filter information";
     list snmp-v3-notify-filter {
       description "SNMPv3 notify filter";
       leaf filter-name {
         type string;
         description "Notify filter name";
       }
       leaf subtree {
         type string;
         description "MIB subtree for this filter";
       }
       leaf filter-type {
         type string;
       }
       leaf storage-type {
         type string;
         description "Type of storage for this entry";
       }
       leaf row-status {
         type string;
         description "Status for this entry";
       }
     }
   }
   container snmp-v3-community-information {
     description "SNMPv3 community information";
     list snmp-v3-community {
       description "SNMPv3 community";
       leaf community-index {
         type string;
         description "Community index in this community table entry";
       }
       leaf security-name {
         type string;
         description "Security name";
       }
       leaf context-name {
         type string;
         description "Context name used when performing access control";
       }
       leaf transport-tag {
         type string;
         description "Transport tag used to identify a set of targets";
       }
       leaf storage-type {
         type string;
         description "Type of storage for this entry";
       }
       leaf row-status {
         type string;
         description "Status for this entry";
       }
     }
   }
 }
 grouping snmp-v3-general-information-block {
   list snmp-v3-engine-information {
     leaf engine-id {
       type string;
       description "Engine ID";
     }
     leaf engine-boots {
       type int32;
       description "Number of times this engine has booted";
     }
     leaf engine-time {
       type int32;
       description "Number of seconds since this engine has booted";
     }
     leaf max-msg-size {
       type int32;
       description "Maximum message size allowed by this engine";
     }
   }
 }
 grouping snmp-v3-group-information-block {
   list snmp-v3-group {
     leaf group-name {
       type string;
       description "Group name";
     }
     leaf security-model {
       type string;
       description "Security model";
     }
     leaf security-name {
       type string;
       description "Security name";
     }
     leaf storage-type {
       type string;
       description "Type of storage for this entry";
     }
     leaf row-status {
       type string;
       description "Status for this entry";
     }
   }
 }
 grouping snmp-v3-usm-user-information-block {
   container snmp-v3-usm-user-engine-id {
     leaf user-engine-id {
       type string;
       description "Engine ID";
     }
   }
   list snmp-v3-usm-user {
     leaf user-name {
       type string;
       description "User name";
     }
     leaf auth-type {
       type string;
       description "Type of authentication required by this user";
     }
     leaf priv-type {
       type string;
       description "Type of encryption required by this user";
     }
     leaf storage-type {
       type string;
       description "Type of storage for this entry";
     }
     leaf row-status {
       type string;
       description "Status for this entry";
     }
   }
 }
 grouping snmp-v3-access-information-block {
   container brief {
     list snmp-v3-access {
       leaf group-name {
         type string;
         description "Group name";
       }
       leaf context-prefix {
         type string;
         description "Context prefix";
       }
       leaf security-model {
         type string;
         description "Security model";
       }
       leaf security-level {
         type string;
         description "Security level";
       }
       leaf read-view {
         type string;
         description "MIB view allowed for read access";
       }
       leaf write-view {
         type string;
         description "MIB view allowed for write access";
       }
       leaf notify-view {
         type string;
         description "MIB view allowed for notifications";
       }
       leaf row-status {
         type string;
         description "Status for this entry";
       }
     }
   }
   container verbose {
     list snmp-v3-access {
       leaf group-name {
         type string;
         description "Group name";
       }
       leaf context-prefix {
         type string;
         description "Context prefix";
       }
       leaf security-model {
         type string;
         description "Security model";
       }
       leaf security-level {
         type string;
         description "Security level";
       }
       leaf context-match {
         type string;
       }
       leaf read-view {
         type string;
         description "MIB view allowed for read access";
       }
       leaf write-view {
         type string;
         description "MIB view allowed for write access";
       }
       leaf notify-view {
         type string;
         description "MIB view allowed for notifications";
       }
       leaf storage-type {
         type string;
         description "Type of storage for this entry";
       }
       leaf row-status {
         type string;
         description "Status for this entry";
       }
     }
   }
 }
 grouping snmp-v3-community-information-block {
   list snmp-v3-community {
     description "SNMPv3 community";
     leaf community-index {
       type string;
       description "Community index in this community table entry";
     }
     leaf security-name {
       type string;
       description "Security name";
     }
     leaf context-name {
       type string;
       description "Context name used when performing access control";
     }
     leaf transport-tag {
       type string;
       description "Transport tag used to identify a set of targets";
     }
     leaf storage-type {
       type string;
       description "Type of storage for this entry";
     }
     leaf row-status {
       type string;
       description "Status for this entry";
     }
   }
 }
 grouping snmp-v3-target-information-block {
   container snmp-v3-target-address-information {
     description "SNMPv3 target address information";
     list snmp-v3-target_address {
       description "SNMPv3 target address";
       leaf target-address-name {
         type string;
         description "Target address name in target address table";
       }
       leaf address {
         type string;
         description "Target address";
       }
       leaf port {
         type string;
         description "Target port number";
       }
       leaf target-parameters-name {
         type string;
         description "Target parameters name";
       }
       leaf storage-type {
         type string;
         description "Type of storage for this entry";
       }
       leaf row-status {
         type string;
         description "Status for this entry";
       }
     }
   }
   container snmp-v3-target-parameters-information {
     description "SNMPv3 target parameters information";
     list snmp-v3-target_parameters {
       description "SNMPv3 target parameters";
       leaf target-parameters-name {
         type string;
         description "Target parameters name";
       }
       leaf security-name {
         type string;
         description "Security name";
       }
       leaf security-model {
         type string;
         description "Security model";
       }
       leaf security-level {
         type string;
         description "Security level";
       }
       leaf notify-filter-name {
         type string;
         description "Notify filter name in the notify filter table";
       }
       leaf storage-type {
         type string;
         description "Type of storage for this entry";
       }
       leaf row-status {
         type string;
         description "Status for this entry";
       }
     }
   }
 }
 grouping snmp-v3-target-address-information-block {
   list snmp-v3-target_address {
     description "SNMPv3 target address";
     leaf target-address-name {
       type string;
       description "Target address name in target address table";
     }
     leaf address {
       type string;
       description "Target address";
     }
     leaf port {
       type string;
       description "Target port number";
     }
     leaf target-parameters-name {
       type string;
       description "Target parameters name";
     }
     leaf storage-type {
       type string;
       description "Type of storage for this entry";
     }
     leaf row-status {
       type string;
       description "Status for this entry";
     }
   }
 }
 grouping snmp-v3-target-parameters-information-block {
   list snmp-v3-target_parameters {
     description "SNMPv3 target parameters";
     leaf target-parameters-name {
       type string;
       description "Target parameters name";
     }
     leaf security-name {
       type string;
       description "Security name";
     }
     leaf security-model {
       type string;
       description "Security model";
     }
     leaf security-level {
       type string;
       description "Security level";
     }
     leaf notify-filter-name {
       type string;
       description "Notify filter name in the notify filter table";
     }
     leaf storage-type {
       type string;
       description "Type of storage for this entry";
     }
     leaf row-status {
       type string;
       description "Status for this entry";
     }
   }
 }
 grouping snmp-v3-notify-information-block {
   list snmp-v3-notify {
     description "SNMPv3 notify";
     leaf notify-name {
       type string;
       description "Notify name";
     }
     leaf notify-tag {
       type string;
       description "Notify tag used to identify all acceptable targets";
     }
     leaf notify-type {
       type string;
     }
     leaf storage-type {
       type string;
       description "Type of storage for this entry";
     }
     leaf row-status {
       type string;
       description "Status for this entry";
     }
   }
 }
 grouping snmp-v3-notify-filter-information-block {
   list snmp-v3-notify-filter {
     description "SNMPv3 notify filter";
     leaf filter-name {
       type string;
       description "Notify filter name";
     }
     leaf subtree {
       type string;
       description "MIB subtree for this filter";
     }
     leaf filter-type {
       type string;
     }
     leaf storage-type {
       type string;
       description "Type of storage for this entry";
     }
     leaf row-status {
       type string;
       description "Status for this entry";
     }
   }
 }
 grouping snmp-inform-statistics-block {
   list inform-stats-entry {
     leaf target-name {
       type string;
       description "Name of the target (receiver of Inform requests)";
     }
     leaf target-address {
       type ipaddr;
       description "Target address";
     }
     leaf informs-sent {
       type int32;
       description "Total number of Inform requests sent successfully";
     }
     leaf informs-pending {
       type int32;
       description "Number of Inform requests sent but not yet acknowledged";
     }
     leaf informs-discarded {
       type int32;
       description "Number of Inform requests discarded because no acknowledgment was received";
     }
     leaf inform-timeouts {
       type int32;
       description "Number of Inform requests that timed out";
     }
     leaf inform-probe-failures {
       type int32;
       description "Number of remote engine ID discovery probes that failed";
     }
   }
 }
 grouping snmp-proxy-information-block {
   list snmp-proxy {
     description "SNMP proxy";
     leaf proxy-name {
       type string;
       description "Proxy name in this proxy table entry";
     }
     leaf device-name {
       type string;
       description "Satellite Device name associated to this Proxy";
     }
     leaf version {
       type string;
       description "Version";
     }
     leaf community-or-security-name {
       type string;
       description "Community Or Security Name associated to this Proxy";
     }
     leaf context {
       type string;
       description "Context associated to this Proxy";
     }
     leaf routing-instance {
       type string;
       description "Routing Instance associated to this Proxy";
     }
   }
 }
 }
