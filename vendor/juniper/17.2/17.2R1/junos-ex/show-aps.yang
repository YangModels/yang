/*
 * Copyright (c) 2017 Juniper Networks, Inc.
 * All rights reserved.
 */
 module show-aps {
  namespace "http://yang.juniper.net/yang/1.1/jrpc/show-aps/junos-ex/17.2R1.13";
  prefix show-aps;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-aps-information {
     description "Show Automatic Protection Switching information";
     input {
       leaf level {
         default "brief";
         type enumeration {
           enum "brief" {
             description "Display brief output (default)";
           }
           enum "detail" {
             description "Display detailed output";
           }
           enum "extensive" {
             description "Display extensive output";
           }
           enum "summary" {
             description "Display summary output";
           }
         }
       }
     }
     output {
       container aps-interface-information {
         uses aps-interface-information-block;
       }
     }
   }
   rpc get-aps-interface-information {
     description "Show an APS interface";
     input {
       leaf intf_name {
         description "Interface name";
         type string;
         mandatory true;
       }
     }
     output {
       container aps-interface-information {
         uses aps-interface-information-block;
       }
     }
   }
   rpc get-aps-group-information {
     description "Show an APS group";
     input {
       leaf group_name {
         description "Group name";
         type string;
         mandatory true;
       }
     }
     output {
       container aps-interface-information {
         uses aps-interface-information-block;
       }
     }
   }
 grouping aps-interface-information-block {
   container aps-interface {
     description "Information about an Automatic Protection Switching interface";
     container summary {
       description "Information about an Automatic Protection Switching interface";
       leaf aps-interface-name {
         type string;
         description "Name of the interface";
       }
       leaf aps-interface-group {
         type string;
         description "Name of the interface group";
       }
       leaf aps-interface-circuit-type {
         type string;
         description "Type of the circuit";
       }
       leaf aps-interface-circuit-state {
         type string;
         description "State of the circuit";
       }
       leaf aps-interface-state {
         type string;
         description "State of the interface";
       }
     }
     container brief {
       description "Information about an Automatic Protection Switching interface";
       leaf aps-interface-name {
         type string;
         description "Name of the interface";
       }
       leaf aps-interface-group {
         type string;
         description "Name of the interface group";
       }
       leaf aps-interface-circuit-type {
         type string;
         description "Type of the circuit";
       }
       leaf aps-interface-circuit-state {
         type string;
         description "State of the circuit";
       }
       leaf aps-interface-state {
         type string;
         description "State of the interface";
       }
     }
     container detail {
       description "Information about an Automatic Protection Switching interface";
       leaf aps-interface-name {
         type string;
         description "Name of the interface";
       }
       leaf aps-interface-group {
         type string;
         description "Name of the interface group";
       }
       leaf aps-interface-circuit-type {
         type string;
         description "Type of the circuit";
       }
       leaf aps-interface-circuit-state {
         type string;
         description "State of the circuit";
       }
       leaf aps-interface-state {
         type string;
         description "State of the interface";
       }
       leaf aps-neighbor {
         type string;
         description "Neighbor address";
       }
       leaf aps-adjacent-state {
         type string;
         description "Adjacent state";
       }
       leaf aps-neighbor-select-state {
         type string;
         description "Neighbor interface state";
       }
       leaf aps-time-remaining {
         type string;
         description "Remaining time";
       }
     }
     container extensive {
       description "Information about an Automatic Protection Switching interface";
       leaf aps-interface-name {
         type string;
         description "Name of the interface";
       }
       leaf aps-interface-group {
         type string;
         description "Name of the interface group";
       }
       leaf aps-interface-circuit-type {
         type string;
         description "Type of the circuit";
       }
       leaf aps-interface-circuit-state {
         type string;
         description "State of the circuit";
       }
       leaf aps-interface-state {
         type string;
         description "State of the interface";
       }
       leaf aps-neighbor {
         type string;
         description "Neighbor address";
       }
       leaf aps-adjacent-state {
         type string;
         description "Adjacent state";
       }
       leaf aps-neighbor-select-state {
         type string;
         description "Neighbor interface state";
       }
       leaf aps-time-remaining {
         type string;
         description "Remaining time";
       }
       leaf aps-channel-state {
         type string;
         description "State of the channel";
       }
       leaf aps-annex-b {
         type string;
         description "Annex-b mode";
       }
       leaf aps-loop-circuit-type {
         type string;
         description "Loop circuit type";
       }
       leaf aps-loop-circuit-name {
         type string;
         description "Loop circuit name";
       }
       leaf aps-pair-interface-name {
         type string;
         description "Paired interface name";
       }
       leaf aps-pair-group-name {
         type string;
         description "Paired group name";
       }
       leaf aps-local-mode {
         type string;
         description "APS local mode";
       }
       leaf aps-neighbor-mode {
         type string;
         description "APS neighbor mode";
       }
       leaf aps-request-k1 {
         type string;
         description "Request K1 value";
       }
       leaf aps-receive-k1 {
         type string;
         description "Receive K1 value";
       }
       leaf aps-transmit-k1 {
         type string;
         description "Transmit K1 value";
       }
       leaf aps-neighbor-k1 {
         type string;
         description "Neighbor K1 value";
       }
       leaf aps-request-k2 {
         type string;
         description "Request K2 value";
       }
       leaf aps-receive-k2 {
         type string;
         description "Receive K2 value";
       }
       leaf aps-transmit-k2 {
         type string;
         description "Transmit K2 value";
       }
       leaf aps-neighbor-paired-request {
         type string;
         description "Neighbor paired switch request";
       }
       leaf aps-revert-time {
         type string;
         description "APS revert time";
       }
       leaf aps-neighbor-revert-time {
         type string;
         description "Neighbor revert time";
       }
       leaf aps-wait-to-restore-time {
         type string;
         description "APS annex-b wait to restore time";
       }
       leaf aps-neighbor-wait-to-restore-time {
         type string;
         description "APS annex-b neighbor wait to restore time";
       }
       leaf aps-remaining-revert-time {
         type string;
         description "Remaining revert time";
       }
       leaf aps-remaining-wait-to-restore-time {
         type string;
         description "Remaining wait to restore time";
       }
       leaf aps-remaining-forced-revert-time {
         type string;
         description "Remaining forced revert time";
       }
       leaf aps-remaining-hello-timer {
         type string;
         description "Remaining hello timer";
       }
       leaf aps-remaining-update-timer {
         type string;
         description "Remaining update timer";
       }
       leaf aps-remaining-holddown-timer {
         type string;
         description "Remaining holddown timer";
       }
     }
   }
 }
 }
