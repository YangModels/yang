/*
 * Copyright (c) 2017 Juniper Networks, Inc.
 * All rights reserved.
 */
 module show-services {
  namespace "http://yang.juniper.net/yang/1.1/jrpc/show-services/junos-ex/17.2R1.13";
  prefix show-services;

  import junos-extension {
    prefix junos;
  }

  organization
    "Juniper Networks, Inc.";

  description
    "Junos YANG module for RPC";


revision 2017-01-01 {
  description
    "Junos YANG module for RPC."; 
}
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-probe-results {
     description "Show probe results";
     input {
       leaf owner {
         description "Name of owner";
         type string {
           length "1 .. 32";
         }
       }
       leaf test {
         description "Name of test";
         type string {
           length "1 .. 32";
         }
       }
     }
     output {
       container probe-results {
         uses probe-results-block;
       }
     }
   }
   rpc get-history-results {
     description "Show history results";
     input {
       leaf verbosity_level {
         default "brief";
         type enumeration {
           enum "brief" {
             description "Display brief output (default)";
           }
           enum "detail" {
             description "Display detailed output";
           }
         }
       }
       leaf owner {
         description "Name of owner";
         type string {
           length "1 .. 32";
         }
       }
       leaf test {
         description "Name of test";
         type string {
           length "1 .. 32";
         }
       }
       leaf since {
         description "Show history since YYYY-MM-DD.HH:MM:SS";
         type time;
       }
     }
     output {
       container history-results {
         uses history-results-block;
       }
     }
   }
   rpc get-active-servers {
     description "Show configured servers";
     output {
       container active-servers {
         uses active-servers-block;
       }
     }
   }
   rpc get-pcef-subscribers {
     description "Show subscriber information";
     input {
       leaf address {
         description "IPv4 or IPv6 address of subscriber";
         type string;
       }
       leaf interface {
         description "Interface name, or with wildcards (e.g. fe-0/0/*, fe-0/*/*)";
         type interface-wildcard;
       }
       leaf physical-interface {
         description "Physical Interface name";
         type interface-wildcard;
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type uint16 {
           range "0 .. 4094";
         }
       }
       leaf vlan-id {
         description "VLAN identifier of subscriber";
         type uint16 {
           range "0 .. 4094";
         }
       }
       leaf vpi {
         description "ATM VPI of subscriber";
         type uint16 {
           range "0 .. 255";
         }
       }
       leaf vci {
         description "ATM VCI of subscriber";
         type uint16 {
           range "0 .. 65535";
         }
       }
       leaf id {
         description "Identifier of subscriber";
         type string;
       }
       leaf mac-address {
         description "MAC address of subscriber";
         type mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
   }
   rpc get-pcef-subscribers-summary {
     description "Display pcef subscriber summary";
     input {
       leaf logical-system {
         description "Display summary for specified logical system";
         type string;
       }
       leaf routing-instance {
         description "Display summary for specified routing instance";
         type string;
       }
       leaf physical-interface {
         description "Physical Interface name";
         type interface-wildcard;
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
   }
   rpc get-pcef-pic {
     description "Show physical interface card information";
     input {
       leaf fpc-slot {
         description "FPC slot number";
         type uint32 {
           range "0 .. 63";
         }
       }
       leaf pic-slot {
         description "PIC slot number";
         type uint32 {
           range "0 .. 3";
         }
       }
       leaf display {
         default "terse";
         type enumeration {
           enum "terse" {
             description "Display terse output";
           }
         }
       }
     }
   }
   rpc get-uac-policies {
     description "Access policies from infranet controller";
     input {
       leaf detail {
         description "Display detail output";
         type empty;
       }
       leaf identifier {
         description "Show specified policy information";
         type string;
       }
     }
   }
   rpc get-uac-auth-table {
     description "Show authentication table configured from infranet controller";
     input {
       leaf detail {
         description "Display detail output";
         type empty;
       }
       leaf identifier {
         description "Show specified authentication entry";
         type string;
       }
       leaf extended {
         description "Show authentication entries with all roles";
         type empty;
       }
       leaf role {
         description "Show authentication entries matching the role";
         type string;
       }
       leaf ip {
         description "Show authentication entries matching the ip";
         type string;
       }
       leaf user {
         description "Show authentication entries matching the user";
         type string;
       }
     }
   }
   rpc get-uac-status {
     description "Show connection status with infranet controller";
   }
   rpc get-uac-counters {
     description "Show unified access control(uac) service related counters";
     output {
       container uac-counters {
         uses uac-counters-block;
       }
     }
   }
   rpc get-fips-pic-status-information {
     description "Show FIPS PIC authorization status";
     output {
       container fips-pic-status-information {
         uses fips-pic-status-information-block;
       }
     }
   }
   rpc get-service-mss-sessions-information {
     description "Show mobile subscriber data sessions";
     input {
       leaf imsi {
         description "IMSI of subscriber";
         type string {
           length "5 .. 15";
         }
       }
     }
   }
   rpc get-service-hcm-sessions-stats {
     description "Show hcm session statistics";
     input {
       leaf imsi {
         description "IMSI of subscriber";
         type string {
           length "5 .. 15";
         }
         mandatory true;
       }
     }
   }
   rpc get-service-tdf-sessions-information {
     description "Show traffic-detection-function subscriber data sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-tdf-hcm-sessions-stats {
     description "Show hcm session statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-global-pcp-statistics-information {
     description "Show global PCP statistics";
     input {
       leaf interface {
         description "Name of adaptive services interface";
         type string;
       }
       leaf level {
         type enumeration {
           enum "protocol" {
             description "Display PCP protocol statistics";
           }
         }
       }
     }
   }
 grouping probe-results-block {
   list probe-test-results {
     leaf owner {
       type string;
       description "Test owner name";
     }
     leaf test-name {
       type string;
       description "Name of test";
     }
     leaf target-address {
       type string;
       description "Target address of test";
     }
     leaf target-url {
       type string;
       description "Target URL of test";
     }
     leaf source-address {
       type string;
       description "Source address of test";
     }
     leaf probe-type {
       type string;
       description "Name of the probe";
     }
     leaf icmp-id {
       type uint32;
       description "Icmp id for icmp-ping probes";
     }
     leaf test-size {
       type uint32;
       description "Number of probes in test";
     }
     leaf server-address {
       type ipaddr;
       description "Server address";
     }
     leaf server-port {
       type uint32;
       description "Server port";
     }
     leaf client-address {
       type ipaddr;
       description "Client address";
     }
     leaf client-port {
       type uint32;
       description "Client port";
     }
     leaf reflector-address {
       type ipaddr;
       description "Reflector address";
     }
     leaf reflector-port {
       type uint32;
       description "Reflector port";
     }
     leaf sender-address {
       type ipaddr;
       description "Sender address";
     }
     leaf sender-port {
       type uint32;
       description "Sender port";
     }
     leaf routing-instance-name {
       type string;
       description "Routing Instance Name";
     }
     leaf destination-interface {
       type string;
       description "Name of output interface for probes";
     }
     leaf http-status {
       type uint32;
       description "HTTP Status Code";
     }
     container probe-single-results {
       leaf probe-sent-time {
         type string;
         description "Time at which probe was sent";
       }
       leaf probe-status {
         type string;
         description "Operation response status from probes";
       }
       leaf probe-time {
         type string;
         description "Time at which probe response was received or timed out";
       }
       leaf hardware-timestamp-status {
         type string;
         description "Use of hardware timestamps in probes";
       }
       leaf rtt {
         type uint32;
         description "Round trip time of probes";
       }
       leaf ingress {
         type uint32;
         description "Ingress trip time of probes";
       }
       leaf egress {
         type uint32;
         description "Egress trip time of probes";
       }
       leaf egress-jitter {
         type int32;
         description "Egress jitter of probes";
       }
       leaf ingress-jitter {
         type int32;
         description "Ingress jitter of probes";
       }
       leaf round-trip-jitter {
         type int32;
         description "Round trip jitter of probes";
       }
       leaf egress-interarrival-jitter {
         type int32;
         description "Egress interarrival jitter of probes";
       }
       leaf ingress-interarrival-jitter {
         type int32;
         description "Ingress interarrival jitter of probes";
       }
       leaf round-trip-interarrival-jitter {
         type int32;
         description "Round trip interarrival jitter of probes";
       }
       container verbose {
       }
       container brief {
         leaf owner {
           type string;
           description "Test owner name";
         }
         leaf test-name {
           type string;
           description "Name of test";
         }
         leaf probe-sent-time {
           type string;
           description "Time at which probe was sent";
         }
         leaf probe-time {
           type string;
           description "Time at which probe response was received or timed out";
         }
         leaf rtt {
           type uint32;
           description "Round trip time of probes";
         }
         leaf probe-status {
           type string;
           description "Operation response status from probes";
         }
       }
     }
     container probe-test-current-results {
       container probe-test-generic-results {
         leaf results-scope {
           type string;
           description "Scope of results";
         }
         leaf probes-sent {
           type uint32;
           description "Number of probes sent";
         }
         leaf probe-responses {
           type uint32;
           description "Responses from probes";
         }
         leaf loss-percentage {
           type string;
           description "Percentage of probes lost (no response)";
         }
         container probe-last-test-info {
           leaf last-test-time {
             type string;
             description "Time at which last test was completed";
           }
         }
         container probe-test-rtt {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-egress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-ingress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
       }
     }
     container probe-last-test-results {
       container probe-test-generic-results {
         leaf results-scope {
           type string;
           description "Scope of results";
         }
         leaf probes-sent {
           type uint32;
           description "Number of probes sent";
         }
         leaf probe-responses {
           type uint32;
           description "Responses from probes";
         }
         leaf loss-percentage {
           type string;
           description "Percentage of probes lost (no response)";
         }
         container probe-last-test-info {
           leaf last-test-time {
             type string;
             description "Time at which last test was completed";
           }
         }
         container probe-test-rtt {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-egress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-ingress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
       }
     }
     container probe-test-moving-results {
       container probe-test-generic-results {
         leaf results-scope {
           type string;
           description "Scope of results";
         }
         leaf probes-sent {
           type uint32;
           description "Number of probes sent";
         }
         leaf probe-responses {
           type uint32;
           description "Responses from probes";
         }
         leaf loss-percentage {
           type string;
           description "Percentage of probes lost (no response)";
         }
         container probe-last-test-info {
           leaf last-test-time {
             type string;
             description "Time at which last test was completed";
           }
         }
         container probe-test-rtt {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-egress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-ingress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
       }
     }
     container probe-test-global-results {
       container probe-test-generic-results {
         leaf results-scope {
           type string;
           description "Scope of results";
         }
         leaf probes-sent {
           type uint32;
           description "Number of probes sent";
         }
         leaf probe-responses {
           type uint32;
           description "Responses from probes";
         }
         leaf loss-percentage {
           type string;
           description "Percentage of probes lost (no response)";
         }
         container probe-last-test-info {
           leaf last-test-time {
             type string;
             description "Time at which last test was completed";
           }
         }
         container probe-test-rtt {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-egress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-ingress {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-egress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-ingress-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-positive-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
         container probe-test-negative-round-trip-jitter {
           container probe-summary-results {
             leaf probe-results-type {
               type string;
               description "Results type";
             }
             leaf samples {
               type uint32;
               description "Number of samples";
             }
             leaf min-delay {
               type uint32;
               description "Minimum delay time";
             }
             leaf max-delay {
               type uint32;
               description "Maximum delay time";
             }
             leaf avg-delay {
               type uint32;
               description "Average delay time";
             }
             leaf jitter-delay {
               type uint32;
               description "Difference between maximum and minimum delay times";
             }
             leaf stddev-delay {
               type uint64;
               description "Standard deviation of delay time";
             }
             leaf sum-delay {
               type uint64;
               description "Sum of delay times";
             }
           }
         }
       }
     }
     container probe-test-hwts-err-stats {
       leaf invalid-client-recv-ts-cntr {
         type uint32;
         description "Client recv timestamp less than Client send timestamp";
       }
       leaf invalid-server-send-ts-cntr {
         type uint32;
         description "Server send timestamp less than Server recv timestamp";
       }
       leaf invalid-server-spent-time-cntr {
         type uint32;
         description "Server side spent time greater than RTT";
       }
     }
   }
 }
 grouping history-results-block {
   list history-test-results {
     list verbose {
       leaf owner {
         type string;
         description "Test owner name";
       }
       leaf test-name {
         type string;
         description "Name of test";
       }
       leaf probe-type {
         type string;
         description "Name of the probe";
       }
       leaf icmp-id {
         type uint32;
         description "Icmp id for icmp-ping probes";
       }
       leaf target-address {
         type string;
         description "Target address of test";
       }
       leaf target-url {
         type string;
         description "Target URL of test";
       }
       leaf source-address {
         type string;
         description "Source address of test";
       }
       leaf destination-interface {
         type string;
         description "Name of output interface for probes";
       }
       leaf loss-thresh-total {
         type uint32;
         description "Maximum number of all lost probes";
       }
       leaf loss-thresh-succ {
         type uint32;
         description "Maximum number of successive lost probes";
       }
       leaf delay-thresh {
         type uint32;
         description "Maximum delay threshold";
       }
       leaf jitter-thresh {
         type uint32;
         description "Maximum jitter threshold";
       }
       leaf stddev-thresh {
         type uint32;
         description "Maximum standard deviation threshold";
       }
       leaf egress-thresh {
         type uint32;
         description "Maximum egress delay threshold";
       }
       leaf egress-jitter-thresh {
         type uint32;
         description "Maximum egress jitter threshold";
       }
       leaf ingress-thresh {
         type uint32;
         description "Maximum ingress delay threshold";
       }
       leaf ingress-jitter-thresh {
         type uint32;
         description "Maximum ingress jitter threshold";
       }
       container probe-single-results {
         container brief {
           leaf probe-sent-time {
             type string;
             description "Time at which probe was sent";
           }
           leaf probe-time {
             type string;
             description "Time at which probe response was received or timed out";
           }
           leaf rtt {
             type uint32;
             description "Round trip time of probes";
           }
           leaf probe-status {
             type string;
             description "Operation response status from probes";
           }
         }
       }
       container probe-test-current-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
         }
       }
     }
     list brief {
       container probe-single-results {
         container verbose {
           leaf probe-sent-time {
             type string;
             description "Time at which probe was sent";
           }
           leaf probe-status {
             type string;
             description "Operation response status from probes";
           }
           leaf probe-time {
             type string;
             description "Time at which probe response was received or timed out";
           }
           leaf hardware-timestamp-status {
             type string;
             description "Use of hardware timestamps in probes";
           }
           leaf http-status {
             type uint32;
             description "HTTP Status Code";
           }
           leaf rtt {
             type uint32;
             description "Round trip time of probes";
           }
           leaf ingress {
             type uint32;
             description "Ingress trip time of probes";
           }
           leaf egress {
             type uint32;
             description "Egress trip time of probes";
           }
           leaf egress-jitter {
             type int32;
             description "Egress jitter of probes";
           }
           leaf ingress-jitter {
             type int32;
             description "Ingress jitter of probes";
           }
           leaf round-trip-jitter {
             type int32;
             description "Round trip jitter of probes";
           }
           leaf egress-interarrival-jitter {
             type int32;
             description "Egress interarrival jitter of probes";
           }
           leaf ingress-interarrival-jitter {
             type int32;
             description "Ingress interarrival jitter of probes";
           }
           leaf round-trip-interarrival-jitter {
             type int32;
             description "Round trip interarrival jitter of probes";
           }
         }
         container brief {
           leaf owner {
             type string;
             description "Test owner name";
           }
           leaf test-name {
             type string;
             description "Name of test";
           }
           leaf probe-sent-time {
             type string;
             description "Time at which probe was sent";
           }
           leaf probe-time {
             type string;
             description "Time at which probe response was received or timed out";
           }
           leaf rtt {
             type uint32;
             description "Round trip time of probes";
           }
           leaf probe-status {
             type string;
             description "Operation response status from probes";
           }
         }
       }
       container probe-test-current-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
         }
       }
     }
   }
 }
 grouping active-servers-block {
   list configured-servers {
     leaf protocol {
       type string;
       description "Protocol";
     }
     leaf port {
       type uint32;
       description "Port";
     }
     leaf destination-interface {
       type string;
       description "Name of output interface for probes";
     }
   }
 }
 grouping uac-counters-block {
   list uac-counter {
     description "UAC counter for the PFE";
     leaf pfe-name {
       type string;
       description "PFE";
     }
     leaf allowed-policy-action {
       type uint32;
       description "Sessions allowed due to policy action";
     }
     leaf allowed-timeout-action {
       type uint32;
       description "Sessions allowed due to timeout action";
     }
     leaf denied-unauthenticated {
       type uint32;
       description "Sessions denied due to lack of authentication";
     }
     leaf denied-policy-action {
       type uint32;
       description "Sessions denied due to policy action";
     }
     leaf denied-policy-unmatched {
       type uint32;
       description "Sessions denied due to unmatched policy";
     }
     leaf denied-timeout-action {
       type uint32;
       description "Sessions denied due to timeout action";
     }
     leaf terminated-reevaluation {
       type uint32;
       description "Sessions terminated due to reevaluation";
     }
     leaf terminated-signout {
       type uint32;
       description "Sessions terminated due to user signout";
     }
     leaf auth-added {
       type uint32;
       description "Auth entry added to PFE";
     }
     leaf auth-deleted {
       type uint32;
       description "Auth entry deleted from PFE";
     }
     leaf current-auth-cnt {
       type uint32;
       description "UAC total auth count";
     }
   }
 }
 grouping fips-pic-status-information-block {
   list fips-pic-status {
     leaf fpc-slot {
       type int32;
       description "FPC slot";
     }
     leaf pic-slot {
       type int32;
       description "PIC slot";
     }
     leaf serial-number {
       type string;
       description "PIC serial number";
     }
     leaf authorization-status {
       type string;
       description "PIC authorization status";
     }
   }
 }
 }
