/*
 * Copyright (c) 2017 Juniper Networks, Inc.
 * All rights reserved.
 */
 module show-event-viewer {
  namespace "http://yang.juniper.net/yang/1.1/jrpc/show-event-viewer/junos-es/17.3R1.9";
  prefix show-event-viewer;

  import junos-extension {
    prefix junos;
  }

  organization
    "Juniper Networks, Inc.";

  description
    "Junos YANG module for RPC";


  revision 2017-01-01 {
    description
      "Junos YANG module for RPC."; 
  }
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-event-summary {
     description "Show syslog event";
     input {
       leaf syslogfile {
         description "Syslog file name filter";
         type string {
           junos:posix-pattern "![/ %]";
           junos:pattern-message "Must not contain '/', % or a space";
         }
       }
       leaf event-id {
         description "Event Id filter";
         type string {
           length "1 .. 256";
         }
       }
       leaf daemon-name {
         description "Daemon name filter";
         type string {
           length "1 .. 256";
         }
       }
       leaf event-description {
         description "Regular expression for description filter ";
         type string;
       }
       leaf start-time {
         description "Start time filter. Format is mm/dd/yyyy hour:min";
         type string {
           junos:posix-pattern "[0-9]{2}/[0-9]{2}/[0-9]{4} [0-9]{2}:[0-9]{2}";
           junos:pattern-message "Invalid start-time";
         }
       }
       leaf end-time {
         description "End time filter. Format is mm/dd/yyyy hour:min";
         type string {
           junos:posix-pattern "[0-9]{2}/[0-9]{2}/[0-9]{4} [0-9]{2}:[0-9]{2}";
           junos:pattern-message "Invalid start-time";
         }
       }
       leaf total-message-display {
         description "Number of messages displayed per page";
         default "25";
         type union {
           type string {
             pattern "<.*>";
           }
           type uint32 {
             range "1 .. 100";
           }
         }
       }
       leaf show-start-event {
         description "Requested event starting number";
         type union {
           type string {
             pattern "<.*>";
           }
           type uint32 {
             range "1 .. 4294967295";
           }
         }
       }
       leaf show-end-event {
         description "Requested event ending number";
         type union {
           type string {
             pattern "<.*>";
           }
           type uint32 {
             range "1 .. 4294967295";
           }
         }
       }
       leaf new-search {
         description "It is a new search";
         type empty;
       }
       leaf ignore-event-info {
         description "To suppress the details about event-id";
         type empty;
       }
       leaf output-file-name {
         description "File name where filtered messages are stored";
         type string {
           junos:posix-pattern "![/ %]";
           junos:pattern-message "Must not contain '/', % or a space";
         }
       }
     }
     output {
       leaf output {
         type string;
       }
     }
   }
 }
