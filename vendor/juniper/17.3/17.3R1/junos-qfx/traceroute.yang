/*
 * Copyright (c) 2017 Juniper Networks, Inc.
 * All rights reserved.
 */
 module traceroute {
  namespace "http://yang.juniper.net/yang/1.1/jrpc/traceroute/junos-qfx/17.3R1.9";
  prefix traceroute;

  import junos-extension {
    prefix junos;
  }

  organization
    "Juniper Networks, Inc.";

  description
    "Junos YANG module for RPC";


  revision 2017-01-01 {
    description
      "Junos YANG module for RPC."; 
  }
   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicast {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc traceroute {
     description "Trace route to remote host";
     input {
       leaf gateway {
         description "Address of router gateway to route through";
         type string;
       }
       leaf ttl {
         description "IP maximum time-to-live value (or IPv6 maximum hop-limit value)";
         type string;
       }
       leaf wait {
         description "Number of seconds to wait for response";
         units "seconds";
         type string;
       }
       leaf no-resolve {
         description "Don't attempt to print addresses symbolically";
         type empty;
       }
       leaf source {
         description "Source address to use in outgoing traceroute packets";
         type string;
       }
       leaf tos {
         description "IP type-of-service field (IPv4)";
         type union {
           type string {
             pattern "<.*>";
           }
           type int32 {
             range "0 .. 255";
           }
         }
       }
       leaf as-number-lookup {
         description "Look up AS numbers for each hop";
         type empty;
       }
       leaf bypass-routing {
         description "Bypass routing table, use specified interface";
         type empty;
       }
       leaf inet {
         description "Force traceroute to IPv4 destination";
         type empty;
       }
       leaf inet6 {
         description "Force traceroute to IPv6 destination";
         type empty;
       }
       leaf interface {
         description "Name of interface to use for outgoing traffic";
         type union {
           type interface-name;
           type string {
             pattern "<.*>";
           }
         }
       }
       leaf routing-instance {
         description "Name of routing instance for traceroute attempt";
         type string;
       }
       leaf vpn-interface {
         description "VPN interface for traceroute attempt";
         status deprecated;
         type union {
           type interface-name;
           type string {
             pattern "<.*>";
           }
         }
       }
       leaf propagate-ttl {
         description "Enable propagate-ttl for locally sourced RE traffic";
         type empty;
       }
       leaf host {
         description "Hostname or address of remote host";
         type string;
         mandatory true;
       }
       leaf port {
         description "Port for ssh connection (default is 22)";
         type union {
           type uint32;
           type string {
             pattern "<.*>";
           }
         }
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml traceroute-results;
         }
         case multichassis-tag {
           anyxml multi-routing-engine-results;
         }
       }
     }
   }
   rpc request-traceroute-overlay {
     description "Traceroute overlay path";
     input {
       leaf tunnel-type {
         description "Tunnel type";
         default "vxlan";
         type enumeration {
           enum "vxlan" {
             description "Vxlan tunnel-type";
           }
         }
       }
       leaf vni {
         description "Value of the vni that identifies the overlay segment";
         type union {
           type string {
             pattern "<.*>";
           }
           type uint32 {
             range "1 .. 16777215";
           }
         }
         mandatory true;
       }
       leaf tunnel-src {
         description "Source VTEP IP address";
         type ipv4addr;
         mandatory true;
       }
       leaf tunnel-dst {
         description "Remote VTEP IP address";
         type ipv4addr;
         mandatory true;
       }
       choice address {
         case mac {
           leaf mac {
             description "Validate MAC address";
             type mac-unicast;
           }
         }
       }
       leaf ttl {
         description "TTL to use in the OAM packets";
         default "255";
         type union {
           type string {
             pattern "<.*>";
           }
           type uint32 {
             range "1 .. 255";
           }
         }
       }
       leaf hash-input-interface {
         type union {
           type interface-device;
           type string {
             pattern "<.*>";
           }
         }
       }
       leaf hash-source-mac {
         type mac-unicast;
       }
       leaf hash-destination-mac {
         type mac-unicast;
       }
       leaf hash-protocol {
         type union {
           type string {
             pattern "<.*>";
           }
           type uint32 {
             range "1 .. 255";
           }
         }
       }
       leaf hash-source-address {
         type ipv4addr;
       }
       leaf hash-destination-address {
         type ipv4addr;
       }
       leaf hash-source-port {
         type union {
           type string {
             pattern "<.*>";
           }
           type uint32 {
             range "1 .. 65535";
           }
         }
       }
       leaf hash-destination-port {
         type union {
           type string {
             pattern "<.*>";
           }
           type uint32 {
             range "1 .. 65535";
           }
         }
       }
       leaf hash-vlan {
         type union {
           type string {
             pattern "<.*>";
           }
           type uint32 {
             range "1 .. 4094";
           }
         }
       }
     }
     output {
       leaf output {
         type string;
       }
     }
   }
   rpc traceroute-mpls-ldp {
     description "Trace FEC paths";
     input {
       leaf logical-system {
         description "Name of logical system";
         type string {
           junos:posix-pattern "^[a-zA-Z0-9_-]{1,63}$";
           junos:pattern-message "Logical-system name is a string consisting of up to 63 letters, numbers, dashes and underscores";
         }
       }
       leaf fec {
         description "IP address and optional prefix length of FEC";
         type ipprefix;
         mandatory true;
       }
       leaf retries {
         description "Number of times to resend probe";
         type union {
           type string {
             pattern "<.*>";
           }
           type uint8 {
             range "1 .. 9";
           }
         }
       }
       leaf source {
         description "Source address to use when sending probes";
         type ipv4addr;
       }
       leaf exp {
         description "Class-of-service to use when sending probes";
         type union {
           type string {
             pattern "<.*>";
           }
           type uint8 {
             range "0 .. 7";
           }
         }
       }
       leaf detail {
         description "Display detailed output";
         type empty;
       }
       leaf no-resolve {
         description "Don't attempt to print addresses symbolically";
         type empty;
       }
       leaf routing-instance {
         description "Name of routing instance for traceroute attempt";
         type string;
       }
       leaf ttl {
         description "Maximum time-to-live value";
         type union {
           type string {
             pattern "<.*>";
           }
           type uint8 {
             range "1 .. 255";
           }
         }
       }
       leaf wait {
         description "Number of seconds to wait before resending probe";
         type union {
           type string {
             pattern "<.*>";
           }
           type uint8 {
             range "5 .. 15";
           }
         }
       }
       leaf paths {
         description "Maximum number of paths to traverse";
         type union {
           type string {
             pattern "<.*>";
           }
           type uint8 {
             range "1 .. 255";
           }
         }
       }
       leaf update {
         description "Update database contents with traceroute results";
         type empty;
       }
       leaf fanout {
         description "Maximum number of nexthops to search per node";
         type union {
           type string {
             pattern "<.*>";
           }
           type uint8 {
             range "1 .. 64";
           }
         }
       }
       leaf destination {
         description "Destination address to use when sending probes";
         type ipv4addr;
       }
       leaf pipe-mode {
         description "Traces only the outermost FEC";
         type empty;
       }
     }
     output {
       choice output_c {
         case output-tag {
           leaf output {
             type string;
           }
         }
         case actual-tag {
           anyxml tracelsp;
         }
         case multichassis-tag {
           anyxml multi-routing-engine-results;
         }
       }
     }
   }
   rpc traceroute-mpls-bgp {
     description "Trace FEC paths";
     input {
       leaf logical-system {
         description "Name of logical system";
         type string {
           junos:posix-pattern "^[a-zA-Z0-9_-]{1,63}$";
           junos:pattern-message "Logical-system name is a string consisting of up to 63 letters, numbers, dashes and underscores";
         }
       }
       leaf fec {
         description "IP address and optional prefix length of FEC";
         type ipprefix;
         mandatory true;
       }
       leaf retries {
         description "Number of times to resend probe";
         type union {
           type string {
             pattern "<.*>";
           }
           type uint8 {
             range "1 .. 9";
           }
         }
       }
       leaf source {
         description "Source address to use when sending probes";
         type ipv4addr;
       }
       leaf exp {
         description "Class-of-service to use when sending probes";
         type union {
           type string {
             pattern "<.*>";
           }
           type uint8 {
             range "0 .. 7";
           }
         }
       }
       leaf detail {
         description "Display detailed output";
         type empty;
       }
       leaf no-resolve {
         description "Don't attempt to print addresses symbolically";
         type empty;
       }
       leaf routing-instance {
         description "Name of routing instance for traceroute attempt";
         type string;
       }
       leaf ttl {
         description "Maximum time-to-live value";
         type union {
           type string {
             pattern "<.*>";
           }
           type uint8 {
             range "1 .. 255";
           }
         }
       }
       leaf wait {
         description "Number of seconds to wait before resending probe";
         type union {
           type string {
             pattern "<.*>";
           }
           type uint8 {
             range "5 .. 15";
           }
         }
       }
       leaf paths {
         description "Maximum number of paths to traverse";
         type union {
           type string {
             pattern "<.*>";
           }
           type uint8 {
             range "1 .. 255";
           }
         }
       }
       leaf pipe-mode {
         description "Traces only the outermost FEC";
         type empty;
       }
       leaf fanout {
         description "Maximum number of nexthops to search per node";
         type union {
           type string {
             pattern "<.*>";
           }
           type uint8 {
             range "1 .. 64";
           }
         }
       }
       leaf destination {
         description "Destination address to use when sending probes";
         type ipv4addr;
       }
     }
     output {
       choice output_c {
         case output-tag {
           leaf output {
             type string;
           }
         }
         case actual-tag {
           anyxml tracelsp;
         }
         case multichassis-tag {
           anyxml multi-routing-engine-results;
         }
       }
     }
   }
   rpc traceroute-mpls-rsvp {
     description "Trace RSVP-signaled LSP paths";
     input {
       leaf logical-system {
         description "Name of logical system";
         type string {
           junos:posix-pattern "^[a-zA-Z0-9_-]{1,63}$";
           junos:pattern-message "Logical-system name is a string consisting of up to 63 letters, numbers, dashes and underscores";
         }
       }
       leaf lsp-name {
         description "Name of LSP";
         type string {
           length "1 .. 64";
         }
         mandatory true;
       }
       leaf egress {
         description "Request only a specific multipoint egress to respond";
         type ipv4addr;
       }
       leaf multipoint {
         description "Probe multipoint LSP";
         type empty;
       }
       leaf ttl {
         description "Maximum time-to-live value";
         type union {
           type string {
             pattern "<.*>";
           }
           type uint8 {
             range "1 .. 255";
           }
         }
       }
       leaf retries {
         description "Number of times to resend probe";
         type union {
           type string {
             pattern "<.*>";
           }
           type uint8 {
             range "1 .. 9";
           }
         }
       }
       leaf source {
         description "Source address to use when sending probes";
         type ipv4addr;
       }
       leaf exp {
         description "Class-of-service to use when sending probes";
         type union {
           type string {
             pattern "<.*>";
           }
           type uint8 {
             range "0 .. 7";
           }
         }
       }
       leaf detail {
         description "Display detailed output";
         type empty;
       }
       leaf no-resolve {
         description "Don't attempt to print addresses symbolically";
         type empty;
       }
       leaf routing-instance {
         description "Name of routing instance for traceroute attempt";
         type string;
       }
     }
     output {
       choice output_c {
         case output-tag {
           leaf output {
             type string;
           }
         }
         case actual-tag {
           anyxml tracelsp;
         }
         case multichassis-tag {
           anyxml multi-routing-engine-results;
         }
       }
     }
   }
   rpc traceroute-mpls-l2vpn {
     description "Trace L2vpn fec129";
     output {
       choice output_c {
         case output-tag {
           leaf output {
             type string;
           }
         }
         case actual-tag {
           anyxml tracepw;
         }
         case multichassis-tag {
           anyxml multi-routing-engine-results;
         }
       }
     }
   }
   rpc traceroute-mpls-mspw {
     description "Trace the Layer 2 VPN connection";
     input {
       leaf logical-system {
         description "Name of logical system";
         type string {
           junos:posix-pattern "^[a-zA-Z0-9_-]{1,63}$";
           junos:pattern-message "Logical-system name is a string consisting of up to 63 letters, numbers, dashes and underscores";
         }
       }
       leaf interface {
         description "Name of l2vpn fec129 interface";
         type string {
           length "1 .. 64";
         }
         mandatory true;
       }
       leaf ttl {
         description "Maximum time-to-live value";
         type union {
           type string {
             pattern "<.*>";
           }
           type uint8 {
             range "1 .. 255";
           }
         }
       }
       leaf retries {
         description "Number of times to resend probe";
         type union {
           type string {
             pattern "<.*>";
           }
           type uint8 {
             range "1 .. 9";
           }
         }
       }
       leaf source {
         description "Source address to use when sending probes";
         type ipv4addr;
       }
       leaf exp {
         description "Class-of-service to use when sending probes";
         type union {
           type string {
             pattern "<.*>";
           }
           type uint8 {
             range "0 .. 7";
           }
         }
       }
       leaf detail {
         description "Display detailed output";
         type empty;
       }
       leaf no-resolve {
         description "Don't attempt to print addresses symbolically";
         type empty;
       }
     }
     output {
       choice output_c {
         case output-tag {
           leaf output {
             type string;
           }
         }
         case actual-tag {
           anyxml tracelsp;
         }
         case multichassis-tag {
           anyxml multi-routing-engine-results;
         }
       }
     }
   }
   rpc request-traceroute-ethernet {
     description "Trace route to an ethernet host by unicast mac address";
     input {
       leaf ttl {
         description "Maximum time-to-live value";
         type union {
           type string {
             pattern "<.*>";
           }
           type int32 {
             range "1 .. 255";
           }
         }
       }
       leaf wait {
         description "Number of seconds to wait for response";
         units "seconds";
         type union {
           type string {
             pattern "<.*>";
           }
           type int32 {
             range "1 .. 255";
           }
         }
       }
       leaf maintenance-domain {
         description "Name of maintenance domain";
         type string {
           length "1 .. 45";
         }
         mandatory true;
       }
       leaf maintenance-association {
         description "Name of maintenance association";
         type string {
           length "1 .. 45";
         }
         mandatory true;
       }
       leaf host {
         description "MAC address of remote host in xx:xx:xx:xx:xx:xx format";
         type mac-unicast;
       }
       leaf mep {
         description "MEP identifier of remote host (default 1)";
         type union {
           type string {
             pattern "<.*>";
           }
           type int32 {
             range "1 .. 8191";
           }
         }
       }
       leaf local-mep {
         description "MEP identifier of local host";
         type union {
           type string {
             pattern "<.*>";
           }
           type int32 {
             range "1 .. 8191";
           }
         }
       }
       leaf priority {
         description "Frame priority (802.1p) value";
         type union {
           type string {
             pattern "<.*>";
           }
           type int32 {
             range "0 .. 7";
           }
         }
       }
       leaf verbosity {
         default "brief";
         type enumeration {
           enum "brief" {
             description "Display brief output";
           }
           enum "detail" {
             description "Display detail output";
           }
         }
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml ethtraceroute-results;
         }
         case multichassis-tag {
           anyxml multi-routing-engine-results;
         }
       }
     }
   }
 }
