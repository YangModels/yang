/*
 * Copyright (c) 2017 Juniper Networks, Inc.
 * All rights reserved.
 */

 module show-multi-chassis {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-mclag-config-consistency-information {
     description "Show all configuration consistency information";
     output {
       container multichassis-consistency-check-list {
         leaf multichassis-global {
           type string;
         }
         container multichassis-ifd-name {
         }
         container multichassis-ifl-name {
         }
         container multichassis-vlan-name {
         }
         container multichassis-irb-name {
         }
         container multichassis-vrrp-grp-id {
         }
         container multichassis-consistency-check-entry {
           leaf config-item {
             type string;
             description "Name of the Configuration Item";
           }
           leaf consistency-check {
             type string;
             description "Type of Consistency Check performed";
           }
           leaf local-value {
             type string;
             description "Configured value on the local MC-LAG node";
           }
           leaf peer-value {
             type string;
             description "Configured value on the peer MC-LAG node";
           }
           leaf result {
             type string;
             description "Result of Configuration Consistency Check";
           }
         }
       }
     }
   }
   rpc get-mclag-global-config-consistency-information {
     description "Configuration related to system-wide operations";
     output {
       container multichassis-consistency-check-list {
         leaf multichassis-global {
           type string;
         }
         container multichassis-ifd-name {
         }
         container multichassis-ifl-name {
         }
         container multichassis-vlan-name {
         }
         container multichassis-irb-name {
         }
         container multichassis-vrrp-grp-id {
         }
         container multichassis-consistency-check-entry {
           leaf config-item {
             type string;
             description "Name of the Configuration Item";
           }
           leaf consistency-check {
             type string;
             description "Type of Consistency Check performed";
           }
           leaf local-value {
             type string;
             description "Configured value on the local MC-LAG node";
           }
           leaf peer-value {
             type string;
             description "Configured value on the peer MC-LAG node";
           }
           leaf result {
             type string;
             description "Result of Configuration Consistency Check";
           }
         }
       }
     }
   }
   rpc get-mclag-icl-config-consistency-information {
     description "Configuration related to ICL";
     output {
       container multichassis-consistency-check-list {
         leaf multichassis-global {
           type string;
         }
         container multichassis-ifd-name {
         }
         container multichassis-ifl-name {
         }
         container multichassis-vlan-name {
         }
         container multichassis-irb-name {
         }
         container multichassis-vrrp-grp-id {
         }
         container multichassis-consistency-check-entry {
           leaf config-item {
             type string;
             description "Name of the Configuration Item";
           }
           leaf consistency-check {
             type string;
             description "Type of Consistency Check performed";
           }
           leaf local-value {
             type string;
             description "Configured value on the local MC-LAG node";
           }
           leaf peer-value {
             type string;
             description "Configured value on the peer MC-LAG node";
           }
           leaf result {
             type string;
             description "Result of Configuration Consistency Check";
           }
         }
       }
     }
   }
   rpc get-mclag-config-consistency-information-mcae {
     description "Configuration related to MCAE interfaces";
     output {
       container multichassis-consistency-check-list {
         leaf multichassis-global {
           type string;
         }
         container multichassis-ifd-name {
         }
         container multichassis-ifl-name {
         }
         container multichassis-vlan-name {
         }
         container multichassis-irb-name {
         }
         container multichassis-vrrp-grp-id {
         }
         container multichassis-consistency-check-entry {
           leaf config-item {
             type string;
             description "Name of the Configuration Item";
           }
           leaf consistency-check {
             type string;
             description "Type of Consistency Check performed";
           }
           leaf local-value {
             type string;
             description "Configured value on the local MC-LAG node";
           }
           leaf peer-value {
             type string;
             description "Configured value on the peer MC-LAG node";
           }
           leaf result {
             type string;
             description "Result of Configuration Consistency Check";
           }
         }
       }
     }
   }
   rpc get-mclag-vrrp-config-consistency-information {
     description "Configuration related to MCAE interfaces";
     output {
       container multichassis-consistency-check-list {
         leaf multichassis-global {
           type string;
         }
         container multichassis-ifd-name {
         }
         container multichassis-ifl-name {
         }
         container multichassis-vlan-name {
         }
         container multichassis-irb-name {
         }
         container multichassis-vrrp-grp-id {
         }
         container multichassis-consistency-check-entry {
           leaf config-item {
             type string;
             description "Name of the Configuration Item";
           }
           leaf consistency-check {
             type string;
             description "Type of Consistency Check performed";
           }
           leaf local-value {
             type string;
             description "Configured value on the local MC-LAG node";
           }
           leaf peer-value {
             type string;
             description "Configured value on the peer MC-LAG node";
           }
           leaf result {
             type string;
             description "Result of Configuration Consistency Check";
           }
         }
       }
     }
   }
   rpc get-mclag-config-consistency-information-params {
     description "Show list of configuration items checked for consistency";
     output {
       container multichassis-consistency-params-list {
         container multichassis-consistency-param-entry {
           leaf param-config-item {
             type string;
             description "Identifier of the Configuration Item";
           }
           leaf param-config-name {
             type string;
             description "Name of the Configuration Item";
           }
           leaf param-config-level {
             type string;
             description "Configuration Level of the Config Item";
           }
           leaf param-consistency-requirement {
             type string;
             description "Requirement to be Consistent";
           }
           leaf param-consistency-check {
             type string;
             description "Consistency Check Type for this Config";
           }
         }
       }
     }
   }
   rpc get-mclag-vlan-config-consistency-information {
     description "Configuration related to VLAN";
     output {
       container multichassis-consistency-check-list {
         leaf multichassis-global {
           type string;
         }
         container multichassis-ifd-name {
         }
         container multichassis-ifl-name {
         }
         container multichassis-vlan-name {
         }
         container multichassis-irb-name {
         }
         container multichassis-vrrp-grp-id {
         }
         container multichassis-consistency-check-entry {
           leaf config-item {
             type string;
             description "Name of the Configuration Item";
           }
           leaf consistency-check {
             type string;
             description "Type of Consistency Check performed";
           }
           leaf local-value {
             type string;
             description "Configured value on the local MC-LAG node";
           }
           leaf peer-value {
             type string;
             description "Configured value on the peer MC-LAG node";
           }
           leaf result {
             type string;
             description "Result of Configuration Consistency Check";
           }
         }
       }
     }
   }
 }
