/*
 * Copyright (c) 2017 Juniper Networks, Inc.
 * All rights reserved.
 */

 module show-ted {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-ted-database-information {
     description "Show current Traffic Engineering Database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of routing instance";
         type string;
       }
       leaf system-id {
         description "System ID or node ID";
         type string;
       }
       leaf local {
         description "Shows any local augmentation of TED";
         type empty;
       }
     }
     output {
       container ted-database-information {
         container ted-database-summary {
           leaf ted-database-iso-count {
             type int32;
           }
           leaf ted-database-inet-count {
             type int32;
           }
         }
         container ted-database {
           description "MPLS traffic engineering database";
           container brief {
             description "MPLS traffic engineering database";
             leaf ted-database-id {
               type string;
             }
             leaf ted-database-type {
               type string;
             }
             leaf ted-database-age {
               type int32;
             }
             leaf ted-database-link-in {
               type int32;
             }
             leaf ted-database-link-out {
               type int32;
             }
             leaf ted-database-protocol {
               type string;
             }
             container ted-link {
               container database {
                 leaf ted-link-to {
                   type string;
                 }
                 leaf ted-link-local-address {
                   type ipaddr;
                 }
                 leaf ted-link-remote-address {
                   type ipaddr;
                 }
                 leaf ted-link-local-ifindex {
                   type uint32;
                   description "Local interface index";
                 }
                 leaf ted-link-remote-ifindex {
                   type uint32;
                   description "Remote interface index";
                 }
                 leaf ted-link-metric {
                   type uint32;
                 }
                 leaf ted-link-igp-metric {
                   type uint32;
                 }
                 leaf ted-link-static-bandwidth {
                   type int32;
                 }
                 leaf ted-link-reservable-bandwidth {
                   type int32;
                 }
                 leaf ted-link-unreserved-bw-tlv-meaning {
                   type string;
                 }
                 leaf ted-link-avail-bw0 {
                   type int32;
                 }
                 leaf ted-link-avail-bw1 {
                   type int32;
                 }
                 leaf ted-link-avail-bw2 {
                   type int32;
                 }
                 leaf ted-link-avail-bw3 {
                   type int32;
                 }
                 leaf ted-link-avail-bw4 {
                   type int32;
                 }
                 leaf ted-link-avail-bw5 {
                   type int32;
                 }
                 leaf ted-link-avail-bw6 {
                   type int32;
                 }
                 leaf ted-link-avail-bw7 {
                   type int32;
                 }
                 leaf ted-link-model {
                   type string;
                 }
                 leaf ted-link-dste-tlv-meaning {
                   type string;
                 }
                 leaf ted-link-ct-bw0 {
                   type int32;
                 }
                 leaf ted-link-ct-bw1 {
                   type int32;
                 }
                 leaf ted-link-ct-bw2 {
                   type int32;
                 }
                 leaf ted-link-ct-bw3 {
                   type int32;
                 }
                 leaf ted-link-ct-bw4 {
                   type int32;
                 }
                 leaf ted-link-ct-bw5 {
                   type int32;
                 }
                 leaf ted-link-ct-bw6 {
                   type int32;
                 }
                 leaf ted-link-ct-bw7 {
                   type int32;
                 }
                 leaf ted-link-protocol {
                   type string;
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container ted-link-extended-admin-group {
                   leaf ted-link-extended-admin-group.heading {
                     type string;
                   }
                   leaf admin-group-name {
                     type string;
                     description "Name of the admin group";
                   }
                 }
                 container ted-link-abstract-hop {
                   leaf ted-link-abstract-hop.heading {
                     type string;
                   }
                   leaf abstract-hop-name {
                     type string;
                   }
                 }
                 container switching-capability-descriptor {
                   description "Switching capability of an interface";
                   leaf switching-capability-descriptor.heading {
                     type string;
                     description "Switching capability of an interface";
                   }
                   leaf switching-type {
                     type string;
                     description "LSP switching capability";
                   }
                   leaf encoding-type {
                     type string;
                     description "LSP encoding type";
                   }
                   leaf maximum-lsp-bw0 {
                     type int32;
                   }
                   leaf maximum-lsp-bw1 {
                     type int32;
                   }
                   leaf maximum-lsp-bw2 {
                     type int32;
                   }
                   leaf maximum-lsp-bw3 {
                     type int32;
                   }
                   leaf maximum-lsp-bw4 {
                     type int32;
                   }
                   leaf maximum-lsp-bw5 {
                     type int32;
                   }
                   leaf maximum-lsp-bw6 {
                     type int32;
                   }
                   leaf maximum-lsp-bw7 {
                     type int32;
                     description "Maximum bandwidth an LSP could reserve";
                   }
                   leaf minimum-lsp-bw {
                     type int32;
                     description "Minimum bandwidth an LSP could reserve";
                   }
                   leaf mtu {
                     type int32;
                     description "MTU along an interface";
                   }
                   leaf tdm-indication {
                     type string;
                   }
                 }
                 container ted-link-srlg {
                   leaf ted-link-srlg.heading {
                     type string;
                   }
                   leaf srlg-name {
                     type string;
                     description "Name of the srlg";
                   }
                 }
               }
               container brief {
                 leaf ted-link-from {
                   type string;
                 }
                 leaf ted-link-to {
                   type string;
                 }
                 leaf ted-link-link-out {
                   type int32;
                 }
                 leaf ted-link-local-bw7 {
                   type int32;
                 }
                 leaf ted-link-protocol {
                   type string;
                 }
               }
               container detail {
                 leaf ted-link-from {
                   type string;
                 }
                 leaf ted-link-to {
                   type string;
                 }
                 leaf ted-link-local-address {
                   type ipaddr;
                 }
                 leaf ted-link-remote-address {
                   type ipaddr;
                 }
                 leaf ted-link-local-ifindex {
                   type uint32;
                   description "Local interface index";
                 }
                 leaf ted-link-remote-ifindex {
                   type uint32;
                   description "Remote interface index";
                 }
                 leaf ted-link-link-out {
                   type int32;
                 }
                 leaf ted-link-metric {
                   type uint32;
                 }
                 leaf ted-link-igp-metric {
                   type uint32;
                 }
                 leaf ted-link-static-bandwidth {
                   type int32;
                 }
                 leaf ted-link-avail-bw7 {
                   type int32;
                 }
                 leaf ted-link-forwarding-adjacency {
                   type empty;
                   description "Indicates that the link is a forwarding adjacency";
                 }
                 leaf ted-link-local-bw0 {
                   type int32;
                 }
                 leaf ted-link-local-bw1 {
                   type int32;
                 }
                 leaf ted-link-local-bw2 {
                   type int32;
                 }
                 leaf ted-link-local-bw3 {
                   type int32;
                 }
                 leaf ted-link-local-bw4 {
                   type int32;
                 }
                 leaf ted-link-local-bw5 {
                   type int32;
                 }
                 leaf ted-link-local-bw6 {
                   type int32;
                 }
                 leaf ted-link-local-bw7 {
                   type int32;
                 }
                 leaf ted-link-ct-bw0 {
                   type int32;
                 }
                 leaf ted-link-ct-bw1 {
                   type int32;
                 }
                 leaf ted-link-ct-bw2 {
                   type int32;
                 }
                 leaf ted-link-ct-bw3 {
                   type int32;
                 }
                 leaf ted-link-ct-bw4 {
                   type int32;
                 }
                 leaf ted-link-ct-bw5 {
                   type int32;
                 }
                 leaf ted-link-ct-bw6 {
                   type int32;
                 }
                 leaf ted-link-ct-bw7 {
                   type int32;
                 }
                 leaf ted-link-protocol {
                   type string;
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container ted-link-extended-admin-group {
                   leaf ted-link-extended-admin-group.heading {
                     type string;
                   }
                   leaf admin-group-name {
                     type string;
                     description "Name of the admin group";
                   }
                 }
                 container ted-link-abstract-hop {
                   leaf ted-link-abstract-hop.heading {
                     type string;
                   }
                   leaf abstract-hop-name {
                     type string;
                   }
                 }
                 container ted-link-srlg {
                   leaf ted-link-srlg.heading {
                     type string;
                   }
                   leaf srlg-name {
                     type string;
                     description "Name of the srlg";
                   }
                 }
               }
             }
             container ted-prefix {
               leaf ted-prefix-protocol {
                 type string;
               }
             }
             container ted-prefixes {
               container ted-prefix {
                 leaf ted-prefix-protocol {
                   type string;
                 }
               }
             }
           }
           container detail {
             description "MPLS traffic engineering database";
             leaf ted-database-id {
               type string;
             }
             leaf ted-database-id-overload {
               type string;
             }
             leaf ted-database-type {
               type string;
             }
             leaf ted-database-age {
               type int32;
             }
             leaf ted-database-link-in {
               type int32;
             }
             leaf ted-database-link-out {
               type int32;
             }
             leaf ted-database-protocol {
               type string;
             }
             container ted-link {
               container database {
                 leaf ted-link-to {
                   type string;
                 }
                 leaf ted-link-local-address {
                   type ipaddr;
                 }
                 leaf ted-link-remote-address {
                   type ipaddr;
                 }
                 leaf ted-link-local-ifindex {
                   type uint32;
                   description "Local interface index";
                 }
                 leaf ted-link-remote-ifindex {
                   type uint32;
                   description "Remote interface index";
                 }
                 leaf ted-link-metric {
                   type uint32;
                 }
                 leaf ted-link-igp-metric {
                   type uint32;
                 }
                 leaf ted-link-static-bandwidth {
                   type int32;
                 }
                 leaf ted-link-reservable-bandwidth {
                   type int32;
                 }
                 leaf ted-link-unreserved-bw-tlv-meaning {
                   type string;
                 }
                 leaf ted-link-avail-bw0 {
                   type int32;
                 }
                 leaf ted-link-avail-bw1 {
                   type int32;
                 }
                 leaf ted-link-avail-bw2 {
                   type int32;
                 }
                 leaf ted-link-avail-bw3 {
                   type int32;
                 }
                 leaf ted-link-avail-bw4 {
                   type int32;
                 }
                 leaf ted-link-avail-bw5 {
                   type int32;
                 }
                 leaf ted-link-avail-bw6 {
                   type int32;
                 }
                 leaf ted-link-avail-bw7 {
                   type int32;
                 }
                 leaf ted-link-model {
                   type string;
                 }
                 leaf ted-link-dste-tlv-meaning {
                   type string;
                 }
                 leaf ted-link-ct-bw0 {
                   type int32;
                 }
                 leaf ted-link-ct-bw1 {
                   type int32;
                 }
                 leaf ted-link-ct-bw2 {
                   type int32;
                 }
                 leaf ted-link-ct-bw3 {
                   type int32;
                 }
                 leaf ted-link-ct-bw4 {
                   type int32;
                 }
                 leaf ted-link-ct-bw5 {
                   type int32;
                 }
                 leaf ted-link-ct-bw6 {
                   type int32;
                 }
                 leaf ted-link-ct-bw7 {
                   type int32;
                 }
                 leaf ted-link-protocol {
                   type string;
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container ted-link-extended-admin-group {
                   leaf ted-link-extended-admin-group.heading {
                     type string;
                   }
                   leaf admin-group-name {
                     type string;
                     description "Name of the admin group";
                   }
                 }
                 container ted-link-abstract-hop {
                   leaf ted-link-abstract-hop.heading {
                     type string;
                   }
                   leaf abstract-hop-name {
                     type string;
                   }
                 }
                 container switching-capability-descriptor {
                   description "Switching capability of an interface";
                   leaf switching-capability-descriptor.heading {
                     type string;
                     description "Switching capability of an interface";
                   }
                   leaf switching-type {
                     type string;
                     description "LSP switching capability";
                   }
                   leaf encoding-type {
                     type string;
                     description "LSP encoding type";
                   }
                   leaf maximum-lsp-bw0 {
                     type int32;
                   }
                   leaf maximum-lsp-bw1 {
                     type int32;
                   }
                   leaf maximum-lsp-bw2 {
                     type int32;
                   }
                   leaf maximum-lsp-bw3 {
                     type int32;
                   }
                   leaf maximum-lsp-bw4 {
                     type int32;
                   }
                   leaf maximum-lsp-bw5 {
                     type int32;
                   }
                   leaf maximum-lsp-bw6 {
                     type int32;
                   }
                   leaf maximum-lsp-bw7 {
                     type int32;
                     description "Maximum bandwidth an LSP could reserve";
                   }
                   leaf minimum-lsp-bw {
                     type int32;
                     description "Minimum bandwidth an LSP could reserve";
                   }
                   leaf mtu {
                     type int32;
                     description "MTU along an interface";
                   }
                   leaf tdm-indication {
                     type string;
                   }
                 }
                 container ted-link-srlg {
                   leaf ted-link-srlg.heading {
                     type string;
                   }
                   leaf srlg-name {
                     type string;
                     description "Name of the srlg";
                   }
                 }
               }
               container brief {
                 leaf ted-link-from {
                   type string;
                 }
                 leaf ted-link-to {
                   type string;
                 }
                 leaf ted-link-link-out {
                   type int32;
                 }
                 leaf ted-link-local-bw7 {
                   type int32;
                 }
                 leaf ted-link-protocol {
                   type string;
                 }
               }
               container detail {
                 leaf ted-link-from {
                   type string;
                 }
                 leaf ted-link-to {
                   type string;
                 }
                 leaf ted-link-local-address {
                   type ipaddr;
                 }
                 leaf ted-link-remote-address {
                   type ipaddr;
                 }
                 leaf ted-link-local-ifindex {
                   type uint32;
                   description "Local interface index";
                 }
                 leaf ted-link-remote-ifindex {
                   type uint32;
                   description "Remote interface index";
                 }
                 leaf ted-link-link-out {
                   type int32;
                 }
                 leaf ted-link-metric {
                   type uint32;
                 }
                 leaf ted-link-igp-metric {
                   type uint32;
                 }
                 leaf ted-link-static-bandwidth {
                   type int32;
                 }
                 leaf ted-link-avail-bw7 {
                   type int32;
                 }
                 leaf ted-link-forwarding-adjacency {
                   type empty;
                   description "Indicates that the link is a forwarding adjacency";
                 }
                 leaf ted-link-local-bw0 {
                   type int32;
                 }
                 leaf ted-link-local-bw1 {
                   type int32;
                 }
                 leaf ted-link-local-bw2 {
                   type int32;
                 }
                 leaf ted-link-local-bw3 {
                   type int32;
                 }
                 leaf ted-link-local-bw4 {
                   type int32;
                 }
                 leaf ted-link-local-bw5 {
                   type int32;
                 }
                 leaf ted-link-local-bw6 {
                   type int32;
                 }
                 leaf ted-link-local-bw7 {
                   type int32;
                 }
                 leaf ted-link-ct-bw0 {
                   type int32;
                 }
                 leaf ted-link-ct-bw1 {
                   type int32;
                 }
                 leaf ted-link-ct-bw2 {
                   type int32;
                 }
                 leaf ted-link-ct-bw3 {
                   type int32;
                 }
                 leaf ted-link-ct-bw4 {
                   type int32;
                 }
                 leaf ted-link-ct-bw5 {
                   type int32;
                 }
                 leaf ted-link-ct-bw6 {
                   type int32;
                 }
                 leaf ted-link-ct-bw7 {
                   type int32;
                 }
                 leaf ted-link-protocol {
                   type string;
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container ted-link-extended-admin-group {
                   leaf ted-link-extended-admin-group.heading {
                     type string;
                   }
                   leaf admin-group-name {
                     type string;
                     description "Name of the admin group";
                   }
                 }
                 container ted-link-abstract-hop {
                   leaf ted-link-abstract-hop.heading {
                     type string;
                   }
                   leaf abstract-hop-name {
                     type string;
                   }
                 }
                 container ted-link-srlg {
                   leaf ted-link-srlg.heading {
                     type string;
                   }
                   leaf srlg-name {
                     type string;
                     description "Name of the srlg";
                   }
                 }
               }
             }
             container ted-prefix {
               leaf ted-prefix-protocol {
                 type string;
               }
             }
             container ted-database-lcl-addr {
               leaf ted-lcl-addr {
                 type ipaddr;
               }
             }
             container ted-prefixes {
               container ted-prefix {
                 leaf ted-prefix-address {
                   type ipaddr;
                 }
                 leaf ted-prefix-length {
                   type uint32;
                 }
                 leaf ted-prefix-protocol {
                   type string;
                 }
               }
             }
           }
         }
       }
     }
   }
   rpc get-ted-link-information {
     description "Show current Traffic Engineering Database link";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf instance {
         description "Name of routing instance";
         type string;
       }
     }
     output {
       container ted-link-information {
         container ted-link {
           container database {
             leaf ted-link-to {
               type string;
             }
             leaf ted-link-local-address {
               type ipaddr;
             }
             leaf ted-link-remote-address {
               type ipaddr;
             }
             leaf ted-link-local-ifindex {
               type uint32;
               description "Local interface index";
             }
             leaf ted-link-remote-ifindex {
               type uint32;
               description "Remote interface index";
             }
             leaf ted-link-metric {
               type uint32;
             }
             leaf ted-link-igp-metric {
               type uint32;
             }
             leaf ted-link-static-bandwidth {
               type int32;
             }
             leaf ted-link-reservable-bandwidth {
               type int32;
             }
             leaf ted-link-unreserved-bw-tlv-meaning {
               type string;
             }
             leaf ted-link-avail-bw0 {
               type int32;
             }
             leaf ted-link-avail-bw1 {
               type int32;
             }
             leaf ted-link-avail-bw2 {
               type int32;
             }
             leaf ted-link-avail-bw3 {
               type int32;
             }
             leaf ted-link-avail-bw4 {
               type int32;
             }
             leaf ted-link-avail-bw5 {
               type int32;
             }
             leaf ted-link-avail-bw6 {
               type int32;
             }
             leaf ted-link-avail-bw7 {
               type int32;
             }
             leaf ted-link-model {
               type string;
             }
             leaf ted-link-dste-tlv-meaning {
               type string;
             }
             leaf ted-link-ct-bw0 {
               type int32;
             }
             leaf ted-link-ct-bw1 {
               type int32;
             }
             leaf ted-link-ct-bw2 {
               type int32;
             }
             leaf ted-link-ct-bw3 {
               type int32;
             }
             leaf ted-link-ct-bw4 {
               type int32;
             }
             leaf ted-link-ct-bw5 {
               type int32;
             }
             leaf ted-link-ct-bw6 {
               type int32;
             }
             leaf ted-link-ct-bw7 {
               type int32;
             }
             leaf ted-link-protocol {
               type string;
             }
             container admin-groups {
               leaf admin-groups.heading {
                 type string;
               }
               leaf color {
                 type int32;
               }
               leaf no-group-flag {
                 type empty;
               }
               leaf admin-group-name {
                 type string;
                 description "Name of the admin group";
               }
               leaf admin-group-number {
                 type int32;
                 description "Number of the admin group";
               }
             }
             container ted-link-extended-admin-group {
               leaf ted-link-extended-admin-group.heading {
                 type string;
               }
               leaf admin-group-name {
                 type string;
                 description "Name of the admin group";
               }
             }
             container ted-link-abstract-hop {
               leaf ted-link-abstract-hop.heading {
                 type string;
               }
               leaf abstract-hop-name {
                 type string;
               }
             }
             container switching-capability-descriptor {
               description "Switching capability of an interface";
               leaf switching-capability-descriptor.heading {
                 type string;
                 description "Switching capability of an interface";
               }
               leaf switching-type {
                 type string;
                 description "LSP switching capability";
               }
               leaf encoding-type {
                 type string;
                 description "LSP encoding type";
               }
               leaf maximum-lsp-bw0 {
                 type int32;
               }
               leaf maximum-lsp-bw1 {
                 type int32;
               }
               leaf maximum-lsp-bw2 {
                 type int32;
               }
               leaf maximum-lsp-bw3 {
                 type int32;
               }
               leaf maximum-lsp-bw4 {
                 type int32;
               }
               leaf maximum-lsp-bw5 {
                 type int32;
               }
               leaf maximum-lsp-bw6 {
                 type int32;
               }
               leaf maximum-lsp-bw7 {
                 type int32;
                 description "Maximum bandwidth an LSP could reserve";
               }
               leaf minimum-lsp-bw {
                 type int32;
                 description "Minimum bandwidth an LSP could reserve";
               }
               leaf mtu {
                 type int32;
                 description "MTU along an interface";
               }
               leaf tdm-indication {
                 type string;
               }
             }
             container ted-link-srlg {
               leaf ted-link-srlg.heading {
                 type string;
               }
               leaf srlg-name {
                 type string;
                 description "Name of the srlg";
               }
             }
           }
           container brief {
             leaf ted-link-from {
               type string;
             }
             leaf ted-link-to {
               type string;
             }
             leaf ted-link-link-out {
               type int32;
             }
             leaf ted-link-local-bw7 {
               type int32;
             }
             leaf ted-link-protocol {
               type string;
             }
           }
           container detail {
             leaf ted-link-from {
               type string;
             }
             leaf ted-link-to {
               type string;
             }
             leaf ted-link-local-address {
               type ipaddr;
             }
             leaf ted-link-remote-address {
               type ipaddr;
             }
             leaf ted-link-local-ifindex {
               type uint32;
               description "Local interface index";
             }
             leaf ted-link-remote-ifindex {
               type uint32;
               description "Remote interface index";
             }
             leaf ted-link-link-out {
               type int32;
             }
             leaf ted-link-metric {
               type uint32;
             }
             leaf ted-link-igp-metric {
               type uint32;
             }
             leaf ted-link-static-bandwidth {
               type int32;
             }
             leaf ted-link-avail-bw7 {
               type int32;
             }
             leaf ted-link-forwarding-adjacency {
               type empty;
               description "Indicates that the link is a forwarding adjacency";
             }
             leaf ted-link-local-bw0 {
               type int32;
             }
             leaf ted-link-local-bw1 {
               type int32;
             }
             leaf ted-link-local-bw2 {
               type int32;
             }
             leaf ted-link-local-bw3 {
               type int32;
             }
             leaf ted-link-local-bw4 {
               type int32;
             }
             leaf ted-link-local-bw5 {
               type int32;
             }
             leaf ted-link-local-bw6 {
               type int32;
             }
             leaf ted-link-local-bw7 {
               type int32;
             }
             leaf ted-link-ct-bw0 {
               type int32;
             }
             leaf ted-link-ct-bw1 {
               type int32;
             }
             leaf ted-link-ct-bw2 {
               type int32;
             }
             leaf ted-link-ct-bw3 {
               type int32;
             }
             leaf ted-link-ct-bw4 {
               type int32;
             }
             leaf ted-link-ct-bw5 {
               type int32;
             }
             leaf ted-link-ct-bw6 {
               type int32;
             }
             leaf ted-link-ct-bw7 {
               type int32;
             }
             leaf ted-link-protocol {
               type string;
             }
             container admin-groups {
               leaf admin-groups.heading {
                 type string;
               }
               leaf color {
                 type int32;
               }
               leaf no-group-flag {
                 type empty;
               }
               leaf admin-group-name {
                 type string;
                 description "Name of the admin group";
               }
               leaf admin-group-number {
                 type int32;
                 description "Number of the admin group";
               }
             }
             container ted-link-extended-admin-group {
               leaf ted-link-extended-admin-group.heading {
                 type string;
               }
               leaf admin-group-name {
                 type string;
                 description "Name of the admin group";
               }
             }
             container ted-link-abstract-hop {
               leaf ted-link-abstract-hop.heading {
                 type string;
               }
               leaf abstract-hop-name {
                 type string;
               }
             }
             container ted-link-srlg {
               leaf ted-link-srlg.heading {
                 type string;
               }
               leaf srlg-name {
                 type string;
                 description "Name of the srlg";
               }
             }
           }
         }
       }
     }
   }
   rpc get-ted-protocol-information {
     description "Show current contributing protocols";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf instance {
         description "Name of routing instance";
         type string;
       }
     }
     output {
       container ted-protocol-information {
         container ted-protocol {
           leaf ted-protocol-name {
             type string;
             description "Protocol that filled in the TED entry";
           }
           leaf ted-protocol-credibility {
             type int32;
           }
           leaf ted-protocol-self-node {
             type string;
           }
         }
       }
     }
   }
 }
