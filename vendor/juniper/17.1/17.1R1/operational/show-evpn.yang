/*
 * Copyright (c) 2017 Juniper Networks, Inc.
 * All rights reserved.
 */

 module show-evpn {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-evpn-instance-information {
     description "Show EVPN instance information";
     input {
       leaf instance-name {
         description "Name of EVPN instance";
         default "all";
         type string;
       }
       leaf neighbor {
         description "Address of EVPN neighbor";
         type ipaddr;
       }
       leaf esi {
         description "Ethernet segment identifier";
         type string;
       }
       leaf verbosity {
         type enumeration {
           enum "brief" {
             description "Display brief version of output";
           }
           enum "extensive" {
             description "Display extensive version of output";
           }
           enum "designated-forwarder" {
             description "Display only designated forwarder information";
           }
           enum "backup-forwarder" {
             description "Display only backup forwarder information";
           }
         }
       }
     }
     output {
       container evpn-instance-information {
         container evpn-instance {
           container extensive {
             leaf evpn-instance-name {
               type string;
             }
             leaf route-distinguisher {
               type string;
             }
             leaf evpn-encap-type {
               type string;
             }
             leaf evpn-instance-vlan-id {
               type string;
             }
             leaf evpn-instance-pbb-evpn-core {
               type string;
             }
             leaf evpn-instance-pbb-optimize-multicast {
               type string;
             }
             leaf evpn-instance-control-word {
               type string;
             }
             leaf evpn-service-interface-type {
               type string;
             }
             leaf evpn-instance-mac-label {
               type string;
             }
             leaf evpn-instance-mc-label {
               type string;
             }
             leaf evpn-etree-leaf-label {
               type string;
             }
             leaf num-local-macs {
               type int32;
             }
             leaf num-remote-macs {
               type int32;
             }
             leaf local-interfaces {
               type int32;
             }
             leaf local-interfaces-up {
               type int32;
             }
             leaf irb-interfaces {
               type int32;
             }
             leaf irb-interfaces-up {
               type int32;
             }
             leaf num-bridge-domains {
               type int32;
             }
             leaf num-bundle-bridge-domains {
               type int32;
             }
             leaf evpn-num-neighbors {
               type int32;
             }
             leaf evpn-num-esi {
               type int32;
             }
             leaf evpn-router-id {
               type ipaddr;
             }
             leaf evpn-source-vtep-ipaddr {
               type ipaddr;
             }
             container mac-database-status-table {
               leaf local-macs {
                 type int32;
               }
               leaf remote-macs {
                 type int32;
               }
               leaf local-mac-ips {
                 type int32;
               }
               leaf remote-mac-ips {
                 type int32;
               }
               leaf local-default-gateway-macs {
                 type int32;
               }
               leaf remote-default-gateway-macs {
                 type int32;
               }
             }
             container evpn-interface-status-table {
               container extensive {
                 container evpn-interface {
                   leaf evpn-interface-name {
                     type string;
                   }
                   leaf evpn-interface-esi {
                     type string;
                   }
                   leaf evpn-interface-mode {
                     type string;
                   }
                   leaf evpn-interface-status {
                     type string;
                   }
                   leaf evpn-interface-etree-role {
                     type string;
                   }
                 }
               }
             }
             container irb-interface-status-table {
               container extensive {
                 container irb-interface {
                   leaf irb-interface-name {
                     type string;
                   }
                   leaf irb-interface-vlan-id {
                     type string;
                   }
                   leaf irb-interface-vni-id {
                     type string;
                   }
                   leaf irb-interface-status {
                     type string;
                   }
                   leaf irb-interface-l3-context {
                     type string;
                   }
                 }
               }
             }
             container bridge-domain-status-table {
               container extensive {
                 container bridge-domain {
                   leaf vlan-id {
                     type int32;
                   }
                   leaf domain-id {
                     type int32;
                   }
                   leaf interfaces {
                     type int32;
                   }
                   leaf interfaces-up {
                     type int32;
                   }
                   leaf irb-interface {
                     type string;
                   }
                   leaf mode {
                     type string;
                   }
                   leaf mac-sync-status {
                     type string;
                   }
                   leaf inclusive-multicast-label {
                     type int32;
                   }
                 }
               }
             }
             container bundle-bridge-domain-status-table {
               container extensive {
                 container bundle-bridge-domain {
                   leaf domain-name {
                     type string;
                   }
                   leaf num-isids {
                     type int32;
                   }
                   leaf mode {
                     type string;
                   }
                   leaf mac-sync-status {
                     type string;
                   }
                 }
               }
             }
             container evpn-neighbor {
               leaf evpn-neighbor-address {
                 type ipaddr;
               }
               container evpn-neighbor-route-information {
                 container extensive {
                   leaf evpn-num-mac-routes {
                     type int32;
                   }
                   leaf evpn-num-mac-ip-routes {
                     type int32;
                   }
                   leaf evpn-num-ethernet-autodiscovery-routes {
                     type int32;
                   }
                   leaf evpn-num-inclusive-multicast-routes {
                     type int32;
                   }
                   leaf evpn-num-ethernet-segment-routes {
                     type int32;
                   }
                   leaf evpn-peer-leaf-label {
                     type int32;
                   }
                 }
               }
             }
             container evpn-esi {
               leaf evpn-esi-value {
                 type string;
               }
               leaf evpn-esi-status {
                 type string;
               }
               leaf evpn-esi-min-isid {
                 type int32;
               }
               leaf evpn-esi-mac-label {
                 type int32;
               }
               leaf evpn-esi-aliasing-label {
                 type int32;
               }
               leaf evpn-esi-split-horizon-label {
                 type int32;
               }
               container extensive {
                 container evpn-esi-local-intf-information {
                   leaf evpn-esi-local-intf-name {
                     type string;
                   }
                   leaf evpn-esi-local-intf-status {
                     type string;
                   }
                 }
                 container evpn-esi-remote-pe-information {
                   leaf evpn-esi-num-remote-pe {
                     type int32;
                   }
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-designated-forwarder {
                     type string;
                   }
                   leaf esi-backup-forwarder {
                     type string;
                   }
                   leaf esi-last-df-update-timestamp {
                     type string;
                   }
                   container extensive {
                   }
                   container df-only {
                     leaf esi-designated-forwarder {
                       type string;
                     }
                   }
                   container bf-only {
                     leaf esi-backup-forwarder {
                       type string;
                     }
                   }
                 }
               }
               container df-only {
                 leaf evpn-esi-value {
                   type string;
                 }
                 container evpn-esi-remote-pe-information {
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-designated-forwarder {
                     type string;
                   }
                   container extensive {
                     leaf esi-backup-forwarder {
                       type string;
                     }
                     leaf esi-last-df-update-timestamp {
                       type string;
                     }
                   }
                   container df-only {
                     leaf esi-designated-forwarder {
                       type string;
                     }
                   }
                   container bf-only {
                     leaf esi-backup-forwarder {
                       type string;
                     }
                   }
                 }
               }
               container bf-only {
                 leaf evpn-esi-value {
                   type string;
                 }
                 container evpn-esi-remote-pe-information {
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-backup-forwarder {
                     type string;
                   }
                   container extensive {
                     leaf esi-designated-forwarder {
                       type string;
                     }
                     leaf esi-last-df-update-timestamp {
                       type string;
                     }
                   }
                   container df-only {
                     leaf esi-designated-forwarder {
                       type string;
                     }
                   }
                   container bf-only {
                     leaf esi-backup-forwarder {
                       type string;
                     }
                   }
                 }
               }
             }
           }
           container normal {
             leaf evpn-instance-name {
               type string;
             }
             leaf local-interfaces {
               type int32;
             }
             leaf local-interfaces-up {
               type int32;
             }
             leaf irb-interfaces {
               type int32;
             }
             leaf irb-interfaces-up {
               type int32;
             }
             leaf evpn-num-neighbors {
               type int32;
             }
             leaf evpn-num-esi {
               type int32;
             }
             leaf num-local-macs {
               type int32;
             }
             leaf num-remote-macs {
               type int32;
             }
             container mac-database-status-table {
               container extensive {
                 leaf local-macs {
                   type int32;
                 }
                 leaf remote-macs {
                   type int32;
                 }
                 leaf local-mac-ips {
                   type int32;
                 }
                 leaf remote-mac-ips {
                   type int32;
                 }
                 leaf local-default-gateway-macs {
                   type int32;
                 }
                 leaf remote-default-gateway-macs {
                   type int32;
                 }
               }
             }
             container evpn-interface-status-table {
               container extensive {
                 container evpn-interface {
                   leaf evpn-interface-name {
                     type string;
                   }
                   leaf evpn-interface-esi {
                     type string;
                   }
                   leaf evpn-interface-mode {
                     type string;
                   }
                   leaf evpn-interface-status {
                     type string;
                   }
                   leaf evpn-interface-etree-role {
                     type string;
                   }
                 }
               }
             }
             container irb-interface-status-table {
               container extensive {
                 container irb-interface {
                   leaf irb-interface-name {
                     type string;
                   }
                   leaf irb-interface-vlan-id {
                     type string;
                   }
                   leaf irb-interface-vni-id {
                     type string;
                   }
                   leaf irb-interface-status {
                     type string;
                   }
                   leaf irb-interface-l3-context {
                     type string;
                   }
                 }
               }
             }
             container bridge-domain-status-table {
               container extensive {
                 container bridge-domain {
                   leaf vlan-id {
                     type int32;
                   }
                   leaf domain-id {
                     type int32;
                   }
                   leaf interfaces {
                     type int32;
                   }
                   leaf interfaces-up {
                     type int32;
                   }
                   leaf irb-interface {
                     type string;
                   }
                   leaf mode {
                     type string;
                   }
                   leaf mac-sync-status {
                     type string;
                   }
                   leaf inclusive-multicast-label {
                     type int32;
                   }
                 }
               }
             }
             container bundle-bridge-domain-status-table {
               container extensive {
                 container bundle-bridge-domain {
                   leaf domain-name {
                     type string;
                   }
                   leaf num-isids {
                     type int32;
                   }
                   leaf mode {
                     type string;
                   }
                   leaf mac-sync-status {
                     type string;
                   }
                 }
               }
             }
             container evpn-neighbor {
               leaf evpn-neighbor-address {
                 type ipaddr;
               }
               container evpn-neighbor-route-information {
                 container extensive {
                   leaf evpn-num-mac-routes {
                     type int32;
                   }
                   leaf evpn-num-mac-ip-routes {
                     type int32;
                   }
                   leaf evpn-num-ethernet-autodiscovery-routes {
                     type int32;
                   }
                   leaf evpn-num-inclusive-multicast-routes {
                     type int32;
                   }
                   leaf evpn-num-ethernet-segment-routes {
                     type int32;
                   }
                   leaf evpn-peer-leaf-label {
                     type int32;
                   }
                 }
               }
             }
             container evpn-esi {
               container extensive {
                 leaf evpn-esi-value {
                   type string;
                 }
                 leaf evpn-esi-status {
                   type string;
                 }
                 leaf evpn-esi-min-isid {
                   type int32;
                 }
                 leaf evpn-esi-mac-label {
                   type int32;
                 }
                 leaf evpn-esi-aliasing-label {
                   type int32;
                 }
                 leaf evpn-esi-split-horizon-label {
                   type int32;
                 }
                 container evpn-esi-local-intf-information {
                   leaf evpn-esi-local-intf-name {
                     type string;
                   }
                   leaf evpn-esi-local-intf-status {
                     type string;
                   }
                 }
                 container evpn-esi-remote-pe-information {
                   leaf evpn-esi-num-remote-pe {
                     type int32;
                   }
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-designated-forwarder {
                     type string;
                   }
                   leaf esi-backup-forwarder {
                     type string;
                   }
                   leaf esi-last-df-update-timestamp {
                     type string;
                   }
                   container extensive {
                   }
                   container df-only {
                     leaf esi-designated-forwarder {
                       type string;
                     }
                   }
                   container bf-only {
                     leaf esi-backup-forwarder {
                       type string;
                     }
                   }
                 }
               }
               container df-only {
                 leaf evpn-esi-value {
                   type string;
                 }
                 container evpn-esi-remote-pe-information {
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-designated-forwarder {
                     type string;
                   }
                   container extensive {
                     leaf esi-backup-forwarder {
                       type string;
                     }
                     leaf esi-last-df-update-timestamp {
                       type string;
                     }
                   }
                   container df-only {
                     leaf esi-designated-forwarder {
                       type string;
                     }
                   }
                   container bf-only {
                     leaf esi-backup-forwarder {
                       type string;
                     }
                   }
                 }
               }
               container bf-only {
                 leaf evpn-esi-value {
                   type string;
                 }
                 container evpn-esi-remote-pe-information {
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-backup-forwarder {
                     type string;
                   }
                   container extensive {
                     leaf esi-designated-forwarder {
                       type string;
                     }
                     leaf esi-last-df-update-timestamp {
                       type string;
                     }
                   }
                   container df-only {
                     leaf esi-designated-forwarder {
                       type string;
                     }
                   }
                   container bf-only {
                     leaf esi-backup-forwarder {
                       type string;
                     }
                   }
                 }
               }
             }
           }
           container df-only {
             leaf evpn-instance-name {
               type string;
             }
             leaf evpn-num-esi {
               type int32;
             }
             container mac-database-status-table {
               container extensive {
                 leaf local-macs {
                   type int32;
                 }
                 leaf remote-macs {
                   type int32;
                 }
                 leaf local-mac-ips {
                   type int32;
                 }
                 leaf remote-mac-ips {
                   type int32;
                 }
                 leaf local-default-gateway-macs {
                   type int32;
                 }
                 leaf remote-default-gateway-macs {
                   type int32;
                 }
               }
             }
             container evpn-interface-status-table {
               container extensive {
                 container evpn-interface {
                   leaf evpn-interface-name {
                     type string;
                   }
                   leaf evpn-interface-esi {
                     type string;
                   }
                   leaf evpn-interface-mode {
                     type string;
                   }
                   leaf evpn-interface-status {
                     type string;
                   }
                   leaf evpn-interface-etree-role {
                     type string;
                   }
                 }
               }
             }
             container irb-interface-status-table {
               container extensive {
                 container irb-interface {
                   leaf irb-interface-name {
                     type string;
                   }
                   leaf irb-interface-vlan-id {
                     type string;
                   }
                   leaf irb-interface-vni-id {
                     type string;
                   }
                   leaf irb-interface-status {
                     type string;
                   }
                   leaf irb-interface-l3-context {
                     type string;
                   }
                 }
               }
             }
             container bridge-domain-status-table {
               container extensive {
                 container bridge-domain {
                   leaf vlan-id {
                     type int32;
                   }
                   leaf domain-id {
                     type int32;
                   }
                   leaf interfaces {
                     type int32;
                   }
                   leaf interfaces-up {
                     type int32;
                   }
                   leaf irb-interface {
                     type string;
                   }
                   leaf mode {
                     type string;
                   }
                   leaf mac-sync-status {
                     type string;
                   }
                   leaf inclusive-multicast-label {
                     type int32;
                   }
                 }
               }
             }
             container bundle-bridge-domain-status-table {
               container extensive {
                 container bundle-bridge-domain {
                   leaf domain-name {
                     type string;
                   }
                   leaf num-isids {
                     type int32;
                   }
                   leaf mode {
                     type string;
                   }
                   leaf mac-sync-status {
                     type string;
                   }
                 }
               }
             }
             container evpn-neighbor {
               leaf evpn-neighbor-address {
                 type ipaddr;
               }
               container evpn-neighbor-route-information {
                 container extensive {
                   leaf evpn-num-mac-routes {
                     type int32;
                   }
                   leaf evpn-num-mac-ip-routes {
                     type int32;
                   }
                   leaf evpn-num-ethernet-autodiscovery-routes {
                     type int32;
                   }
                   leaf evpn-num-inclusive-multicast-routes {
                     type int32;
                   }
                   leaf evpn-num-ethernet-segment-routes {
                     type int32;
                   }
                   leaf evpn-peer-leaf-label {
                     type int32;
                   }
                 }
               }
             }
             container evpn-esi {
               leaf evpn-esi-value {
                 type string;
               }
               container extensive {
                 leaf evpn-esi-status {
                   type string;
                 }
                 leaf evpn-esi-min-isid {
                   type int32;
                 }
                 leaf evpn-esi-mac-label {
                   type int32;
                 }
                 leaf evpn-esi-aliasing-label {
                   type int32;
                 }
                 leaf evpn-esi-split-horizon-label {
                   type int32;
                 }
                 container evpn-esi-local-intf-information {
                   leaf evpn-esi-local-intf-name {
                     type string;
                   }
                   leaf evpn-esi-local-intf-status {
                     type string;
                   }
                 }
                 container evpn-esi-remote-pe-information {
                   leaf evpn-esi-num-remote-pe {
                     type int32;
                   }
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-designated-forwarder {
                     type string;
                   }
                   leaf esi-backup-forwarder {
                     type string;
                   }
                   leaf esi-last-df-update-timestamp {
                     type string;
                   }
                   container extensive {
                   }
                   container df-only {
                     leaf esi-designated-forwarder {
                       type string;
                     }
                   }
                   container bf-only {
                     leaf esi-backup-forwarder {
                       type string;
                     }
                   }
                 }
               }
               container df-only {
                 leaf evpn-esi-value {
                   type string;
                 }
                 container evpn-esi-remote-pe-information {
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-designated-forwarder {
                     type string;
                   }
                   container extensive {
                     leaf esi-backup-forwarder {
                       type string;
                     }
                     leaf esi-last-df-update-timestamp {
                       type string;
                     }
                   }
                   container df-only {
                     leaf esi-designated-forwarder {
                       type string;
                     }
                   }
                   container bf-only {
                     leaf esi-backup-forwarder {
                       type string;
                     }
                   }
                 }
               }
               container bf-only {
                 leaf evpn-esi-value {
                   type string;
                 }
                 container evpn-esi-remote-pe-information {
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-backup-forwarder {
                     type string;
                   }
                   container extensive {
                     leaf esi-designated-forwarder {
                       type string;
                     }
                     leaf esi-last-df-update-timestamp {
                       type string;
                     }
                   }
                   container df-only {
                     leaf esi-designated-forwarder {
                       type string;
                     }
                   }
                   container bf-only {
                     leaf esi-backup-forwarder {
                       type string;
                     }
                   }
                 }
               }
             }
           }
           container bf-only {
             leaf evpn-instance-name {
               type string;
             }
             leaf evpn-num-esi {
               type int32;
             }
             container mac-database-status-table {
               container extensive {
                 leaf local-macs {
                   type int32;
                 }
                 leaf remote-macs {
                   type int32;
                 }
                 leaf local-mac-ips {
                   type int32;
                 }
                 leaf remote-mac-ips {
                   type int32;
                 }
                 leaf local-default-gateway-macs {
                   type int32;
                 }
                 leaf remote-default-gateway-macs {
                   type int32;
                 }
               }
             }
             container evpn-interface-status-table {
               container extensive {
                 container evpn-interface {
                   leaf evpn-interface-name {
                     type string;
                   }
                   leaf evpn-interface-esi {
                     type string;
                   }
                   leaf evpn-interface-mode {
                     type string;
                   }
                   leaf evpn-interface-status {
                     type string;
                   }
                   leaf evpn-interface-etree-role {
                     type string;
                   }
                 }
               }
             }
             container irb-interface-status-table {
               container extensive {
                 container irb-interface {
                   leaf irb-interface-name {
                     type string;
                   }
                   leaf irb-interface-vlan-id {
                     type string;
                   }
                   leaf irb-interface-vni-id {
                     type string;
                   }
                   leaf irb-interface-status {
                     type string;
                   }
                   leaf irb-interface-l3-context {
                     type string;
                   }
                 }
               }
             }
             container bridge-domain-status-table {
               container extensive {
                 container bridge-domain {
                   leaf vlan-id {
                     type int32;
                   }
                   leaf domain-id {
                     type int32;
                   }
                   leaf interfaces {
                     type int32;
                   }
                   leaf interfaces-up {
                     type int32;
                   }
                   leaf irb-interface {
                     type string;
                   }
                   leaf mode {
                     type string;
                   }
                   leaf mac-sync-status {
                     type string;
                   }
                   leaf inclusive-multicast-label {
                     type int32;
                   }
                 }
               }
             }
             container bundle-bridge-domain-status-table {
               container extensive {
                 container bundle-bridge-domain {
                   leaf domain-name {
                     type string;
                   }
                   leaf num-isids {
                     type int32;
                   }
                   leaf mode {
                     type string;
                   }
                   leaf mac-sync-status {
                     type string;
                   }
                 }
               }
             }
             container evpn-neighbor {
               leaf evpn-neighbor-address {
                 type ipaddr;
               }
               container evpn-neighbor-route-information {
                 container extensive {
                   leaf evpn-num-mac-routes {
                     type int32;
                   }
                   leaf evpn-num-mac-ip-routes {
                     type int32;
                   }
                   leaf evpn-num-ethernet-autodiscovery-routes {
                     type int32;
                   }
                   leaf evpn-num-inclusive-multicast-routes {
                     type int32;
                   }
                   leaf evpn-num-ethernet-segment-routes {
                     type int32;
                   }
                   leaf evpn-peer-leaf-label {
                     type int32;
                   }
                 }
               }
             }
             container evpn-esi {
               leaf evpn-esi-value {
                 type string;
               }
               container extensive {
                 leaf evpn-esi-status {
                   type string;
                 }
                 leaf evpn-esi-min-isid {
                   type int32;
                 }
                 leaf evpn-esi-mac-label {
                   type int32;
                 }
                 leaf evpn-esi-aliasing-label {
                   type int32;
                 }
                 leaf evpn-esi-split-horizon-label {
                   type int32;
                 }
                 container evpn-esi-local-intf-information {
                   leaf evpn-esi-local-intf-name {
                     type string;
                   }
                   leaf evpn-esi-local-intf-status {
                     type string;
                   }
                 }
                 container evpn-esi-remote-pe-information {
                   leaf evpn-esi-num-remote-pe {
                     type int32;
                   }
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-designated-forwarder {
                     type string;
                   }
                   leaf esi-backup-forwarder {
                     type string;
                   }
                   leaf esi-last-df-update-timestamp {
                     type string;
                   }
                   container extensive {
                   }
                   container df-only {
                     leaf esi-designated-forwarder {
                       type string;
                     }
                   }
                   container bf-only {
                     leaf esi-backup-forwarder {
                       type string;
                     }
                   }
                 }
               }
               container df-only {
                 leaf evpn-esi-value {
                   type string;
                 }
                 container evpn-esi-remote-pe-information {
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-designated-forwarder {
                     type string;
                   }
                   container extensive {
                     leaf esi-backup-forwarder {
                       type string;
                     }
                     leaf esi-last-df-update-timestamp {
                       type string;
                     }
                   }
                   container df-only {
                     leaf esi-designated-forwarder {
                       type string;
                     }
                   }
                   container bf-only {
                     leaf esi-backup-forwarder {
                       type string;
                     }
                   }
                 }
               }
               container bf-only {
                 leaf evpn-esi-value {
                   type string;
                 }
                 container evpn-esi-remote-pe-information {
                   container evpn-esi-remote-pe {
                     leaf evpn-esi-remote-pe-ipaddr {
                       type ipaddr;
                     }
                     leaf evpn-esi-remote-mac-label {
                       type int32;
                     }
                     leaf evpn-esi-remote-aliasing-label {
                       type int32;
                     }
                     leaf evpn-esi-remote-pe-mode {
                       type string;
                     }
                   }
                 }
                 container evpn-esi-df-information {
                   leaf esi-backup-forwarder {
                     type string;
                   }
                   container extensive {
                     leaf esi-designated-forwarder {
                       type string;
                     }
                     leaf esi-last-df-update-timestamp {
                       type string;
                     }
                   }
                   container df-only {
                     leaf esi-designated-forwarder {
                       type string;
                     }
                   }
                   container bf-only {
                     leaf esi-backup-forwarder {
                       type string;
                     }
                   }
                 }
               }
             }
           }
         }
       }
     }
   }
   rpc get-evpn-statistics-information {
     description "Show EVPN statistics";
     input {
       leaf instance {
         description "Name of EVPN instance";
         type string;
       }
     }
     output {
       container evpn-statistics-information {
         container instance {
           leaf instance-name {
             type string;
           }
           container normal {
             leaf instance-display-error {
               type string;
             }
             leaf edge-protection {
               type string;
             }
             leaf edge-protector {
               type string;
             }
             container reference-site {
               leaf automatic-site-name {
                 type string;
                 description "VPLS automatic site name";
               }
               leaf automatic-site-id-status {
                 type string;
                 description "VPLS automatic site identifier status";
               }
               leaf automatic-site-claim-id {
                 type int32;
                 description "Claim site identifier";
               }
               leaf automatic-site-collisions {
                 type int32;
                 description "Number of collisions";
               }
               leaf automatic-site-timer-status {
                 type string;
                 description "VPLS automatic site timer status";
               }
               leaf vpls-signaling-protocol-identifier {
                 type string;
               }
               leaf local-site-id {
                 type string;
               }
               leaf source-attachment-id {
                 type string;
                 description "Local source attachment identifier";
               }
               leaf vpls-id {
                 type int32;
                 description "VPLS instance identifier";
               }
               leaf l2vpn-id {
                 type string;
               }
               leaf local-id {
                 type ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               leaf target-attachment-id {
                 type string;
                 description "Remote target attachment identifier";
               }
               container mesh-group-interfaces {
                 description "Information about all interfaces associated with a mesh-group";
                 leaf mesh-group-name {
                   type string;
                   description "Name of mesh-group";
                 }
                 leaf mesh-group-state {
                   type string;
                   description "Mesh-group state";
                 }
                 leaf mesh-group-id {
                   type int32;
                   description "Mesh-group Identifier";
                 }
                 container interface {
                   leaf interface-name {
                     type string;
                     description "Name of interface";
                   }
                   leaf interface-description {
                     type string;
                   }
                   leaf interface-flags-description {
                     type string;
                   }
                   leaf interface-flags {
                     type int32;
                   }
                 }
               }
               container interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               container label-block {
                 leaf label-block.heading {
                   type string;
                 }
                 leaf label-block-base {
                   type int32;
                 }
                 leaf label-block-offset {
                   type int32;
                 }
                 leaf label-block-size {
                   type int32;
                 }
                 leaf label-block-range {
                   type int32;
                 }
                 leaf label-block-preference {
                   type int32;
                 }
                 leaf label-block-status-vector {
                   type string;
                 }
               }
               container connection {
                 leaf connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 leaf auto-sensed {
                   type empty;
                   description "Auto-sensed";
                 }
                 container local-interface {
                   leaf interface-name {
                     type string;
                     description "Name of interface";
                   }
                   leaf interface-status {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   description "Information about one or more VPLS RSVP-TE point-to-multipoint LSPs";
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container spe-info {
                   leaf spe-info.heading {
                     type string;
                   }
                   leaf local-ip-addr {
                     type ipaddr;
                   }
                   leaf remote-ip-addr {
                     type ipaddr;
                   }
                   leaf pw-status {
                     type string;
                   }
                 }
                 container history {
                   leaf history.category-heading {
                     type string;
                   }
                   leaf history.heading {
                     type string;
                   }
                   leaf log-time-stamp {
                     type string;
                   }
                   leaf log-event {
                     type string;
                   }
                   leaf changed-entity {
                     type string;
                   }
                 }
               }
               container mesh-group-connection {
                 description "Information about all vc-connections of a specific mesh-group";
                 leaf mesh-group-name {
                   type string;
                   description "Name of mesh-group";
                 }
                 container connection {
                   leaf connection.heading {
                     type string;
                   }
                   leaf connection-id {
                     type string;
                   }
                   leaf connection-type {
                     type string;
                   }
                   leaf connection-status {
                     type string;
                   }
                   leaf last-change {
                     type string;
                   }
                   leaf up-transitions {
                     type int32;
                   }
                   leaf remote-pe {
                     type ipaddr;
                   }
                   leaf control-word {
                     type string;
                   }
                   leaf control-word-type {
                     type string;
                   }
                   leaf interface-encapsulation {
                     type string;
                   }
                   leaf inbound-label {
                     type string;
                   }
                   leaf outbound-label {
                     type string;
                   }
                   leaf pw-status-tlv {
                     type string;
                   }
                   leaf local-pw-status-code {
                     type int32;
                   }
                   leaf remote-pw-status-code {
                     type int32;
                   }
                   leaf connection-protection {
                     type string;
                   }
                   leaf vc-flow-label-transmit {
                     type string;
                   }
                   leaf vc-flow-label-receive {
                     type string;
                   }
                   leaf auto-sensed {
                     type empty;
                     description "Auto-sensed";
                   }
                   container local-interface {
                     leaf interface-name {
                       type string;
                       description "Name of interface";
                     }
                     leaf interface-status {
                       type string;
                     }
                     leaf working-status {
                       type string;
                     }
                     leaf profile-name {
                       type string;
                     }
                     leaf profile-varset-name {
                       type string;
                     }
                     leaf interface-description {
                       type string;
                     }
                   }
                   container remote-interface {
                     leaf interface-name {
                       type string;
                       description "Name of interface";
                     }
                     leaf interface-status {
                       type string;
                     }
                     leaf interface-encapsulation {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
               container automatic-site-timers {
                 leaf automatic-site-timers.heading {
                   type string;
                 }
                 leaf automatic-site-startup-wait-time {
                   type string;
                 }
                 leaf automatic-site-new-site-wait-time {
                   type string;
                 }
                 leaf automatic-site-collision-detect-time {
                   type string;
                 }
                 leaf automatic-site-reclaim-wait-time {
                   type string;
                 }
               }
             }
             container ldp-vpls-reference-site {
               description "Information about LDP-VPLS";
               leaf vpls-signaling-protocol-identifier {
                 type string;
               }
               leaf local-site-id {
                 type string;
               }
               leaf vpls-id {
                 type int32;
                 description "VPLS instance identifier";
               }
               leaf l2vpn-id {
                 type string;
               }
               leaf local-id {
                 type ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               container mesh-group-interfaces {
                 description "Information about all interfaces associated with a mesh-group";
                 leaf mesh-group-name {
                   type string;
                   description "Name of mesh-group";
                 }
                 leaf mesh-group-state {
                   type string;
                   description "Mesh-group state";
                 }
                 leaf mesh-group-id {
                   type int32;
                   description "Mesh-group Identifier";
                 }
                 container interface {
                   leaf interface-name {
                     type string;
                     description "Name of interface";
                   }
                   leaf interface-description {
                     type string;
                   }
                   leaf interface-flags-description {
                     type string;
                   }
                   leaf interface-flags {
                     type int32;
                   }
                 }
               }
               container interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               container connection {
                 leaf connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 leaf auto-sensed {
                   type empty;
                   description "Auto-sensed";
                 }
                 container local-interface {
                   leaf interface-name {
                     type string;
                     description "Name of interface";
                   }
                   leaf interface-status {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   description "Information about one or more VPLS RSVP-TE point-to-multipoint LSPs";
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   leaf log-time-stamp {
                     type string;
                   }
                   leaf log-event {
                     type string;
                   }
                   leaf changed-entity {
                     type string;
                   }
                 }
               }
               container mesh-group-connection {
                 description "Information about all vc-connections of a specific mesh-group";
                 leaf mesh-group-name {
                   type string;
                   description "Name of mesh-group";
                 }
                 container connection {
                   leaf connection.heading {
                     type string;
                   }
                   leaf connection-id {
                     type string;
                   }
                   leaf connection-type {
                     type string;
                   }
                   leaf connection-status {
                     type string;
                   }
                   leaf last-change {
                     type string;
                   }
                   leaf up-transitions {
                     type int32;
                   }
                   leaf remote-pe {
                     type ipaddr;
                   }
                   leaf control-word {
                     type string;
                   }
                   leaf control-word-type {
                     type string;
                   }
                   leaf interface-encapsulation {
                     type string;
                   }
                   leaf inbound-label {
                     type string;
                   }
                   leaf outbound-label {
                     type string;
                   }
                   leaf pw-status-tlv {
                     type string;
                   }
                   leaf local-pw-status-code {
                     type int32;
                   }
                   leaf remote-pw-status-code {
                     type int32;
                   }
                   leaf connection-protection {
                     type string;
                   }
                   leaf vc-flow-label-transmit {
                     type string;
                   }
                   leaf vc-flow-label-receive {
                     type string;
                   }
                   leaf auto-sensed {
                     type empty;
                     description "Auto-sensed";
                   }
                   container local-interface {
                     leaf interface-name {
                       type string;
                       description "Name of interface";
                     }
                     leaf interface-status {
                       type string;
                     }
                     leaf working-status {
                       type string;
                     }
                     leaf profile-name {
                       type string;
                     }
                     leaf profile-varset-name {
                       type string;
                     }
                     leaf interface-description {
                       type string;
                     }
                   }
                   container remote-interface {
                     leaf interface-name {
                       type string;
                       description "Name of interface";
                     }
                     leaf interface-status {
                       type string;
                     }
                     leaf interface-encapsulation {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
             }
             container vpls-protocol-state {
               leaf vpls-signaling-protocol-identifier {
                 type string;
               }
               leaf num-local-interfaces {
                 type int32;
               }
               leaf num-local-interfaces-up {
                 type int32;
               }
               leaf irb-present {
                 type string;
               }
               leaf mesh-group-count {
                 type int32;
               }
               leaf mesh-group-up-count {
                 type int32;
               }
               container mesh-group-interfaces {
                 description "Information about all interfaces associated with a mesh-group";
                 container interface {
                   leaf interface-flags {
                     type int32;
                   }
                 }
               }
               container interface {
                 leaf interface-flags {
                   type int32;
                 }
               }
               container mesh-group-connection {
                 description "Information about all vc-connections of a specific mesh-group";
                 leaf mesh-group-name {
                   type string;
                   description "Name of mesh-group";
                 }
                 container connection {
                   leaf connection.heading {
                     type string;
                   }
                   leaf remote-pe {
                     type ipaddr;
                   }
                   leaf l2vpn-local-site-id {
                     type int32;
                     description "Local site identifier";
                   }
                   leaf l2vpn-remote-site-id {
                     type int32;
                     description "Remote site identifier";
                   }
                   leaf connection-status {
                     type string;
                   }
                   leaf last-change {
                     type string;
                   }
                   leaf inbound-label {
                     type string;
                   }
                   leaf outbound-label {
                     type string;
                   }
                   container local-interface {
                     leaf interface-name {
                       type string;
                       description "Name of interface";
                     }
                     leaf interface-status {
                       type string;
                     }
                     leaf interface-encapsulation {
                       type string;
                     }
                     leaf working-status {
                       type string;
                     }
                     leaf profile-name {
                       type string;
                     }
                     leaf profile-varset-name {
                       type string;
                     }
                     leaf interface-description {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
               container reference-site {
                 leaf automatic-site-name {
                   type string;
                   description "VPLS automatic site name";
                 }
                 leaf automatic-site-id-status {
                   type string;
                   description "VPLS automatic site identifier status";
                 }
                 leaf automatic-site-claim-id {
                   type int32;
                   description "Claim site identifier";
                 }
                 leaf automatic-site-collisions {
                   type int32;
                   description "Number of collisions";
                 }
                 leaf automatic-site-timer-status {
                   type string;
                   description "VPLS automatic site timer status";
                 }
                 leaf vpls-signaling-protocol-identifier {
                   type string;
                 }
                 leaf local-site-id {
                   type string;
                 }
                 leaf source-attachment-id {
                   type string;
                   description "Local source attachment identifier";
                 }
                 leaf vpls-id {
                   type int32;
                   description "VPLS instance identifier";
                 }
                 leaf l2vpn-id {
                   type string;
                 }
                 leaf local-id {
                   type ipaddr;
                 }
                 leaf num-local-interfaces {
                   type int32;
                 }
                 leaf num-local-interfaces-up {
                   type int32;
                 }
                 leaf irb-present {
                   type string;
                 }
                 leaf mesh-group-count {
                   type int32;
                 }
                 leaf mesh-group-up-count {
                   type int32;
                 }
                 leaf remote-site-id {
                   type string;
                 }
                 leaf target-attachment-id {
                   type string;
                   description "Remote target attachment identifier";
                 }
                 container mesh-group-interfaces {
                   description "Information about all interfaces associated with a mesh-group";
                   leaf mesh-group-name {
                     type string;
                     description "Name of mesh-group";
                   }
                   leaf mesh-group-state {
                     type string;
                     description "Mesh-group state";
                   }
                   leaf mesh-group-id {
                     type int32;
                     description "Mesh-group Identifier";
                   }
                   container interface {
                     leaf interface-name {
                       type string;
                       description "Name of interface";
                     }
                     leaf interface-description {
                       type string;
                     }
                     leaf interface-flags-description {
                       type string;
                     }
                     leaf interface-flags {
                       type int32;
                     }
                   }
                 }
                 container interface {
                   leaf interface-name {
                     type string;
                     description "Name of interface";
                   }
                   leaf interface-id {
                     type int32;
                   }
                   leaf interface-description {
                     type string;
                   }
                   leaf interface-flags-description {
                     type string;
                   }
                   leaf interface-flags {
                     type int32;
                   }
                 }
                 container connection {
                 }
                 container mesh-group-connection {
                   description "Information about all vc-connections of a specific mesh-group";
                   container connection {
                   }
                 }
               }
             }
             container vpls-rsvp-te-ingress-p2mp-lsp {
               leaf vpls-ingress-p2mp-lsp-name {
                 type string;
                 description "Name of ingress point-to-multipoint LSP";
               }
               leaf vpls-rsvp-te-p2mp-flood-nexthop-id {
                 type int32;
                 description "Identifier for VPLS RSVP traffic-engineering ingress flood next hop";
               }
             }
             container multihome {
               leaf multihome.heading {
                 type string;
               }
               container multihome-site {
                 leaf multihome-site-name {
                   type string;
                   description "Name of site";
                 }
                 leaf multihome-site-id {
                   type int32;
                   description "Site Identifier";
                 }
                 leaf multihome-site-preference {
                   type int32;
                   description "Site Preference";
                 }
                 leaf multihome-site-state {
                   type string;
                   description "Site state";
                 }
                 leaf multihome-num-interfaces {
                   type int32;
                 }
                 leaf multihome-num-interfaces-up {
                   type int32;
                 }
                 container interface {
                   leaf interface-name {
                     type string;
                     description "Name of interface";
                   }
                   leaf interface-id {
                     type int32;
                   }
                   leaf interface-description {
                     type string;
                   }
                   leaf interface-flags-description {
                     type string;
                   }
                   leaf interface-flags {
                     type int32;
                   }
                 }
                 container remote-advertisements {
                   leaf remote-advertisements.heading {
                     type string;
                   }
                   container remote-adv {
                     leaf remote-adv-addr {
                       type string;
                     }
                     leaf remote-adv-preference {
                       type int32;
                       description "Remote PE preference";
                     }
                     leaf remote-adv-ctrl-flag {
                       type int32;
                       description "Remote PE Control flags";
                     }
                     leaf remote-adv-ctrl-flag-description {
                       type string;
                       description "Control flags description";
                     }
                   }
                 }
               }
             }
             container history {
               leaf history.category-heading {
                 type string;
               }
               leaf history.heading {
                 type string;
               }
               leaf log-time-stamp {
                 type string;
               }
               leaf log-event {
                 type string;
               }
               leaf changed-entity {
                 type string;
               }
             }
           }
           container summary {
             leaf instance-name {
               type string;
             }
             leaf instance-display-error {
               type string;
             }
             leaf edge-protection {
               type string;
             }
             leaf edge-protector {
               type string;
             }
             container reference-site {
               leaf automatic-site-name {
                 type string;
                 description "VPLS automatic site name";
               }
               leaf automatic-site-id-status {
                 type string;
                 description "VPLS automatic site identifier status";
               }
               leaf automatic-site-claim-id {
                 type int32;
                 description "Claim site identifier";
               }
               leaf automatic-site-collisions {
                 type int32;
                 description "Number of collisions";
               }
               leaf automatic-site-timer-status {
                 type string;
                 description "VPLS automatic site timer status";
               }
               leaf vpls-signaling-protocol-identifier {
                 type string;
               }
               leaf local-site-id {
                 type string;
               }
               leaf source-attachment-id {
                 type string;
                 description "Local source attachment identifier";
               }
               leaf vpls-id {
                 type int32;
                 description "VPLS instance identifier";
               }
               leaf l2vpn-id {
                 type string;
               }
               leaf local-id {
                 type ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               leaf target-attachment-id {
                 type string;
                 description "Remote target attachment identifier";
               }
               container mesh-group-interfaces {
                 description "Information about all interfaces associated with a mesh-group";
                 container interface {
                   leaf interface-flags {
                     type int32;
                   }
                 }
               }
               container interface {
                 leaf interface-flags {
                   type int32;
                 }
               }
               container connection {
               }
               container mesh-group-connection {
                 description "Information about all vc-connections of a specific mesh-group";
                 container connection {
                 }
               }
               container connections-summary {
                 leaf vc-up-count {
                   type int32;
                 }
                 leaf vc-down-count {
                   type int32;
                 }
               }
             }
             container ldp-vpls-reference-site {
               description "Information about LDP-VPLS";
               leaf vpls-signaling-protocol-identifier {
                 type string;
               }
               leaf local-site-id {
                 type string;
               }
               leaf vpls-id {
                 type int32;
                 description "VPLS instance identifier";
               }
               leaf l2vpn-id {
                 type string;
               }
               leaf local-id {
                 type ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               container mesh-group-interfaces {
                 description "Information about all interfaces associated with a mesh-group";
                 container interface {
                   leaf interface-flags {
                     type int32;
                   }
                 }
               }
               container interface {
                 leaf interface-flags {
                   type int32;
                 }
               }
               container connection {
               }
               container mesh-group-connection {
                 description "Information about all vc-connections of a specific mesh-group";
                 container connection {
                 }
               }
               container connections-summary {
                 leaf vc-up-count {
                   type int32;
                 }
                 leaf vc-down-count {
                   type int32;
                 }
               }
             }
             container vpls-protocol-state {
               leaf vpls-signaling-protocol-identifier {
                 type string;
               }
               leaf num-local-interfaces {
                 type int32;
               }
               leaf num-local-interfaces-up {
                 type int32;
               }
               leaf irb-present {
                 type string;
               }
               leaf mesh-group-count {
                 type int32;
               }
               leaf mesh-group-up-count {
                 type int32;
               }
               container mesh-group-interfaces {
                 description "Information about all interfaces associated with a mesh-group";
                 container interface {
                   leaf interface-flags {
                     type int32;
                   }
                 }
               }
               container interface {
                 leaf interface-flags {
                   type int32;
                 }
               }
               container mesh-group-connection {
                 description "Information about all vc-connections of a specific mesh-group";
                 leaf mesh-group-name {
                   type string;
                   description "Name of mesh-group";
                 }
                 container connection {
                 }
                 container connections-summary {
                   leaf vc-up-count {
                     type int32;
                   }
                   leaf vc-down-count {
                     type int32;
                   }
                 }
               }
               container reference-site {
                 container mesh-group-interfaces {
                   description "Information about all interfaces associated with a mesh-group";
                   container interface {
                     leaf interface-flags {
                       type int32;
                     }
                   }
                 }
                 container interface {
                   leaf interface-flags {
                     type int32;
                   }
                 }
                 container connection {
                 }
                 container mesh-group-connection {
                   description "Information about all vc-connections of a specific mesh-group";
                   container connection {
                   }
                 }
               }
             }
             container multihome {
               container multihome-site {
                 container interface {
                   leaf interface-flags {
                     type int32;
                   }
                 }
                 container remote-advertisements {
                 }
               }
             }
           }
         }
         container interface-statistics {
           leaf remote-pe {
             type ipaddr;
           }
           leaf broadcast-packets {
             type uint64;
             description "Broadcast packets";
           }
           leaf broadcast-bytes {
             type uint64;
             description "Broadcast bytes";
           }
           leaf multicast-packets {
             type uint64;
             description "Multicast packets";
           }
           leaf multicast-bytes {
             type uint64;
             description "Multicast bytes";
           }
           leaf flooded-packets {
             type uint64;
             description "Flooded packets";
           }
           leaf flooded-bytes {
             type uint64;
             description "Flooded bytes";
           }
           leaf unicast-packets {
             type uint64;
             description "Unicast packets";
           }
           leaf unicast-bytes {
             type uint64;
             description "Unicast bytes";
           }
           leaf num-mac-count {
             type int32;
             description "Number of addresses learned on the interface";
           }
           leaf mac-limit {
             type int32;
             description "Limit of number of addresses learned on interface";
           }
           container interface {
             leaf interface-name {
               type string;
               description "Name of interface";
             }
             leaf local-interface-index {
               type int32;
               description "SNMP ifIndex of local interface";
             }
             leaf interface-flags {
               type int32;
             }
           }
         }
       }
     }
   }
   rpc get-evpn-database-information {
     description "Show EVPN internal MAC database";
     input {
       leaf mac-address {
         description "Display a specifc MAC address";
         type mac-addr;
       }
       leaf instance {
         description "Display MAC address from a specifiec EVPN instance";
         type string;
       }
       leaf l2-domain-id {
         description "Display MAC address with a specific VLAN or VNI or ISID";
         type int32 {
           range "1 .. 16777214";
         }
       }
       leaf esi {
         description "Ethernet segment identifier";
         type string;
       }
       container origin-choice {
         choice origin-choice_c {
           case neighbor {
             leaf neighbor {
               description "Display MAC address learned from a specifiec neighbor";
               type ipaddr;
             }
           }
           case interface {
             leaf interface {
               description "Display MAC address learned from a specifiec interface";
               type string;
             }
           }
           case origin {
             leaf origin {
               description "Display MAC address with a specific origin";
               type enumeration {
                 enum "local" {
                   description "Display local MAC address";
                 }
                 enum "remote" {
                   description "Display remote MAC address";
                 }
               }
             }
           }
         }
       }
       leaf state {
         description "Display MAC address with a specific state";
         type enumeration {
           enum "default-gateway" {
             description "Display default gateway MAC address";
           }
           enum "static" {
             description "Display static MAC address";
           }
         }
       }
       leaf verbosity {
         type enumeration {
           enum "extensive" {
             description "Display extensive version of output";
           }
         }
       }
     }
     output {
       container evpn-database-information {
         container evpn-database-instance {
           container normal {
             leaf instance-name {
               type string;
             }
             container mac-entry {
               leaf vlan-id {
                 type int32;
               }
               leaf vni-id {
                 type int32;
               }
               leaf isid-val {
                 type int32;
               }
               leaf mac-address {
                 type mac-addr;
               }
               leaf active-source {
                 type string;
               }
               leaf active-source-timestamp {
                 type string;
               }
               leaf ip-address {
                 type ipaddr;
               }
               container extensive {
                 leaf mac-state {
                   type string;
                 }
                 leaf nexthop-id {
                   type string;
                 }
                 container mac-source {
                   leaf source-name {
                     type string;
                   }
                   leaf source-rank {
                     type string;
                   }
                   leaf source-status {
                     type string;
                   }
                   leaf source-local-origin {
                     type string;
                   }
                   leaf source-remote-origin {
                     type string;
                   }
                   leaf source-remote-mac-label {
                     type int32;
                   }
                   leaf source-local-mac-label {
                     type int32;
                   }
                   leaf source-timestamp {
                     type string;
                   }
                   leaf source-timestamp-value {
                     type int32;
                   }
                   leaf source-state {
                     type string;
                   }
                 }
               }
             }
           }
           container extensive {
             leaf instance-name {
               type string;
             }
             container mac-entry {
               leaf vlan-id {
                 type int32;
               }
               leaf vni-id {
                 type int32;
               }
               leaf mac-address {
                 type mac-addr;
               }
               leaf isid-val {
                 type int32;
               }
               leaf active-source {
                 type string;
               }
               leaf mac-state {
                 type string;
               }
               leaf nexthop-id {
                 type string;
               }
               container normal {
                 leaf active-source-timestamp {
                   type string;
                 }
                 leaf ip-address {
                   type ipaddr;
                 }
                 container mac-source {
                 }
               }
               container extensive {
                 leaf vlan-id {
                   type int32;
                 }
                 leaf vni-id {
                   type int32;
                 }
                 leaf mac-address {
                   type mac-addr;
                 }
                 leaf isid-val {
                   type int32;
                 }
                 leaf active-source {
                   type string;
                 }
                 leaf mac-state {
                   type string;
                 }
                 leaf nexthop-id {
                   type string;
                 }
                 container mac-source {
                   leaf source-name {
                     type string;
                   }
                   leaf source-rank {
                     type string;
                   }
                   leaf source-status {
                     type string;
                   }
                   leaf source-local-origin {
                     type string;
                   }
                   leaf source-remote-origin {
                     type string;
                   }
                   leaf source-remote-mac-label {
                     type int32;
                   }
                   leaf source-local-mac-label {
                     type int32;
                   }
                   leaf source-timestamp {
                     type string;
                   }
                   leaf source-timestamp-value {
                     type int32;
                   }
                   leaf source-state {
                     type string;
                   }
                 }
               }
             }
           }
         }
       }
     }
   }
   rpc get-evpn-vpws-information {
     description "Show EVPN VPWS instance information";
     input {
       leaf instance-name {
         description "Name of EVPN VPWS instance";
         default "all";
         type string;
       }
     }
     output {
       container evpn-vpws-information {
         container evpn-vpws-instance {
           container normal {
             leaf evpn-vpws-instance-name {
               type string;
             }
             leaf route-distinguisher {
               type string;
             }
             leaf local-interfaces {
               type int32;
             }
             leaf local-interfaces-up {
               type int32;
             }
             container evpn-vpws-interface-status-table {
             }
             container evpn-vpws-esi-info-status-table {
               container normal {
                 container evpn-vpws-esi-info {
                   leaf evpn-vpws-esi-val {
                     type string;
                   }
                   leaf evpn-vpws-num-pes {
                     type int32;
                   }
                   container evpn-vpws-esi-pe-status-table {
                   }
                 }
               }
             }
             container evpn-vpws-esi-df-table {
               leaf evpn-esi-value {
                 type string;
               }
               leaf evpn-vpws-esi-df-min-sid {
                 type int32;
               }
               leaf evpn-vpws-esi-df-primary-pe {
                 type string;
               }
               leaf evpn-vpws-esi-df-backup-pe {
                 type string;
               }
               leaf evpn-vpws-esi-df-other-pe {
                 type string;
               }
               leaf evpn-vpws-esi-df-timestamp {
                 type string;
               }
               container normal {
               }
             }
             container evpn-vpws-service-id-local-status-table {
               container normal {
                 container evpn-vpws-sid-local {
                   leaf evpn-vpws-sid-local-value {
                     type int32;
                   }
                   leaf evpn-vpws-sid-advertised-label {
                     type int32;
                   }
                   leaf evpn-vpws-sid-local-interface-name {
                     type string;
                   }
                   leaf evpn-vpws-sid-remote-interface-name {
                     type string;
                   }
                   leaf evpn-vpws-sid-local-interface-status {
                     type string;
                   }
                   container evpn-vpws-sid-pe-status-table {
                   }
                 }
               }
             }
             container evpn-vpws-sid-pe-status-table {
               container normal {
                 container evpn-vpws-sid-pe-info {
                   leaf evpn-vpws-sid-pe-ipaddr {
                     type ipaddr;
                   }
                   leaf evpn-vpws-sid-interface-esi {
                     type string;
                   }
                   leaf evpn-vpws-sid-pe-label {
                     type int32;
                   }
                   leaf evpn-vpws-sid-pe-mode {
                     type string;
                   }
                   leaf evpn-vpws-sid-pe-role {
                     type string;
                   }
                   leaf evpn-vpws-sid-pe-ts {
                     type string;
                   }
                   leaf evpn-vpws-sid-pe-status {
                     type string;
                   }
                 }
               }
             }
             container evpn-vpws-service-id-remote-status-table {
               container normal {
                 container evpn-vpws-sid-remote {
                   leaf evpn-vpws-sid-remote-value {
                     type int32;
                   }
                   leaf evpn-vpws-sid-local-interface-name {
                     type string;
                   }
                   leaf evpn-vpws-sid-local-interface-status {
                     type string;
                   }
                   leaf evpn-vpws-sid-remote-interface-name {
                     type string;
                   }
                   container evpn-vpws-sid-pe-status-table {
                   }
                 }
               }
             }
           }
         }
       }
     }
   }
   rpc get-evpn-l3-context-information {
     description "Show EVPN L3 context information";
     input {
       leaf l3-context-name {
         description "Name of EVPN L3 context";
         default "all";
         type string;
       }
       leaf verbosity {
         type enumeration {
           enum "brief" {
             description "Display brief version of output";
           }
           enum "extensive" {
             description "Display extensive version of output";
           }
         }
       }
     }
     output {
       container evpn-l3-context-information {
         container evpn-l3-context {
           container extensive {
             leaf context-name {
               type string;
             }
             leaf context-type {
               type string;
               description "Type";
             }
             leaf context-advertisement-mode {
               type string;
             }
             leaf context-gateway-interface {
               type string;
             }
             leaf context-router-mac {
               type string;
             }
             leaf context-encapsulation {
               type string;
             }
             leaf context-label {
               type int32;
             }
             leaf context-vni {
               type int32;
             }
             leaf context-import-policy {
               type string;
             }
             leaf context-export-policy {
               type string;
             }
             leaf route-distinguisher {
               type string;
             }
             leaf context-flags {
               type int32;
             }
             leaf context-flags-descriptions {
               type string;
             }
             leaf context-change-flags {
               type int32;
             }
             leaf context-change-flags-descriptions {
               type string;
             }
             leaf context-composite-nexthop-support {
               type string;
             }
             leaf context-reference-count {
               type int32;
             }
             container context-overlay-gateway {
               leaf gateway-family {
                 type string;
               }
               leaf gateway-address {
                 type ipaddr;
               }
             }
             container context-source-vtep {
               leaf vtep-family {
                 type string;
               }
               leaf vtep-address {
                 type ipaddr;
               }
               container extensive {
               }
             }
           }
           container normal {
             leaf context-name {
               type string;
             }
             leaf context-type {
               type string;
               description "Type";
             }
             leaf context-advertisement-mode {
               type string;
             }
             leaf context-encapsulation {
               type string;
             }
             leaf context-vni {
               type int32;
             }
             leaf context-label {
               type int32;
             }
             leaf context-router-mac {
               type string;
             }
             leaf context-gateway-interface {
               type string;
             }
             container context-overlay-gateway {
               container extensive {
                 leaf gateway-family {
                   type string;
                 }
                 leaf gateway-address {
                   type ipaddr;
                 }
               }
             }
             container context-source-vtep {
               container extensive {
                 leaf vtep-family {
                   type string;
                 }
                 leaf vtep-address {
                   type ipaddr;
                 }
               }
             }
           }
         }
       }
     }
   }
   rpc get-evpn-ip-prefix-database-information {
     description "Show EVPN internal IP prefix database";
     input {
       leaf l3-context {
         description "Display IP prefix from a specific EVPN L3 context";
         type string;
       }
       leaf family {
         description "Display IP prefix with a specific address family";
         type enumeration {
           enum "inet" {
             description "Display IPv4 prefixes";
           }
           enum "inet6" {
             description "Display IPv6 prefixes";
           }
         }
       }
       leaf direction {
         description "Display IP prefix with a specific import/export direction";
         type enumeration {
           enum "imported" {
             description "Display imported EVPN IP prefixes";
           }
           enum "exported" {
             description "Display exported IP prefixes";
           }
         }
       }
       leaf prefix {
         description "Display a specifc IP prefix";
         type ipprefix;
       }
       leaf ethernet-tag {
         description "Display IP prefix with a specific ethernet tag";
         type int32 {
           range "0 .. 16777214";
         }
       }
       leaf gateway {
         description "Display IP prefix with a specific overlay gateway address";
         type ipaddr;
       }
       leaf esi {
         description "Display IP prefix with a specific overlay ESI";
         type string;
       }
       leaf nexthop {
         description "Display IP prefix with a specific underlay nexthop";
         type ipaddr;
       }
       leaf verbosity {
         type enumeration {
           enum "extensive" {
             description "Display extensive version of output";
           }
         }
       }
     }
     output {
       container evpn-ip-prefix-database-information {
         container evpn-pfxdb-l3-context {
           container normal {
             leaf context-name {
               type string;
             }
             container evpn-pfxdb-ip-table {
               leaf table-description {
                 type string;
               }
               container extensive {
                 container evpn-pfxdb-ip-entry {
                   leaf entry-prefix {
                     type ipprefix;
                   }
                   leaf entry-evpn-route-status {
                     type string;
                   }
                   leaf entry-evpn-route-error {
                     type string;
                   }
                   leaf entry-change-flags {
                     type int32;
                   }
                   leaf entry-change-flags-descriptions {
                     type string;
                   }
                   leaf entry-advertisement-mode {
                     type string;
                   }
                   leaf entry-encap {
                     type string;
                   }
                   leaf entry-vni {
                     type int32;
                   }
                   leaf entry-label {
                     type int32;
                   }
                   leaf entry-overlay-gateway-address {
                     type ipaddr;
                   }
                   leaf entry-router-mac {
                     type string;
                   }
                 }
               }
             }
             container evpn-pfxdb-evpn-ip-table {
               leaf table-description {
                 type string;
               }
               container normal {
                 container evpn-pfxdb-evpn-ip-entry {
                   leaf entry-prefix {
                     type ipprefix;
                   }
                   leaf entry-etag {
                     type int32;
                   }
                   container extensive {
                     leaf entry-change-flags {
                       type int32;
                     }
                     leaf entry-change-flags-descriptions {
                       type string;
                     }
                     container evpn-pfxdb-evpn-ip-adv {
                     }
                   }
                 }
                 container evpn-pfxdb-evpn-ip-adv {
                   leaf route-distinguisher {
                     type string;
                   }
                   leaf adv-vni {
                     type int32;
                   }
                   leaf adv-label {
                     type int32;
                   }
                   leaf adv-router-mac {
                     type string;
                   }
                   leaf adv-bgp-nexthop {
                     type ipaddr;
                   }
                   leaf adv-overlay-gateway-address {
                     type ipaddr;
                   }
                   leaf adv-esi {
                     type string;
                   }
                   container normal {
                   }
                   container extensive {
                     leaf route-distinguisher {
                       type string;
                     }
                     leaf adv-vni {
                       type int32;
                     }
                     leaf adv-label {
                       type int32;
                     }
                     leaf adv-router-mac {
                       type string;
                     }
                     leaf adv-bgp-nexthop {
                       type ipaddr;
                     }
                     leaf adv-overlay-gateway-address {
                       type ipaddr;
                     }
                     leaf adv-esi {
                       type string;
                     }
                     leaf adv-ip-route-status {
                       type string;
                     }
                     leaf adv-ip-route-error {
                       type string;
                     }
                   }
                 }
               }
               container extensive {
                 leaf table-description {
                   type string;
                 }
                 container evpn-pfxdb-evpn-ip-entry {
                   leaf entry-prefix {
                     type ipprefix;
                   }
                   leaf entry-etag {
                     type int32;
                   }
                   leaf entry-change-flags {
                     type int32;
                   }
                   leaf entry-change-flags-descriptions {
                     type string;
                   }
                   container normal {
                     container evpn-pfxdb-evpn-ip-adv {
                     }
                   }
                   container extensive {
                     leaf entry-prefix {
                       type ipprefix;
                     }
                     leaf entry-etag {
                       type int32;
                     }
                     leaf entry-change-flags {
                       type int32;
                     }
                     leaf entry-change-flags-descriptions {
                       type string;
                     }
                     container evpn-pfxdb-evpn-ip-adv {
                       container normal {
                         leaf route-distinguisher {
                           type string;
                         }
                         leaf adv-vni {
                           type int32;
                         }
                         leaf adv-label {
                           type int32;
                         }
                         leaf adv-router-mac {
                           type string;
                         }
                         leaf adv-bgp-nexthop {
                           type ipaddr;
                         }
                         leaf adv-overlay-gateway-address {
                           type ipaddr;
                         }
                         leaf adv-esi {
                           type string;
                         }
                       }
                     }
                   }
                 }
                 container evpn-pfxdb-evpn-ip-adv {
                   leaf route-distinguisher {
                     type string;
                   }
                   leaf adv-vni {
                     type int32;
                   }
                   leaf adv-label {
                     type int32;
                   }
                   leaf adv-router-mac {
                     type string;
                   }
                   leaf adv-bgp-nexthop {
                     type ipaddr;
                   }
                   leaf adv-overlay-gateway-address {
                     type ipaddr;
                   }
                   leaf adv-esi {
                     type string;
                   }
                   leaf adv-ip-route-status {
                     type string;
                   }
                   leaf adv-ip-route-error {
                     type string;
                   }
                   container normal {
                   }
                   container extensive {
                     leaf route-distinguisher {
                       type string;
                     }
                     leaf adv-vni {
                       type int32;
                     }
                     leaf adv-label {
                       type int32;
                     }
                     leaf adv-router-mac {
                       type string;
                     }
                     leaf adv-bgp-nexthop {
                       type ipaddr;
                     }
                     leaf adv-overlay-gateway-address {
                       type ipaddr;
                     }
                     leaf adv-esi {
                       type string;
                     }
                     leaf adv-ip-route-status {
                       type string;
                     }
                     leaf adv-ip-route-error {
                       type string;
                     }
                   }
                 }
               }
             }
           }
           container extensive {
             leaf context-name {
               type string;
             }
             container evpn-pfxdb-ip-table {
               leaf table-description {
                 type string;
               }
               container normal {
                 container evpn-pfxdb-ip-entry {
                   leaf entry-prefix {
                     type ipprefix;
                   }
                   leaf entry-evpn-route-status {
                     type string;
                   }
                 }
               }
               container extensive {
                 leaf table-description {
                   type string;
                 }
                 container evpn-pfxdb-ip-entry {
                   leaf entry-prefix {
                     type ipprefix;
                   }
                   leaf entry-evpn-route-status {
                     type string;
                   }
                   leaf entry-evpn-route-error {
                     type string;
                   }
                   leaf entry-change-flags {
                     type int32;
                   }
                   leaf entry-change-flags-descriptions {
                     type string;
                   }
                   leaf entry-advertisement-mode {
                     type string;
                   }
                   leaf entry-encap {
                     type string;
                   }
                   leaf entry-vni {
                     type int32;
                   }
                   leaf entry-label {
                     type int32;
                   }
                   leaf entry-overlay-gateway-address {
                     type ipaddr;
                   }
                   leaf entry-router-mac {
                     type string;
                   }
                   container normal {
                   }
                   container extensive {
                     leaf entry-prefix {
                       type ipprefix;
                     }
                     leaf entry-evpn-route-status {
                       type string;
                     }
                     leaf entry-evpn-route-error {
                       type string;
                     }
                     leaf entry-change-flags {
                       type int32;
                     }
                     leaf entry-change-flags-descriptions {
                       type string;
                     }
                     leaf entry-advertisement-mode {
                       type string;
                     }
                     leaf entry-encap {
                       type string;
                     }
                     leaf entry-vni {
                       type int32;
                     }
                     leaf entry-label {
                       type int32;
                     }
                     leaf entry-overlay-gateway-address {
                       type ipaddr;
                     }
                     leaf entry-router-mac {
                       type string;
                     }
                   }
                 }
               }
             }
             container evpn-pfxdb-evpn-ip-table {
               leaf table-description {
                 type string;
               }
               container normal {
                 container evpn-pfxdb-evpn-ip-entry {
                   leaf entry-prefix {
                     type ipprefix;
                   }
                   leaf entry-etag {
                     type int32;
                   }
                   container extensive {
                     leaf entry-change-flags {
                       type int32;
                     }
                     leaf entry-change-flags-descriptions {
                       type string;
                     }
                     container evpn-pfxdb-evpn-ip-adv {
                     }
                   }
                 }
                 container evpn-pfxdb-evpn-ip-adv {
                   leaf route-distinguisher {
                     type string;
                   }
                   leaf adv-vni {
                     type int32;
                   }
                   leaf adv-label {
                     type int32;
                   }
                   leaf adv-router-mac {
                     type string;
                   }
                   leaf adv-bgp-nexthop {
                     type ipaddr;
                   }
                   leaf adv-overlay-gateway-address {
                     type ipaddr;
                   }
                   leaf adv-esi {
                     type string;
                   }
                   container normal {
                   }
                   container extensive {
                     leaf route-distinguisher {
                       type string;
                     }
                     leaf adv-vni {
                       type int32;
                     }
                     leaf adv-label {
                       type int32;
                     }
                     leaf adv-router-mac {
                       type string;
                     }
                     leaf adv-bgp-nexthop {
                       type ipaddr;
                     }
                     leaf adv-overlay-gateway-address {
                       type ipaddr;
                     }
                     leaf adv-esi {
                       type string;
                     }
                     leaf adv-ip-route-status {
                       type string;
                     }
                     leaf adv-ip-route-error {
                       type string;
                     }
                   }
                 }
               }
               container extensive {
                 leaf table-description {
                   type string;
                 }
                 container evpn-pfxdb-evpn-ip-entry {
                   leaf entry-prefix {
                     type ipprefix;
                   }
                   leaf entry-etag {
                     type int32;
                   }
                   leaf entry-change-flags {
                     type int32;
                   }
                   leaf entry-change-flags-descriptions {
                     type string;
                   }
                   container normal {
                     container evpn-pfxdb-evpn-ip-adv {
                     }
                   }
                   container extensive {
                     leaf entry-prefix {
                       type ipprefix;
                     }
                     leaf entry-etag {
                       type int32;
                     }
                     leaf entry-change-flags {
                       type int32;
                     }
                     leaf entry-change-flags-descriptions {
                       type string;
                     }
                     container evpn-pfxdb-evpn-ip-adv {
                       container normal {
                         leaf route-distinguisher {
                           type string;
                         }
                         leaf adv-vni {
                           type int32;
                         }
                         leaf adv-label {
                           type int32;
                         }
                         leaf adv-router-mac {
                           type string;
                         }
                         leaf adv-bgp-nexthop {
                           type ipaddr;
                         }
                         leaf adv-overlay-gateway-address {
                           type ipaddr;
                         }
                         leaf adv-esi {
                           type string;
                         }
                       }
                     }
                   }
                 }
                 container evpn-pfxdb-evpn-ip-adv {
                   leaf route-distinguisher {
                     type string;
                   }
                   leaf adv-vni {
                     type int32;
                   }
                   leaf adv-label {
                     type int32;
                   }
                   leaf adv-router-mac {
                     type string;
                   }
                   leaf adv-bgp-nexthop {
                     type ipaddr;
                   }
                   leaf adv-overlay-gateway-address {
                     type ipaddr;
                   }
                   leaf adv-esi {
                     type string;
                   }
                   leaf adv-ip-route-status {
                     type string;
                   }
                   leaf adv-ip-route-error {
                     type string;
                   }
                   container normal {
                   }
                   container extensive {
                     leaf route-distinguisher {
                       type string;
                     }
                     leaf adv-vni {
                       type int32;
                     }
                     leaf adv-label {
                       type int32;
                     }
                     leaf adv-router-mac {
                       type string;
                     }
                     leaf adv-bgp-nexthop {
                       type ipaddr;
                     }
                     leaf adv-overlay-gateway-address {
                       type ipaddr;
                     }
                     leaf adv-esi {
                       type string;
                     }
                     leaf adv-ip-route-status {
                       type string;
                     }
                     leaf adv-ip-route-error {
                       type string;
                     }
                   }
                 }
               }
             }
           }
         }
       }
     }
   }
   rpc get-evpn-mac-table {
     description "Show media access control table";
     input {
       leaf instance {
         description "Display information for a specified vpls";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Display MAC address learned on a specified VLAN";
         type string;
       }
       leaf isid {
         description "Display Information for specified ISID or all ISID(s)";
         type string;
       }
       leaf address {
         description "MAC address";
         default "all";
         type mac-addr;
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       container l2ald-rtb-macdb {
         leaf l2ald-macdb-rtb-name {
           type string;
           description "Bridging MAC database for a routing instance";
         }
         container l2ald-mac-entry {
           container brief {
             leaf l2-mac-address {
               type mac-addr;
               description "Media access control address learned from another source";
             }
             leaf l2-mac-logical-interface {
               type string;
               description "Name of logical interface on which MAC address was learned";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pvlan {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pbn-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-beb-mac-address {
               type mac-addr;
               description "Media access control address of remote backbone edge bridge (BEB)";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container extensive {
             leaf l2-mac-address {
               type mac-addr;
               description "Media access control address learned from another source";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-logical-interface {
               type string;
               description "Name of logical interface on which MAC address was learned";
             }
             leaf l2-mac-base-logical-interface {
               type string;
               description "Name of logical interface on which MAC address was learnt first";
             }
             leaf l2-remote-beb-mac-address {
               type mac-addr;
               description "Media access control address of remote backbone edge bridge (BEB)";
             }
             leaf l2-mac-entry-flags {
               type string;
               description "Forwarding entry flags associated with these MAC addresses";
             }
             leaf l2-mac-epoch {
               type uint32;
               description "Spanning Tree Protocol (STP) epoch number when MAC address was learned";
             }
             leaf l2-mac-sequence-number {
               type uint32;
               description "Sequence number assigned to this MAC address";
             }
             leaf l2-mac-learn-mask {
               type string;
               description "Mask of Packet Forwarding Engines where this MAC address was learned";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
             container l2ald-mac-source-address-statistics {
               description "MAC source address statistics";
               leaf packet-count {
                 type uint64;
                 description "Packet count";
               }
               leaf byte-count {
                 type uint64;
                 description "Byte count";
               }
             }
             container l2ald-mac-destination-address-statistics {
               description "MAC destination address statistics";
               leaf packet-count {
                 type uint64;
                 description "Packet count";
               }
               leaf byte-count {
                 type uint64;
                 description "Byte count";
               }
             }
           }
           container brief-rvtep {
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-vtep-address {
               type string;
               description "Remote VXLAN tunnel endpoint ip address";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-vxlan-evpn {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-active-source {
               type string;
               description "Remote VXLAN tunnel endpoint ip address or ESI value";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
         }
       }
     }
   }
   rpc get-evpn-interface-mac-table {
     description "Display MAC table for a specified interface";
     input {
       container interface-choice {
         choice interface-choice_c {
           case interface-name {
             leaf interface-name {
               description "Name of interface for which to display table";
               type string;
             }
           }
           case all {
             leaf all {
               description "Display MAC table for all the interfaces";
               type empty;
             }
           }
         }
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       container l2ald-interface-macdb {
         leaf l2ald-macdb-if-name {
           type string;
         }
         container l2ald-mac-entry {
           container brief {
             leaf l2-mac-address {
               type mac-addr;
               description "Media access control address learned from another source";
             }
             leaf l2-mac-logical-interface {
               type string;
               description "Name of logical interface on which MAC address was learned";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pvlan {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pbn-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-beb-mac-address {
               type mac-addr;
               description "Media access control address of remote backbone edge bridge (BEB)";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container extensive {
             leaf l2-mac-address {
               type mac-addr;
               description "Media access control address learned from another source";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-logical-interface {
               type string;
               description "Name of logical interface on which MAC address was learned";
             }
             leaf l2-mac-base-logical-interface {
               type string;
               description "Name of logical interface on which MAC address was learnt first";
             }
             leaf l2-remote-beb-mac-address {
               type mac-addr;
               description "Media access control address of remote backbone edge bridge (BEB)";
             }
             leaf l2-mac-entry-flags {
               type string;
               description "Forwarding entry flags associated with these MAC addresses";
             }
             leaf l2-mac-epoch {
               type uint32;
               description "Spanning Tree Protocol (STP) epoch number when MAC address was learned";
             }
             leaf l2-mac-sequence-number {
               type uint32;
               description "Sequence number assigned to this MAC address";
             }
             leaf l2-mac-learn-mask {
               type string;
               description "Mask of Packet Forwarding Engines where this MAC address was learned";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
             container l2ald-mac-source-address-statistics {
               description "MAC source address statistics";
               leaf packet-count {
                 type uint64;
                 description "Packet count";
               }
               leaf byte-count {
                 type uint64;
                 description "Byte count";
               }
             }
             container l2ald-mac-destination-address-statistics {
               description "MAC destination address statistics";
               leaf packet-count {
                 type uint64;
                 description "Packet count";
               }
               leaf byte-count {
                 type uint64;
                 description "Byte count";
               }
             }
           }
           container brief-rvtep {
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-vtep-address {
               type string;
               description "Remote VXLAN tunnel endpoint ip address";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-vxlan-evpn {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-active-source {
               type string;
               description "Remote VXLAN tunnel endpoint ip address or ESI value";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
         }
       }
     }
   }
   rpc get-evpn-flood-information {
     description "Show EVPN flooding information";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf verbosity {
         default "detail";
         type enumeration {
           enum "detail" {
             description "Display detailed output";
           }
           enum "brief" {
             description "Display brief output";
           }
           enum "extensive" {
             description "Display extensive output";
           }
         }
       }
     }
   }
   rpc get-evpn-ce-flood-route-information {
     description "Show customer edge flood route";
     input {
       leaf interface {
         description "Interface for which to show CE flood route";
         type interface-unit;
         mandatory true;
       }
     }
   }
   rpc get-evpn-all-flood-route-information {
     description "Show route for flooding traffic from customer edge router";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
   }
   rpc get-evpn-all-ce-flood-route-information {
     description "Show route for flooding traffic to all CE routers";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
   }
   rpc get-evpn-re-flood-route-information {
     description "Show route for Routing Engine flooding to all interfaces";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
   }
   rpc get-evpn-mlp-flood-route-information {
     description "Show route for flooding traffic to MAC learning chips";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
   }
   rpc get-evpn-alt-root-flood-route-information {
     description "Show STP alt-root flooding route used for interface";
     input {
       leaf interface {
         description "Interface for which to show alternate-root flooding route";
         type interface-unit;
         mandatory true;
       }
     }
   }
   rpc get-evpn-event-queue-information {
     description "Show queue of pending EVPN flood events";
   }
   rpc get-evpn-arp-table {
     description "Show ARP entries associated with MACs learned";
     input {
       leaf instance {
         description "Display information for a specified vpls";
         default "all";
         type string;
       }
       leaf address {
         description "MAC address";
         default "all";
         type mac-addr;
       }
       leaf show-choice {
         default "brief";
         type enumeration {
           enum "detail" {
             description "Display detailed output";
           }
           enum "brief" {
             description "Display brief output";
           }
           enum "extensive" {
             description "Display extensive output";
           }
           enum "count" {
             description "Display count only";
           }
         }
       }
     }
     output {
       container l2rtb-evpn-arp-db {
         leaf l2rtb-evpn-arp-db-rtb-name {
           type string;
           description "Bridging MAC INET database for a routing instance";
         }
         container l2rtb-evpn-arp-entry {
           container brief {
             leaf l2-evpn-arp-inet-address {
               type ipaddr;
               description "INET addresses learned via ARP";
             }
             leaf l2-mac-address {
               type mac-addr;
               description "Media access control address learned from another source";
             }
             leaf l2-mac-logical-interface {
               type string;
               description "Name of logical interface on which MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
           }
           container brief-rtb {
             leaf l2-mac-routing-instance {
               type string;
               description "Routing instance in which the MAC address was learned";
             }
             leaf l2-mac-bridging-domain {
               type string;
               description "Bridging domain in which the MAC address was learned";
             }
             leaf l2-evpn-arp-inet-address {
               type ipaddr;
               description "INET addresses learned via ARP";
             }
             leaf l2-mac-address {
               type mac-addr;
               description "Media access control address learned from another source";
             }
             leaf l2-mac-logical-interface {
               type string;
               description "Name of logical interface on which MAC address was learned";
             }
             leaf l2-mac-interface-device {
               type string;
               description "Name of interface device on which MAC address was learned";
             }
           }
           container extensive {
             leaf l2-evpn-arp-inet-address {
               type ipaddr;
               description "INET addresses learned via ARP";
             }
             leaf l2-mac-address {
               type mac-addr;
               description "Media access control address learned from another source";
             }
             leaf l2-mac-routing-instance {
               type string;
               description "Routing instance in which the MAC address was learned";
             }
             leaf l2-mac-bridging-domain {
               type string;
               description "Bridging domain in which the MAC address was learned";
             }
             leaf l2-mac-logical-interface {
               type string;
               description "Name of logical interface on which MAC address was learned";
             }
             leaf l2-mac-interface-device {
               type string;
               description "Name of interface device on which MAC address was learned";
             }
             container l2ald-mac-destination-address-statistics {
               description "MAC destination address statistics";
               leaf packet-count {
                 type uint64;
                 description "Packet count";
               }
               leaf byte-count {
                 type uint64;
                 description "Byte count";
               }
             }
             container l2ald-mac-source-address-statistics {
               description "MAC source address statistics";
               leaf packet-count {
                 type uint64;
                 description "Packet count";
               }
               leaf byte-count {
                 type uint64;
                 description "Byte count";
               }
             }
           }
         }
       }
     }
   }
   rpc get-evpn-nd-table {
     description "Show ND entries associated with MACs learned";
     input {
       leaf instance {
         description "Display information for a specified vpls";
         default "all";
         type string;
       }
       leaf address {
         description "MAC address";
         default "all";
         type mac-addr;
       }
       leaf show-choice {
         default "brief";
         type enumeration {
           enum "detail" {
             description "Display detailed output";
           }
           enum "brief" {
             description "Display brief output";
           }
           enum "extensive" {
             description "Display extensive output";
           }
           enum "count" {
             description "Display count only";
           }
         }
       }
     }
     output {
       container l2rtb-evpn-nd-db {
         leaf l2rtb-evpn-nd-db-rtb-name {
           type string;
           description "Bridging MAC INET6 database for a routing instance";
         }
         container l2rtb-evpn-nd-entry {
           container brief {
             leaf l2-evpn-nd-inet6-address {
               type ipv6addr;
               description "INET6 addresses learned via NDP";
             }
             leaf l2-mac-address {
               type mac-addr;
               description "Media access control address learned from another source";
             }
             leaf l2-mac-logical-interface {
               type string;
               description "Name of logical interface on which MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
           }
           container brief-rtb {
             leaf l2-mac-routing-instance {
               type string;
               description "Routing instance in which the MAC address was learned";
             }
             leaf l2-mac-bridging-domain {
               type string;
               description "Bridging domain in which the MAC address was learned";
             }
             leaf l2-evpn-nd-inet6-address {
               type ipv6addr;
               description "INET6 addresses learned via NDP";
             }
             leaf l2-mac-address {
               type mac-addr;
               description "Media access control address learned from another source";
             }
             leaf l2-mac-logical-interface {
               type string;
               description "Name of logical interface on which MAC address was learned";
             }
             leaf l2-mac-interface-device {
               type string;
               description "Name of interface device on which MAC address was learned";
             }
           }
           container extensive {
             leaf l2-evpn-nd-inet6-address {
               type ipv6addr;
               description "INET6 addresses learned via NDP";
             }
             leaf l2-mac-address {
               type mac-addr;
               description "Media access control address learned from another source";
             }
             leaf l2-mac-routing-instance {
               type string;
               description "Routing instance in which the MAC address was learned";
             }
             leaf l2-mac-bridging-domain {
               type string;
               description "Bridging domain in which the MAC address was learned";
             }
             leaf l2-mac-logical-interface {
               type string;
               description "Name of logical interface on which MAC address was learned";
             }
             leaf l2-mac-interface-device {
               type string;
               description "Name of interface device on which MAC address was learned";
             }
             container l2ald-mac-destination-address-statistics {
               description "MAC destination address statistics";
               leaf packet-count {
                 type uint64;
                 description "Packet count";
               }
               leaf byte-count {
                 type uint64;
                 description "Byte count";
               }
             }
             container l2ald-mac-source-address-statistics {
               description "MAC source address statistics";
               leaf packet-count {
                 type uint64;
                 description "Packet count";
               }
               leaf byte-count {
                 type uint64;
                 description "Byte count";
               }
             }
           }
         }
       }
     }
   }
   rpc get-evpn-peer-gateway-mac {
     description "Show MAC addresses installed as gateway MACs";
     input {
       leaf instance {
         description "Display information for a specified instance";
         default "all";
         type string;
       }
       leaf address {
         description "MAC address";
         default "all";
         type mac-addr;
       }
     }
     output {
       container l2rtb-peer-gateway-macdb {
         container l2rtb-peer-gateway-mac-entry {
           container brief {
             leaf l2-gateway-mac-routing-instance {
               type string;
               description "Routing instance in which the GW MAC address is installed";
             }
             leaf l2-gateway-mac-bridge-domain {
               type string;
               description "Bridging domain in which the GW MAC address is installed";
             }
             leaf l2-gateway-mac-bridge-vlan {
               type string;
               description "Vlan for the bridging domain";
             }
             leaf l2-gateway-mac-address {
               type mac-addr;
               description "MAC address Installed as gateway (route-able) MAC";
             }
           }
         }
       }
     }
   }
 }
