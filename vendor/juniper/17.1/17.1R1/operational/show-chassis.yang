/*
 * Copyright (c) 2017 Juniper Networks, Inc.
 * All rights reserved.
 */

 module show-chassis {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-alarm-information {
     description "Show alarm status";
     output {
       container alarm-information {
         container alarm-summary {
           description "Number of alarms currently active";
           leaf active-alarm-count {
             type int32;
             description "Number of active alarms";
           }
           leaf no-active-alarms {
             type empty;
             description "No active alarms";
           }
           container satellite {
             description "Number of alarms currently active";
             leaf active-fpc-slot {
               type int32;
               description "FPC slot with active alarms";
             }
             leaf no-active-fpc-slot {
               type int32;
               description "FPC slot with non active alarms";
             }
           }
         }
         container alarm-detail {
           description "Detailed information about an active alarm";
           leaf alarm-time {
             type string;
             description "Time of the alarm";
           }
           leaf alarm-class {
             type string;
             description "Class of the alarm";
           }
           leaf alarm-description {
             type string;
             description "Description of the alarm";
           }
           leaf alarm-short-description {
             type string;
             description "Short description of the alarm";
           }
           leaf alarm-type {
             type string;
             description "Type (class) of the alarm";
           }
         }
       }
     }
   }
   rpc get-craft-information {
     description "Show craft interface status";
     output {
       container craft-information {
         leaf output {
           type string;
           description "Formatted ASCII output displayed by the CLI";
         }
         container front-panel {
           description "Information from the craft interface";
           container display-panel {
             description "Text currently appearing on the craft interface display";
             leaf display-line {
               type string;
               description "Single line of text currently appearing on the craft interface display";
             }
           }
           container re-panel {
             description "State of status LEDs on the craft interface for one or more Routing Engines. The front panel of each Routing Engine has the same LEDs.";
             container re {
               description "State of status LEDs on the craft interface for a Routing Engine. The front panel of the Routing Engine has the same LEDs.";
               leaf slot {
                 type int32;
               }
               leaf ok-led {
                 type empty;
                 description "OK LED is lit";
               }
               leaf fail-led {
                 type empty;
                 description "Fail LED is lit";
               }
               leaf master-led {
                 type empty;
                 description "Master LED is lit";
               }
             }
           }
           container alarm-indicators {
             description "Information about alarms from the craft interface";
             leaf red-led {
               type empty;
               description "Red LED is lit";
             }
             leaf yellow-led {
               type empty;
               description "Yellow LED is lit";
             }
             leaf major-alarm-relay {
               type empty;
               description "Major (red) alarm relay is active";
             }
             leaf minor-alarm-relay {
               type empty;
               description "Minor (yellow) alarm relay is active";
             }
           }
           container fpc-panel {
             description "State of status LEDs on the craft interface for Flexible PIC Concentrators";
             container fpc {
               leaf red-led {
                 type empty;
                 description "Red LED is lit";
               }
               leaf green-led {
                 type empty;
                 description "Green LED is lit";
               }
               container pic-detail {
                 container port-information {
                 }
                 container package-information {
                   container package {
                     leaf package-name {
                       type string;
                     }
                   }
                 }
                 container port-speed-information {
                 }
               }
             }
           }
           container sib-panel {
             description "State of the status LEDs on the faceplate of one or more Switch Interface Boards. Some of the LEDs also appear on the craft interface.";
             container sib {
               leaf ok-led {
                 type empty;
                 description "OK LED is lit";
               }
               leaf fail-led {
                 type empty;
                 description "Fail LED is lit";
               }
               leaf active-led {
                 type empty;
                 description "Active LED is lit";
               }
             }
           }
           container ccg-panel {
             description "State of the status LEDs on the faceplate of one or more SONET ClockGenerators";
             container ccg {
               description "State of the CCG status LEDs on the craft interface";
               leaf slot {
                 type int32;
               }
               leaf ok-led {
                 type empty;
                 description "OK LED is lit";
               }
               leaf fail-led {
                 type empty;
                 description "Fail LED is lit";
               }
               leaf master-led {
                 type empty;
                 description "Master LED is lit";
               }
             }
           }
           container fan-tray-panel {
             description "State of status LEDs on the craft interface for Fan Trays";
             container fan-tray {
               description "State of the status LEDs on the craft interface for a fan tray";
               leaf slot {
                 type int32;
               }
               leaf red-led {
                 type empty;
                 description "Red LED is lit";
               }
               leaf green-led {
                 type empty;
                 description "Green LED is lit";
               }
             }
           }
           container power-supply-panel {
             description "State of the status LEDs on the faceplate of one or more power supplies";
             container power-supply {
               description "State of the status LEDs on the faceplate of a power supply";
               leaf slot {
                 type int32;
               }
               leaf amber-led {
                 type empty;
                 description "Amber LED is lit";
               }
               leaf green-led {
                 type empty;
                 description "Green LED is lit";
               }
               leaf blue-led {
                 type empty;
                 description "Blue LED is lit";
               }
             }
             container pdu {
               description "State of the PDU status LEDs on the craft interface";
               leaf slot {
                 type int32;
               }
               leaf red-led {
                 type empty;
                 description "Red LED is lit";
               }
               leaf green-led {
                 type empty;
                 description "Green LED is lit";
               }
               container psm {
                 description "State of the PSM status LEDs on the craft interface";
               }
             }
           }
         }
         container recb-panel {
           description "Information about LEDs from the craft interface";
           container ha-led {
             description "State of the HA LED on the craft interface";
             leaf red-led {
               type empty;
               description "Red LED is lit";
             }
             leaf yellow-led {
               type empty;
               description "Yellow LED is lit";
             }
             leaf amber-led {
               type empty;
               description "Amber LED is lit";
             }
           }
           container rps-led {
             description "State of the RPS LED on the craft interface";
             leaf red-led {
               type empty;
               description "Red LED is lit";
             }
             leaf green-led {
               type empty;
               description "Green LED is lit";
             }
             leaf led-off {
               type empty;
               description "LED is off";
             }
           }
           container mpim1-led {
             description "State of the MPIM1 LED on the craft interface";
             leaf green-led {
               type empty;
               description "Green LED is lit";
             }
             leaf led-off {
               type empty;
               description "LED is off";
             }
           }
           container mpim2-led {
             description "State of the MPIM2 LED on the craft interface";
             leaf green-led {
               type empty;
               description "Green LED is lit";
             }
             leaf led-off {
               type empty;
               description "LED is off";
             }
           }
           container storage-led {
             description "State of the external storage LED on the craft interface";
             leaf green-led {
               type empty;
               description "Green LED is lit";
             }
             leaf led-off {
               type empty;
               description "LED is off";
             }
           }
           container sfb-led {
             description "State of the SFB LED on the craft interface";
             leaf red-led {
               type empty;
               description "Red LED is lit";
             }
             leaf yellow-led {
               type empty;
               description "Yellow LED is lit";
             }
             leaf amber-led {
               type empty;
               description "Amber LED is lit";
             }
             leaf blink-led {
               type empty;
               description "LED is blinking";
             }
           }
           container cfm-ok-fail-led {
             description "State of the CFM Ok/Fail LED on the craft interface";
             leaf red-led {
               type empty;
               description "Red LED is lit";
             }
             leaf yellow-led {
               type empty;
               description "Yellow LED is lit";
             }
             leaf amber-led {
               type empty;
               description "Amber LED is lit";
             }
           }
           container cfm-service-led {
             description "State of the CFM Service LED on the craft interface";
             leaf red-led {
               type empty;
               description "Red LED is lit";
             }
             leaf yellow-led {
               type empty;
               description "Yellow LED is lit";
             }
             leaf amber-led {
               type empty;
               description "Amber LED is lit";
             }
           }
           container sysio-status-led {
             description "State of the SYSIO Status LED on the craft interface";
             leaf red-led {
               type empty;
               description "Red LED is lit";
             }
             leaf yellow-led {
               type empty;
               description "Yellow LED is lit";
             }
             leaf amber-led {
               type empty;
               description "Amber LED is lit";
             }
             leaf blink-led {
               type empty;
               description "LED is blinking";
             }
           }
         }
         container mcs-panel {
           description "State of the status LEDs on the faceplate of one or more Miscellaneous Control Subsystems";
           container mcs {
             description "State of the status LEDs on the faceplate of a Miscellaneous Control Subsystem";
             leaf slot {
               type int32;
             }
             leaf amber-led {
               type empty;
               description "Amber LED is lit";
             }
             leaf green-led {
               type empty;
               description "Green LED is lit";
             }
             leaf blue-led {
               type empty;
               description "Blue LED is lit";
             }
           }
         }
         container sfm-panel {
           description "State of the status LEDs on the faceplate of one or more Switching and Forwarding Modules";
           container sfm {
             description "State of the status LEDs on the faceplate of a Switching andForwarding Module";
             leaf slot {
               type int32;
             }
             leaf amber-led {
               type empty;
               description "Amber LED is lit";
             }
             leaf green-led {
               type empty;
               description "Green LED is lit";
             }
             leaf blue-led {
               type empty;
               description "Blue LED is lit";
             }
           }
         }
         container pcg-panel {
           description "State of the status LEDs on the faceplate of one or more Packet Forwarding Engine Clock Generators";
           container pcg {
             description "State of the status LEDs on the faceplate of a Packet Forwarding Engine Clock Generator";
             leaf slot {
               type int32;
             }
             leaf amber-led {
               type empty;
               description "Amber LED is lit";
             }
             leaf green-led {
               type empty;
               description "Green LED is lit";
             }
             leaf blue-led {
               type empty;
               description "Blue LED is lit";
             }
           }
         }
         container cb-panel {
           description "State of status LEDs on one or more Control Boards";
           container cb {
             description "State of status LEDs on a Control Board";
             leaf slot {
               type int32;
             }
             leaf amber-led {
               type empty;
               description "Amber LED is lit";
             }
             leaf green-led {
               type empty;
               description "Green LED is lit";
             }
             leaf blue-led {
               type empty;
               description "Blue LED is lit";
             }
           }
         }
         container sib-panel {
           description "State of the status LEDs on the faceplate of one or more Switch Interface Boards. Some of the LEDs also appear on the craft interface.";
           container sib {
             leaf ok-led {
               type empty;
               description "OK LED is lit";
             }
             leaf fail-led {
               type empty;
               description "Fail LED is lit";
             }
             leaf active-led {
               type empty;
               description "Active LED is lit";
             }
           }
         }
         container scg-panel {
           description "State of the status LEDs on the faceplate of one or more SONET ClockGenerators";
           container scg {
             description "State of the status LEDs on the faceplate of a SONET Clock Generator";
             leaf slot {
               type int32;
             }
             leaf amber-led {
               type empty;
               description "Amber LED is lit";
             }
             leaf green-led {
               type empty;
               description "Green LED is lit";
             }
             leaf blue-led {
               type empty;
               description "Blue LED is lit";
             }
           }
         }
         container feb-panel {
           description "State of the status LEDs on the faceplate of one or more Forwarding Engine Boards";
           container feb {
             description "State of the status LEDs on the faceplate of a Forwarding Engine Board";
             leaf slot {
               type int32;
             }
             leaf ok-led {
               type empty;
               description "OK LED is lit";
             }
             leaf fail-led {
               type empty;
               description "Fail LED is lit";
             }
             leaf active-led {
               type empty;
               description "Active LED is lit";
             }
           }
         }
         container power-supply-panel {
           description "State of the status LEDs on the faceplate of one or more power supplies";
           container power-supply {
             description "State of the status LEDs on the faceplate of a power supply";
             leaf slot {
               type int32;
             }
             leaf amber-led {
               type empty;
               description "Amber LED is lit";
             }
             leaf green-led {
               type empty;
               description "Green LED is lit";
             }
             leaf blue-led {
               type empty;
               description "Blue LED is lit";
             }
           }
           container pdu {
             description "State of the PDU status LEDs on the craft interface";
             leaf slot {
               type int32;
             }
             leaf red-led {
               type empty;
               description "Red LED is lit";
             }
             leaf green-led {
               type empty;
               description "Green LED is lit";
             }
             container psm {
               description "State of the PSM status LEDs on the craft interface";
             }
           }
         }
         container fan-tray-panel {
           description "State of status LEDs on the craft interface for Fan Trays";
           container fan-tray {
             description "State of the status LEDs on the craft interface for a fan tray";
             leaf slot {
               type int32;
             }
             leaf red-led {
               type empty;
               description "Red LED is lit";
             }
             leaf green-led {
               type empty;
               description "Green LED is lit";
             }
           }
         }
       }
     }
   }
   rpc get-environment-information {
     description "Show component status and temperature, cooling system speeds";
     output {
       container environment-information {
         container environment-item {
           leaf class {
             type string;
           }
           leaf name {
             type string;
             description "Name of this component";
           }
           leaf status {
             type string;
             description "Status of clock synchronization source";
           }
           leaf temperature {
             type string;
             description "Temperature of the item";
           }
           leaf comment {
             type string;
           }
         }
       }
     }
   }
   rpc get-environment-re-information {
     description "Show Routing Engine information";
     output {
       container environment-component-information {
         container environment-component-item {
           description "Chassis environment component";
           leaf name {
             type string;
             description "Name of this component";
           }
           leaf state {
             type string;
             description "Status of the component";
           }
           leaf bus-revision {
             type int32;
             description "Bus revision";
           }
           leaf cmb-revision {
             type int32;
             description "CMB revision";
           }
           leaf fpga-revision {
             type int32;
             description "FPGA revision";
           }
           leaf ac-feed0-voltage {
             type string;
             description "AC feed0 voltage";
           }
           leaf ac-feed0-current {
             type string;
             description "AC feed0 current";
           }
           leaf ac-feed0-power {
             type string;
             description "AC feed0 power";
           }
           leaf ac-feed1-voltage {
             type string;
             description "AC feed1 voltage";
           }
           leaf ac-feed1-current {
             type string;
             description "AC feed1 current";
           }
           leaf ac-feed1-power {
             type string;
             description "AC feed1 power";
           }
           leaf reason {
             type string;
             description "Reason";
           }
           leaf frequency {
             type string;
             description "Frequency";
           }
           leaf slave-revision {
             type uint32;
             description "Slave revision";
           }
           leaf load {
             type string;
             description "Load";
           }
           leaf time-used {
             type string;
             description "Length of time this component has been used";
           }
           leaf check-input1-alarm {
             type string;
             description "Check input1 alarm";
           }
           leaf check-input2-alarm {
             type string;
             description "Check input2 alarm";
           }
           leaf ac-input_status {
             type string;
             description "AC input status";
           }
           container temperature-reading {
             leaf temperature-name {
               type string;
             }
             leaf temperature {
               type string;
               description "Temperature of the item";
             }
           }
           container fan-speed-reading {
             leaf fan-name {
               type string;
             }
             leaf fan-speed {
               type string;
               description "Fan speed in RPM";
             }
           }
           container fpga-revision-detail {
             description "FPGA revision in detail";
             leaf fpga-revision-name {
               type string;
             }
             leaf fpga-revision-value {
               type string;
             }
           }
           container revision {
             leaf revision-name {
               type string;
               description "Revision Name";
             }
             leaf revision-number {
               type uint32;
               description "Revision Number";
             }
           }
           container slave-registers-information {
             leaf slave-registers-title {
               type string;
               description "Title for the dump of slave registers";
             }
             container slave-registers {
               description "Slave register values";
             }
           }
           container cowra-registers-information {
             leaf cowra-registers-title {
               type string;
               description "Title for the dump of cowra registers";
             }
             container cowra-registers {
               description "Cowra register values";
             }
           }
           container fpga-registers {
             description "FPGA register values";
             leaf fpga-registers-type {
               type string;
             }
             leaf fpga-registers-name {
               type string;
             }
             leaf fpga-registers-value {
               type string;
             }
           }
           container firmware {
             description "Firmware version";
             leaf firmware-name {
               type string;
               description "Name of this component";
             }
             leaf firmware-version {
               type string;
               description "Firmware version string for this component";
             }
           }
           container power-information {
             leaf voltage-title {
               type string;
               description "Title for the display of voltage";
             }
             leaf max-power-consumption-ambient-temp {
               type int32;
             }
             leaf psm-hours-used {
               type uint32;
               description "Hours used for this component";
             }
             container power-title {
             }
             container voltage {
             }
             container current {
               leaf reference-curr {
                 type string;
                 description "Current of the item in Amps";
               }
               leaf actual-curr {
                 type int32;
                 description "Current of the item in mAmps";
               }
             }
             container voltage-power {
             }
           }
           container pcg-frequency {
             description "PCG Frequency";
             leaf pcg-frequency-setting {
               type string;
             }
             leaf pcg-frequency-measurement {
               type string;
             }
           }
           container dc-information {
             leaf dc-feed0-voltage {
               type string;
               description "DC feed0 voltage";
             }
             leaf dc-feed0-current {
               type string;
               description "DC feed0 current";
             }
             leaf dc-feed0-power {
               type string;
               description "DC feed0 power";
             }
             leaf dc-feed1-voltage {
               type string;
               description "DC feed1 voltage";
             }
             leaf dc-feed1-current {
               type string;
               description "DC feed1 current";
             }
             leaf dc-feed1-power {
               type string;
               description "DC feed1 power";
             }
             leaf dc-input {
               type string;
               description "DC input state";
             }
             leaf dc-output {
               type string;
               description "DC output state";
             }
             leaf ac-input {
               type string;
               description "AC input state";
             }
             leaf ac-output {
               type string;
               description "AC output state";
             }
             leaf dc-input-status {
               type string;
               description "DC input status";
             }
             leaf dc-input1 {
               type string;
               description "DC input1 state";
             }
             leaf dc-input2 {
               type string;
               description "DC input2 state";
             }
             leaf ac-input1 {
               type string;
               description "AC input1 state";
             }
             leaf ac-input2 {
               type string;
               description "AC input2 state";
             }
             container dc-detail {
               description "Detailed DC information";
               leaf str2-dc-voltage {
                 type string;
               }
               leaf str2-dc-current {
                 type string;
               }
               leaf str2-dc-power {
                 type string;
               }
               leaf str2-dc-load {
                 type string;
               }
             }
             container dc-in-detail2 {
               description "Detailed DC input information";
             }
             container dc-detail2 {
               description "Detailed DC information";
             }
           }
           container pmbus-table {
             container pmbus-table-entry {
               description "Power Management Bus Device information";
             }
           }
           container airflow-direction {
             leaf airflow {
               type string;
             }
             leaf direction {
               type string;
               description "Airflow direction";
             }
           }
           container input-voltage {
             leaf voltage-name {
               type string;
               description "Input voltage";
             }
             leaf voltage-value {
               type uint32;
             }
           }
           container output-detail {
             description "Detailed power output information";
             leaf output-voltage {
               type uint32;
             }
             leaf output-current {
               type uint32;
               description "Output Current in Ampere(A)";
             }
           }
           container pdu-information {
             leaf hours-used {
               type uint32;
               description "Hours used for this component";
             }
             leaf pdu-status {
               type string;
             }
             container efuse {
               description "PDU efuse information";
               leaf name {
                 type string;
                 description "Name of this component";
               }
               leaf state {
                 type string;
                 description "Status of the component";
               }
             }
             container pdu-firmware {
               description "PDU firmware information";
               leaf firmware-name {
                 type string;
                 description "Name of this component";
               }
               leaf firmware-version {
                 type string;
                 description "Firmware version string for this component";
               }
             }
             container pdu-component {
               description "PDU specific component information";
               leaf component-name {
                 type string;
                 description "PDU component name";
               }
               leaf component-state {
                 type string;
                 description "PDU component state";
               }
             }
           }
           container psm-information {
             leaf temperature {
               type string;
               description "Temperature of the item";
             }
             leaf hours-used {
               type uint32;
               description "Hours used for this component";
             }
             leaf firmware-version {
               type string;
               description "Firmware version string for this component";
             }
             container psm-status {
               leaf fans {
                 type string;
                 description "Fan status for this component";
               }
               leaf dc-input {
                 type string;
                 description "DC input state";
               }
               leaf dc-input1 {
                 type string;
                 description "DC input1 state";
               }
               leaf dc-input2 {
                 type string;
                 description "DC input2 state";
               }
               leaf ac-input {
                 type string;
                 description "AC input state";
               }
               leaf ac-input1 {
                 type string;
                 description "AC input1 state";
               }
               leaf ac-input2 {
                 type string;
                 description "AC input2 state";
               }
               leaf check-input1-alarm {
                 type string;
                 description "Check input1 alarm";
               }
               leaf check-input2-alarm {
                 type string;
                 description "Check input2 alarm";
               }
               leaf dc-output {
                 type string;
                 description "DC output state";
               }
               leaf ac-output {
                 type string;
                 description "AC output state";
               }
             }
           }
           container pem-information {
             leaf fpc-slot {
               type int32;
               description "FPC slot";
             }
             leaf pem-slot {
               type uint32;
             }
             leaf pem-state {
               type string;
               description "State of power supply unit";
             }
             leaf pem-temperature {
               type uint32;
               description "Temperature in (C)";
             }
             leaf input-current {
               type uint32;
               description "Input Current in Ampere(A)";
             }
             leaf input-volt {
               type uint32;
               description "Input Volt in Volt(V)";
             }
             leaf input-power {
               type uint32;
               description "Input Power in Watt(W)";
             }
             leaf output-current {
               type uint32;
               description "Output Current in Ampere(A)";
             }
             leaf output-volt {
               type uint32;
               description "Output Volt in Volt(V)";
             }
             leaf output-power {
               type uint32;
               description "Output Power in Watt(W)";
             }
           }
         }
       }
     }
   }
   rpc get-firmware-information {
     description "Show firmware and operating system version for components";
     output {
       container firmware-information {
         container chassis {
           description "Hardware inventory of this chassis";
           container inventory {
             description "Hardware inventory of this chassis";
             leaf name {
               type string;
               description "Name of this component";
             }
             leaf version {
               type string;
               description "Version of this component";
             }
             leaf part-number {
               type string;
               description "Part number of this component";
             }
             leaf serial-number {
               type string;
               description "Serial number of this component";
             }
             leaf description {
               type string;
               description "Description of this component";
             }
             leaf hardware-incomplete {
               type empty;
             }
             leaf model-number {
               type string;
               description "Model number of this component";
             }
             leaf clei-code {
               type string;
               description "Common Language Equipment Identifier code of this component";
             }
             container i2c-information {
               leaf jedec-code {
                 type string;
               }
               leaf eeprom-version {
                 type string;
               }
               leaf assembly-identifier {
                 type string;
               }
               leaf assembly-version {
                 type string;
               }
               leaf manufacture-date {
                 type string;
                 description "Date this component was manufactured";
               }
               leaf assembly-flags {
                 type string;
               }
               leaf i2c-version {
                 type string;
               }
               leaf i2c-identifier {
                 type string;
               }
               leaf board-information-record {
                 type string;
                 description "Hex dump of board information record";
               }
               leaf i2c-data {
                 type string;
                 description "Hex dump of I2C data";
               }
             }
             container chassis-module {
               leaf name {
                 type string;
                 description "Name of this component";
               }
               leaf version {
                 type string;
                 description "Version of this component";
               }
               leaf part-number {
                 type string;
                 description "Part number of this component";
               }
               leaf serial-number {
                 type string;
                 description "Serial number of this component";
               }
               leaf description {
                 type string;
                 description "Description of this component";
               }
               leaf ir-mode {
                 type string;
                 description "R/IR mode configured";
               }
               leaf license-mode {
                 type string;
                 description "PTX R/IR mode configured";
               }
               container i2c-information {
                 leaf jedec-code {
                   type string;
                 }
                 leaf eeprom-version {
                   type string;
                 }
                 leaf assembly-identifier {
                   type string;
                 }
                 leaf assembly-version {
                   type string;
                 }
                 leaf manufacture-date {
                   type string;
                   description "Date this component was manufactured";
                 }
                 leaf assembly-flags {
                   type string;
                 }
                 leaf i2c-version {
                   type string;
                 }
                 leaf clei-code {
                   type string;
                   description "Common Language Equipment Identifier code of this component";
                 }
                 leaf i2c-identifier {
                   type string;
                 }
                 leaf model-number {
                   type string;
                   description "Model number of this component";
                 }
                 leaf board-information-record {
                   type string;
                   description "Hex dump of board information record";
                 }
                 leaf i2c-data {
                   type string;
                   description "Hex dump of I2C data";
                 }
               }
               container chassis-sub-module {
                 leaf name {
                   type string;
                   description "Name of this component";
                 }
                 leaf version {
                   type string;
                   description "Version of this component";
                 }
                 leaf part-number {
                   type string;
                   description "Part number of this component";
                 }
                 leaf serial-number {
                   type string;
                   description "Serial number of this component";
                 }
                 leaf description {
                   type string;
                   description "Description of this component";
                 }
                 container i2c-information {
                   leaf jedec-code {
                     type string;
                   }
                   leaf eeprom-version {
                     type string;
                   }
                   leaf assembly-identifier {
                     type string;
                   }
                   leaf assembly-version {
                     type string;
                   }
                   leaf manufacture-date {
                     type string;
                     description "Date this component was manufactured";
                   }
                   leaf assembly-flags {
                     type string;
                   }
                   leaf i2c-version {
                     type string;
                   }
                   leaf clei-code {
                     type string;
                     description "Common Language Equipment Identifier code of this component";
                   }
                   leaf i2c-identifier {
                     type string;
                   }
                   leaf model-number {
                     type string;
                     description "Model number of this component";
                   }
                   leaf board-information-record {
                     type string;
                     description "Hex dump of board information record";
                   }
                   leaf i2c-data {
                     type string;
                     description "Hex dump of I2C data";
                   }
                 }
                 container chassis-sub-sub-module {
                   leaf name {
                     type string;
                     description "Name of this component";
                   }
                   leaf version {
                     type string;
                     description "Version of this component";
                   }
                   leaf part-number {
                     type string;
                     description "Part number of this component";
                   }
                   leaf serial-number {
                     type string;
                     description "Serial number of this component";
                   }
                   leaf description {
                     type string;
                     description "Description of this component";
                   }
                   leaf model-number {
                     type string;
                     description "Model number of this component";
                   }
                   leaf clei-code {
                     type string;
                     description "Common Language Equipment Identifier code of this component";
                   }
                   container chassis-sub-sub-sub-module {
                   }
                 }
               }
               container chassis-re-disk-module {
                 leaf name {
                   type string;
                   description "Name of this component";
                 }
                 leaf disk-size {
                   type int32;
                   description "Disk size (megabytes)";
                 }
                 leaf model {
                   type string;
                 }
                 leaf serial-number {
                   type string;
                   description "Serial number of this component";
                 }
                 leaf description {
                   type string;
                   description "Description of this component";
                 }
               }
               container chassis-re-usb-module {
                 leaf name {
                   type string;
                   description "Name of this component";
                 }
                 leaf product {
                   type string;
                 }
                 leaf product-number {
                   type int32;
                 }
                 leaf vendor {
                   type string;
                 }
                 leaf description {
                   type string;
                   description "Description of this component";
                 }
               }
               container chassis-re-dimm-module {
                 leaf name {
                   type string;
                   description "Name of this component";
                 }
                 leaf part-number {
                   type string;
                   description "Part number of this component";
                 }
                 leaf die-rev {
                   type string;
                   description " DIE revision of the DIMM";
                 }
                 leaf pcb-rev {
                   type string;
                   description "PCB revision ";
                 }
                 leaf mfr-id {
                   type string;
                   description "Manufacture Id of the DIMM";
                 }
               }
               container chassis-compute-node-disk-module {
                 leaf name {
                   type string;
                   description "Name of this component";
                 }
                 leaf disk-size {
                   type int32;
                   description "Disk size (megabytes)";
                 }
                 leaf model {
                   type string;
                 }
                 leaf serial-number {
                   type string;
                   description "Serial number of this component";
                 }
                 leaf description {
                   type string;
                   description "Description of this component";
                 }
               }
             }
           }
           container model-inventory {
             description "Hardware inventory of this chassis";
             leaf model-number {
               type string;
               description "Model number of this component";
             }
             leaf clei-code {
               type string;
               description "Common Language Equipment Identifier code of this component";
             }
             container chassis-module {
               leaf name {
                 type string;
                 description "Name of this component";
               }
               leaf version {
                 type string;
                 description "Version of this component";
               }
               leaf part-number {
                 type string;
                 description "Part number of this component";
               }
               leaf serial-number {
                 type string;
                 description "Serial number of this component";
               }
               container chassis-sub-module {
                 container chassis-sub-sub-module {
                   container chassis-sub-sub-sub-module {
                   }
                 }
               }
             }
           }
           container clei-model-inventory {
             description "Hardware inventory of this chassis";
             leaf model-number {
               type string;
               description "Model number of this component";
             }
             leaf clei-code {
               type string;
               description "Common Language Equipment Identifier code of this component";
             }
             container chassis-module {
               leaf name {
                 type string;
                 description "Name of this component";
               }
               leaf version {
                 type string;
                 description "Version of this component";
               }
               leaf part-number {
                 type string;
                 description "Part number of this component";
               }
               container chassis-sub-module {
                 container chassis-sub-sub-module {
                   container chassis-sub-sub-sub-module {
                   }
                 }
               }
             }
           }
           container firmware {
             description "Hardware inventory of this chassis";
             leaf model-number {
               type string;
               description "Model number of this component";
             }
             leaf clei-code {
               type string;
               description "Common Language Equipment Identifier code of this component";
             }
             container chassis-module {
               leaf name {
                 type string;
                 description "Name of this component";
               }
               container chassis-sub-module {
                 container chassis-sub-sub-module {
                   container chassis-sub-sub-sub-module {
                   }
                 }
               }
             }
           }
         }
       }
     }
   }
   rpc get-fpc-information {
     description "Show Flexible PIC Concentrator status";
     input {
       leaf detail {
         description "Display detailed output";
         type empty;
       }
       leaf fpc-slot {
         description "FPC slot number";
         type uint32 {
           range "0 .. 63";
         }
       }
     }
     output {
       container fpc-information {
         container terse {
           container fpc {
             leaf slot {
               type int32;
             }
             leaf state {
               type string;
               description "Status of the component";
             }
             leaf comment {
               type string;
             }
             leaf temperature {
               type string;
               description "Temperature of the item";
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container brief {
           leaf fpc-slot {
             type int32;
             description "FPC slot";
           }
           leaf fpc-status {
             type string;
             description "FPC status";
           }
           leaf fpc-power-limit {
             type string;
             description "FPC power limit";
           }
           leaf fpc-power {
             type string;
             description "Total FPC power consumption";
           }
           leaf fpc-priority {
             type string;
             description "Priority options";
           }
           leaf fpc-firmware-version {
             type string;
             description "POE firmware version";
           }
           container fpc {
             leaf slot {
               type int32;
             }
             leaf state {
               type string;
               description "Status of the component";
             }
             leaf comment {
               type string;
             }
             leaf temperature {
               type string;
               description "Temperature of the item";
             }
             leaf cpu-total {
               type int32;
               description "Percentage of CPU utilized";
             }
             leaf cpu-interrupt {
               type int32;
               description "Percentage of CPU utilized by interrupt processing";
             }
             leaf cpu-1min-avg {
               type int32;
               description "Percentage of one min average CPU utilized";
             }
             leaf cpu-5min-avg {
               type int32;
               description "Percentage of five min average CPU utilized";
             }
             leaf cpu-15min-avg {
               type int32;
               description "Percentage of fifteen min average CPU utilized";
             }
             leaf memory-dram-size {
               type int32;
               description "DRAM";
             }
             leaf memory-heap-utilization {
               type int32;
               description "Percentage of heap memory utilized";
             }
             leaf memory-buffer-utilization {
               type int32;
               description "Percentage of buffer memory utilized";
             }
             leaf gnf-id {
               type string;
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container verbose {
           container fpc {
             leaf slot {
               type int32;
             }
             leaf state {
               type string;
               description "Status of the component";
             }
             leaf error-code {
               type int32;
               description "Code resulting from major or minor error";
             }
             leaf logical-slot {
               type int32;
             }
             leaf temperature {
               type string;
               description "Temperature of the item";
             }
             leaf cpu-less-info-str {
               type string;
               description "Flexible PIC Concentrator (FPC) without CPU";
             }
             leaf memory-dram-size {
               type int32;
               description "DRAM";
             }
             leaf memory-sram-size {
               type int32;
               description "SRAM";
             }
             leaf memory-sdram-size {
               type int32;
               description "SDRAM";
             }
             leaf memory-notification-sdram-size {
               type int32;
               description "Notification SDRAM";
             }
             leaf memory-rldram-size {
               type int32;
               description "RLDRAM";
             }
             leaf memory-xr2-size {
               type int32;
               description "XR2";
             }
             leaf memory-ddr-dram-size {
               type int32;
               description "DDR DRAM";
             }
             leaf asic-information {
               type string;
             }
             leaf start-time {
               type string;
               description "Time this component was started";
             }
             leaf up-time {
               type string;
               description "Length of time this component has been operational";
             }
             leaf comment {
               type string;
             }
             leaf max-power-consumption {
               type int32;
             }
             leaf max-mpc-base-power-consumption {
               type int32;
               description "Max MPC base power consumption";
             }
             leaf max-mic0-power-consumption {
               type int32;
               description "Max MIC0 power consumption";
             }
             leaf max-mic1-power-consumption {
               type int32;
               description "Max MIC1 power consumption";
             }
             leaf max-mpc-total-power-consumption {
               type int32;
               description "Max MPC total power consumption";
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container pic-style {
           container fpc {
             leaf slot {
               type int32;
             }
             leaf state {
               type string;
               description "Status of the component";
             }
             leaf description {
               type string;
               description "Description of this component";
             }
             leaf red-led {
               type empty;
               description "Red LED is lit";
             }
             leaf green-led {
               type empty;
               description "Green LED is lit";
             }
             container pic {
               leaf pic-slot {
                 type int32;
               }
               leaf pic-state {
                 type string;
               }
               leaf pic-type {
                 type string;
               }
               leaf comment {
                 type string;
               }
             }
             container pic-detail {
               container port-information {
               }
               container package-information {
                 container package {
                   leaf package-name {
                     type string;
                   }
                 }
               }
               container port-speed-information {
               }
             }
           }
         }
         container pic-style-detail {
           container fpc {
             leaf red-led {
               type empty;
               description "Red LED is lit";
             }
             leaf green-led {
               type empty;
               description "Green LED is lit";
             }
             container pic-detail {
               leaf slot {
                 type int32;
               }
               leaf pic-slot {
                 type int32;
               }
               leaf pic-type {
                 type string;
               }
               leaf comment {
                 type string;
               }
               leaf asic-type {
                 type string;
                 description "Type of ASIC on the PIC";
               }
               leaf account-layer2-overhead {
                 type string;
                 description "Account Layer2 Overhead Knob Status";
               }
               leaf state {
                 type string;
                 description "Status of the component";
               }
               leaf pic-version {
                 type string;
                 description "PIC hardware version";
               }
               leaf cpu-sw-version {
                 type string;
                 description "Version of operating system running on the PIC";
               }
               leaf cpu-rom-version {
                 type string;
                 description "PIC ROM version";
               }
               leaf cpu-total {
                 type int32;
                 description "Percentage of CPU utilized";
               }
               leaf cpu-interrupt {
                 type int32;
                 description "Percentage of CPU utilized by interrupt processing";
               }
               leaf memory-dram-size {
                 type int32;
                 description "DRAM";
               }
               leaf memory-buffer-utilization {
                 type int32;
                 description "Percentage of buffer memory utilized";
               }
               leaf memory-heap-utilization {
                 type int32;
                 description "Percentage of heap memory utilized";
               }
               leaf up-time {
                 type string;
                 description "Length of time this component has been operational";
               }
               leaf pic-package {
                 type string;
               }
               leaf pic-clock-sync {
                 type string;
                 description "PIC Clock Synchronization";
               }
               leaf pic-multirate-mode {
                 type string;
               }
               leaf pic-channelization-mode {
                 type string;
                 description "PIC Channelization Mode";
               }
               leaf configured-mode {
                 type string;
               }
               leaf control-cores {
                 type int32;
               }
               leaf data-cores {
                 type int32;
               }
               leaf object-cache-size {
                 type int32;
               }
               leaf policy-db-size {
                 type int32;
               }
               leaf forwarding-db-size {
                 type int32;
               }
               leaf wired-process-mem-size {
                 type int32;
               }
               leaf wired-max-processes {
                 type int32;
               }
               container port-information {
                 container port {
                   leaf port-number {
                     type int32;
                     description "Port number on the PIC";
                   }
                   leaf cable-type {
                     type string;
                     description "Port cable type";
                   }
                   leaf fiber-mode {
                     type string;
                     description "Single or multi-mode";
                   }
                   leaf sfp-vendor-name {
                     type string;
                     description "SFP vendor name";
                   }
                   leaf sfp-vendor-pno {
                     type string;
                     description "SFP vendor part number";
                   }
                   leaf wavelength {
                     type string;
                     description "Wavelength of the optical transceiver";
                   }
                   leaf sfp-vendor-fw-ver {
                     type string;
                     description "Vendor firmware version";
                   }
                 }
               }
               container pic-transport-information {
                 leaf pic-transport-admin-state {
                   type string;
                 }
                 leaf pic-transport-oper-state {
                   type string;
                 }
               }
               container package-information {
                 container package {
                   leaf package-name {
                     type string;
                   }
                 }
               }
               container port-speed-information {
                 container port {
                   leaf port-number1 {
                     type int32;
                     description "PIC port number";
                   }
                   leaf speed-capability {
                     type string;
                     description "Port speed capabilities";
                   }
                 }
               }
             }
           }
         }
         container detail {
           leaf fpc-slot {
             type int32;
             description "FPC slot";
           }
           leaf fpc-status {
             type string;
             description "FPC status";
           }
           leaf fpc-power-limit {
             type string;
             description "FPC power limit";
           }
           leaf fpc-power {
             type string;
             description "Total FPC power consumption";
           }
           leaf fpc-priority {
             type string;
             description "Priority options";
           }
           leaf fpc-firmware-version {
             type string;
             description "POE firmware version";
           }
           container fpc {
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
       }
     }
   }
   rpc get-pic-information {
     description "Show Physical Interface Cards installed in FPC";
     input {
       leaf slot {
         description "FPC slot number";
         type uint32 {
           range "0 .. 63";
         }
       }
     }
     output {
       container fpc-information {
         container terse {
           container fpc {
             leaf slot {
               type int32;
             }
             leaf state {
               type string;
               description "Status of the component";
             }
             leaf comment {
               type string;
             }
             leaf temperature {
               type string;
               description "Temperature of the item";
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container brief {
           leaf fpc-slot {
             type int32;
             description "FPC slot";
           }
           leaf fpc-status {
             type string;
             description "FPC status";
           }
           leaf fpc-power-limit {
             type string;
             description "FPC power limit";
           }
           leaf fpc-power {
             type string;
             description "Total FPC power consumption";
           }
           leaf fpc-priority {
             type string;
             description "Priority options";
           }
           leaf fpc-firmware-version {
             type string;
             description "POE firmware version";
           }
           container fpc {
             leaf slot {
               type int32;
             }
             leaf state {
               type string;
               description "Status of the component";
             }
             leaf comment {
               type string;
             }
             leaf temperature {
               type string;
               description "Temperature of the item";
             }
             leaf cpu-total {
               type int32;
               description "Percentage of CPU utilized";
             }
             leaf cpu-interrupt {
               type int32;
               description "Percentage of CPU utilized by interrupt processing";
             }
             leaf cpu-1min-avg {
               type int32;
               description "Percentage of one min average CPU utilized";
             }
             leaf cpu-5min-avg {
               type int32;
               description "Percentage of five min average CPU utilized";
             }
             leaf cpu-15min-avg {
               type int32;
               description "Percentage of fifteen min average CPU utilized";
             }
             leaf memory-dram-size {
               type int32;
               description "DRAM";
             }
             leaf memory-heap-utilization {
               type int32;
               description "Percentage of heap memory utilized";
             }
             leaf memory-buffer-utilization {
               type int32;
               description "Percentage of buffer memory utilized";
             }
             leaf gnf-id {
               type string;
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container verbose {
           container fpc {
             leaf slot {
               type int32;
             }
             leaf state {
               type string;
               description "Status of the component";
             }
             leaf error-code {
               type int32;
               description "Code resulting from major or minor error";
             }
             leaf logical-slot {
               type int32;
             }
             leaf temperature {
               type string;
               description "Temperature of the item";
             }
             leaf cpu-less-info-str {
               type string;
               description "Flexible PIC Concentrator (FPC) without CPU";
             }
             leaf memory-dram-size {
               type int32;
               description "DRAM";
             }
             leaf memory-sram-size {
               type int32;
               description "SRAM";
             }
             leaf memory-sdram-size {
               type int32;
               description "SDRAM";
             }
             leaf memory-notification-sdram-size {
               type int32;
               description "Notification SDRAM";
             }
             leaf memory-rldram-size {
               type int32;
               description "RLDRAM";
             }
             leaf memory-xr2-size {
               type int32;
               description "XR2";
             }
             leaf memory-ddr-dram-size {
               type int32;
               description "DDR DRAM";
             }
             leaf asic-information {
               type string;
             }
             leaf start-time {
               type string;
               description "Time this component was started";
             }
             leaf up-time {
               type string;
               description "Length of time this component has been operational";
             }
             leaf comment {
               type string;
             }
             leaf max-power-consumption {
               type int32;
             }
             leaf max-mpc-base-power-consumption {
               type int32;
               description "Max MPC base power consumption";
             }
             leaf max-mic0-power-consumption {
               type int32;
               description "Max MIC0 power consumption";
             }
             leaf max-mic1-power-consumption {
               type int32;
               description "Max MIC1 power consumption";
             }
             leaf max-mpc-total-power-consumption {
               type int32;
               description "Max MPC total power consumption";
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container pic-style {
           container fpc {
             leaf slot {
               type int32;
             }
             leaf state {
               type string;
               description "Status of the component";
             }
             leaf description {
               type string;
               description "Description of this component";
             }
             leaf red-led {
               type empty;
               description "Red LED is lit";
             }
             leaf green-led {
               type empty;
               description "Green LED is lit";
             }
             container pic {
               leaf pic-slot {
                 type int32;
               }
               leaf pic-state {
                 type string;
               }
               leaf pic-type {
                 type string;
               }
               leaf comment {
                 type string;
               }
             }
             container pic-detail {
               container port-information {
               }
               container package-information {
                 container package {
                   leaf package-name {
                     type string;
                   }
                 }
               }
               container port-speed-information {
               }
             }
           }
         }
         container pic-style-detail {
           container fpc {
             leaf red-led {
               type empty;
               description "Red LED is lit";
             }
             leaf green-led {
               type empty;
               description "Green LED is lit";
             }
             container pic-detail {
               leaf slot {
                 type int32;
               }
               leaf pic-slot {
                 type int32;
               }
               leaf pic-type {
                 type string;
               }
               leaf comment {
                 type string;
               }
               leaf asic-type {
                 type string;
                 description "Type of ASIC on the PIC";
               }
               leaf account-layer2-overhead {
                 type string;
                 description "Account Layer2 Overhead Knob Status";
               }
               leaf state {
                 type string;
                 description "Status of the component";
               }
               leaf pic-version {
                 type string;
                 description "PIC hardware version";
               }
               leaf cpu-sw-version {
                 type string;
                 description "Version of operating system running on the PIC";
               }
               leaf cpu-rom-version {
                 type string;
                 description "PIC ROM version";
               }
               leaf cpu-total {
                 type int32;
                 description "Percentage of CPU utilized";
               }
               leaf cpu-interrupt {
                 type int32;
                 description "Percentage of CPU utilized by interrupt processing";
               }
               leaf memory-dram-size {
                 type int32;
                 description "DRAM";
               }
               leaf memory-buffer-utilization {
                 type int32;
                 description "Percentage of buffer memory utilized";
               }
               leaf memory-heap-utilization {
                 type int32;
                 description "Percentage of heap memory utilized";
               }
               leaf up-time {
                 type string;
                 description "Length of time this component has been operational";
               }
               leaf pic-package {
                 type string;
               }
               leaf pic-clock-sync {
                 type string;
                 description "PIC Clock Synchronization";
               }
               leaf pic-multirate-mode {
                 type string;
               }
               leaf pic-channelization-mode {
                 type string;
                 description "PIC Channelization Mode";
               }
               leaf configured-mode {
                 type string;
               }
               leaf control-cores {
                 type int32;
               }
               leaf data-cores {
                 type int32;
               }
               leaf object-cache-size {
                 type int32;
               }
               leaf policy-db-size {
                 type int32;
               }
               leaf forwarding-db-size {
                 type int32;
               }
               leaf wired-process-mem-size {
                 type int32;
               }
               leaf wired-max-processes {
                 type int32;
               }
               container port-information {
                 container port {
                   leaf port-number {
                     type int32;
                     description "Port number on the PIC";
                   }
                   leaf cable-type {
                     type string;
                     description "Port cable type";
                   }
                   leaf fiber-mode {
                     type string;
                     description "Single or multi-mode";
                   }
                   leaf sfp-vendor-name {
                     type string;
                     description "SFP vendor name";
                   }
                   leaf sfp-vendor-pno {
                     type string;
                     description "SFP vendor part number";
                   }
                   leaf wavelength {
                     type string;
                     description "Wavelength of the optical transceiver";
                   }
                   leaf sfp-vendor-fw-ver {
                     type string;
                     description "Vendor firmware version";
                   }
                 }
               }
               container pic-transport-information {
                 leaf pic-transport-admin-state {
                   type string;
                 }
                 leaf pic-transport-oper-state {
                   type string;
                 }
               }
               container package-information {
                 container package {
                   leaf package-name {
                     type string;
                   }
                 }
               }
               container port-speed-information {
                 container port {
                   leaf port-number1 {
                     type int32;
                     description "PIC port number";
                   }
                   leaf speed-capability {
                     type string;
                     description "Port speed capabilities";
                   }
                 }
               }
             }
           }
         }
         container detail {
           leaf fpc-slot {
             type int32;
             description "FPC slot";
           }
           leaf fpc-status {
             type string;
             description "FPC status";
           }
           leaf fpc-power-limit {
             type string;
             description "FPC power limit";
           }
           leaf fpc-power {
             type string;
             description "Total FPC power consumption";
           }
           leaf fpc-priority {
             type string;
             description "Priority options";
           }
           leaf fpc-firmware-version {
             type string;
             description "POE firmware version";
           }
           container fpc {
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
       }
     }
   }
   rpc get-fpc-port-information {
     description "Show Port status installed in FPC";
     input {
       leaf slot {
         description "FPC slot number";
         type uint32 {
           range "0 .. 63";
         }
       }
     }
     output {
       container fpc-port-information {
         container brief {
           description "Display the port stats for FPC";
           container fpc {
             leaf slot {
               type int32;
             }
             leaf port-num {
               type int32;
             }
             leaf port-config-map {
               type string;
             }
             leaf port-map {
               type string;
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
       }
     }
   }
   rpc get-fpc-optical-information {
     description "Show optical properties of the card";
     output {
       container fpc-optical-information {
         container mfg {
           leaf fpc-optical-prod-mb {
             type string;
             description "Optical module main board product name";
           }
           leaf fpc-optical-prod-edfa {
             type string;
             description "Optical module EDFA product name";
           }
           leaf fpc-optical-prod-wss {
             type string;
             description "Optical module WSS product name";
           }
           leaf fpc-optical-prod-ocm {
             type string;
             description "Optical module OCM product name";
           }
           leaf fpc-optical-mod-mb {
             type string;
             description "Optical module main board module type";
           }
           leaf fpc-optical-mod-edfa {
             type string;
             description "Optical module EDFA module type";
           }
           leaf fpc-optical-mod-wss {
             type string;
             description "Optical module WSS module type";
           }
           leaf fpc-optical-mod-ocm {
             type string;
             description "Optical module OCM module type";
           }
           leaf fpc-optical-boot-edfa {
             type string;
             description "Optical module EDFA boot version";
           }
           leaf fpc-optical-boot-ocm {
             type string;
             description "Optical module OCM boot version";
           }
           leaf fpc-optical-sw-mb {
             type string;
             description "Optical module main board software version";
           }
           leaf fpc-optical-fw-mb {
             type string;
             description "Optical module main board firmware version";
           }
           leaf fpc-optical-fw-edfa {
             type string;
             description "Optical module EDFA firmware version";
           }
           leaf fpc-optical-fw-wss {
             type string;
             description "Optical module WSS firmware version";
           }
           leaf fpc-optical-fw-ocm {
             type string;
             description "Optical module OCM firmware version";
           }
           leaf fpc-optical-fpga-mb {
             type string;
             description "Optical module main board FPGA version";
           }
           leaf fpc-optical-fpga-edfa {
             type string;
             description "Optical module EDFA FPGA version";
           }
           leaf fpc-optical-cpld-mb {
             type string;
             description "Optical module main board CPLD version";
           }
           leaf fpc-optical-hw-mb {
             type string;
             description "Optical module main board hardware version";
           }
           leaf fpc-optical-hw-edfa {
             type string;
             description "Optical module EDFA hardware version";
           }
           leaf fpc-optical-hw-wss {
             type string;
             description "Optical module WSS hardware version";
           }
           leaf fpc-optical-hw-ocm {
             type string;
             description "Optical module OCM hardware version";
           }
           leaf fpc-optical-pcb-mb {
             type string;
             description "Optical module main board PCB revision";
           }
           leaf fpc-optical-pcb-edfa {
             type string;
             description "Optical module EDFA PCB revision";
           }
           leaf fpc-optical-pcb-wss {
             type string;
             description "Optical module WSS PCB revision";
           }
           leaf fpc-optical-pcb-ocm {
             type string;
             description "Optical module OCM PCB revision";
           }
           leaf fpc-optical-pn-mb {
             type string;
             description "Optical module main board part number";
           }
           leaf fpc-optical-pn-edfa {
             type string;
             description "Optical module EDFA part number";
           }
           leaf fpc-optical-pn-wss {
             type string;
             description "Optical module WSS part number";
           }
           leaf fpc-optical-pn-ocm {
             type string;
             description "Optical module OCM part number";
           }
           leaf fpc-optical-sn-mb {
             type string;
             description "Optical module main board serial number";
           }
           leaf fpc-optical-sn-edfa {
             type string;
             description "Optical module EDFA serial number";
           }
           leaf fpc-optical-sn-wss {
             type string;
             description "Optical module WSS serial number";
           }
           leaf fpc-optical-sn-ocm {
             type string;
             description "Optical module OCM serial number";
           }
           leaf fpc-optical-mdate-mb {
             type string;
             description "Optical module main board manufacture date";
           }
           leaf fpc-optical-mdate-edfa {
             type string;
             description "Optical module EDFA manufacture date";
           }
           leaf fpc-optical-mdate-wss {
             type string;
             description "Optical module WSS manufacture date";
           }
           leaf fpc-optical-mdate-ocm {
             type string;
             description "Optical module OCM manufacture date";
           }
           leaf fpc-optical-cdate-mb {
             type string;
             description "Optical module main board calibration date";
           }
           leaf fpc-optical-cdate-edfa {
             type string;
             description "Optical module EDFA calibration date";
           }
           leaf fpc-optical-cdate-wss {
             type string;
             description "Optical module WSS calibration date";
           }
           leaf fpc-optical-cdate-ocm {
             type string;
             description "Optical module OCM calibration date";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container status {
           leaf fpc-optical-status-uptime {
             type string;
             description "Optical module operational uptime";
           }
           leaf fpc-optical-status-edfa1-temp {
             type string;
             description "Optical module operational EDFA 1 case temperature";
           }
           leaf fpc-optical-status-edfa1-pump {
             type string;
             description "Optical module operational EDFA 1 pump temperature";
           }
           leaf fpc-optical-status-edfa1-coil {
             type string;
             description "Optical module operational EDFA 1 coil temperature";
           }
           leaf fpc-optical-status-edfa2-temp {
             type string;
             description "Optical module operational EDFA 2 case temperature";
           }
           leaf fpc-optical-status-edfa2-pump {
             type string;
             description "Optical module operational EDFA 2 pump temperature";
           }
           leaf fpc-optical-status-edfa2-coil {
             type string;
             description "Optical module operational EDFA 2 coil temperature";
           }
           leaf fpc-optical-status-wss-vol {
             type string;
             description "Optical module operational WSS voltage";
           }
           leaf fpc-optical-status-wss-temp {
             type string;
             description "Optical module operational WSS temperature";
           }
           leaf fpc-optical-status-ocm-temp {
             type string;
             description "Optical module operational OCM temperature";
           }
           leaf fpc-optical-status-osc-status {
             type string;
             description "Optical module operational OSC status";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container alarm {
           leaf fpc-optical-alarm {
             type string;
             description "Optical module alarm status";
           }
           leaf fpc-optical-alarm-edfa1 {
             type string;
             description "Optical module EDFA1 alarm status";
           }
           leaf fpc-optical-alarm-edfa2 {
             type string;
             description "Optical module EDFA2 alarm status";
           }
           leaf fpc-optical-alarm-wss {
             type string;
             description "Optical module WSS alarm status";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container edfa {
           leaf fpc-optical-edfa1-gains {
             type string;
             description "Optical module EDFA1 gain setting save";
           }
           leaf fpc-optical-edfa2-gains {
             type string;
             description "Optical module EDFA2 gain setting save";
           }
           leaf fpc-optical-edfa1-tilt {
             type string;
             description "Optical module EDFA1 gain tilt";
           }
           leaf fpc-optical-edfa2-tilt {
             type string;
             description "Optical module EDFA2 gain tilt";
           }
           leaf fpc-optical-edfa1-ilos-ut {
             type string;
             description "Optical module EDFA1 input LOS upper threshold";
           }
           leaf fpc-optical-edfa2-ilos-ut {
             type string;
             description "Optical module EDFA2 input LOS upper threshold";
           }
           leaf fpc-optical-edfa1-ilos-lt {
             type string;
             description "Optical module EDFA1 input LOS lower threshold";
           }
           leaf fpc-optical-edfa2-ilos-lt {
             type string;
             description "Optical module EDFA2 input LOS lower threshold";
           }
           leaf fpc-optical-edfa1-olos-ut {
             type string;
             description "Optical module EDFA1 output LOS upper threshold";
           }
           leaf fpc-optical-edfa2-olos-ut {
             type string;
             description "Optical module EDFA2 output LOS upper threshold";
           }
           leaf fpc-optical-edfa1-olos-lt {
             type string;
             description "Optical module EDFA1 output LOS lower threshold";
           }
           leaf fpc-optical-edfa2-olos-lt {
             type string;
             description "Optical module EDFA2 output LOS lower threshold";
           }
           leaf fpc-optical-edfa1-gain {
             type string;
             description "Optical module EDFA1 gain setting";
           }
           leaf fpc-optical-edfa2-gain {
             type string;
             description "Optical module EDFA2 gain setting";
           }
           leaf fpc-optical-edfa1-output {
             type string;
             description "Optical module EDFA1 output enable";
           }
           leaf fpc-optical-edfa2-output {
             type string;
             description "Optical module EDFA2 output enable";
           }
           leaf fpc-optical-edfa1-autolos {
             type string;
             description "Optical module EDFA1 auto LOS enable";
           }
           leaf fpc-optical-edfa2-autolos {
             type string;
             description "Optical module EDFA2 auto LOS enable";
           }
           leaf fpc-optical-edfa1-mode {
             type string;
             description "Optical module EDFA1 mode";
           }
           leaf fpc-optical-edfa2-mode {
             type string;
             description "Optical module EDFA2 mode";
           }
           leaf fpc-optical-edfa1-plim {
             type string;
             description "Optical module EDFA1 plim power";
           }
           leaf fpc-optical-edfa2-plim {
             type string;
             description "Optical module EDFA2 plim power";
           }
           leaf fpc-optical-ila-edfa-info {
             type string;
             description "Optical ila edfa information";
           }
           leaf fpc-optical-ila-edfa-index {
             type string;
             description "Optical ila edfa index";
           }
           leaf fpc-optical-ila-edfa-mfg-info {
             type string;
             description "Optical ila edfa manufacture info";
           }
           leaf fpc-optical-ila-edfa-module-type {
             type string;
             description "Optical ila edfa module type";
           }
           leaf fpc-optical-ila-edfa-part-number {
             type string;
             description "Optical ila edfa part number";
           }
           leaf fpc-optical-ila-edfa-serial-number {
             type string;
             description "Optical ila edfa serial number";
           }
           leaf fpc-optical-ila-edfa-mfg-date {
             type string;
             description "Optical ila edfa manufacture date";
           }
           leaf fpc-optical-ila-edfa-cali-date {
             type string;
             description "Optical ila edfa calibration date";
           }
           leaf fpc-optical-ila-edfa-firmware-ver {
             type string;
             description "Optical ila edfa firmware version";
           }
           leaf fpc-optical-ila-edfa-hardware-ver {
             type string;
             description "Optical ila edfa hardware version";
           }
           leaf fpc-optical-ila-edfa-mode {
             type string;
             description "Optical ila edfa mode";
           }
           leaf fpc-optical-ila-edfa-gain-setting {
             type string;
             description "Optical ila edfa gain setting";
           }
           leaf fpc-optical-ila-edfa-tilt {
             type string;
             description "Optical ila edfa tilt";
           }
           leaf fpc-optical-ila-edfa-work-status {
             type string;
             description "Optical ila edfa work status";
           }
           leaf fpc-optical-ila-edfa-apr-enable {
             type string;
             description "Optical ila edfa apr enable";
           }
           leaf fpc-optical-ila-edfa-work-range {
             type string;
             description "Optical ila edfa work range";
           }
           leaf fpc-optical-ila-edfa-actual-gain {
             type string;
             description "Optical ila edfa actual gain";
           }
           leaf fpc-optical-ila-edfa-case-temp {
             type string;
             description "Optical ila edfa case temperature";
           }
           leaf fpc-optical-ila-edfa-pump-temp {
             type string;
             description "Optical ila edfa pump temperature";
           }
           leaf fpc-optical-ila-edfa-asc {
             type string;
             description "Optical ila edfa asc";
           }
           leaf fpc-optical-ila-edfa-upstream-output-power {
             type string;
             description "Optical ila edfa upstream output power";
           }
           leaf fpc-optical-ila-edfa-input-power {
             type string;
             description "Optical ila edfa input power";
           }
           leaf fpc-optical-ila-edfa-output-power {
             type string;
             description "Optical ila edfa output power";
           }
           leaf fpc-optical-ila-edfa-downstream-input-power {
             type string;
             description "Optical ila edfa downstream input power";
           }
           leaf fpc-optical-ila-edfa-input-los-threshold {
             type string;
             description "Optical ila edfa input los threshold";
           }
           leaf fpc-optical-ila-edfa-output-los-threshold {
             type string;
             description "Optical ila edfa output los threshold";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container ocm {
           leaf fpc-optical-topology-wavelength {
             type string;
             description "Optical module topology";
           }
           leaf fpc-optical-port {
             type string;
             description "Optical module WSS port";
           }
           leaf fpc-optical-frequency {
             type string;
             description "Optical module frequency";
           }
           leaf fpc-optical-ocm-lout {
             type string;
             description "Optical module OCM channel 0 line out port power";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container wss {
           leaf fpc-optical-topology-wavelength {
             type string;
             description "Optical module topology";
           }
           leaf fpc-optical-port {
             type string;
             description "Optical module WSS port";
           }
           leaf fpc-optical-frequency {
             type string;
             description "Optical module frequency";
           }
           leaf fpc-optical-wss-port {
             type string;
             description "Optical module WSS channel 0 port";
           }
           leaf fpc-optical-wss-attn {
             type string;
             description "Optical module WSS channel 0 attenuation";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container pm {
           leaf fpc-optical-pm-slot {
             type string;
             description "Optical module PM FPC slot";
           }
           leaf fpc-optical-pm-timestamp {
             type string;
             description "Optical module PM timestamp";
           }
           leaf fpc-optical-pm-suspect-flag {
             type string;
             description "Optical module PM suspect flag";
           }
           leaf fpc-optical-pm-suspect-reason {
             type string;
             description "Optical module PM suspect reason";
           }
           leaf fpc-optical-pm-osc-txpwr-cur {
             type string;
             description "Optical module PM OSC Tx power current";
           }
           leaf fpc-optical-pm-osc-txpwr-min {
             type string;
             description "Optical module PM OSC Tx power min";
           }
           leaf fpc-optical-pm-osc-txpwr-max {
             type string;
             description "Optical module PM OSC Tx power max";
           }
           leaf fpc-optical-pm-osc-txpwr-avg {
             type string;
             description "Optical module PM OSC Tx power avg";
           }
           leaf fpc-optical-pm-osc-txpwr-min-tca-th {
             type string;
             description "Optical module PM OSC Tx power TCA min threshold";
           }
           leaf fpc-optical-pm-osc-txpwr-max-tca-th {
             type string;
             description "Optical module PM OSC Tx power TCA max threshold";
           }
           leaf fpc-optical-pm-osc-txpwr-min-tca-en {
             type string;
             description "Optical module PM OSC Tx power TCA min enable";
           }
           leaf fpc-optical-pm-osc-txpwr-max-tca-en {
             type string;
             description "Optical module PM OSC Tx power TCA max enable";
           }
           leaf fpc-optical-pm-osc-txpwr-min-tca-state {
             type string;
             description "Optical module PM OSC Tx power TCA min state";
           }
           leaf fpc-optical-pm-osc-txpwr-max-tca-state {
             type string;
             description "Optical module PM OSC Tx power TCA max state";
           }
           leaf fpc-optical-pm-osc-rxpwr-cur {
             type string;
             description "Optical module PM OSC Rx power current";
           }
           leaf fpc-optical-pm-osc-rxpwr-min {
             type string;
             description "Optical module PM OSC Rx power min";
           }
           leaf fpc-optical-pm-osc-rxpwr-max {
             type string;
             description "Optical module PM OSC Rx power max";
           }
           leaf fpc-optical-pm-osc-rxpwr-avg {
             type string;
             description "Optical module PM OSC Rx power avg";
           }
           leaf fpc-optical-pm-osc-rxpwr-min-tca-th {
             type string;
             description "Optical module PM OSC Rx power TCA min threshold";
           }
           leaf fpc-optical-pm-osc-rxpwr-max-tca-th {
             type string;
             description "Optical module PM OSC Rx power TCA max threshold";
           }
           leaf fpc-optical-pm-osc-rxpwr-min-tca-en {
             type string;
             description "Optical module PM OSC Rx power TCA min enable";
           }
           leaf fpc-optical-pm-osc-rxpwr-max-tca-en {
             type string;
             description "Optical module PM OSC Rx power TCA max enable";
           }
           leaf fpc-optical-pm-osc-rxpwr-min-tca-state {
             type string;
             description "Optical module PM OSC Rx power TCA min state";
           }
           leaf fpc-optical-pm-osc-rxpwr-max-tca-state {
             type string;
             description "Optical module PM OSC Rx power TCA max state";
           }
           leaf fpc-optical-pm-osc-los-cur {
             type string;
             description "Optical module PM OSC LOS current";
           }
           leaf fpc-optical-pm-osc-los-min {
             type string;
             description "Optical module PM OSC LOS min";
           }
           leaf fpc-optical-pm-osc-los-max {
             type string;
             description "Optical module PM OSC LOS max";
           }
           leaf fpc-optical-pm-osc-los-avg {
             type string;
             description "Optical module PM OSC LOS avg";
           }
           leaf fpc-optical-pm-osc-los-min-tca-th {
             type string;
             description "Optical module PM OSC LOS TCA min threshold";
           }
           leaf fpc-optical-pm-osc-los-max-tca-th {
             type string;
             description "Optical module PM OSC LOS TCA max threshold";
           }
           leaf fpc-optical-pm-osc-los-min-tca-en {
             type string;
             description "Optical module PM OSC LOS TCA min enable";
           }
           leaf fpc-optical-pm-osc-los-max-tca-en {
             type string;
             description "Optical module PM OSC LOS TCA max enable";
           }
           leaf fpc-optical-pm-osc-los-min-tca-state {
             type string;
             description "Optical module PM OSC LOS TCA min state";
           }
           leaf fpc-optical-pm-osc-los-max-tca-state {
             type string;
             description "Optical module PM OSC LOS TCA max state";
           }
           leaf fpc-optical-pm-lout-voa-cur {
             type string;
             description "Optical module PM LOUT VOA attenuation current";
           }
           leaf fpc-optical-pm-lout-voa-min {
             type string;
             description "Optical module PM LOUT VOA attenuation min";
           }
           leaf fpc-optical-pm-lout-voa-max {
             type string;
             description "Optical module PM LOUT VOA attenuation max";
           }
           leaf fpc-optical-pm-lout-voa-avg {
             type string;
             description "Optical module PM LOUT VOA attenuation avg";
           }
           leaf fpc-optical-pm-lout-voa-min-tca-th {
             type string;
             description "Optical module PM LOUT VOA attenuation TCA min threshold";
           }
           leaf fpc-optical-pm-lout-voa-max-tca-th {
             type string;
             description "Optical module PM LOUT VOA attenuation TCA max threshold";
           }
           leaf fpc-optical-pm-lout-voa-min-tca-en {
             type string;
             description "Optical module PM LOUT VOA attenuation TCA min enable";
           }
           leaf fpc-optical-pm-lout-voa-max-tca-en {
             type string;
             description "Optical module PM LOUT VOA attenuation TCA max enable";
           }
           leaf fpc-optical-pm-lout-voa-min-tca-state {
             type string;
             description "Optical module PM LOUT VOA attenuation TCA min state";
           }
           leaf fpc-optical-pm-lout-voa-max-tca-state {
             type string;
             description "Optical module PM LOUT VOA attenuation TCA max state";
           }
           leaf fpc-optical-pm-edfa1-inpwr-cur {
             type string;
             description "Optical module PM EDFA1 input power current";
           }
           leaf fpc-optical-pm-edfa1-inpwr-min {
             type string;
             description "Optical module PM EDFA1 input power min";
           }
           leaf fpc-optical-pm-edfa1-inpwr-max {
             type string;
             description "Optical module PM EDFA1 input power max";
           }
           leaf fpc-optical-pm-edfa1-inpwr-avg {
             type string;
             description "Optical module PM EDFA1 input power avg";
           }
           leaf fpc-optical-pm-edfa1-inpwr-min-tca-th {
             type string;
             description "Optical module PM EDFA1 input power TCA min threshold";
           }
           leaf fpc-optical-pm-edfa1-inpwr-max-tca-th {
             type string;
             description "Optical module PM EDFA1 input power TCA max threshold";
           }
           leaf fpc-optical-pm-edfa1-inpwr-min-tca-en {
             type string;
             description "Optical module PM EDFA1 input power TCA min enable";
           }
           leaf fpc-optical-pm-edfa1-inpwr-max-tca-en {
             type string;
             description "Optical module PM EDFA1 input power TCA max enable";
           }
           leaf fpc-optical-pm-edfa1-inpwr-min-tca-state {
             type string;
             description "Optical module PM EDFA1 input power TCA min state";
           }
           leaf fpc-optical-pm-edfa1-inpwr-max-tca-state {
             type string;
             description "Optical module PM EDFA1 input power TCA max state";
           }
           leaf fpc-optical-pm-edfa1-outpwr-cur {
             type string;
             description "Optical module PM EDFA1 output power current";
           }
           leaf fpc-optical-pm-edfa1-outpwr-min {
             type string;
             description "Optical module PM EDFA1 output power min";
           }
           leaf fpc-optical-pm-edfa1-outpwr-max {
             type string;
             description "Optical module PM EDFA1 output power max";
           }
           leaf fpc-optical-pm-edfa1-outpwr-avg {
             type string;
             description "Optical module PM EDFA1 output power avg";
           }
           leaf fpc-optical-pm-edfa1-outpwr-min-tca-th {
             type string;
             description "Optical module PM EDFA1 output power TCA min threshold";
           }
           leaf fpc-optical-pm-edfa1-outpwr-max-tca-th {
             type string;
             description "Optical module PM EDFA1 output power TCA max threshold";
           }
           leaf fpc-optical-pm-edfa1-outpwr-min-tca-en {
             type string;
             description "Optical module PM EDFA1 output power TCA min enable";
           }
           leaf fpc-optical-pm-edfa1-outpwr-max-tca-en {
             type string;
             description "Optical module PM EDFA1 output power TCA max enable";
           }
           leaf fpc-optical-pm-edfa1-outpwr-min-tca-state {
             type string;
             description "Optical module PM EDFA1 output power TCA min state";
           }
           leaf fpc-optical-pm-edfa1-outpwr-max-tca-state {
             type string;
             description "Optical module PM EDFA1 output power TCA max state";
           }
           leaf fpc-optical-pm-edfa1-sigpwr-cur {
             type string;
             description "Optical module PM EDFA1 signal power current";
           }
           leaf fpc-optical-pm-edfa1-sigpwr-min {
             type string;
             description "Optical module PM EDFA1 signal power min";
           }
           leaf fpc-optical-pm-edfa1-sigpwr-max {
             type string;
             description "Optical module PM EDFA1 signal power max";
           }
           leaf fpc-optical-pm-edfa1-sigpwr-avg {
             type string;
             description "Optical module PM EDFA1 signal power avg";
           }
           leaf fpc-optical-pm-edfa1-sigpwr-min-tca-th {
             type string;
             description "Optical module PM EDFA1 signal power TCA min threshold";
           }
           leaf fpc-optical-pm-edfa1-sigpwr-max-tca-th {
             type string;
             description "Optical module PM EDFA1 signal power TCA max threshold";
           }
           leaf fpc-optical-pm-edfa1-sigpwr-min-tca-en {
             type string;
             description "Optical module PM EDFA1 signal power TCA min enable";
           }
           leaf fpc-optical-pm-edfa1-sigpwr-max-tca-en {
             type string;
             description "Optical module PM EDFA1 signal power TCA max enable";
           }
           leaf fpc-optical-pm-edfa1-sigpwr-min-tca-state {
             type string;
             description "Optical module PM EDFA1 signal power TCA min state";
           }
           leaf fpc-optical-pm-edfa1-sigpwr-max-tca-state {
             type string;
             description "Optical module PM EDFA1 signal power TCA max state";
           }
           leaf fpc-optical-pm-edfa1-pump-cur {
             type string;
             description "Optical module PM EDFA1 pump current current";
           }
           leaf fpc-optical-pm-edfa1-pump-min {
             type string;
             description "Optical module PM EDFA1 pump current min";
           }
           leaf fpc-optical-pm-edfa1-pump-max {
             type string;
             description "Optical module PM EDFA1 pump current max";
           }
           leaf fpc-optical-pm-edfa1-pump-avg {
             type string;
             description "Optical module PM EDFA1 pump current avg";
           }
           leaf fpc-optical-pm-edfa1-pump-min-tca-th {
             type string;
             description "Optical module PM EDFA1 pump current TCA min threshold";
           }
           leaf fpc-optical-pm-edfa1-pump-max-tca-th {
             type string;
             description "Optical module PM EDFA1 pump current TCA max threshold";
           }
           leaf fpc-optical-pm-edfa1-pump-min-tca-en {
             type string;
             description "Optical module PM EDFA1 pump current TCA min enable";
           }
           leaf fpc-optical-pm-edfa1-pump-max-tca-en {
             type string;
             description "Optical module PM EDFA1 pump current TCA max enable";
           }
           leaf fpc-optical-pm-edfa1-pump-min-tca-state {
             type string;
             description "Optical module PM EDFA1 pump current TCA min state";
           }
           leaf fpc-optical-pm-edfa1-pump-max-tca-state {
             type string;
             description "Optical module PM EDFA1 pump current TCA max state";
           }
           leaf fpc-optical-pm-edfa2-inpwr-cur {
             type string;
             description "Optical module PM EDFA2 input power current";
           }
           leaf fpc-optical-pm-edfa2-inpwr-min {
             type string;
             description "Optical module PM EDFA2 input power min";
           }
           leaf fpc-optical-pm-edfa2-inpwr-max {
             type string;
             description "Optical module PM EDFA2 input power max";
           }
           leaf fpc-optical-pm-edfa2-inpwr-avg {
             type string;
             description "Optical module PM EDFA2 input power avg";
           }
           leaf fpc-optical-pm-edfa2-inpwr-min-tca-th {
             type string;
             description "Optical module PM EDFA2 input power TCA min threshold";
           }
           leaf fpc-optical-pm-edfa2-inpwr-max-tca-th {
             type string;
             description "Optical module PM EDFA2 input power TCA max threshold";
           }
           leaf fpc-optical-pm-edfa2-inpwr-min-tca-en {
             type string;
             description "Optical module PM EDFA2 input power TCA min enable";
           }
           leaf fpc-optical-pm-edfa2-inpwr-max-tca-en {
             type string;
             description "Optical module PM EDFA2 input power TCA max enable";
           }
           leaf fpc-optical-pm-edfa2-inpwr-min-tca-state {
             type string;
             description "Optical module PM EDFA2 input power TCA min state";
           }
           leaf fpc-optical-pm-edfa2-inpwr-max-tca-state {
             type string;
             description "Optical module PM EDFA2 input power TCA max state";
           }
           leaf fpc-optical-pm-edfa2-outpwr-cur {
             type string;
             description "Optical module PM EDFA2 output power current";
           }
           leaf fpc-optical-pm-edfa2-outpwr-min {
             type string;
             description "Optical module PM EDFA2 output power min";
           }
           leaf fpc-optical-pm-edfa2-outpwr-max {
             type string;
             description "Optical module PM EDFA2 output power max";
           }
           leaf fpc-optical-pm-edfa2-outpwr-avg {
             type string;
             description "Optical module PM EDFA2 output power avg";
           }
           leaf fpc-optical-pm-edfa2-outpwr-min-tca-th {
             type string;
             description "Optical module PM EDFA2 output power TCA min threshold";
           }
           leaf fpc-optical-pm-edfa2-outpwr-max-tca-th {
             type string;
             description "Optical module PM EDFA2 output power TCA max threshold";
           }
           leaf fpc-optical-pm-edfa2-outpwr-min-tca-en {
             type string;
             description "Optical module PM EDFA2 output power TCA min enable";
           }
           leaf fpc-optical-pm-edfa2-outpwr-max-tca-en {
             type string;
             description "Optical module PM EDFA2 output power TCA max enable";
           }
           leaf fpc-optical-pm-edfa2-outpwr-min-tca-state {
             type string;
             description "Optical module PM EDFA2 output power TCA min state";
           }
           leaf fpc-optical-pm-edfa2-outpwr-max-tca-state {
             type string;
             description "Optical module PM EDFA2 output power TCA max state";
           }
           leaf fpc-optical-pm-edfa2-sigpwr-cur {
             type string;
             description "Optical module PM EDFA2 signal power current";
           }
           leaf fpc-optical-pm-edfa2-sigpwr-min {
             type string;
             description "Optical module PM EDFA2 signal power min";
           }
           leaf fpc-optical-pm-edfa2-sigpwr-max {
             type string;
             description "Optical module PM EDFA2 signal power max";
           }
           leaf fpc-optical-pm-edfa2-sigpwr-avg {
             type string;
             description "Optical module PM EDFA2 signal power avg";
           }
           leaf fpc-optical-pm-edfa2-sigpwr-min-tca-th {
             type string;
             description "Optical module PM EDFA2 signal power TCA min threshold";
           }
           leaf fpc-optical-pm-edfa2-sigpwr-max-tca-th {
             type string;
             description "Optical module PM EDFA2 signal power TCA max threshold";
           }
           leaf fpc-optical-pm-edfa2-sigpwr-min-tca-en {
             type string;
             description "Optical module PM EDFA2 signal power TCA min enable";
           }
           leaf fpc-optical-pm-edfa2-sigpwr-max-tca-en {
             type string;
             description "Optical module PM EDFA2 signal power TCA max enable";
           }
           leaf fpc-optical-pm-edfa2-sigpwr-min-tca-state {
             type string;
             description "Optical module PM EDFA2 signal power TCA min state";
           }
           leaf fpc-optical-pm-edfa2-sigpwr-max-tca-state {
             type string;
             description "Optical module PM EDFA2 signal power TCA max state";
           }
           leaf fpc-optical-pm-edfa2-pump-cur {
             type string;
             description "Optical module PM EDFA2 pump current current";
           }
           leaf fpc-optical-pm-edfa2-pump-min {
             type string;
             description "Optical module PM EDFA2 pump current min";
           }
           leaf fpc-optical-pm-edfa2-pump-max {
             type string;
             description "Optical module PM EDFA2 pump current max";
           }
           leaf fpc-optical-pm-edfa2-pump-avg {
             type string;
             description "Optical module PM EDFA2 pump current avg";
           }
           leaf fpc-optical-pm-edfa2-pump-min-tca-th {
             type string;
             description "Optical module PM EDFA2 pump current TCA min threshold";
           }
           leaf fpc-optical-pm-edfa2-pump-max-tca-th {
             type string;
             description "Optical module PM EDFA2 pump current TCA max threshold";
           }
           leaf fpc-optical-pm-edfa2-pump-min-tca-en {
             type string;
             description "Optical module PM EDFA2 pump current TCA min enable";
           }
           leaf fpc-optical-pm-edfa2-pump-max-tca-en {
             type string;
             description "Optical module PM EDFA2 pump current TCA max enable";
           }
           leaf fpc-optical-pm-edfa2-pump-min-tca-state {
             type string;
             description "Optical module PM EDFA2 pump current TCA min state";
           }
           leaf fpc-optical-pm-edfa2-pump-max-tca-state {
             type string;
             description "Optical module PM EDFA2 pump current TCA max state";
           }
           leaf fpc-optical-pm-powermon-awg-cur {
             type string;
             description "Optical module PM power monitor AWG port current";
           }
           leaf fpc-optical-pm-powermon-awg-min {
             type string;
             description "Optical module PM power monitor AWG port min";
           }
           leaf fpc-optical-pm-powermon-awg-max {
             type string;
             description "Optical module PM power monitor AWG port max";
           }
           leaf fpc-optical-pm-powermon-awg-avg {
             type string;
             description "Optical module PM power monitor AWG port avg";
           }
           leaf fpc-optical-pm-powermon-awg-min-tca-th {
             type string;
             description "Optical module PM power monitor AWG port TCA min threshold";
           }
           leaf fpc-optical-pm-powermon-awg-max-tca-th {
             type string;
             description "Optical module PM power monitor AWG port TCA max threshold";
           }
           leaf fpc-optical-pm-powermon-awg-min-tca-en {
             type string;
             description "Optical module PM power monitor AWG port TCA min enable";
           }
           leaf fpc-optical-pm-powermon-awg-max-tca-en {
             type string;
             description "Optical module PM power monitor AWG port TCA max enable";
           }
           leaf fpc-optical-pm-powermon-awg-min-tca-state {
             type string;
             description "Optical module PM power monitor AWG port TCA min state";
           }
           leaf fpc-optical-pm-powermon-awg-max-tca-state {
             type string;
             description "Optical module PM power monitor AWG port TCA max state";
           }
           leaf fpc-optical-pm-powermon-expin-cur {
             type string;
             description "Optical module PM power monitor Express In port current";
           }
           leaf fpc-optical-pm-powermon-expin-min {
             type string;
             description "Optical module PM power monitor Express In port min";
           }
           leaf fpc-optical-pm-powermon-expin-max {
             type string;
             description "Optical module PM power monitor Express In port max";
           }
           leaf fpc-optical-pm-powermon-expin-avg {
             type string;
             description "Optical module PM power monitor Express In port avg";
           }
           leaf fpc-optical-pm-powermon-expin-min-tca-th {
             type string;
             description "Optical module PM power monitor Express In port TCA min threshold";
           }
           leaf fpc-optical-pm-powermon-expin-max-tca-th {
             type string;
             description "Optical module PM power monitor Express In port TCA max threshold";
           }
           leaf fpc-optical-pm-powermon-expin-min-tca-en {
             type string;
             description "Optical module PM power monitor Express In port TCA min enable";
           }
           leaf fpc-optical-pm-powermon-expin-max-tca-en {
             type string;
             description "Optical module PM power monitor Express In port TCA max enable";
           }
           leaf fpc-optical-pm-powermon-expin-min-tca-state {
             type string;
             description "Optical module PM power monitor Express In port TCA min state";
           }
           leaf fpc-optical-pm-powermon-expin-max-tca-state {
             type string;
             description "Optical module PM power monitor Express In port TCA max state";
           }
           leaf fpc-optical-channel-lout {
             type string;
             description "Optical module OCM channel LOUT";
           }
           leaf fpc-optical-ocm-lout {
             type string;
             description "Optical module OCM channel 0 line out port power";
           }
           leaf fpc-optical-pm-ocm-lout-min {
             type string;
             description "Optical module OCM channel 0 min power";
           }
           leaf fpc-optical-pm-ocm-lout-max {
             type string;
             description "Optical module OCM channel 0 max power";
           }
           leaf fpc-optical-pm-ocm-lout-avg {
             type string;
             description "Optical module OCM channel 0 avg power";
           }
           leaf fpc-optical-pm-ocm-lout-min-tca-th {
             type string;
             description "Optical module OCM channel 0 min TCA threshold";
           }
           leaf fpc-optical-pm-ocm-lout-max-tca-th {
             type string;
             description "Optical module OCM channel 0 max TCA threshold";
           }
           leaf fpc-optical-pm-ocm-lout-min-tca-en {
             type string;
             description "Optical module OCM channel 0 min TCA enable";
           }
           leaf fpc-optical-pm-ocm-lout-max-tca-en {
             type string;
             description "Optical module OCM channel 0 max TCA enable";
           }
           leaf fpc-optical-pm-ocm-lout-min-tca-state {
             type string;
             description "Optical module OCM channel 0 min TCA state";
           }
           leaf fpc-optical-pm-ocm-lout-max-tca-state {
             type string;
             description "Optical module OCM channel 0 max TCA state";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container topology {
           leaf fpc-optical-topology-express-in-state {
             type string;
             description "Optical module topology state";
           }
           leaf fpc-optical-topology-express-in-connected-to {
             type string;
             description "Optical module topology state";
           }
           leaf fpc-optical-topology-expansion-state {
             type string;
             description "Optical module topology state";
           }
           leaf fpc-optical-topology-expansion-connected-to {
             type string;
             description "Optical module topology connected-to";
           }
           leaf fpc-optical-topology-wavelength {
             type string;
             description "Optical module topology";
           }
           leaf fpc-optical-port {
             type string;
             description "Optical module WSS port";
           }
           leaf fpc-optical-frequency {
             type string;
             description "Optical module frequency";
           }
           leaf fpc-optical-topology-wavelength-state {
             type string;
             description "Optical module topology state";
           }
           leaf fpc-optical-topology-wavelength-connected-to {
             type string;
             description "Optical module topology state";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container amplifier-topology {
           leaf fpc-optical-amplifier-topology-name {
             type string;
             description "Optical module amplifier topology name";
           }
           leaf fpc-optical-amplifier-topology-ipaddr {
             type string;
             description "Optical module amplifier topology ip address";
           }
           leaf fpc-optical-amplifier-topology-reachable {
             type string;
             description "Optical module amplifier topology reachability";
           }
           leaf fpc-optical-amplifier-topology-connected-to {
             type string;
             description "Optical module amplifier topology connected-to";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container summary {
           leaf fpc-optical-ila-summary-ila-num {
             type string;
             description "Optical module ila summary ila number";
           }
           leaf fpc-optical-ila-summary-ila-name {
             type string;
             description "Optical module ila summary ila name";
           }
           leaf fpc-optical-ila-summary-position {
             type string;
             description "Optical module ila summary ila position";
           }
           leaf fpc-optical-ila-summary-ip-address {
             type string;
             description "Optical module ila summary ila ip address";
           }
           leaf fpc-optical-ila-summary-mfg-name {
             type string;
             description "Optical module ila summary ila manufactory name";
           }
           leaf fpc-optical-ila-summary-mfg-date {
             type string;
             description "Optical module ila summary ila manufactory date";
           }
           leaf fpc-optical-ila-summary-part-num {
             type string;
             description "Optical module ila summary ila part number";
           }
           leaf fpc-optical-ila-summary-serial-num {
             type string;
             description "Optical module ila summary ila serial number";
           }
           leaf fpc-optical-ila-summary-calibration-date {
             type string;
             description "Optical module ila summary ila calibration date";
           }
           leaf fpc-optical-ila-summary-firmware-ver {
             type string;
             description "Optical module ila summary ila firmware version";
           }
           leaf fpc-optical-ila-summary-hardware-ver {
             type string;
             description "Optical module ila summary ila hardware version";
           }
           leaf fpc-optical-ila-summary-fpga-ver {
             type string;
             description "Optical module ila summary ila fpga version";
           }
           leaf fpc-optical-ila-summary-x86cpld-ver {
             type string;
             description "Optical module ila summary ila x86cpld version";
           }
           leaf fpc-optical-ila-summary-board-cpld-ver {
             type string;
             description "Optical module ila summary ila board cpld version";
           }
           leaf fpc-optical-ila-summary-system-date {
             type string;
             description "Optical module ila summary ila system date";
           }
           leaf fpc-optical-ila-summary-system-time {
             type string;
             description "Optical module ila summary system time";
           }
           leaf fpc-optical-ila-summary-up-time {
             type string;
             description "Optical module ila summary ila up time";
           }
           leaf fpc-optical-ila-summary-ipv4-info {
             type string;
             description "Optical module ila summary ipv4 address/mask/gateway";
           }
           leaf fpc-optical-ila-summary-mac-address {
             type string;
             description "Optical module ila summary ila MAC address";
           }
           leaf fpc-optical-ila-summary-board-temp {
             type string;
             description "Optical module ila summary board temperature";
           }
           leaf fpc-optical-ila-summary-temp-thre {
             type string;
             description "Optical module ila summary temperature threshold";
           }
           leaf fpc-optical-ila-summary-pwr-fan-plug-status {
             type string;
             description "Optical module ila summary power fan plug status";
           }
           leaf fpc-optical-ila-summary-fan-speed {
             type string;
             description "Optical module ila summary fan speed";
           }
           leaf fpc-optical-ila-summary-system-mode {
             type string;
             description "Optical module ila summary system mode";
           }
           leaf fpc-optical-ila-summary-firmware-upgrade-status {
             type string;
             description "Optical module ila summary firmware upgrade status";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container voa {
           leaf fpc-optical-ila-voa-info {
             type string;
             description "Optical module ila voa information";
           }
           leaf fpc-optical-ila-voa-index {
             type string;
             description "Optical module ila voa index";
           }
           leaf fpc-optical-ila-voa-attenuation {
             type string;
             description "Optical module ila voa index";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container osc {
           leaf fpc-optical-ila-osc-info {
             type string;
             description "Optical module ila osc information";
           }
           leaf fpc-optical-ila-osc-index {
             type string;
             description "Optical module ila osc index";
           }
           leaf fpc-optical-ila-osc-mfg-node {
             type string;
             description "Optical ila OSC manufacture node";
           }
           leaf fpc-optical-ila-osc-enable {
             type string;
             description "Optical ila OSC enable";
           }
           leaf fpc-optical-ila-osc-add-power-value {
             type string;
             description "Optical ila OSC add power value";
           }
           leaf fpc-optical-ila-osc-drop-power-value {
             type string;
             description "Optical ila OSC drop power value";
           }
           leaf fpc-optical-ila-osc-add-los-thr {
             type string;
             description "Optical ila OSC add los threshold";
           }
           leaf fpc-optical-ila-osc-drop-los-thr {
             type string;
             description "Optical ila OSC drop los threshold";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
         container ila-alarm {
           leaf fpc-optical-ila-alarm-board-temp-abnormal {
             type string;
             description "Optical ila alarm board temperatur abnormal";
           }
           leaf fpc-optical-ila-alarm-communication-abnormal {
             type string;
             description "Optical ila alarm communication abnormal";
           }
           leaf fpc-optical-ila-alarm-fan1-online-abnormal {
             type string;
             description "Optical ila alarm fan1 online abnormal";
           }
           leaf fpc-optical-ila-alarm-fan2-online-abnormal {
             type string;
             description "Optical ila alarm fan2 online abnormal";
           }
           leaf fpc-optical-ila-alarm-fan3-online-abnormal {
             type string;
             description "Optical ila alarm fan3 online abnormal";
           }
           leaf fpc-optical-ila-alarm-fan1-speed-abnormal {
             type string;
             description "Optical ila alarm fan1 speed abnormal";
           }
           leaf fpc-optical-ila-alarm-fan2-speed-abnormal {
             type string;
             description "Optical ila alarm fan2 speed abnormal";
           }
           leaf fpc-optical-ila-alarm-fan3-speed-abnormal {
             type string;
             description "Optical ila alarm fan3 speed abnormal";
           }
           leaf fpc-optical-ila-alarm-software-version-abnormal {
             type string;
             description "Optical ila alarm software version abnormal";
           }
           leaf fpc-optical-ila-alarm-ac-power-abnormal {
             type string;
             description "Optical ila alarm ac power abnormal";
           }
           leaf fpc-optical-ila-alarm-dc-power-abnormal {
             type string;
             description "Optical ila alarm dc power abnormal";
           }
           leaf fpc-optical-ila-alarm-table-err {
             type string;
             description "Optical ila alarm table error";
           }
           leaf fpc-optical-ila-alarm-edfa-ab-case-temp {
             type string;
             description "Optical ila alarm edfa ab case temperature";
           }
           leaf fpc-optical-ila-alarm-edfa-ab-rfl {
             type string;
             description "Optical ila alarm edfa ab RFL";
           }
           leaf fpc-optical-ila-alarm-edfa-ab-oop {
             type string;
             description "Optical ila alarm edfa ab OOP";
           }
           leaf fpc-optical-ila-alarm-edfa-ab-oog {
             type string;
             description "Optical ila alarm edfa ab OOG";
           }
           leaf fpc-optical-ila-alarm-edfa-ab-pump1-eol {
             type string;
             description "Optical ila alarm edfa ab pump 1 EOL";
           }
           leaf fpc-optical-ila-alarm-edfa-ab-pump2-eol {
             type string;
             description "Optical ila alarm edfa ab pump 2 EOL";
           }
           leaf fpc-optical-ila-alarm-edfa-ab-pump1-temp-abnormal {
             type string;
             description "Optical ila alarm edfa ab pump 1 temp abmornal";
           }
           leaf fpc-optical-ila-alarm-edfa-ab-pump2-temp-abnormal {
             type string;
             description "Optical ila alarm edfa ab pump 2 temp abmornal";
           }
           leaf fpc-optical-ila-alarm-edfa-ab-input-los {
             type string;
             description "Optical ila alarm edfa ab input LOS";
           }
           leaf fpc-optical-ila-alarm-edfa-ab-output-alarm {
             type string;
             description "Optical ila alarm edfa ab output alarm";
           }
           leaf fpc-optical-ila-alarm-edfa-ab-cali-tbl-err {
             type string;
             description "Optical ila alarm edfa ab cali table error";
           }
           leaf fpc-optical-ila-alarm-edfa-ba-case-temp {
             type string;
             description "Optical ila alarm edfa ba case temperature";
           }
           leaf fpc-optical-ila-alarm-edfa-ba-rfl {
             type string;
             description "Optical ila alarm edfa ba RFL";
           }
           leaf fpc-optical-ila-alarm-edfa-ba-oop {
             type string;
             description "Optical ila alarm edfa ba OOP";
           }
           leaf fpc-optical-ila-alarm-edfa-ba-oog {
             type string;
             description "Optical ila alarm edfa ba OOG";
           }
           leaf fpc-optical-ila-alarm-edfa-ba-pump1-eol {
             type string;
             description "Optical ila alarm edfa ba pump 1 EOL";
           }
           leaf fpc-optical-ila-alarm-edfa-ba-pump2-eol {
             type string;
             description "Optical ila alarm edfa ba pump 2 EOL";
           }
           leaf fpc-optical-ila-alarm-edfa-ba-pump1-temp-abnormal {
             type string;
             description "Optical ila alarm edfa ba pump 1 temp abmornal";
           }
           leaf fpc-optical-ila-alarm-edfa-ba-pump2-temp-abnormal {
             type string;
             description "Optical ila alarm edfa ba pump 2 temp abmornal";
           }
           leaf fpc-optical-ila-alarm-edfa-ba-input-los {
             type string;
             description "Optical ila alarm edfa ba input LOS";
           }
           leaf fpc-optical-ila-alarm-edfa-ba-output-alarm {
             type string;
             description "Optical ila alarm edfa ba output alarm";
           }
           leaf fpc-optical-ila-alarm-edfa-ba-cali-tbl-err {
             type string;
             description "Optical ila alarm edfa ba cali table error";
           }
           leaf fpc-optical-ila-alarm-osc-a-add-power-alarm {
             type string;
             description "Optical ila alarm osc a add power alarm";
           }
           leaf fpc-optical-ila-alarm-osc-a-drop-power-alarm {
             type string;
             description "Optical ila alarm osc a drop power alarm";
           }
           leaf fpc-optical-ila-alarm-osc-b-add-power-alarm {
             type string;
             description "Optical ila alarm osc b add power alarm";
           }
           leaf fpc-optical-ila-alarm-osc-b-drop-power-alarm {
             type string;
             description "Optical ila alarm osc b drop power alarm";
           }
           leaf fpc-optical-ocm-awg {
             type string;
             description "Optical module OCM channel 0 AWG port power";
           }
           leaf fpc-optical-ocm-e2out {
             type string;
             description "Optical module OCM channel 0 E2 output port power";
           }
           leaf fpc-optical-channel {
             type string;
             description "Optical module OCM channel";
           }
           leaf fpc-optical-channel-awg {
             type string;
             description "Optical module OCM channel AWG";
           }
           leaf fpc-optical-channel-e2out {
             type string;
             description "Optical module OCM channel E2OUT";
           }
         }
       }
     }
   }
   rpc get-fpc-optical-mfg-info-information {
     description "Show mfg-info of optical module";
     input {
       leaf fpc-slot {
         description "FPC slot number";
         type uint32 {
           range "0 .. 63";
         }
         mandatory true;
       }
     }
   }
   rpc get-fpc-optical-status-information {
     description "Show status of optical module";
     input {
       leaf fpc-slot {
         description "FPC slot number";
         type uint32 {
           range "0 .. 63";
         }
         mandatory true;
       }
     }
   }
   rpc get-fpc-optical-alarms-information {
     description "Show alarms of optical module";
     input {
       leaf fpc-slot {
         description "FPC slot number";
         type uint32 {
           range "0 .. 63";
         }
         mandatory true;
       }
     }
   }
   rpc get-fpc-optical-edfa-information {
     description "Show edfa of optical module";
     input {
       leaf fpc-slot {
         description "FPC slot number";
         type uint32 {
           range "0 .. 63";
         }
         mandatory true;
       }
     }
   }
   rpc get-fpc-optical-ocm-information {
     description "Show ocm of optical module";
     input {
       leaf fpc-slot {
         description "FPC slot number";
         type uint32 {
           range "0 .. 63";
         }
         mandatory true;
       }
     }
   }
   rpc get-fpc-optical-wss-information {
     description "Show wss of optical module";
     input {
       leaf fpc-slot {
         description "FPC slot number";
         type uint32 {
           range "0 .. 63";
         }
         mandatory true;
       }
     }
   }
   rpc get-fpc-optical-pm-current-information {
     description "Show pm-current of optical module";
     input {
       leaf fpc-slot {
         description "FPC slot number";
         type uint32 {
           range "0 .. 63";
         }
         mandatory true;
       }
     }
   }
   rpc get-fpc-optical-pm-interval-information {
     description "Show pm-interval of optical module";
     input {
       leaf fpc-slot {
         description "FPC slot number";
         type uint32 {
           range "0 .. 63";
         }
         mandatory true;
       }
     }
   }
   rpc get-fpc-optical-pm-currentday-information {
     description "Show pm-currentday of optical module";
     input {
       leaf fpc-slot {
         description "FPC slot number";
         type uint32 {
           range "0 .. 63";
         }
         mandatory true;
       }
     }
   }
   rpc get-fpc-optical-pm-previousday-information {
     description "Show pm-previousday of optical module";
     input {
       leaf fpc-slot {
         description "FPC slot number";
         type uint32 {
           range "0 .. 63";
         }
         mandatory true;
       }
     }
   }
   rpc get-fpc-optical-amplifier-topology-information {
     description "Show amplifier-topology of optical module";
     input {
       leaf fpc-slot {
         description "FPC slot number";
         type uint32 {
           range "0 .. 63";
         }
         mandatory true;
       }
     }
   }
   rpc get-fpc-optical-topology-information {
     description "Show IPLC Topology Information";
     input {
       leaf fpc-slot {
         description "FPC slot number";
         type uint32 {
           range "0 .. 63";
         }
         mandatory true;
       }
       leaf detail {
         description "Show IPLC Topology Detailed Information";
         type empty;
       }
     }
   }
   rpc get-fpc-optical-amplifier-chain-information {
     description "Show in-line amplifier amplifier-chain information";
   }
   rpc get-fpc-optical-ila-summary-information {
     description "Show summary of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-edfa-information {
     description "Show edfa of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-osc-information {
     description "Show osc of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-voa-information {
     description "Show voa of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-alarms-information {
     description "Show alarms of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-pm-current-information {
     description "Show pm-current of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-pm-interval-information {
     description "Show pm-interval of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-pm-currentday-information {
     description "Show pm-currentday of ila module";
     input {
       leaf fpc-slot {
         description "FPC slot number";
         type uint32 {
           range "0 .. 63";
         }
         mandatory true;
       }
       leaf ila-number {
         description "In-line amplifier number";
         type uint32;
         mandatory true;
       }
     }
   }
   rpc get-fpc-optical-ila-pm-previousday-information {
     description "Show pm-previousday of ila module";
     input {
       leaf fpc-slot {
         description "FPC slot number";
         type uint32 {
           range "0 .. 63";
         }
         mandatory true;
       }
       leaf ila-number {
         description "In-line amplifier number";
         type uint32;
         mandatory true;
       }
     }
   }
   rpc get-pic-detail {
     description "Show Physical Interface Card state, type, and uptime";
     input {
       leaf fpc-slot {
         description "Slot number of FPC that houses PIC";
         type uint32 {
           range "0 .. 63";
         }
       }
       leaf pic-slot {
         description "PIC slot number";
         type int32 {
           range "0 .. 3";
         }
         mandatory true;
       }
     }
     output {
       container fpc-information {
         container terse {
           container fpc {
             leaf slot {
               type int32;
             }
             leaf state {
               type string;
               description "Status of the component";
             }
             leaf comment {
               type string;
             }
             leaf temperature {
               type string;
               description "Temperature of the item";
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container brief {
           leaf fpc-slot {
             type int32;
             description "FPC slot";
           }
           leaf fpc-status {
             type string;
             description "FPC status";
           }
           leaf fpc-power-limit {
             type string;
             description "FPC power limit";
           }
           leaf fpc-power {
             type string;
             description "Total FPC power consumption";
           }
           leaf fpc-priority {
             type string;
             description "Priority options";
           }
           leaf fpc-firmware-version {
             type string;
             description "POE firmware version";
           }
           container fpc {
             leaf slot {
               type int32;
             }
             leaf state {
               type string;
               description "Status of the component";
             }
             leaf comment {
               type string;
             }
             leaf temperature {
               type string;
               description "Temperature of the item";
             }
             leaf cpu-total {
               type int32;
               description "Percentage of CPU utilized";
             }
             leaf cpu-interrupt {
               type int32;
               description "Percentage of CPU utilized by interrupt processing";
             }
             leaf cpu-1min-avg {
               type int32;
               description "Percentage of one min average CPU utilized";
             }
             leaf cpu-5min-avg {
               type int32;
               description "Percentage of five min average CPU utilized";
             }
             leaf cpu-15min-avg {
               type int32;
               description "Percentage of fifteen min average CPU utilized";
             }
             leaf memory-dram-size {
               type int32;
               description "DRAM";
             }
             leaf memory-heap-utilization {
               type int32;
               description "Percentage of heap memory utilized";
             }
             leaf memory-buffer-utilization {
               type int32;
               description "Percentage of buffer memory utilized";
             }
             leaf gnf-id {
               type string;
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container verbose {
           container fpc {
             leaf slot {
               type int32;
             }
             leaf state {
               type string;
               description "Status of the component";
             }
             leaf error-code {
               type int32;
               description "Code resulting from major or minor error";
             }
             leaf logical-slot {
               type int32;
             }
             leaf temperature {
               type string;
               description "Temperature of the item";
             }
             leaf cpu-less-info-str {
               type string;
               description "Flexible PIC Concentrator (FPC) without CPU";
             }
             leaf memory-dram-size {
               type int32;
               description "DRAM";
             }
             leaf memory-sram-size {
               type int32;
               description "SRAM";
             }
             leaf memory-sdram-size {
               type int32;
               description "SDRAM";
             }
             leaf memory-notification-sdram-size {
               type int32;
               description "Notification SDRAM";
             }
             leaf memory-rldram-size {
               type int32;
               description "RLDRAM";
             }
             leaf memory-xr2-size {
               type int32;
               description "XR2";
             }
             leaf memory-ddr-dram-size {
               type int32;
               description "DDR DRAM";
             }
             leaf asic-information {
               type string;
             }
             leaf start-time {
               type string;
               description "Time this component was started";
             }
             leaf up-time {
               type string;
               description "Length of time this component has been operational";
             }
             leaf comment {
               type string;
             }
             leaf max-power-consumption {
               type int32;
             }
             leaf max-mpc-base-power-consumption {
               type int32;
               description "Max MPC base power consumption";
             }
             leaf max-mic0-power-consumption {
               type int32;
               description "Max MIC0 power consumption";
             }
             leaf max-mic1-power-consumption {
               type int32;
               description "Max MIC1 power consumption";
             }
             leaf max-mpc-total-power-consumption {
               type int32;
               description "Max MPC total power consumption";
             }
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
         container pic-style {
           container fpc {
             leaf slot {
               type int32;
             }
             leaf state {
               type string;
               description "Status of the component";
             }
             leaf description {
               type string;
               description "Description of this component";
             }
             leaf red-led {
               type empty;
               description "Red LED is lit";
             }
             leaf green-led {
               type empty;
               description "Green LED is lit";
             }
             container pic {
               leaf pic-slot {
                 type int32;
               }
               leaf pic-state {
                 type string;
               }
               leaf pic-type {
                 type string;
               }
               leaf comment {
                 type string;
               }
             }
             container pic-detail {
               container port-information {
               }
               container package-information {
                 container package {
                   leaf package-name {
                     type string;
                   }
                 }
               }
               container port-speed-information {
               }
             }
           }
         }
         container pic-style-detail {
           container fpc {
             leaf red-led {
               type empty;
               description "Red LED is lit";
             }
             leaf green-led {
               type empty;
               description "Green LED is lit";
             }
             container pic-detail {
               leaf slot {
                 type int32;
               }
               leaf pic-slot {
                 type int32;
               }
               leaf pic-type {
                 type string;
               }
               leaf comment {
                 type string;
               }
               leaf asic-type {
                 type string;
                 description "Type of ASIC on the PIC";
               }
               leaf account-layer2-overhead {
                 type string;
                 description "Account Layer2 Overhead Knob Status";
               }
               leaf state {
                 type string;
                 description "Status of the component";
               }
               leaf pic-version {
                 type string;
                 description "PIC hardware version";
               }
               leaf cpu-sw-version {
                 type string;
                 description "Version of operating system running on the PIC";
               }
               leaf cpu-rom-version {
                 type string;
                 description "PIC ROM version";
               }
               leaf cpu-total {
                 type int32;
                 description "Percentage of CPU utilized";
               }
               leaf cpu-interrupt {
                 type int32;
                 description "Percentage of CPU utilized by interrupt processing";
               }
               leaf memory-dram-size {
                 type int32;
                 description "DRAM";
               }
               leaf memory-buffer-utilization {
                 type int32;
                 description "Percentage of buffer memory utilized";
               }
               leaf memory-heap-utilization {
                 type int32;
                 description "Percentage of heap memory utilized";
               }
               leaf up-time {
                 type string;
                 description "Length of time this component has been operational";
               }
               leaf pic-package {
                 type string;
               }
               leaf pic-clock-sync {
                 type string;
                 description "PIC Clock Synchronization";
               }
               leaf pic-multirate-mode {
                 type string;
               }
               leaf pic-channelization-mode {
                 type string;
                 description "PIC Channelization Mode";
               }
               leaf configured-mode {
                 type string;
               }
               leaf control-cores {
                 type int32;
               }
               leaf data-cores {
                 type int32;
               }
               leaf object-cache-size {
                 type int32;
               }
               leaf policy-db-size {
                 type int32;
               }
               leaf forwarding-db-size {
                 type int32;
               }
               leaf wired-process-mem-size {
                 type int32;
               }
               leaf wired-max-processes {
                 type int32;
               }
               container port-information {
                 container port {
                   leaf port-number {
                     type int32;
                     description "Port number on the PIC";
                   }
                   leaf cable-type {
                     type string;
                     description "Port cable type";
                   }
                   leaf fiber-mode {
                     type string;
                     description "Single or multi-mode";
                   }
                   leaf sfp-vendor-name {
                     type string;
                     description "SFP vendor name";
                   }
                   leaf sfp-vendor-pno {
                     type string;
                     description "SFP vendor part number";
                   }
                   leaf wavelength {
                     type string;
                     description "Wavelength of the optical transceiver";
                   }
                   leaf sfp-vendor-fw-ver {
                     type string;
                     description "Vendor firmware version";
                   }
                 }
               }
               container pic-transport-information {
                 leaf pic-transport-admin-state {
                   type string;
                 }
                 leaf pic-transport-oper-state {
                   type string;
                 }
               }
               container package-information {
                 container package {
                   leaf package-name {
                     type string;
                   }
                 }
               }
               container port-speed-information {
                 container port {
                   leaf port-number1 {
                     type int32;
                     description "PIC port number";
                   }
                   leaf speed-capability {
                     type string;
                     description "Port speed capabilities";
                   }
                 }
               }
             }
           }
         }
         container detail {
           leaf fpc-slot {
             type int32;
             description "FPC slot";
           }
           leaf fpc-status {
             type string;
             description "FPC status";
           }
           leaf fpc-power-limit {
             type string;
             description "FPC power limit";
           }
           leaf fpc-power {
             type string;
             description "Total FPC power consumption";
           }
           leaf fpc-priority {
             type string;
             description "Priority options";
           }
           leaf fpc-firmware-version {
             type string;
             description "POE firmware version";
           }
           container fpc {
             leaf red-led {
               type empty;
               description "Red LED is lit";
             }
             leaf green-led {
               type empty;
               description "Green LED is lit";
             }
             container pic-detail {
               container port-information {
               }
               container package-information {
                 container package {
                   leaf package-name {
                     type string;
                   }
                 }
               }
               container port-speed-information {
               }
             }
           }
         }
       }
     }
   }
   rpc get-chassis-inventory {
     description "Show installed hardware components";
     input {
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
     output {
       container chassis-inventory {
         container chassis {
           description "Hardware inventory of this chassis";
           container inventory {
             description "Hardware inventory of this chassis";
             leaf name {
               type string;
               description "Name of this component";
             }
             leaf version {
               type string;
               description "Version of this component";
             }
             leaf part-number {
               type string;
               description "Part number of this component";
             }
             leaf serial-number {
               type string;
               description "Serial number of this component";
             }
             leaf description {
               type string;
               description "Description of this component";
             }
             leaf hardware-incomplete {
               type empty;
             }
             leaf model-number {
               type string;
               description "Model number of this component";
             }
             leaf clei-code {
               type string;
               description "Common Language Equipment Identifier code of this component";
             }
             container i2c-information {
               leaf jedec-code {
                 type string;
               }
               leaf eeprom-version {
                 type string;
               }
               leaf assembly-identifier {
                 type string;
               }
               leaf assembly-version {
                 type string;
               }
               leaf manufacture-date {
                 type string;
                 description "Date this component was manufactured";
               }
               leaf assembly-flags {
                 type string;
               }
               leaf i2c-version {
                 type string;
               }
               leaf i2c-identifier {
                 type string;
               }
               leaf board-information-record {
                 type string;
                 description "Hex dump of board information record";
               }
               leaf i2c-data {
                 type string;
                 description "Hex dump of I2C data";
               }
             }
             container chassis-module {
               leaf name {
                 type string;
                 description "Name of this component";
               }
               leaf version {
                 type string;
                 description "Version of this component";
               }
               leaf part-number {
                 type string;
                 description "Part number of this component";
               }
               leaf serial-number {
                 type string;
                 description "Serial number of this component";
               }
               leaf description {
                 type string;
                 description "Description of this component";
               }
               leaf ir-mode {
                 type string;
                 description "R/IR mode configured";
               }
               leaf license-mode {
                 type string;
                 description "PTX R/IR mode configured";
               }
               container i2c-information {
                 leaf jedec-code {
                   type string;
                 }
                 leaf eeprom-version {
                   type string;
                 }
                 leaf assembly-identifier {
                   type string;
                 }
                 leaf assembly-version {
                   type string;
                 }
                 leaf manufacture-date {
                   type string;
                   description "Date this component was manufactured";
                 }
                 leaf assembly-flags {
                   type string;
                 }
                 leaf i2c-version {
                   type string;
                 }
                 leaf clei-code {
                   type string;
                   description "Common Language Equipment Identifier code of this component";
                 }
                 leaf i2c-identifier {
                   type string;
                 }
                 leaf model-number {
                   type string;
                   description "Model number of this component";
                 }
                 leaf board-information-record {
                   type string;
                   description "Hex dump of board information record";
                 }
                 leaf i2c-data {
                   type string;
                   description "Hex dump of I2C data";
                 }
               }
               container chassis-sub-module {
                 leaf name {
                   type string;
                   description "Name of this component";
                 }
                 leaf version {
                   type string;
                   description "Version of this component";
                 }
                 leaf part-number {
                   type string;
                   description "Part number of this component";
                 }
                 leaf serial-number {
                   type string;
                   description "Serial number of this component";
                 }
                 leaf description {
                   type string;
                   description "Description of this component";
                 }
                 container i2c-information {
                   leaf jedec-code {
                     type string;
                   }
                   leaf eeprom-version {
                     type string;
                   }
                   leaf assembly-identifier {
                     type string;
                   }
                   leaf assembly-version {
                     type string;
                   }
                   leaf manufacture-date {
                     type string;
                     description "Date this component was manufactured";
                   }
                   leaf assembly-flags {
                     type string;
                   }
                   leaf i2c-version {
                     type string;
                   }
                   leaf clei-code {
                     type string;
                     description "Common Language Equipment Identifier code of this component";
                   }
                   leaf i2c-identifier {
                     type string;
                   }
                   leaf model-number {
                     type string;
                     description "Model number of this component";
                   }
                   leaf board-information-record {
                     type string;
                     description "Hex dump of board information record";
                   }
                   leaf i2c-data {
                     type string;
                     description "Hex dump of I2C data";
                   }
                 }
                 container chassis-sub-sub-module {
                   leaf name {
                     type string;
                     description "Name of this component";
                   }
                   leaf version {
                     type string;
                     description "Version of this component";
                   }
                   leaf part-number {
                     type string;
                     description "Part number of this component";
                   }
                   leaf serial-number {
                     type string;
                     description "Serial number of this component";
                   }
                   leaf description {
                     type string;
                     description "Description of this component";
                   }
                   leaf model-number {
                     type string;
                     description "Model number of this component";
                   }
                   leaf clei-code {
                     type string;
                     description "Common Language Equipment Identifier code of this component";
                   }
                   container chassis-sub-sub-sub-module {
                   }
                 }
               }
               container chassis-re-disk-module {
                 leaf name {
                   type string;
                   description "Name of this component";
                 }
                 leaf disk-size {
                   type int32;
                   description "Disk size (megabytes)";
                 }
                 leaf model {
                   type string;
                 }
                 leaf serial-number {
                   type string;
                   description "Serial number of this component";
                 }
                 leaf description {
                   type string;
                   description "Description of this component";
                 }
               }
               container chassis-re-usb-module {
                 leaf name {
                   type string;
                   description "Name of this component";
                 }
                 leaf product {
                   type string;
                 }
                 leaf product-number {
                   type int32;
                 }
                 leaf vendor {
                   type string;
                 }
                 leaf description {
                   type string;
                   description "Description of this component";
                 }
               }
               container chassis-re-dimm-module {
                 leaf name {
                   type string;
                   description "Name of this component";
                 }
                 leaf part-number {
                   type string;
                   description "Part number of this component";
                 }
                 leaf die-rev {
                   type string;
                   description " DIE revision of the DIMM";
                 }
                 leaf pcb-rev {
                   type string;
                   description "PCB revision ";
                 }
                 leaf mfr-id {
                   type string;
                   description "Manufacture Id of the DIMM";
                 }
               }
               container chassis-compute-node-disk-module {
                 leaf name {
                   type string;
                   description "Name of this component";
                 }
                 leaf disk-size {
                   type int32;
                   description "Disk size (megabytes)";
                 }
                 leaf model {
                   type string;
                 }
                 leaf serial-number {
                   type string;
                   description "Serial number of this component";
                 }
                 leaf description {
                   type string;
                   description "Description of this component";
                 }
               }
             }
           }
           container model-inventory {
             description "Hardware inventory of this chassis";
             leaf model-number {
               type string;
               description "Model number of this component";
             }
             leaf clei-code {
               type string;
               description "Common Language Equipment Identifier code of this component";
             }
             container chassis-module {
               leaf name {
                 type string;
                 description "Name of this component";
               }
               leaf version {
                 type string;
                 description "Version of this component";
               }
               leaf part-number {
                 type string;
                 description "Part number of this component";
               }
               leaf serial-number {
                 type string;
                 description "Serial number of this component";
               }
               container chassis-sub-module {
                 container chassis-sub-sub-module {
                   container chassis-sub-sub-sub-module {
                   }
                 }
               }
             }
           }
           container clei-model-inventory {
             description "Hardware inventory of this chassis";
             leaf model-number {
               type string;
               description "Model number of this component";
             }
             leaf clei-code {
               type string;
               description "Common Language Equipment Identifier code of this component";
             }
             container chassis-module {
               leaf name {
                 type string;
                 description "Name of this component";
               }
               leaf version {
                 type string;
                 description "Version of this component";
               }
               leaf part-number {
                 type string;
                 description "Part number of this component";
               }
               container chassis-sub-module {
                 container chassis-sub-sub-module {
                   container chassis-sub-sub-sub-module {
                   }
                 }
               }
             }
           }
           container firmware {
             description "Hardware inventory of this chassis";
             leaf model-number {
               type string;
               description "Model number of this component";
             }
             leaf clei-code {
               type string;
               description "Common Language Equipment Identifier code of this component";
             }
             container chassis-module {
               leaf name {
                 type string;
                 description "Name of this component";
               }
               container chassis-sub-module {
                 container chassis-sub-sub-module {
                   container chassis-sub-sub-sub-module {
                   }
                 }
               }
             }
           }
         }
       }
     }
   }
   rpc get-chassis-mac-addresses {
     description "Show media access control addresses";
     output {
       container chassis-mac-addresses {
         container chassis-mac-addresses-edge-info {
           container re-mac-address {
             leaf re-fc-mac-base {
               type string;
             }
             leaf re-fc-mac-count {
               type string;
             }
             leaf re-vlan-mac {
               type string;
             }
           }
           container fpc-mac-address {
             leaf name {
               type string;
               description "Name of this component";
             }
             leaf fpc-mac-base {
               type string;
             }
             leaf fpc-mac-count {
               type string;
             }
           }
         }
         container mac-address-information {
           leaf public-base-address {
             type string;
           }
           leaf public-count {
             type string;
           }
           leaf private-base-address {
             type string;
           }
           leaf private-count {
             type string;
           }
         }
         container external-mac-address-information {
           leaf external-base-address {
             type string;
           }
           leaf external-count {
             type string;
           }
           leaf external-available {
             type string;
           }
         }
       }
     }
   }
   rpc get-route-engine-information {
     description "Show Routing Engine status";
     output {
       container route-engine-information {
         container route-engine {
           leaf slot {
             type int32;
           }
           leaf physical-slot {
             type int32;
           }
           leaf mastership-state {
             type string;
             description "Current state of mastership on this Routing Engine";
           }
           leaf mastership-priority {
             type string;
             description "Configured priority for mastership on this Routing Engine";
           }
           leaf temperature {
             type string;
             description "Temperature of the item";
           }
           leaf cpu-temperature {
             type string;
           }
           leaf memory-dram-size {
             type int32;
             description "DRAM";
           }
           leaf memory-installed-size {
             type string;
             description "Installed RAM";
           }
           leaf memory-buffer-utilization {
             type int32;
             description "Percentage of buffer memory utilized";
           }
           leaf memory-system-total {
             type int32;
             description "Display the total system memory";
           }
           leaf memory-system-total-used {
             type int32;
             description "Display overall utilization of system memory";
           }
           leaf memory-system-total-util {
             type int32;
             description "Display overall %utilization of system memory";
           }
           leaf memory-control-plane {
             type int32;
             description "Display the total memory with control plane";
           }
           leaf memory-control-plane-used {
             type int32;
             description "Display the memory utilization of control plane mem";
           }
           leaf memory-control-plane-util {
             type int32;
             description "Display the %memory utilization of control plane mem";
           }
           leaf memory-data-plane {
             type int32;
             description "Display the total memory preallocated for data plane";
           }
           leaf memory-data-plane-used {
             type int32;
             description "Display the memory utilization of data plane mem";
           }
           leaf memory-data-plane-util {
             type int32;
             description "Display the %memory utilization of data plane mem";
           }
           leaf control-plane-cpu-count {
             type int32;
             description "Display the number of CPUS dedicated for control-plane";
           }
           leaf data-plane-cpu-count {
             type int32;
             description "Display the number of CPUS dedicated for data-plane";
           }
           leaf cpu-user {
             type int32;
             description "Percentage of CPU utilized by user processes";
           }
           leaf cpu-real-time {
             type int32;
             description "Percentage of CPU utilized by real-time threads";
           }
           leaf cpu-background {
             type int32;
             description "Percentage of CPU utilized by background processes";
           }
           leaf cpu-system {
             type int32;
             description "Percentage of CPU utilized by the kernel";
           }
           leaf cpu-interrupt {
             type int32;
             description "Percentage of CPU utilized by interrupt processing";
           }
           leaf cpu-idle {
             type int32;
             description "Percentage of CPU idle time";
           }
           leaf cpu-user1 {
             type int32;
             description "Percentage of CPU utilized by user processes";
           }
           leaf cpu-background1 {
             type int32;
             description "Percentage of CPU utilized by background processes";
           }
           leaf cpu-system1 {
             type int32;
             description "Percentage of CPU utilized by the kernel";
           }
           leaf cpu-interrupt1 {
             type int32;
             description "Percentage of CPU utilized by the Interrupt";
           }
           leaf cpu-idle1 {
             type int32;
             description "Percentage of CPU idle time";
           }
           leaf cpu-user2 {
             type int32;
             description "Percentage of CPU utilized by user processes";
           }
           leaf cpu-background2 {
             type int32;
             description "Percentage of CPU utilized by background processes";
           }
           leaf cpu-system2 {
             type int32;
             description "Percentage of CPU utilized by the kernel";
           }
           leaf cpu-interrupt2 {
             type int32;
             description "Percentage of CPU utilized by the Interrupt";
           }
           leaf cpu-idle2 {
             type int32;
             description "Percentage of CPU idle time";
           }
           leaf cpu-user3 {
             type int32;
             description "Percentage of CPU utilized by user processes";
           }
           leaf cpu-background3 {
             type int32;
             description "Percentage of CPU utilized by background processes";
           }
           leaf cpu-system3 {
             type int32;
             description "Percentage of CPU utilized by the kernel";
           }
           leaf cpu-interrupt3 {
             type int32;
             description "Percentage of CPU utilized by the Interrupt";
           }
           leaf cpu-idle3 {
             type int32;
             description "Percentage of CPU idle time";
           }
           leaf model {
             type string;
           }
           leaf serial-number {
             type string;
             description "Serial number of this component";
           }
           leaf start-time {
             type string;
             description "Time this component was started";
           }
           leaf up-time {
             type string;
             description "Length of time this component has been operational";
           }
           leaf last-reboot-reason {
             type string;
             description "Last reboot reason of routinge engine";
           }
           leaf load-average-one {
             type string;
           }
           leaf load-average-five {
             type string;
           }
           leaf load-average-fifteen {
             type string;
           }
           leaf bios-version {
             type string;
             description "Routing engine BIOS version";
           }
           leaf bios-date {
             type string;
             description "Routing engine BIOS date";
           }
           leaf bios-id {
             type string;
             description "Routing engine BIOS ID";
           }
           leaf loader-name {
             type string;
             description "Routing engine Loader name";
           }
           leaf loader-version {
             type string;
             description "Routing engine Loader version";
           }
           leaf icrt-version {
             type string;
             description "Routing engine iCRT version";
           }
           leaf description {
             type string;
             description "Description of this component";
           }
           leaf status {
             type string;
             description "Status of clock synchronization source";
           }
         }
       }
     }
   }
   rpc get-bios-version-information {
     description "Show BIOS firmware version";
   }
   rpc get-chassis-routing-engine-errors {
     description "Show re errors";
   }
   rpc get-chassis-location {
     description "Show physical location of chassis";
     output {
       container chassis-location {
         container chassis-location-information {
           leaf country-code {
             type string;
             description "Country code";
           }
           leaf postal-code {
             type string;
             description "Postal code";
           }
           leaf npa-nxx {
             type string;
             description "Six digits of the phone number";
           }
           leaf altitude {
             type int32;
             description "Feet above (or below) sea level";
           }
           leaf lata {
             type string;
             description "Long distance service area";
           }
           leaf latitude {
             type string;
             description "Latitude";
           }
           leaf longitude {
             type string;
             description "Longitude";
           }
           leaf vcoord {
             type string;
             description "Bellcore vertical coordinate";
           }
           leaf hcoord {
             type string;
             description "Bellcore horizontal coordinate";
           }
           leaf building {
             type string;
             description "Building information";
           }
           leaf floor {
             type uint32;
             description "Floor in building";
           }
           leaf rack {
             type uint32;
             description "Rack";
           }
         }
       }
     }
   }
   rpc get-temperature-threshold-information {
     description "Show chassis temperature threshold settings";
     output {
       container temperature-threshold-information {
         container temperature-threshold {
           description "Temperature threshold information for a component on the routing platform.";
         }
       }
     }
   }
   rpc get-chassis-oss-map {
     description "Show Operation Supported System's translated model";
     output {
       container chassis-oss-map {
         leaf chassis-model {
           type string;
           description "Actual chassis model";
         }
         leaf oss-map {
           type string;
           description "Configured OSS chassis model";
         }
       }
     }
   }
 }
