/*
 * Copyright (c) 2017 Juniper Networks, Inc.
 * All rights reserved.
 */

 module show-protection-group {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-raps-pdu-information {
     description "Show RAPS PDU information for ethernet ring";
     input {
       leaf verbosity_level {
         default "brief";
         type enumeration {
           enum "brief" {
             description "Display brief output (default)";
           }
           enum "detail" {
             description "Display detailed output";
           }
         }
       }
       leaf group-name {
         description "Name of protection group";
         type string;
       }
     }
     output {
       container erp-rpdu-information {
         container erp-rpdus {
           container brief {
             container erp-rpdu-entry {
               description "Information about Ethernet Ring RAPS PDU of a Ethernet Ring protection group";
               leaf protection-group-name {
                 type string;
                 description "Name of protection group";
               }
               leaf request-state {
                 type string;
                 description "Request/State of RAPS PDU";
               }
               leaf rb-flag {
                 type string;
                 description "Ring protection link blocking bit in the status field of RAPS PDU";
               }
               leaf dnf-flag {
                 type string;
                 description "Do not flush bit in the status field of RAPS PDU";
               }
               leaf bpr-val {
                 type int32;
                 description "Ring protection link blocked port reference bit in the status field of RAPS PDU";
               }
               leaf originator {
                 type string;
                 description "This node is the origination of RAPS PDU";
               }
               leaf remote-node-id {
                 type string;
                 description "Media access control address of bridge";
               }
             }
           }
           container detail {
             container erp-rpdu-entry {
               description "Information about Ethernet Ring RAPS PDU of a Ethernet Ring protection group";
               leaf protection-group-name {
                 type string;
                 description "Name of protection group";
               }
               leaf request-state {
                 type string;
                 description "Request/State of RAPS PDU";
               }
               leaf rb-flag {
                 type string;
                 description "Ring protection link blocking bit in the status field of RAPS PDU";
               }
               leaf dnf-flag {
                 type string;
                 description "Do not flush bit in the status field of RAPS PDU";
               }
               leaf bpr-val {
                 type int32;
                 description "Ring protection link blocked port reference bit in the status field of RAPS PDU";
               }
               leaf originator {
                 type string;
                 description "This node is the origination of RAPS PDU";
               }
               leaf remote-node-id {
                 type string;
                 description "Media access control address of bridge";
               }
             }
           }
         }
       }
     }
   }
   rpc get-raps-state-machine-information {
     description "Show RAPS state machine information for ethernet ring";
     input {
       leaf verbosity_level {
         default "brief";
         type enumeration {
           enum "brief" {
             description "Display brief output (default)";
           }
           enum "detail" {
             description "Display detailed output";
           }
         }
       }
       leaf group-name {
         description "Name of protection group";
         type string;
       }
     }
     output {
       container erp-raps-information {
         container erp-raps {
           container brief {
             container erp-raps-entry {
               description "Information about Ethernet Ring Automatic Protection Switching state machine of a protection group";
               leaf protection-group-name {
                 type string;
                 description "Name of protection group";
               }
               leaf aps-state {
                 type string;
                 description "Automatic Protection Switching state";
               }
               leaf aps-event {
                 type string;
                 description "Current Automatic Protection Switching event";
               }
               leaf rpl-owner {
                 type string;
                 description "Ring protection link owner flag";
               }
               leaf wtr-timer {
                 type string;
                 description "Wait to restore timer state";
               }
               leaf wtb-timer {
                 type string;
                 description "Wait to block timer state";
               }
               leaf guard-timer {
                 type string;
                 description "Guard timer state";
               }
               leaf operation-state {
                 type string;
                 description "Operation state";
               }
             }
           }
           container detail {
             container erp-raps-entry {
               description "Information about Ethernet Ring Automatic Protection Switching state machine of a protection group";
               leaf protection-group-name {
                 type string;
                 description "Name of protection group";
               }
               leaf aps-state {
                 type string;
                 description "Automatic Protection Switching state";
               }
               leaf aps-event {
                 type string;
                 description "Current Automatic Protection Switching event";
               }
               leaf rpl-owner {
                 type string;
                 description "Ring protection link owner flag";
               }
               leaf wtr-timer {
                 type string;
                 description "Wait to restore timer state";
               }
               leaf wtb-timer {
                 type string;
                 description "Wait to block timer state";
               }
               leaf guard-timer {
                 type string;
                 description "Guard timer state";
               }
               leaf operation-state {
                 type string;
                 description "Operation state";
               }
             }
           }
         }
       }
     }
   }
   rpc get-ring-interface-information {
     description "Show interface information for ethernet ring";
     input {
       leaf verbosity_level {
         default "brief";
         type enumeration {
           enum "brief" {
             description "Display brief output (default)";
           }
           enum "detail" {
             description "Display detailed output";
           }
         }
       }
       leaf group-name {
         description "Name of protection group";
         type string;
       }
     }
     output {
       container erp-interface-information {
         container ethernet-ring-pg {
           container erp-interfaces {
             description "Information about ring ports";
             container brief {
               description "Information about ring ports";
               container erp-interface-entry {
                 description "Information about Ethernet Ring port of a Ethernet Ring protection group";
                 leaf erp-interface-name {
                   type string;
                   description "Name of ring port physical interface";
                 }
                 leaf control-channel-name {
                   type string;
                   description "Name of logical interface of ring port control channel";
                 }
                 leaf erp-interface-direction {
                   type string;
                   description "Direction on the interface (East/West)";
                 }
                 leaf forward-state {
                   type string;
                   description "Forward state";
                 }
                 leaf rpl-end {
                   type string;
                   description "Ring potection link end flag";
                 }
                 leaf sf-flag {
                   type string;
                   description "Signal failure flag of the ring port";
                 }
                 leaf interface-state {
                   type string;
                   description "Control interface state";
                 }
               }
             }
             container detail {
               description "Information about ring ports";
               container erp-interface-entry {
                 description "Information about Ethernet Ring port of a Ethernet Ring protection group";
                 leaf erp-interface-name {
                   type string;
                   description "Name of ring port physical interface";
                 }
                 leaf control-channel-name {
                   type string;
                   description "Name of logical interface of ring port control channel";
                 }
                 leaf erp-interface-direction {
                   type string;
                   description "Direction on the interface (East/West)";
                 }
                 leaf forward-state {
                   type string;
                   description "Forward state";
                 }
                 leaf rpl-end {
                   type string;
                   description "Ring potection link end flag";
                 }
                 leaf sf-flag {
                   type string;
                   description "Signal failure flag of the ring port";
                 }
                 leaf interface-state {
                   type string;
                   description "Control interface state";
                 }
               }
             }
           }
         }
       }
     }
   }
   rpc get-ring-statistics {
     description "Show statistics for ethernet ring";
     input {
       leaf verbosity_level {
         default "brief";
         type enumeration {
           enum "brief" {
             description "Display brief output (default)";
           }
           enum "detail" {
             description "Display detailed output";
           }
         }
       }
       leaf group-name {
         description "Name of protection group";
         type string;
       }
     }
     output {
       container ethernet-ring-statistics {
         container ethernet-ring-pg-statistics {
           container ethernet-ring-stats {
             description "Ethernet ring statistics for a ring instance";
             container brief {
               description "Ethernet ring statistics for a ring instance";
               container ethernet-ring-statistics-entry {
                 leaf protection-group-name {
                   type string;
                   description "Name of protection group";
                 }
                 leaf raps-event-sent {
                   type int32;
                   description "Total number of RAPS PDU sent out";
                 }
                 leaf raps-event-received {
                   type int32;
                   description "Total number of RAPS PDUs received";
                 }
                 leaf raps-local-sf {
                   type int32;
                   description "Total number of Local SF event happened";
                 }
                 leaf raps-remote-sf {
                   type int32;
                   description "Total number of Remote SF event happened";
                 }
                 leaf raps-nr-sent {
                   type int32;
                   description "Total number of NR event sent";
                 }
                 leaf raps-nr-received {
                   type int32;
                   description "Total number of NR event received";
                 }
                 leaf raps-nr-rb-sent {
                   type int32;
                   description "Total number of NR-RB event sent";
                 }
                 leaf raps-nr-rb-received {
                   type int32;
                   description "Total number of NR-RB event received";
                 }
                 leaf raps-local-flush-event {
                   type int32;
                   description "Total number of flush event sent";
                 }
                 leaf raps-remote-flush-event {
                   type int32;
                   description "Total number of flush event received";
                 }
                 leaf raps-local-fs {
                   type int32;
                   description "Total number of local FS event happened";
                 }
                 leaf raps-remote-fs {
                   type int32;
                   description "Total number of remote FS event happened";
                 }
                 leaf raps-local-ms {
                   type int32;
                   description "Total number of local MS event happened";
                 }
                 leaf raps-remote-ms {
                   type int32;
                   description "Total number of remote MS event happened";
                 }
                 leaf raps-pdu-received {
                   type int32;
                   description "Total number of valid raps PDU received";
                 }
               }
             }
             container detail {
               description "Ethernet ring statistics for a ring instance";
               container ethernet-ring-statistics-entry {
                 leaf protection-group-name {
                   type string;
                   description "Name of protection group";
                 }
                 leaf raps-event-sent {
                   type int32;
                   description "Total number of RAPS PDU sent out";
                 }
                 leaf raps-event-received {
                   type int32;
                   description "Total number of RAPS PDUs received";
                 }
                 leaf raps-local-sf {
                   type int32;
                   description "Total number of Local SF event happened";
                 }
                 leaf raps-remote-sf {
                   type int32;
                   description "Total number of Remote SF event happened";
                 }
                 leaf raps-nr-sent {
                   type int32;
                   description "Total number of NR event sent";
                 }
                 leaf raps-nr-received {
                   type int32;
                   description "Total number of NR event received";
                 }
                 leaf raps-nr-rb-sent {
                   type int32;
                   description "Total number of NR-RB event sent";
                 }
                 leaf raps-nr-rb-received {
                   type int32;
                   description "Total number of NR-RB event received";
                 }
                 leaf raps-local-flush-event {
                   type int32;
                   description "Total number of flush event sent";
                 }
                 leaf raps-remote-flush-event {
                   type int32;
                   description "Total number of flush event received";
                 }
                 leaf raps-local-fs {
                   type int32;
                   description "Total number of local FS event happened";
                 }
                 leaf raps-remote-fs {
                   type int32;
                   description "Total number of remote FS event happened";
                 }
                 leaf raps-local-ms {
                   type int32;
                   description "Total number of local MS event happened";
                 }
                 leaf raps-remote-ms {
                   type int32;
                   description "Total number of remote MS event happened";
                 }
                 leaf flush-fdb-counter {
                   type int32;
                   description "Total number of times fdb flush triggered";
                 }
                 leaf flush-logic-triggered-flush {
                   type int32;
                   description "Number of times fdb flush triggered by flush-logic";
                 }
                 leaf raps-pdu-received {
                   type int32;
                   description "Total number of valid raps PDU received";
                 }
                 leaf raps-gdt-dropped {
                   type int32;
                   description "Total number of raps PDU dropped to to guard-timer";
                 }
                 leaf raps-inv-dropped {
                   type int32;
                   description "Total number of raps PDU dropped due to validity check";
                 }
                 leaf raps-misc-err-dropped {
                   type int32;
                   description "Total number raps PDU dropped due to miscellaneous errors";
                 }
                 leaf raps-self-dropped {
                   type int32;
                   description "Total number of self raps PDU dropped";
                 }
               }
             }
           }
         }
       }
     }
   }
   rpc get-ring-data-channel-information {
     description "Show data channel for ethernet ring";
     input {
       leaf verbosity_level {
         default "brief";
         type enumeration {
           enum "brief" {
             description "Display brief output (default)";
           }
           enum "detail" {
             description "Display detailed output";
           }
         }
       }
       leaf group-name {
         description "Name of protection group";
         type string;
       }
     }
     output {
       container erp-data-channel-information {
         container erp-data-channels {
           container erp-data-channel-interfaces {
             description "Data channel information about ring ports";
             container brief {
               description "Data channel information about ring ports";
               container erp-data-channel-entry {
                 description "Data channel information about Ring port of a Ethernet Ring instance";
                 leaf data-channel-interface-name {
                   type string;
                   description "Name of ring port physical interface";
                 }
                 leaf data-channel-stp-index {
                   type int32;
                   description "STP index of the interface of ring instance";
                 }
                 leaf data-channel-forward-state {
                   type string;
                   description "Forward state";
                 }
               }
             }
             container detail {
               description "Data channel information about ring ports";
               container erp-data-channel-entry {
                 description "Data channel information about Ring port of a Ethernet Ring instance";
                 leaf data-channel-interface-name {
                   type string;
                   description "Name of ring port physical interface";
                 }
                 leaf data-channel-stp-index {
                   type int32;
                   description "STP index of the interface of ring instance";
                 }
                 leaf data-channel-forward-state {
                   type string;
                   description "Forward state";
                 }
               }
             }
           }
         }
       }
     }
   }
   rpc get-ring-vlan-information {
     description "Show VLAN information for ethernet ring data channel";
     input {
       leaf verbosity_level {
         default "brief";
         type enumeration {
           enum "brief" {
             description "Display brief output (default)";
           }
           enum "detail" {
             description "Display detailed output";
           }
         }
       }
       leaf group-name {
         description "Name of protection group";
         type string;
       }
     }
     output {
       container erp-ifbd-information {
         container erp-ifbds {
           container erp-ifbd-entries {
             description "VLAN information for one specific iring port";
             container brief {
               description "VLAN information for one specific iring port";
               container erp-ifbd-entry {
                 description "IFBD information controlled by a Ethernet Ring instance";
                 leaf erp-ifbd-interface-name {
                   type string;
                   description "Name of ring port physical interface for a IFBD";
                 }
                 leaf erp-ifbd-vlan {
                   type int32;
                   description "VLAN of IFBD";
                 }
                 leaf erp-ifbd-stp-index {
                   type int32;
                   description "STP index on the interface of ring instance";
                 }
                 leaf erp-ifbd-bridge-domain {
                   type string;
                   description "Bridge domain name of IFBD";
                 }
               }
             }
             container detail {
               description "VLAN information for one specific iring port";
               container erp-ifbd-entry {
                 description "IFBD information controlled by a Ethernet Ring instance";
                 leaf erp-ifbd-interface-name {
                   type string;
                   description "Name of ring port physical interface for a IFBD";
                 }
                 leaf erp-ifbd-vlan {
                   type int32;
                   description "VLAN of IFBD";
                 }
                 leaf erp-ifbd-stp-index {
                   type int32;
                   description "STP index on the interface of ring instance";
                 }
                 leaf erp-ifbd-bridge-domain {
                   type string;
                   description "Bridge domain name of IFBD";
                 }
               }
             }
           }
         }
       }
     }
   }
 }
