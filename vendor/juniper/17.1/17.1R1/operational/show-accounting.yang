/*
 * Copyright (c) 2017 Juniper Networks, Inc.
 * All rights reserved.
 */

 module show-accounting {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-accounting-profile-information {
     description "Show accounting profile information";
     input {
       leaf profile {
         description "Profile name";
         type string;
       }
     }
     output {
       container accounting-profile-information {
         container accounting-profile-header {
           description "Information from the accounting profile header";
           container per-profile {
             description "Information from the accounting profile header";
             leaf profile-name {
               type string;
               description "Name of the accounting profile";
             }
             leaf profile-interval {
               type int32;
               description "Frequency of statistics collection for each object sampled by the profile";
             }
             leaf profile-use-count {
               type int32;
               description "Number of objects to which this profile is applied (number of objects for which the statistics defined in this profile are collected)";
             }
             leaf filename {
               type string;
               description "Name of the file in the /var/log directory to which records are written";
             }
             leaf filesize {
               type int32;
               description "Maximum number of bytes of data written to the active version of the file before the file is closed, and a new file opened. If the transfer interval expires first, the file might contain less data.";
             }
             leaf filenumber {
               type int32;
               description "Maximum number of rotating versions of the file in the /var/log directory (the active file plus compressed files containing earlier data)";
             }
             leaf bytes-written {
               type int32;
               description "Number of bytes of data written to the file between the start of the most recent collection interval and the time of the request for information about the profile";
             }
             leaf transfer-interval {
               type int32;
               description "Frequency, in minutes, that the active file is closed and transferred to the configured archive site. The file is closed even if the maximum amount of data has not yet been written. As when the file is closed because the maximum size is reached, the contents of the active file are also compressed and copied to the first rotating file in the /var/log directory.";
             }
             leaf next-transfer-time {
               type string;
               description "Date and time when the active file will next be closed and transferred to the configured archive site, in the format YYYY-MM-DD-hh:mm:ss (year, month, day, hour in 24-hour format, minute, second)";
             }
           }
           container summary {
             description "Information from the accounting profile header";
             leaf profile-name {
               type string;
               description "Name of the accounting profile";
             }
             leaf profile-type {
               type string;
               description "Type of object to which the profile is applied";
             }
             leaf profile-interval {
               type int32;
               description "Frequency of statistics collection for each object sampled by the profile";
             }
             leaf filename {
               type string;
               description "Name of the file in the /var/log directory to which records are written";
             }
           }
         }
         container accounting-profile-columns {
           description "Name of each JUNOScript output tag that is included in records generated based on the profile";
           leaf column-label {
             type string;
             description "Name of an output tag that is included in records generated based on the profile";
           }
         }
         container accounting-profile-interfaces {
           description "Name of each interface to which the profile is applied";
           leaf interface-name {
             type string;
             description "Name of the interface";
           }
           leaf next-scheduled-collection {
             type string;
             description "Local time at which statistics collection will next begin, in the format YYYY-MM-DD-hh:mm:ss (year, month, day, hour in 24-hour format, minute, second)";
           }
         }
         container accounting-profile-mib {
           description "Name of each Management Information Base to which the profile is applied";
           leaf mib-name {
             type string;
             description "Name of a MIB";
           }
           leaf next-scheduled-collection {
             type string;
             description "Local time at which statistics collection will next begin, in the format YYYY-MM-DD-hh:mm:ss (year, month, day, hour in 24-hour format, minute, second)";
           }
         }
         container accounting-profile-filter {
           description "Name of each filter to which the profile is applied";
           leaf filter-name {
             type string;
             description "Name of the filter";
           }
           leaf next-scheduled-collection {
             type string;
             description "Local time at which statistics collection will next begin, in the format YYYY-MM-DD-hh:mm:ss (year, month, day, hour in 24-hour format, minute, second)";
           }
         }
       }
     }
   }
   rpc get-accounting-record-information {
     description "Show accounting records";
     input {
       leaf profile {
         description "Name of profile";
         type string;
         mandatory true;
       }
       leaf since {
         description "Timestamp on earliest records to show (YYYY-MM-DD.HH:MM:SS)";
         type string;
       }
       leaf utc-timestamp {
         description "Display timestamp in UTC format";
         type empty;
       }
     }
     output {
       container accounting-record-information {
         container interface-accounting-statistics {
           description "Information from one or more records that were generated based on an interface profile";
           container interface-accounting-record {
             description "Information in a record that was generated based on an interface profile";
             container epoch-timestamp-style {
               description "Information in a record that was generated based on an interface profile";
               leaf epoch-timestamp {
                 type string;
                 description "Time at which the record was written, expressed as local time";
               }
               leaf interface-name {
                 type string;
                 description "Name of the interface";
               }
               leaf snmp-index {
                 type string;
                 description "Simple Network Management Protocol index of the object described in the record";
               }
               leaf input-bytes {
                 type string;
                 description "Number of bytes received at the interface during the collection interval";
               }
               leaf output-bytes {
                 type string;
                 description "Number of bytes sent from the interface during the collection interval";
               }
               leaf input-packets {
                 type string;
                 description "Number of packets received at the interface during the collection interval";
               }
               leaf output-packets {
                 type string;
                 description "Number of packets sent from the interface during the collection interval";
               }
               leaf input-unicast {
                 type string;
                 description "Number of unicast packets received at the interface during the collection interval";
               }
               leaf output-unicast {
                 type string;
                 description "Number of unicast packets sent from the interface during the collection interval";
               }
               leaf input-multicast {
                 type string;
                 description "Number of multicast packets received at the interface during the collection interval";
               }
               leaf output-multicast {
                 type string;
                 description "Number of multicast packets sent from the interface during the collection interval";
               }
               leaf no-proto {
                 type string;
                 description "Number of packets that used an unsupported protocol";
               }
               leaf input-errors {
                 type string;
                 description "Number of packets received at the interface during the collection interval that had errors (for example, frame checksum sequence errors, or an invalid header length)";
               }
               leaf output-errors {
                 type string;
                 description "Number of packets scheduled to be sent from the interface during the collection interval that were not sent because of error conditions (for example, congestion or interface outages)";
               }
               leaf rpf-check-bytes {
                 type string;
                 description "Number of bytes in reverse-path-forwarding check packets for IPv4";
               }
               leaf rpf-check-packets {
                 type string;
                 description "Number of reverse-path-forwarding check packets for IPv4";
               }
               leaf rpf-check6-bytes {
                 type string;
                 description "Number of bytes in reverse-path-forwarding check packets for IPv6";
               }
               leaf rpf-check6-packets {
                 type string;
                 description "Number of reverse-path-forwarding check packets for IPv6";
               }
               leaf profile-layout {
                 type string;
               }
             }
             container utc-timestamp-style {
               description "Information in a record that was generated based on an interface profile";
               leaf utc-timestamp {
                 type string;
                 description "Time at which the record was written, expressed as Coordinated Universal Time";
               }
               leaf interface-name {
                 type string;
                 description "Name of the interface";
               }
               leaf snmp-index {
                 type string;
                 description "Simple Network Management Protocol index of the object described in the record";
               }
               leaf input-bytes {
                 type string;
                 description "Number of bytes received at the interface during the collection interval";
               }
               leaf output-bytes {
                 type string;
                 description "Number of bytes sent from the interface during the collection interval";
               }
               leaf input-packets {
                 type string;
                 description "Number of packets received at the interface during the collection interval";
               }
               leaf output-packets {
                 type string;
                 description "Number of packets sent from the interface during the collection interval";
               }
               leaf input-unicast {
                 type string;
                 description "Number of unicast packets received at the interface during the collection interval";
               }
               leaf output-unicast {
                 type string;
                 description "Number of unicast packets sent from the interface during the collection interval";
               }
               leaf input-multicast {
                 type string;
                 description "Number of multicast packets received at the interface during the collection interval";
               }
               leaf output-multicast {
                 type string;
                 description "Number of multicast packets sent from the interface during the collection interval";
               }
               leaf no-proto {
                 type string;
                 description "Number of packets that used an unsupported protocol";
               }
               leaf input-errors {
                 type string;
                 description "Number of packets received at the interface during the collection interval that had errors (for example, frame checksum sequence errors, or an invalid header length)";
               }
               leaf output-errors {
                 type string;
                 description "Number of packets scheduled to be sent from the interface during the collection interval that were not sent because of error conditions (for example, congestion or interface outages)";
               }
               leaf rpf-check-bytes {
                 type string;
                 description "Number of bytes in reverse-path-forwarding check packets for IPv4";
               }
               leaf rpf-check-packets {
                 type string;
                 description "Number of reverse-path-forwarding check packets for IPv4";
               }
               leaf rpf-check6-bytes {
                 type string;
                 description "Number of bytes in reverse-path-forwarding check packets for IPv6";
               }
               leaf rpf-check6-packets {
                 type string;
                 description "Number of reverse-path-forwarding check packets for IPv6";
               }
               leaf profile-layout {
                 type string;
               }
             }
           }
         }
         container routing-engine-accounting-statistics {
           description "Information from one or more records that were generated based on a Routing Engine profile";
           container routing-engine-accounting-record {
             description "Information in a record that was generated based on a Routing Engine profile";
             container normal {
               description "Information in a record that was generated based on a Routing Engine profile";
               leaf epoch-timestamp {
                 type string;
                 description "Time at which the record was written, expressed as local time";
               }
               leaf utc-timestamp {
                 type string;
                 description "Time at which the record was written, expressed as Coordinated Universal Time";
               }
               leaf hostname {
                 type string;
                 description "Hostname of the Routing Engine";
               }
               leaf date-yyyymmdd {
                 type string;
                 description "Current date on the Routing Engine, in the format YYYYMMDD (year, month, day)";
               }
               leaf timeofday-hhmmss {
                 type string;
                 description "Current time on the Routing Engine, in the format hhmmss (hour in 24-hour format, minute, second)";
               }
               leaf uptime {
                 type int32;
                 description "Number of seconds since the Routing Engine last rebooted";
               }
               leaf cpu1min {
                 type int32;
                 description "The load average for the minute before the record was written (a damped time-dependent average based on the number of active jobs and jobs in the CPU run queue)";
               }
               leaf cpu5min {
                 type int32;
                 description "The load average for the five minutes before the record was written (a damped time-dependent average based on the number of active jobs and jobs in the CPU run queue)";
               }
               leaf cpu15min {
                 type int32;
                 description "The load average for the 15 minutes before the record was written (a damped time-dependent average based on the number of active jobs and jobs in the CPU run queue)";
               }
               leaf memory-usage {
                 type int32;
                 description "Megabytes of RAM in use";
               }
               leaf total-cpu-usage {
                 type int32;
                 description "Current CPU load, expressed as a percent";
               }
               leaf profile-layout {
                 type string;
               }
             }
           }
         }
         container filter-accounting-statistics {
           description "Information from one or more records that were generated based on a filter profile";
           container filter-accounting-record {
             description "Information in a record that was generated based on a filter profile";
             container epoch-timestamp-style {
               description "Information in a record that was generated based on a filter profile";
               leaf epoch-timestamp {
                 type string;
                 description "Time at which the record was written, expressed as local time";
               }
               leaf filter-name {
                 type string;
                 description "Name of the filter";
               }
               leaf interfaces {
                 type string;
                 description "Name of one or more interfaces for which the record was collected";
               }
               leaf counter-name {
                 type string;
                 description "Name of the counter";
               }
               leaf packet-count {
                 type string;
                 description "Number of packets processed by the counter";
               }
               leaf byte-count {
                 type string;
                 description "Number of bytes processed by the counter";
               }
               leaf profile-layout {
                 type string;
               }
             }
             container utc-timestamp-style {
               description "Information in a record that was generated based on a filter profile";
               leaf utc-timestamp {
                 type string;
                 description "Time at which the record was written, expressed as Coordinated Universal Time";
               }
               leaf filter-name {
                 type string;
                 description "Name of the filter";
               }
               leaf interfaces {
                 type string;
                 description "Name of one or more interfaces for which the record was collected";
               }
               leaf counter-name {
                 type string;
                 description "Name of the counter";
               }
               leaf packet-count {
                 type string;
                 description "Number of packets processed by the counter";
               }
               leaf byte-count {
                 type string;
                 description "Number of bytes processed by the counter";
               }
               leaf profile-layout {
                 type string;
               }
             }
           }
         }
         container cu-accounting-statistics {
           description "Information from one or more records that were generated based on a destination class usage or source class usage profile";
           container cu-accounting-record {
             description "Information in a record that was generated based on a destination class usage or source class usage profile";
             container epoch-timestamp-style {
               description "Information in a record that was generated based on a destination class usage or source class usage profile";
               leaf epoch-timestamp {
                 type string;
                 description "Time at which the record was written, expressed as local time";
               }
               leaf interface-name {
                 type string;
                 description "Name of the interface";
               }
               leaf address-family {
                 type string;
                 description "Interface family configured on the interface";
               }
               leaf destination-class-name {
                 type string;
                 description "Name of the destination class";
               }
               leaf source-class-name {
                 type string;
                 description "Name of the source class";
               }
               leaf packet-count {
                 type string;
                 description "Number of packets processed by the counter";
               }
               leaf byte-count {
                 type string;
                 description "Number of bytes processed by the counter";
               }
               leaf profile-layout {
                 type string;
               }
               leaf counter-name {
                 type string;
                 description "Name of the counter";
               }
             }
             container utc-timestamp-style {
               description "Information in a record that was generated based on a destination class usage or source class usage profile";
               leaf utc-timestamp {
                 type string;
                 description "Time at which the record was written, expressed as Coordinated Universal Time";
               }
               leaf interface-name {
                 type string;
                 description "Name of the interface";
               }
               leaf address-family {
                 type string;
                 description "Interface family configured on the interface";
               }
               leaf destination-class-name {
                 type string;
                 description "Name of the destination class";
               }
               leaf source-class-name {
                 type string;
                 description "Name of the source class";
               }
               leaf packet-count {
                 type string;
                 description "Number of packets processed by the counter";
               }
               leaf byte-count {
                 type string;
                 description "Number of bytes processed by the counter";
               }
               leaf profile-layout {
                 type string;
               }
               leaf counter-name {
                 type string;
                 description "Name of the counter";
               }
             }
           }
         }
         container mib-accounting-statistics {
           description "Information from one or more records that were generated based on a Management Information Base profile";
           container mib-accounting-record {
             description "Information in a record that was generated based on a Management Information Base profile";
             container epoch-timestamp-style {
               description "Information in a record that was generated based on a Management Information Base profile";
               leaf epoch-timestamp {
                 type string;
                 description "Time at which the record was written, expressed as local time";
               }
               leaf name {
                 type string;
                 description "SNMP object name";
               }
               leaf object-value {
                 type string;
                 description "SNMP object value";
               }
               leaf profile {
                 type string;
                 description "Name of the MIB profile";
               }
             }
             container utc-timestamp-style {
               description "Information in a record that was generated based on a Management Information Base profile";
               leaf utc-timestamp {
                 type string;
                 description "Time at which the record was written, expressed as Coordinated Universal Time";
               }
               leaf name {
                 type string;
                 description "SNMP object name";
               }
               leaf object-value {
                 type string;
                 description "SNMP object value";
               }
               leaf profile {
                 type string;
                 description "Name of the MIB profile";
               }
             }
           }
         }
         container file-accounting-records {
           description "Records from an accounting file";
           container file-accounting-record {
             description "Record from an accounting file";
             leaf profile-layout {
               type string;
             }
             leaf epoch-timestamp {
               type string;
               description "Time at which the record was written, expressed as local time";
             }
           }
         }
       }
     }
   }
   rpc get-pending-accounting-stops {
     description "Show pending accounting stops related information";
     input {
       leaf access-profile {
         description "Show pending accounting stops for this access-profile";
         type string;
       }
       leaf level {
         default "terse";
         type enumeration {
           enum "terse" {
             description "Show brief output";
           }
           enum "detail" {
             description "Show detailed output";
           }
         }
       }
     }
   }
 }
