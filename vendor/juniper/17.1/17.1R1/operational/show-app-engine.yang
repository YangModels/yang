/*
 * Copyright (c) 2017 Juniper Networks, Inc.
 * All rights reserved.
 */

 module show-app-engine {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-virtual-machine-package-remote {
     description "Remote status of virtual machine packages";
     input {
       leaf compute-cluster {
         description "Compute cluster name";
         type string {
           length "1 .. 15";
         }
       }
       leaf package-name {
         description "Name of virtual machine package";
         type string;
       }
     }
   }
   rpc get-virtual-machine-package-system {
     description "Local status of virtual machine packages";
     input {
       leaf package-name {
         description "Name of virtual machine package";
         type string;
       }
     }
   }
   rpc get-virtual-machine-information {
     description "Show virtual-machine instance information";
     input {
       leaf level {
         default "brief";
         type enumeration {
           enum "detail" {
             description "Display detailed status";
           }
           enum "brief" {
             description "Display brief status (default)";
           }
         }
       }
       leaf instance-name {
         description "Virtual-machine instance name";
         type string;
       }
     }
     output {
       container sdk-vmmd-vm-information {
         container detail {
           container ve-vm-instance {
             leaf sdk-vmmd-vm-name {
               type string;
               description "Virtual machine name";
             }
             leaf sdk-vmmd-vm-compute-cluster {
               type string;
               description "Compute cluster name";
             }
             leaf sdk-vmmd-vm-error {
               type string;
               description "Virtual machine error message";
             }
             leaf sdk-vmmd-vm-compute-node {
               type string;
               description "Compute node name";
             }
             leaf sdk-vmmd-vm-status {
               type string;
               description "VM active or inactive status";
             }
             leaf sdk-vmmd-vm-uuid {
               type string;
               description "VM UUID";
             }
             leaf sdk-vmmd-vm-image {
               type string;
               description "VM disk image";
             }
             leaf sdk-vmmd-vm-cpus {
               type uint32;
               description "Number of CPUs for the VM";
             }
             leaf sdk-vmmd-vm-memory {
               type uint32;
               description "VM memory in GB";
             }
             leaf sdk-vmmd-vm-console {
               type string;
               description "VM console";
             }
             leaf sdk-vmmd-vm-pid {
               type uint32;
               description "PID of the VM";
             }
             container sdk-vmmd-vm-intf {
               leaf sdk-vmmd-vm-intf-ip {
                 type string;
                 description "Interfaces of the VM";
               }
             }
             container sdk-vmmd-vm-disk {
               leaf sdk-vmmd-vm-disk-size {
                 type string;
                 description "Disks of the VM";
               }
             }
             container sdk-vmmd-vm-route {
               leaf sdk-vmmd-vm-route-info {
                 type string;
                 description "Routing table of the VM";
               }
             }
           }
         }
         container brief {
           container ve-vm-instance {
             leaf sdk-vmmd-vm-name {
               type string;
               description "Virtual machine name";
             }
             leaf sdk-vmmd-vm-compute-cluster {
               type string;
               description "Compute cluster name";
             }
             leaf sdk-vmmd-vm-error {
               type string;
               description "Virtual machine error message";
             }
             leaf sdk-vmmd-vm-status {
               type string;
               description "VM active or inactive status";
             }
             container sdk-vmmd-vm-intf {
               leaf sdk-vmmd-vm-intf-ip {
                 type string;
                 description "Interfaces of the VM";
               }
             }
             container sdk-vmmd-vm-disk {
               leaf sdk-vmmd-vm-disk-size {
                 type string;
                 description "Disks of the VM";
               }
             }
             container sdk-vmmd-vm-route {
               leaf sdk-vmmd-vm-route-info {
                 type string;
                 description "Routing table of the VM";
               }
             }
           }
         }
       }
     }
   }
   rpc get-virtual-machine-package-information {
     description "Show virtual-machine package information";
     input {
       leaf package-name {
         description "Name of virtual machine package";
         type string;
       }
     }
     output {
       container sdk-vmmd-vm-pkg-information {
         container sdk-vmmd-vm-package {
           leaf sdk-vmmd-pkg-name {
             type string;
             description "VM package name";
           }
           leaf sdk-vmmd-img-name {
             type string;
             description "VM disk image name";
           }
           leaf sdk-vmmd-pkg-overall {
             type string;
             description "VM package overall download status";
           }
           container sdk-vmmd-pkg-download {
             leaf sdk-vmmd-pkg-compute-cluster {
               type string;
               description "Compute cluster name";
             }
             leaf sdk-vmmd-pkg-download-status {
               type string;
               description "Package download status";
             }
           }
         }
       }
     }
   }
 }
