/*
 * Copyright (c) 2017 Juniper Networks, Inc.
 * All rights reserved.
 */

 module show-rip {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-rip-statistics-information {
     description "Show RIP statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf neighbor-name {
         description "Name of RIP neighbor";
         type string;
       }
       leaf instance {
         description "Name of RIP instance";
         type string;
       }
     }
     output {
       container rip-statistics-information {
         container rip-timer-values {
           description "Information about RIP timer values";
           leaf rip-protocol-name {
             type string;
             description "Protocol name";
           }
           leaf rip-port {
             type int32;
             description "Port on which the protocol is running";
           }
           leaf rip-holddown {
             type int32;
             description "Value of the hold-down timer";
           }
         }
         container rip-restart-values {
           description "Information about RIP restart values";
           leaf rip-restart-state {
             type string;
             description "Indicates if graceful restart is in progress";
           }
           leaf rip-restart-time {
             type int32;
             description "Restart time locally configured";
           }
           leaf rip-restart-timeout {
             type int32;
             description "Time after which graceful restart is complete";
           }
         }
         container rip-global-statistics {
           description "RIP global statistics";
           leaf rip-routes-learned {
             type int32;
             description "Number of routes learned";
           }
           leaf rip-routes-holddown {
             type int32;
             description "Number of routes in hold-down state";
           }
           leaf rip-requests-dropped {
             type int32;
             description "Number of requests dropped";
           }
           leaf rip-responses-dropped {
             type int32;
             description "Number of responses dropped";
           }
         }
         container rip-neighbor-statistics {
           description "RIP neighbor statistics";
           leaf rip-neighbor-name {
             type string;
             description "Neighbor name";
           }
           leaf rip-neighbor-learnt-routes {
             type int32;
             description "Number of routes learned by this neighbor";
           }
           leaf rip-neighbor-advertised-routes {
             type int32;
             description "Number of routes advertised by this neighbor";
           }
           leaf rip-neighbor-route-timeout {
             type int32;
             description "Timeout value for routes learned from this neighbor";
           }
           leaf rip-neighbor-update-interval {
             type int32;
             description "Value of update interval timer for this neighbor";
           }
           container rip-message-statistics {
             leaf rip-message {
               type string;
             }
             leaf rip-message-total {
               type int32;
               description "Total number of messages";
             }
             leaf rip-message-last-5minutes {
               type int32;
               description "Number of messages in the last 5 minutes";
             }
             leaf rip-message-last-minute {
               type int32;
               description "Number of messages in the last minute";
             }
           }
         }
       }
     }
   }
   rpc get-rip-peer-information {
     description "Show peer statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf address {
         description "Ip address of peer";
         type string;
       }
       leaf peer-all {
         description "Show statistics of all peers";
         type enumeration {
           enum "all" {
             description "Show statistics of all peers";
           }
         }
       }
     }
   }
   rpc get-rip-general-statistics-information {
     description "Show RIP general statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container rip-general-statistics-information {
         container rip-general-statistics {
           leaf rip-protocol-name {
             type string;
             description "Protocol name";
           }
           leaf rip-bad-messages {
             type int32;
             description "Number of bad messages";
           }
           leaf rip-interface-count {
             type int32;
             description "Number of receiving interfaces";
           }
           leaf rip-current-memory {
             type int32;
             description "Memory currently in use";
           }
           leaf rip-maximum-memory {
             type int32;
             description "Maximum memory ever used";
           }
         }
       }
     }
   }
   rpc get-rip-neighbor-information {
     description "Show RIP interfaces";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf neighbor-name {
         description "Name of RIP neighbor";
         type string;
       }
       leaf instance {
         description "Name of RIP instance";
         type string;
       }
     }
     output {
       container rip-neighbor-information {
         container rip-neighbor {
           container ripv2 {
             leaf rip-neighbor-name {
               type string;
               description "Neighbor name";
             }
             leaf rip-neighbor-state {
               type string;
               description "Status of a neighbor";
             }
             leaf rip-local-address-ipv4 {
               type ipaddr;
               description "Local address for this neighbor";
             }
             leaf rip-remote-address-ipv4 {
               type ipaddr;
               description "Remote address for this neighbor";
             }
             leaf send-mode-ripv2 {
               type string;
               description "Send state of a neighbor";
             }
             leaf receive-mode-ripv2 {
               type string;
               description "Receive state of a neighbor";
             }
             leaf rip-neighbor-metric-in {
               type int32;
               description "Metric value to add to incoming routes (1..15)";
             }
           }
           container ripng {
             leaf rip-neighbor-name {
               type string;
               description "Neighbor name";
             }
             leaf rip-neighbor-state {
               type string;
               description "Status of a neighbor";
             }
             leaf rip-local-address-ipv6 {
               type ipaddr;
               description "Local address for this neighbor";
             }
             leaf rip-remote-address-ipv6 {
               type ipaddr;
               description "Remote address for this neighbor";
             }
             leaf send-mode-ripng {
               type string;
               description "Send state of a neighbor";
             }
             leaf receive-mode-ripng {
               type string;
               description "Receive state of a neighbor";
             }
             leaf rip-neighbor-metric-in {
               type int32;
               description "Metric value to add to incoming routes (1..15)";
             }
           }
         }
       }
     }
   }
 }
