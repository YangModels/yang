/*
 * Copyright (c) 2017 Juniper Networks, Inc.
 * All rights reserved.
 */

 module show-dhcp {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-dhcp-service-statistics-information {
     description "Show DHCP service statistics";
     input {
       leaf level {
         default "summary";
         type enumeration {
           enum "summary" {
             description "Display summary information";
           }
         }
       }
       leaf interface {
         description "Name of interface";
         type interface-name;
       }
     }
     output {
       container dhcp-service-statistics-information {
         leaf dropped-packet-dhcp-service-total {
           type uint32;
           description "Total packets discard by DHCP service";
         }
         leaf dropped-packet-read-error {
           type uint32;
           description "Packets discarded due to read error";
         }
         leaf dropped-packet-bad-ip-header {
           type uint32;
           description "Packets discarded due to bad IP header";
         }
         leaf dropped-packet-short-packet {
           type uint32;
           description "Packets discarded due to runt packet";
         }
         leaf dropped-packet-no-interface {
           type uint32;
           description "Packets discarded due to no interface";
         }
         leaf dropped-packet-no-routing-instance {
           type uint32;
           description "Packets discarded due to no routing instance";
         }
         leaf dropped-packet-no-mem {
           type uint32;
           description "Packets discarded due to no memory";
         }
         leaf dropped-packet-recovery-in-progress {
           type uint32;
           description "Packets discarded due to switchover recovery in progress";
         }
       }
     }
   }
   rpc get-dhcp-relay-binding-information {
     description "Show DHCP relay client binding information";
     input {
       leaf level {
         default "brief";
         type enumeration {
           enum "brief" {
             description "Display brief information";
           }
           enum "detail" {
             description "Display detailed information";
           }
           enum "summary" {
             description "Display summary information";
           }
         }
       }
       container show-choice {
         choice show-choice_c {
           case address {
             leaf address {
               description "IP address/MAC address/Session Id of DHCP client binding";
               type string;
             }
           }
           case interfaces-wildcard {
             leaf interfaces-wildcard {
               description "Interfaces to show bindings on (can be '*' wildcard)";
               type string {
                 junos:posix-pattern "^( (((ge-)|(xe-)|(et-))( [[:digit:]]+(-([[:digit:]]+))+(-([[:digit:]]+)?)?)?) | (ae))+$";
                 junos:pattern-message "Must be an interface wildcard string";
               }
             }
           }
           case interfaces-vlan {
             leaf interfaces-vlan {
               description "Interface VLAN-ID/SVLAN-ID on which to show bindings";
               type string {
                 junos:posix-pattern "^(( (((ge-)|(xe-)|(et-))( [[:digit:]]+(-([[:digit:]]+))+(-([[:digit:]]+)?)?)?) | (ae))(/:)([[:digit:]]+(-[[:digit:]]+))?)+$";
                 junos:pattern-message "Must be an interface:VLAN string";
               }
             }
           }
         }
       }
       leaf routing-instance {
         description "Name of routing instance";
         type string;
       }
       leaf bridge-domain {
         description "Name of bridge domain";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-relay-binding-information {
         container brief {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf rebinding-count {
               type int32;
             }
             leaf releasing-count {
               type int32;
             }
             leaf restore-count {
               type int32;
               description "Number of clients waiting to be restored";
             }
           }
           container binding-internal-states {
             leaf init {
               type int32;
               description "Number of clients init state";
             }
             leaf selecting {
               type int32;
               description "Number of clients in selecting state";
             }
             leaf requesting {
               type int32;
               description "Number of clients in requesting state";
             }
             leaf bound {
               type int32;
               description "Number of clients in bound state";
             }
             leaf renewing {
               type int32;
               description "Number of clients in renewing state";
             }
             leaf rebinding {
               type int32;
               description "Number of clients in rebinding state";
             }
             leaf wait-cm-add {
               type int32;
               description "Number of clients in wait-cm-add state";
             }
             leaf wait-cm-add-delete {
               type int32;
               description "Number of clients in wait-cm-add-delete state";
             }
             leaf wait-cm-delete {
               type int32;
               description "Number of clients in wait-cm-delete state";
             }
             leaf wait-subscr-add {
               type int32;
               description "Number of clients in wait-subscr-add state";
             }
             leaf wait-subscr-add-delete {
               type int32;
               description "Number of clients in wait-subscr-add-delete state";
             }
             leaf wait-subscr-delete {
               type int32;
               description "Number of clients in wait-subscr-delete state";
             }
             leaf wait-cm-update {
               type int32;
               description "Number of clients in wait-cm-update state";
             }
             leaf wait-cm-update-delete {
               type int32;
               description "Number of clients in wait-cm-update-delete state";
             }
             leaf wait-auth-req {
               type int32;
               description "Number of clients in wait-auth-req state";
             }
             leaf wait-auth-req-delete {
               type int32;
               description "Number of clients in wait-auth-req-delete state";
             }
             leaf wait-auth-req-release {
               type int32;
               description "Number of clients in wait-auth-req-release state";
             }
             leaf wait-auth-req-release-terminated {
               type int32;
               description "Number of clients in wait-auth-req-release-terminated state";
             }
             leaf wait-auth-act-prof {
               type int32;
               description "Number of clients in wait-auth-act-prof state";
             }
             leaf wait-auth-act-prof-delete {
               type int32;
               description "Number of clients in wait-auth-act-prof-delete state";
             }
             leaf wait-service-deactivation {
               type int32;
               description "Number of clients in wait-service-deactivation state";
             }
             leaf wait-dual-stack-peer-logout {
               type int32;
               description "Number of clients in wait-dual-stack-peer-logout state";
             }
             leaf wait-prof-inst {
               type int32;
               description "Number of clients in wait-prof-inst state";
             }
             leaf wait-prof-inst-delete {
               type int32;
               description "Number of clients in wait-prof-inst-delete state";
             }
             leaf wait-prof-delete {
               type int32;
               description "Number of clients in wait-prof-delete state";
             }
             leaf wait-interface {
               type int32;
               description "Number of clients in wait-interface state";
             }
             leaf wait-sdb-init-mirror-req {
               type int32;
               description "Number of clients in wait-sdb-init-mirror-req state";
             }
             leaf wait-sdb-init-mirror-req-delete {
               type int32;
               description "Number of clients in wait-sdb-init-mirror-req-delete state";
             }
             leaf wait-sdb-active-mirror-req {
               type int32;
               description "Number of clients in wait-sdb-active-mirror-req state";
             }
             leaf wait-sdb-active-mirror-req-delete {
               type int32;
               description "Number of clients in wait-sdb-active-mirror-req-delete state";
             }
             leaf wait-sdb-terminated-mirror-req {
               type int32;
               description "Number of clients in wait-sdb-terminated-mirror-req state";
             }
             leaf wait-sdb-dual-stack-terminating {
               type int32;
               description "Number of clients in wait-sdb-dual-stack-terminating state";
             }
             leaf wait-sdb-dual-stack-clear {
               type int32;
               description "Number of clients in wait-sdb-dual-stack-clear state";
             }
             leaf bound-on-intf-delete {
               type int32;
               description "Number of clients in bound-on-intf-delete state";
             }
           }
           container dhcp-binding {
             description "Information about the address assigned to a Dynamic Host Configuration Protocol client";
             leaf allocated-address {
               type ipaddr;
               description "IPv4 or IPv6 address assigned to the DHCP client";
             }
             leaf session-id {
               type string;
               description "Session ID of the client";
             }
             leaf mac-address {
               type mac-addr;
               description "Media access control (hardware) address of the DHCP client";
             }
             leaf lease-expires {
               type int32;
               description "Number of seconds lease will expire in";
             }
             leaf lease-state {
               type string;
               description "Status of the address assignment";
             }
             leaf interface-name {
               type string;
               description "Name of the interface via which the DHCP server transmitted the address assignment";
             }
           }
         }
         container detail {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf rebinding-count {
               type int32;
             }
             leaf releasing-count {
               type int32;
             }
             leaf restore-count {
               type int32;
               description "Number of clients waiting to be restored";
             }
           }
           container binding-internal-states {
             leaf init {
               type int32;
               description "Number of clients init state";
             }
             leaf selecting {
               type int32;
               description "Number of clients in selecting state";
             }
             leaf requesting {
               type int32;
               description "Number of clients in requesting state";
             }
             leaf bound {
               type int32;
               description "Number of clients in bound state";
             }
             leaf renewing {
               type int32;
               description "Number of clients in renewing state";
             }
             leaf rebinding {
               type int32;
               description "Number of clients in rebinding state";
             }
             leaf wait-cm-add {
               type int32;
               description "Number of clients in wait-cm-add state";
             }
             leaf wait-cm-add-delete {
               type int32;
               description "Number of clients in wait-cm-add-delete state";
             }
             leaf wait-cm-delete {
               type int32;
               description "Number of clients in wait-cm-delete state";
             }
             leaf wait-subscr-add {
               type int32;
               description "Number of clients in wait-subscr-add state";
             }
             leaf wait-subscr-add-delete {
               type int32;
               description "Number of clients in wait-subscr-add-delete state";
             }
             leaf wait-subscr-delete {
               type int32;
               description "Number of clients in wait-subscr-delete state";
             }
             leaf wait-cm-update {
               type int32;
               description "Number of clients in wait-cm-update state";
             }
             leaf wait-cm-update-delete {
               type int32;
               description "Number of clients in wait-cm-update-delete state";
             }
             leaf wait-auth-req {
               type int32;
               description "Number of clients in wait-auth-req state";
             }
             leaf wait-auth-req-delete {
               type int32;
               description "Number of clients in wait-auth-req-delete state";
             }
             leaf wait-auth-req-release {
               type int32;
               description "Number of clients in wait-auth-req-release state";
             }
             leaf wait-auth-req-release-terminated {
               type int32;
               description "Number of clients in wait-auth-req-release-terminated state";
             }
             leaf wait-auth-act-prof {
               type int32;
               description "Number of clients in wait-auth-act-prof state";
             }
             leaf wait-auth-act-prof-delete {
               type int32;
               description "Number of clients in wait-auth-act-prof-delete state";
             }
             leaf wait-service-deactivation {
               type int32;
               description "Number of clients in wait-service-deactivation state";
             }
             leaf wait-dual-stack-peer-logout {
               type int32;
               description "Number of clients in wait-dual-stack-peer-logout state";
             }
             leaf wait-prof-inst {
               type int32;
               description "Number of clients in wait-prof-inst state";
             }
             leaf wait-prof-inst-delete {
               type int32;
               description "Number of clients in wait-prof-inst-delete state";
             }
             leaf wait-prof-delete {
               type int32;
               description "Number of clients in wait-prof-delete state";
             }
             leaf wait-interface {
               type int32;
               description "Number of clients in wait-interface state";
             }
             leaf wait-sdb-init-mirror-req {
               type int32;
               description "Number of clients in wait-sdb-init-mirror-req state";
             }
             leaf wait-sdb-init-mirror-req-delete {
               type int32;
               description "Number of clients in wait-sdb-init-mirror-req-delete state";
             }
             leaf wait-sdb-active-mirror-req {
               type int32;
               description "Number of clients in wait-sdb-active-mirror-req state";
             }
             leaf wait-sdb-active-mirror-req-delete {
               type int32;
               description "Number of clients in wait-sdb-active-mirror-req-delete state";
             }
             leaf wait-sdb-terminated-mirror-req {
               type int32;
               description "Number of clients in wait-sdb-terminated-mirror-req state";
             }
             leaf wait-sdb-dual-stack-terminating {
               type int32;
               description "Number of clients in wait-sdb-dual-stack-terminating state";
             }
             leaf wait-sdb-dual-stack-clear {
               type int32;
               description "Number of clients in wait-sdb-dual-stack-clear state";
             }
             leaf bound-on-intf-delete {
               type int32;
               description "Number of clients in bound-on-intf-delete state";
             }
           }
           container dhcp-binding {
             description "Information about the address assigned to a Dynamic Host Configuration Protocol client";
             leaf allocated-address {
               type ipaddr;
               description "IPv4 or IPv6 address assigned to the DHCP client";
             }
             leaf mac-address {
               type mac-addr;
               description "Media access control (hardware) address of the DHCP client";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf lease-start-time {
               type string;
               description "Time when the client obtained the address assignment, in the format YYYY-MM-DD hh:mm:ss TZ (year, month, date, hour in 24-hour format, minute, second, time zone)";
             }
             leaf lease-time-violated {
               type string;
               description "Status of lease time validation violation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf server-interface-name {
               type string;
               description "Interface that server was from";
             }
             leaf bootp-relay-address {
               type ipaddr;
               description "IP address of the bootstrap protocol server that relayed the address assigned by the DHCP server";
             }
             leaf previous-bootp-relay-address {
               type ipaddr;
               description "Previous IP address of the bootstrap protocol server that relayed the address assigned by the DHCP server";
             }
             leaf session-id {
               type string;
               description "Session ID of the client";
             }
             leaf pool-name {
               type string;
               description "Client pool name";
             }
             leaf profile-name {
               type string;
               description "Client profile name";
             }
             leaf liveness-detection-state {
               type string;
               description "Status of the liveness detection session with the client";
             }
             leaf dual-stack-group {
               type string;
               description "Dual stack group referenece by this client";
             }
             leaf dual-stack-peer-address {
               type ipaddr;
               description "Peer IP or IPV6 address for this dual stack client";
             }
             leaf dual-stack-peer-prefix {
               type ipaddr;
               description "Peer IPV6 prefix for this dual stack client";
             }
             leaf generated-circuit-id {
               type string;
               description "Generated circuit id";
             }
             leaf generated-remote-id {
               type string;
               description "Generated remote id";
             }
             leaf dhcp-lease-binding-type {
               type string;
               description "Type of the address assignment";
             }
             leaf client-id-len {
               type int32;
               description "Number of bytes in client id";
             }
             leaf client-id {
               type string;
               description "Four bytes of the client id";
             }
             leaf alt-client-id-len {
               type int32;
               description "Number of bytes in alternate client id";
             }
             leaf alt-client-id {
               type string;
               description "Four byte of the alternate client id";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-82-length-from-client {
               type int32;
               description "Option 82 length from client";
             }
             leaf option-82-data-from-client {
               type string;
               description "Option 82 data from client";
             }
             leaf hardware-type {
               type string;
               description "Client hardware type";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf wholesale-logical-system-routing-instance {
               type string;
               description "L3 wholesale client router context logical system and routing instance";
             }
             leaf antispoof-filter-name {
               type string;
               description "Antispoof filter name";
             }
             leaf antispoof-filter-flags {
               type string;
               description "Antispoof filter flags";
             }
             leaf antispoof-filter-state {
               type string;
               description "Antispoof filter state";
             }
             leaf antispoof-filter-type {
               type string;
               description "Antispoof filter type";
             }
             leaf antispoof-filter-term-id {
               type string;
               description "Antispoof filter term id";
             }
             leaf antispoof-filter-action {
               type string;
               description "Antispoof filter type";
             }
             leaf antispoof-filter-parent {
               type string;
               description "Antispoof filter parent pointer";
             }
             leaf antispoof-filter-owner {
               type string;
               description "Antispoof filter owner pointer";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
           }
         }
       }
     }
   }
   rpc get-dhcp-relay-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-relay-binding-information {
         container brief {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf rebinding-count {
               type int32;
             }
             leaf releasing-count {
               type int32;
             }
             leaf restore-count {
               type int32;
               description "Number of clients waiting to be restored";
             }
           }
           container binding-internal-states {
             leaf init {
               type int32;
               description "Number of clients init state";
             }
             leaf selecting {
               type int32;
               description "Number of clients in selecting state";
             }
             leaf requesting {
               type int32;
               description "Number of clients in requesting state";
             }
             leaf bound {
               type int32;
               description "Number of clients in bound state";
             }
             leaf renewing {
               type int32;
               description "Number of clients in renewing state";
             }
             leaf rebinding {
               type int32;
               description "Number of clients in rebinding state";
             }
             leaf wait-cm-add {
               type int32;
               description "Number of clients in wait-cm-add state";
             }
             leaf wait-cm-add-delete {
               type int32;
               description "Number of clients in wait-cm-add-delete state";
             }
             leaf wait-cm-delete {
               type int32;
               description "Number of clients in wait-cm-delete state";
             }
             leaf wait-subscr-add {
               type int32;
               description "Number of clients in wait-subscr-add state";
             }
             leaf wait-subscr-add-delete {
               type int32;
               description "Number of clients in wait-subscr-add-delete state";
             }
             leaf wait-subscr-delete {
               type int32;
               description "Number of clients in wait-subscr-delete state";
             }
             leaf wait-cm-update {
               type int32;
               description "Number of clients in wait-cm-update state";
             }
             leaf wait-cm-update-delete {
               type int32;
               description "Number of clients in wait-cm-update-delete state";
             }
             leaf wait-auth-req {
               type int32;
               description "Number of clients in wait-auth-req state";
             }
             leaf wait-auth-req-delete {
               type int32;
               description "Number of clients in wait-auth-req-delete state";
             }
             leaf wait-auth-req-release {
               type int32;
               description "Number of clients in wait-auth-req-release state";
             }
             leaf wait-auth-req-release-terminated {
               type int32;
               description "Number of clients in wait-auth-req-release-terminated state";
             }
             leaf wait-auth-act-prof {
               type int32;
               description "Number of clients in wait-auth-act-prof state";
             }
             leaf wait-auth-act-prof-delete {
               type int32;
               description "Number of clients in wait-auth-act-prof-delete state";
             }
             leaf wait-service-deactivation {
               type int32;
               description "Number of clients in wait-service-deactivation state";
             }
             leaf wait-dual-stack-peer-logout {
               type int32;
               description "Number of clients in wait-dual-stack-peer-logout state";
             }
             leaf wait-prof-inst {
               type int32;
               description "Number of clients in wait-prof-inst state";
             }
             leaf wait-prof-inst-delete {
               type int32;
               description "Number of clients in wait-prof-inst-delete state";
             }
             leaf wait-prof-delete {
               type int32;
               description "Number of clients in wait-prof-delete state";
             }
             leaf wait-interface {
               type int32;
               description "Number of clients in wait-interface state";
             }
             leaf wait-sdb-init-mirror-req {
               type int32;
               description "Number of clients in wait-sdb-init-mirror-req state";
             }
             leaf wait-sdb-init-mirror-req-delete {
               type int32;
               description "Number of clients in wait-sdb-init-mirror-req-delete state";
             }
             leaf wait-sdb-active-mirror-req {
               type int32;
               description "Number of clients in wait-sdb-active-mirror-req state";
             }
             leaf wait-sdb-active-mirror-req-delete {
               type int32;
               description "Number of clients in wait-sdb-active-mirror-req-delete state";
             }
             leaf wait-sdb-terminated-mirror-req {
               type int32;
               description "Number of clients in wait-sdb-terminated-mirror-req state";
             }
             leaf wait-sdb-dual-stack-terminating {
               type int32;
               description "Number of clients in wait-sdb-dual-stack-terminating state";
             }
             leaf wait-sdb-dual-stack-clear {
               type int32;
               description "Number of clients in wait-sdb-dual-stack-clear state";
             }
             leaf bound-on-intf-delete {
               type int32;
               description "Number of clients in bound-on-intf-delete state";
             }
           }
           container dhcp-binding {
             description "Information about the address assigned to a Dynamic Host Configuration Protocol client";
             leaf allocated-address {
               type ipaddr;
               description "IPv4 or IPv6 address assigned to the DHCP client";
             }
             leaf session-id {
               type string;
               description "Session ID of the client";
             }
             leaf mac-address {
               type mac-addr;
               description "Media access control (hardware) address of the DHCP client";
             }
             leaf lease-expires {
               type int32;
               description "Number of seconds lease will expire in";
             }
             leaf lease-state {
               type string;
               description "Status of the address assignment";
             }
             leaf interface-name {
               type string;
               description "Name of the interface via which the DHCP server transmitted the address assignment";
             }
           }
         }
         container detail {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf rebinding-count {
               type int32;
             }
             leaf releasing-count {
               type int32;
             }
             leaf restore-count {
               type int32;
               description "Number of clients waiting to be restored";
             }
           }
           container binding-internal-states {
             leaf init {
               type int32;
               description "Number of clients init state";
             }
             leaf selecting {
               type int32;
               description "Number of clients in selecting state";
             }
             leaf requesting {
               type int32;
               description "Number of clients in requesting state";
             }
             leaf bound {
               type int32;
               description "Number of clients in bound state";
             }
             leaf renewing {
               type int32;
               description "Number of clients in renewing state";
             }
             leaf rebinding {
               type int32;
               description "Number of clients in rebinding state";
             }
             leaf wait-cm-add {
               type int32;
               description "Number of clients in wait-cm-add state";
             }
             leaf wait-cm-add-delete {
               type int32;
               description "Number of clients in wait-cm-add-delete state";
             }
             leaf wait-cm-delete {
               type int32;
               description "Number of clients in wait-cm-delete state";
             }
             leaf wait-subscr-add {
               type int32;
               description "Number of clients in wait-subscr-add state";
             }
             leaf wait-subscr-add-delete {
               type int32;
               description "Number of clients in wait-subscr-add-delete state";
             }
             leaf wait-subscr-delete {
               type int32;
               description "Number of clients in wait-subscr-delete state";
             }
             leaf wait-cm-update {
               type int32;
               description "Number of clients in wait-cm-update state";
             }
             leaf wait-cm-update-delete {
               type int32;
               description "Number of clients in wait-cm-update-delete state";
             }
             leaf wait-auth-req {
               type int32;
               description "Number of clients in wait-auth-req state";
             }
             leaf wait-auth-req-delete {
               type int32;
               description "Number of clients in wait-auth-req-delete state";
             }
             leaf wait-auth-req-release {
               type int32;
               description "Number of clients in wait-auth-req-release state";
             }
             leaf wait-auth-req-release-terminated {
               type int32;
               description "Number of clients in wait-auth-req-release-terminated state";
             }
             leaf wait-auth-act-prof {
               type int32;
               description "Number of clients in wait-auth-act-prof state";
             }
             leaf wait-auth-act-prof-delete {
               type int32;
               description "Number of clients in wait-auth-act-prof-delete state";
             }
             leaf wait-service-deactivation {
               type int32;
               description "Number of clients in wait-service-deactivation state";
             }
             leaf wait-dual-stack-peer-logout {
               type int32;
               description "Number of clients in wait-dual-stack-peer-logout state";
             }
             leaf wait-prof-inst {
               type int32;
               description "Number of clients in wait-prof-inst state";
             }
             leaf wait-prof-inst-delete {
               type int32;
               description "Number of clients in wait-prof-inst-delete state";
             }
             leaf wait-prof-delete {
               type int32;
               description "Number of clients in wait-prof-delete state";
             }
             leaf wait-interface {
               type int32;
               description "Number of clients in wait-interface state";
             }
             leaf wait-sdb-init-mirror-req {
               type int32;
               description "Number of clients in wait-sdb-init-mirror-req state";
             }
             leaf wait-sdb-init-mirror-req-delete {
               type int32;
               description "Number of clients in wait-sdb-init-mirror-req-delete state";
             }
             leaf wait-sdb-active-mirror-req {
               type int32;
               description "Number of clients in wait-sdb-active-mirror-req state";
             }
             leaf wait-sdb-active-mirror-req-delete {
               type int32;
               description "Number of clients in wait-sdb-active-mirror-req-delete state";
             }
             leaf wait-sdb-terminated-mirror-req {
               type int32;
               description "Number of clients in wait-sdb-terminated-mirror-req state";
             }
             leaf wait-sdb-dual-stack-terminating {
               type int32;
               description "Number of clients in wait-sdb-dual-stack-terminating state";
             }
             leaf wait-sdb-dual-stack-clear {
               type int32;
               description "Number of clients in wait-sdb-dual-stack-clear state";
             }
             leaf bound-on-intf-delete {
               type int32;
               description "Number of clients in bound-on-intf-delete state";
             }
           }
           container dhcp-binding {
             description "Information about the address assigned to a Dynamic Host Configuration Protocol client";
             leaf allocated-address {
               type ipaddr;
               description "IPv4 or IPv6 address assigned to the DHCP client";
             }
             leaf mac-address {
               type mac-addr;
               description "Media access control (hardware) address of the DHCP client";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf lease-start-time {
               type string;
               description "Time when the client obtained the address assignment, in the format YYYY-MM-DD hh:mm:ss TZ (year, month, date, hour in 24-hour format, minute, second, time zone)";
             }
             leaf lease-time-violated {
               type string;
               description "Status of lease time validation violation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf server-interface-name {
               type string;
               description "Interface that server was from";
             }
             leaf bootp-relay-address {
               type ipaddr;
               description "IP address of the bootstrap protocol server that relayed the address assigned by the DHCP server";
             }
             leaf previous-bootp-relay-address {
               type ipaddr;
               description "Previous IP address of the bootstrap protocol server that relayed the address assigned by the DHCP server";
             }
             leaf session-id {
               type string;
               description "Session ID of the client";
             }
             leaf pool-name {
               type string;
               description "Client pool name";
             }
             leaf profile-name {
               type string;
               description "Client profile name";
             }
             leaf liveness-detection-state {
               type string;
               description "Status of the liveness detection session with the client";
             }
             leaf dual-stack-group {
               type string;
               description "Dual stack group referenece by this client";
             }
             leaf dual-stack-peer-address {
               type ipaddr;
               description "Peer IP or IPV6 address for this dual stack client";
             }
             leaf dual-stack-peer-prefix {
               type ipaddr;
               description "Peer IPV6 prefix for this dual stack client";
             }
             leaf generated-circuit-id {
               type string;
               description "Generated circuit id";
             }
             leaf generated-remote-id {
               type string;
               description "Generated remote id";
             }
             leaf dhcp-lease-binding-type {
               type string;
               description "Type of the address assignment";
             }
             leaf client-id-len {
               type int32;
               description "Number of bytes in client id";
             }
             leaf client-id {
               type string;
               description "Four bytes of the client id";
             }
             leaf alt-client-id-len {
               type int32;
               description "Number of bytes in alternate client id";
             }
             leaf alt-client-id {
               type string;
               description "Four byte of the alternate client id";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-82-length-from-client {
               type int32;
               description "Option 82 length from client";
             }
             leaf option-82-data-from-client {
               type string;
               description "Option 82 data from client";
             }
             leaf hardware-type {
               type string;
               description "Client hardware type";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf wholesale-logical-system-routing-instance {
               type string;
               description "L3 wholesale client router context logical system and routing instance";
             }
             leaf antispoof-filter-name {
               type string;
               description "Antispoof filter name";
             }
             leaf antispoof-filter-flags {
               type string;
               description "Antispoof filter flags";
             }
             leaf antispoof-filter-state {
               type string;
               description "Antispoof filter state";
             }
             leaf antispoof-filter-type {
               type string;
               description "Antispoof filter type";
             }
             leaf antispoof-filter-term-id {
               type string;
               description "Antispoof filter term id";
             }
             leaf antispoof-filter-action {
               type string;
               description "Antispoof filter type";
             }
             leaf antispoof-filter-parent {
               type string;
               description "Antispoof filter parent pointer";
             }
             leaf antispoof-filter-owner {
               type string;
               description "Antispoof filter owner pointer";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
           }
         }
       }
     }
   }
   rpc get-dhcp-relay-interface-bindings {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       container dhcp-relay-binding-information {
         container brief {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf rebinding-count {
               type int32;
             }
             leaf releasing-count {
               type int32;
             }
             leaf restore-count {
               type int32;
               description "Number of clients waiting to be restored";
             }
           }
           container binding-internal-states {
             leaf init {
               type int32;
               description "Number of clients init state";
             }
             leaf selecting {
               type int32;
               description "Number of clients in selecting state";
             }
             leaf requesting {
               type int32;
               description "Number of clients in requesting state";
             }
             leaf bound {
               type int32;
               description "Number of clients in bound state";
             }
             leaf renewing {
               type int32;
               description "Number of clients in renewing state";
             }
             leaf rebinding {
               type int32;
               description "Number of clients in rebinding state";
             }
             leaf wait-cm-add {
               type int32;
               description "Number of clients in wait-cm-add state";
             }
             leaf wait-cm-add-delete {
               type int32;
               description "Number of clients in wait-cm-add-delete state";
             }
             leaf wait-cm-delete {
               type int32;
               description "Number of clients in wait-cm-delete state";
             }
             leaf wait-subscr-add {
               type int32;
               description "Number of clients in wait-subscr-add state";
             }
             leaf wait-subscr-add-delete {
               type int32;
               description "Number of clients in wait-subscr-add-delete state";
             }
             leaf wait-subscr-delete {
               type int32;
               description "Number of clients in wait-subscr-delete state";
             }
             leaf wait-cm-update {
               type int32;
               description "Number of clients in wait-cm-update state";
             }
             leaf wait-cm-update-delete {
               type int32;
               description "Number of clients in wait-cm-update-delete state";
             }
             leaf wait-auth-req {
               type int32;
               description "Number of clients in wait-auth-req state";
             }
             leaf wait-auth-req-delete {
               type int32;
               description "Number of clients in wait-auth-req-delete state";
             }
             leaf wait-auth-req-release {
               type int32;
               description "Number of clients in wait-auth-req-release state";
             }
             leaf wait-auth-req-release-terminated {
               type int32;
               description "Number of clients in wait-auth-req-release-terminated state";
             }
             leaf wait-auth-act-prof {
               type int32;
               description "Number of clients in wait-auth-act-prof state";
             }
             leaf wait-auth-act-prof-delete {
               type int32;
               description "Number of clients in wait-auth-act-prof-delete state";
             }
             leaf wait-service-deactivation {
               type int32;
               description "Number of clients in wait-service-deactivation state";
             }
             leaf wait-dual-stack-peer-logout {
               type int32;
               description "Number of clients in wait-dual-stack-peer-logout state";
             }
             leaf wait-prof-inst {
               type int32;
               description "Number of clients in wait-prof-inst state";
             }
             leaf wait-prof-inst-delete {
               type int32;
               description "Number of clients in wait-prof-inst-delete state";
             }
             leaf wait-prof-delete {
               type int32;
               description "Number of clients in wait-prof-delete state";
             }
             leaf wait-interface {
               type int32;
               description "Number of clients in wait-interface state";
             }
             leaf wait-sdb-init-mirror-req {
               type int32;
               description "Number of clients in wait-sdb-init-mirror-req state";
             }
             leaf wait-sdb-init-mirror-req-delete {
               type int32;
               description "Number of clients in wait-sdb-init-mirror-req-delete state";
             }
             leaf wait-sdb-active-mirror-req {
               type int32;
               description "Number of clients in wait-sdb-active-mirror-req state";
             }
             leaf wait-sdb-active-mirror-req-delete {
               type int32;
               description "Number of clients in wait-sdb-active-mirror-req-delete state";
             }
             leaf wait-sdb-terminated-mirror-req {
               type int32;
               description "Number of clients in wait-sdb-terminated-mirror-req state";
             }
             leaf wait-sdb-dual-stack-terminating {
               type int32;
               description "Number of clients in wait-sdb-dual-stack-terminating state";
             }
             leaf wait-sdb-dual-stack-clear {
               type int32;
               description "Number of clients in wait-sdb-dual-stack-clear state";
             }
             leaf bound-on-intf-delete {
               type int32;
               description "Number of clients in bound-on-intf-delete state";
             }
           }
           container dhcp-binding {
             description "Information about the address assigned to a Dynamic Host Configuration Protocol client";
             leaf allocated-address {
               type ipaddr;
               description "IPv4 or IPv6 address assigned to the DHCP client";
             }
             leaf session-id {
               type string;
               description "Session ID of the client";
             }
             leaf mac-address {
               type mac-addr;
               description "Media access control (hardware) address of the DHCP client";
             }
             leaf lease-expires {
               type int32;
               description "Number of seconds lease will expire in";
             }
             leaf lease-state {
               type string;
               description "Status of the address assignment";
             }
             leaf interface-name {
               type string;
               description "Name of the interface via which the DHCP server transmitted the address assignment";
             }
           }
         }
         container detail {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf rebinding-count {
               type int32;
             }
             leaf releasing-count {
               type int32;
             }
             leaf restore-count {
               type int32;
               description "Number of clients waiting to be restored";
             }
           }
           container binding-internal-states {
             leaf init {
               type int32;
               description "Number of clients init state";
             }
             leaf selecting {
               type int32;
               description "Number of clients in selecting state";
             }
             leaf requesting {
               type int32;
               description "Number of clients in requesting state";
             }
             leaf bound {
               type int32;
               description "Number of clients in bound state";
             }
             leaf renewing {
               type int32;
               description "Number of clients in renewing state";
             }
             leaf rebinding {
               type int32;
               description "Number of clients in rebinding state";
             }
             leaf wait-cm-add {
               type int32;
               description "Number of clients in wait-cm-add state";
             }
             leaf wait-cm-add-delete {
               type int32;
               description "Number of clients in wait-cm-add-delete state";
             }
             leaf wait-cm-delete {
               type int32;
               description "Number of clients in wait-cm-delete state";
             }
             leaf wait-subscr-add {
               type int32;
               description "Number of clients in wait-subscr-add state";
             }
             leaf wait-subscr-add-delete {
               type int32;
               description "Number of clients in wait-subscr-add-delete state";
             }
             leaf wait-subscr-delete {
               type int32;
               description "Number of clients in wait-subscr-delete state";
             }
             leaf wait-cm-update {
               type int32;
               description "Number of clients in wait-cm-update state";
             }
             leaf wait-cm-update-delete {
               type int32;
               description "Number of clients in wait-cm-update-delete state";
             }
             leaf wait-auth-req {
               type int32;
               description "Number of clients in wait-auth-req state";
             }
             leaf wait-auth-req-delete {
               type int32;
               description "Number of clients in wait-auth-req-delete state";
             }
             leaf wait-auth-req-release {
               type int32;
               description "Number of clients in wait-auth-req-release state";
             }
             leaf wait-auth-req-release-terminated {
               type int32;
               description "Number of clients in wait-auth-req-release-terminated state";
             }
             leaf wait-auth-act-prof {
               type int32;
               description "Number of clients in wait-auth-act-prof state";
             }
             leaf wait-auth-act-prof-delete {
               type int32;
               description "Number of clients in wait-auth-act-prof-delete state";
             }
             leaf wait-service-deactivation {
               type int32;
               description "Number of clients in wait-service-deactivation state";
             }
             leaf wait-dual-stack-peer-logout {
               type int32;
               description "Number of clients in wait-dual-stack-peer-logout state";
             }
             leaf wait-prof-inst {
               type int32;
               description "Number of clients in wait-prof-inst state";
             }
             leaf wait-prof-inst-delete {
               type int32;
               description "Number of clients in wait-prof-inst-delete state";
             }
             leaf wait-prof-delete {
               type int32;
               description "Number of clients in wait-prof-delete state";
             }
             leaf wait-interface {
               type int32;
               description "Number of clients in wait-interface state";
             }
             leaf wait-sdb-init-mirror-req {
               type int32;
               description "Number of clients in wait-sdb-init-mirror-req state";
             }
             leaf wait-sdb-init-mirror-req-delete {
               type int32;
               description "Number of clients in wait-sdb-init-mirror-req-delete state";
             }
             leaf wait-sdb-active-mirror-req {
               type int32;
               description "Number of clients in wait-sdb-active-mirror-req state";
             }
             leaf wait-sdb-active-mirror-req-delete {
               type int32;
               description "Number of clients in wait-sdb-active-mirror-req-delete state";
             }
             leaf wait-sdb-terminated-mirror-req {
               type int32;
               description "Number of clients in wait-sdb-terminated-mirror-req state";
             }
             leaf wait-sdb-dual-stack-terminating {
               type int32;
               description "Number of clients in wait-sdb-dual-stack-terminating state";
             }
             leaf wait-sdb-dual-stack-clear {
               type int32;
               description "Number of clients in wait-sdb-dual-stack-clear state";
             }
             leaf bound-on-intf-delete {
               type int32;
               description "Number of clients in bound-on-intf-delete state";
             }
           }
           container dhcp-binding {
             description "Information about the address assigned to a Dynamic Host Configuration Protocol client";
             leaf allocated-address {
               type ipaddr;
               description "IPv4 or IPv6 address assigned to the DHCP client";
             }
             leaf mac-address {
               type mac-addr;
               description "Media access control (hardware) address of the DHCP client";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf lease-start-time {
               type string;
               description "Time when the client obtained the address assignment, in the format YYYY-MM-DD hh:mm:ss TZ (year, month, date, hour in 24-hour format, minute, second, time zone)";
             }
             leaf lease-time-violated {
               type string;
               description "Status of lease time validation violation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf server-interface-name {
               type string;
               description "Interface that server was from";
             }
             leaf bootp-relay-address {
               type ipaddr;
               description "IP address of the bootstrap protocol server that relayed the address assigned by the DHCP server";
             }
             leaf previous-bootp-relay-address {
               type ipaddr;
               description "Previous IP address of the bootstrap protocol server that relayed the address assigned by the DHCP server";
             }
             leaf session-id {
               type string;
               description "Session ID of the client";
             }
             leaf pool-name {
               type string;
               description "Client pool name";
             }
             leaf profile-name {
               type string;
               description "Client profile name";
             }
             leaf liveness-detection-state {
               type string;
               description "Status of the liveness detection session with the client";
             }
             leaf dual-stack-group {
               type string;
               description "Dual stack group referenece by this client";
             }
             leaf dual-stack-peer-address {
               type ipaddr;
               description "Peer IP or IPV6 address for this dual stack client";
             }
             leaf dual-stack-peer-prefix {
               type ipaddr;
               description "Peer IPV6 prefix for this dual stack client";
             }
             leaf generated-circuit-id {
               type string;
               description "Generated circuit id";
             }
             leaf generated-remote-id {
               type string;
               description "Generated remote id";
             }
             leaf dhcp-lease-binding-type {
               type string;
               description "Type of the address assignment";
             }
             leaf client-id-len {
               type int32;
               description "Number of bytes in client id";
             }
             leaf client-id {
               type string;
               description "Four bytes of the client id";
             }
             leaf alt-client-id-len {
               type int32;
               description "Number of bytes in alternate client id";
             }
             leaf alt-client-id {
               type string;
               description "Four byte of the alternate client id";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-82-length-from-client {
               type int32;
               description "Option 82 length from client";
             }
             leaf option-82-data-from-client {
               type string;
               description "Option 82 data from client";
             }
             leaf hardware-type {
               type string;
               description "Client hardware type";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf wholesale-logical-system-routing-instance {
               type string;
               description "L3 wholesale client router context logical system and routing instance";
             }
             leaf antispoof-filter-name {
               type string;
               description "Antispoof filter name";
             }
             leaf antispoof-filter-flags {
               type string;
               description "Antispoof filter flags";
             }
             leaf antispoof-filter-state {
               type string;
               description "Antispoof filter state";
             }
             leaf antispoof-filter-type {
               type string;
               description "Antispoof filter type";
             }
             leaf antispoof-filter-term-id {
               type string;
               description "Antispoof filter term id";
             }
             leaf antispoof-filter-action {
               type string;
               description "Antispoof filter type";
             }
             leaf antispoof-filter-parent {
               type string;
               description "Antispoof filter parent pointer";
             }
             leaf antispoof-filter-owner {
               type string;
               description "Antispoof filter owner pointer";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
           }
         }
       }
     }
   }
   rpc get-dhcp-relay-statistics-information {
     description "Show DHCP statistics";
     input {
       leaf level {
         default "summary";
         type enumeration {
           enum "summary" {
             description "Display summary information";
           }
         }
       }
       leaf routing-instance {
         description "Name of routing instance";
         type string;
       }
       leaf bridge-domain {
         description "Name of bridge domain";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-relay-statistics-information {
         leaf dropped-packet-total {
           type uint32;
           description "Total number of packets discarded by the DHCP relay because of errors";
         }
         leaf dropped-packet-bad-hardware {
           type uint32;
           description "Number of packets discarded by the DHCP relay because they specified an invalid hardware address";
         }
         leaf dropped-packet-bootp-packet {
           type uint32;
           description "Number of packets discarded by the DHCP relay because they  are bootp packets";
         }
         leaf dropped-packet-bad-bootp-opcode {
           type uint32;
           description "Number of packets discarded by the DHCP relay because they specified an invalid operation code in bootp";
         }
         leaf dropped-packet-bad-options {
           type uint32;
           description "Number of packets discarded by the DHCP relay because they specified invalid options";
         }
         leaf dropped-packet-invalid-server-address {
           type uint32;
           description "Number of packets discarded by the DHCP relay because they specified an invalid server address";
         }
         leaf dropped-packet-no-addresses {
           type uint32;
           description "Number of packets discarded by the DHCP relay because there were no addresses available for it to assign";
         }
         leaf dropped-packet-no-interface-cfg {
           type uint32;
           description "Number of packets discarded by the DHCP relay because packets arrived on unconfigured interface";
         }
         leaf dropped-packet-no-local-address {
           type uint32;
           description "Number of packets discarded by the DHCP relay because there was no valid local address";
         }
         leaf dropped-packet-too-short {
           type uint32;
           description "Number of packets discarded by the DHCP relay because they were too short";
         }
         leaf dropped-packet-send-error {
           type uint32;
           description "Number of packets that the DHCP relay could not send";
         }
         leaf dropped-packet-option-60 {
           type uint32;
           description "Number of packets discarded with no matching option-60";
         }
         leaf dropped-packet-relay-option {
           type uint32;
           description "Number of packets discarded due to relay-option processing";
         }
         leaf dropped-packet-option-82 {
           type uint32;
           description "Number of packets discarded because option-82 could not be added";
         }
         leaf dropped-packet-authentication {
           type uint32;
           description "Number of packets discarded because authentication failed";
         }
         leaf dropped-packet-dynamic-profile {
           type uint32;
           description "Number of packets discarded because a dynamic profile failed";
         }
         leaf dropped-packet-license {
           type uint32;
           description "Number of packets discarded because of a license failure";
         }
         leaf dropped-packet-bad-dhcp-opcode {
           type uint32;
           description "Number of packets discarded because of bad DHCP opcode";
         }
         leaf dropped-packet-no-options {
           type uint32;
           description "Number of packets discarded because of no options";
         }
         leaf dropped-packet-hop-limit {
           type uint32;
           description "Number of packets discarded because of hop limit reached";
         }
         leaf dropped-packet-ttl-expired {
           type uint32;
           description "Number of packets discarded because of ttl expired";
         }
         leaf dropped-packet-bad-udp-checksum {
           type uint32;
           description "Number of packets discarded because of bad udp checksum";
         }
         leaf dropped-packet-inactive-vlan {
           type uint32;
           description "Number of packets discarded because of inactive VLAN";
         }
         leaf dropped-packet-event-rate-analyzer {
           type uint32;
           description "Number of packets discarded because of ERA throttling";
         }
         leaf dropped-packet-client-lookup {
           type uint32;
           description "Number of packets discarded because no client binding was found";
         }
         leaf dropped-packet-proxy-no-server-addr {
           type uint32;
           description "Number of packets discarded because client server address is 0, but should not be";
         }
         leaf lease-time-violations-drop {
           type uint32;
           description "Packets dropped because of lease time violation";
         }
         leaf dropped-packet-leasequery-repl-no-circuitid {
           type uint32;
           description "Packets discarded as no circuit-id in leasequery replies";
         }
         leaf dropped-packet-leasequery-repl-with-error-code {
           type uint32;
           description "Packets discarded, leasequery reply with error code";
         }
         leaf dropped-packet-leasequery-repl-with-query-term {
           type uint32;
           description "Packets discarded, leasequery reply with error code";
         }
         leaf dropped-packet-older-leasequery-repl {
           type uint32;
           description "Number of packets discarded because leasequery reply is of older timestamp";
         }
         leaf dropped-packet-abort-leasequery-repl {
           type uint32;
           description "Number of packets discarded due to abort of leasequery reply processing";
         }
         leaf dropped-packet-during-leasequery-repl {
           type uint32;
           description "Packets discarded as received during leasequery reply processing";
         }
         leaf dropped-packet-relay-source-no-lpbk-interface {
           type uint32;
           description "Number of packets discarded as received with relay source config without loopback config";
         }
         leaf dropped-packet-dhcp-service-total {
           type uint32;
           description "Total number of packets discarded by the DHCP service because of errors";
         }
         leaf forwarded-packets-total {
           type uint32;
           description "Total number of packets forwarded";
         }
         leaf forwarded-bootrequest-packets {
           type uint32;
           description "Number of bootrequest packets forwarded";
         }
         leaf forwarded-bootreply-packets {
           type uint32;
           description "Number of bootreply packets forwarded";
         }
         leaf dhcp-external-server-response-state {
           type string;
           description "Set if external server is responding otherwise Clear";
         }
         container message-table {
           description "Information about one or more DHCP or bootstrap protocol (BOOTP) messages sent or received by the DHCP relay";
           leaf message-direction {
             type string;
             description "Indicator of whether the DHCP relay sent or received the messages";
           }
           container message {
             description "Information about a DHCP or BOOTP message";
             leaf message-name {
               type string;
               description "Name of the message";
             }
             leaf message-count {
               type uint32;
               description "Number of times the DCHP relay received or sent the message";
             }
           }
         }
       }
     }
   }
   rpc get-dhcp-relay-leasequery-statistics {
     description "Show DHCP relay leasequery statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-relay-leasequery-statistics {
         leaf in-flight-leasequeries {
           type uint32;
           description "Number of in-flight leasequeries";
         }
         leaf total-leasequeries {
           type uint32;
           description "Total Number of leasequeries";
         }
         leaf total-leasequery-attempts {
           type uint32;
           description "Total Number of leasequery attempts";
         }
         leaf total-leasequery-repl-packet-retries {
           type uint32;
           description "Total Number of packet retries";
         }
         leaf total-leasequery-repl-max-retried {
           type uint32;
           description "Total Number of leasequery reply maximum retried";
         }
         container summary {
           description "Leasequery Statistics for DHCP and DHCPv6 Relay";
           container dhcp-leasequery-info-statistics {
           }
         }
         container verbose {
           description "Leasequery Statistics for DHCP and DHCPv6 Relay";
           leaf in-flight-leasequeries {
             type uint32;
             description "Number of in-flight leasequeries";
           }
           leaf total-leasequeries {
             type uint32;
             description "Total Number of leasequeries";
           }
           leaf total-leasequery-attempts {
             type uint32;
             description "Total Number of leasequery attempts";
           }
           leaf total-leasequery-repl-packet-retries {
             type uint32;
             description "Total Number of packet retries";
           }
           leaf total-leasequery-repl-max-retried {
             type uint32;
             description "Total Number of leasequery reply maximum retried";
           }
           container dhcp-leasequery-info-statistics {
             leaf leasequery-xid {
               type uint32;
               description "Leasequery unique XID";
             }
             leaf leasequery-state {
               type string;
               description "Leasequery state";
             }
             leaf leasequery-confirmed-replies {
               type uint32;
               description "Number of confirmed Leasequery replies";
             }
             leaf leasequery-unconfirmed-replies {
               type uint32;
               description "Numnrt of unconfirmed Leasequery replies";
             }
             leaf leasequery-attempts {
               type uint32;
               description "Number of Leasequery attempts";
             }
             container dhcp-leasequery-server-info-statistics {
             }
           }
         }
       }
     }
   }
   rpc get-dhcp-relay-bulk-leasequery-conn-statistics {
     description "Show DHCP relay bulk leasequery statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-relay-bulk-leasequery-conn-statistics {
         leaf total-connections-requested {
           type uint32;
           description "Number of TCP connections requested";
         }
         leaf total-connections-attempted {
           type uint32;
           description "Number of TCP connections attempted";
         }
         leaf total-connections-connected {
           type uint32;
           description "Number of connected TCP connections";
         }
         leaf total-connections-terminated-by-server {
           type uint32;
           description "Number of connections terminated by server";
         }
         leaf total-connections-max-attempted {
           type uint32;
           description "Number of requested TCP connections with max attempts reached";
         }
         leaf total-connections-closed-due-to-error {
           type uint32;
           description "Number of TCP connections closed due to error";
         }
         leaf in-flight-connections-connected {
           type uint32;
           description "Number of in-flight TCP connections in connected state";
         }
         leaf total-bulk-leasequery-repl-packet-retries {
           type uint32;
           description "Number of bulk leasequery reply packet retries";
         }
         leaf total-bulk-leasequery-repl-max-retried {
           type uint32;
           description "Number of bulk leasequery reply max retried";
         }
         container summary {
           description "Bulk Leasequery connection statistics for DHCP and DHCPv6 Relay";
           container dhcp-bulk-leasequery-info-statistics {
           }
         }
         container verbose {
           description "Bulk Leasequery connection statistics for DHCP and DHCPv6 Relay";
           leaf total-connections-requested {
             type uint32;
             description "Number of TCP connections requested";
           }
           leaf total-connections-attempted {
             type uint32;
             description "Number of TCP connections attempted";
           }
           leaf total-connections-connected {
             type uint32;
             description "Number of connected TCP connections";
           }
           leaf total-connections-terminated-by-server {
             type uint32;
             description "Number of connections terminated by server";
           }
           leaf total-connections-max-attempted {
             type uint32;
             description "Number of requested TCP connections with max attempts reached";
           }
           leaf total-connections-closed-due-to-error {
             type uint32;
             description "Number of TCP connections closed due to error";
           }
           leaf in-flight-connections-connected {
             type uint32;
             description "Number of in-flight TCP connections in connected state";
           }
           leaf total-bulk-leasequery-repl-packet-retries {
             type uint32;
             description "Number of bulk leasequery reply packet retries";
           }
           leaf total-bulk-leasequery-repl-max-retried {
             type uint32;
             description "Number of bulk leasequery reply max retried";
           }
           container dhcp-bulk-leasequery-info-statistics {
             leaf bulk-leasequery-xid {
               type uint32;
               description "Bulk Leasequery unique XID";
             }
             leaf bulk-leasequery-total-servers {
               type uint32;
               description "Total Bulk Leasequery servers";
             }
             container dhcp-bulk-leasequery-server-info-statistics {
             }
           }
         }
       }
     }
   }
   rpc get-dhcp-server-binding-information {
     description "Show DHCP server client binding information";
     input {
       leaf level {
         default "brief";
         type enumeration {
           enum "brief" {
             description "Display brief information";
           }
           enum "detail" {
             description "Display detailed information";
           }
           enum "summary" {
             description "Display summary information";
           }
         }
       }
       container show-choice {
         choice show-choice_c {
           case address {
             leaf address {
               description "IP address/MAC address/Session Id of DHCP client binding";
               type string;
             }
           }
           case interfaces-wildcard {
             leaf interfaces-wildcard {
               description "Interfaces to show bindings on (can be '*' wildcard)";
               type string {
                 junos:posix-pattern "^( (((ge-)|(xe-)|(et-))( [[:digit:]]+(-([[:digit:]]+))+(-([[:digit:]]+)?)?)?) | (ae))+$";
                 junos:pattern-message "Must be an interface wildcard string";
               }
             }
           }
           case interfaces-vlan {
             leaf interfaces-vlan {
               description "Interface VLAN-ID/SVLAN-ID on which to show bindings";
               type string {
                 junos:posix-pattern "^(( (((ge-)|(xe-)|(et-))( [[:digit:]]+(-([[:digit:]]+))+(-([[:digit:]]+)?)?)?) | (ae))(/:)([[:digit:]]+(-[[:digit:]]+))?)+$";
                 junos:pattern-message "Must be an interface:VLAN string";
               }
             }
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-server-binding-information {
         container brief {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf releasing-count {
               type int32;
             }
             leaf restore-count {
               type int32;
               description "Number of clients waiting to be restored";
             }
           }
           container dhcp-binding {
             description "Information about the address assigned to a Dynamic Host Configuration Protocol client";
             leaf allocated-address {
               type ipaddr;
               description "IPv4 or IPv6 address assigned to the DHCP client";
             }
             leaf session-id {
               type string;
               description "Session ID of the client";
             }
             leaf mac-address {
               type mac-addr;
               description "Media access control (hardware) address of the DHCP client";
             }
             leaf lease-expires {
               type int32;
               description "Number of seconds lease will expire in";
             }
             leaf lease-state {
               type string;
               description "Status of the address assignment";
             }
             leaf interface-name {
               type string;
               description "Name of the interface via which the DHCP server transmitted the address assignment";
             }
             leaf dhcpv6-relay-id-len {
               type int32;
               description "Number of bytes in client id";
             }
             leaf dhcpv6-relay-id {
               type string;
               description "DHCPv6 relay-id";
             }
           }
         }
         container detail {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf releasing-count {
               type int32;
             }
             leaf restore-count {
               type int32;
               description "Number of clients waiting to be restored";
             }
           }
           container dhcp-binding {
             description "Information about the address assigned to a Dynamic Host Configuration Protocol client";
             leaf allocated-address {
               type ipaddr;
               description "IPv4 or IPv6 address assigned to the DHCP client";
             }
             leaf mac-address {
               type mac-addr;
               description "Media access control (hardware) address of the DHCP client";
             }
             leaf lease-state {
               type string;
               description "Status of the address assignment";
             }
             leaf protocol-used {
               type string;
               description "Protocol used by client to perform this binding BOOTP/DHCP";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf lease-start-time {
               type string;
               description "Time when the client obtained the address assignment, in the format YYYY-MM-DD hh:mm:ss TZ (year, month, date, hour in 24-hour format, minute, second, time zone)";
             }
             leaf lease-time-violated {
               type string;
               description "Status of binding wrt lease time validation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf bootp-relay-address {
               type ipaddr;
               description "IP address of the bootstrap protocol server that relayed the address assigned by the DHCP server";
             }
             leaf previous-bootp-relay-address {
               type ipaddr;
               description "Previous IP address of the bootstrap protocol server that relayed the address assigned by the DHCP server";
             }
             leaf session-id {
               type string;
               description "Session ID of the client";
             }
             leaf pool-name {
               type string;
               description "Client pool name";
             }
             leaf profile-name {
               type string;
               description "Client profile name";
             }
             leaf liveness-detection-state {
               type string;
               description "Status of the liveness detection session with the client";
             }
             leaf dhcp-lease-binding-type {
               type string;
               description "Type of the address assignment";
             }
             leaf client-id-len {
               type int32;
               description "Number of bytes in client id";
             }
             leaf client-id {
               type string;
               description "Client id";
             }
             leaf alt-client-id-len {
               type int32;
               description "Number of bytes in alternate client id";
             }
             leaf alt-client-id {
               type string;
               description "Alternate client id";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-82-length-from-client {
               type int32;
               description "Option 82 length from client";
             }
             leaf option-82-data-from-client {
               type string;
               description "Option 82 data from client";
             }
             leaf hardware-type {
               type string;
               description "Client hardware type";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf retail-bridge-domain {
               type string;
               description "L3 wholesale retail client router context bridge domain";
             }
             leaf wholesale-logical-system-routing-instance {
               type string;
               description "L3 wholesale client router context logical system and routing instance";
             }
             leaf wholesale-bridge-domain {
               type string;
               description "L3 wholesale client router context bridge domain";
             }
             leaf antispoof-filter-name {
               type string;
               description "Antispoof filter name";
             }
             leaf antispoof-filter-flags {
               type string;
               description "Antispoof filter flags";
             }
             leaf antispoof-filter-state {
               type string;
               description "Antispoof filter state";
             }
             leaf antispoof-filter-type {
               type string;
               description "Antispoof filter type";
             }
             leaf antispoof-filter-term-id {
               type string;
               description "Antispoof filter term id";
             }
             leaf antispoof-filter-action {
               type string;
               description "Antispoof filter type";
             }
             leaf antispoof-filter-parent {
               type string;
               description "Antispoof filter parent pointer";
             }
             leaf antispoof-filter-owner {
               type string;
               description "Antispoof filter owner pointer";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
             leaf dhcpv6-relay-id-len {
               type int32;
               description "Number of bytes in client id";
             }
             leaf dhcpv6-relay-id {
               type string;
               description "DHCPv6 relay-id";
             }
           }
         }
       }
     }
   }
   rpc get-dhcp-server-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-server-binding-information {
         container brief {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf releasing-count {
               type int32;
             }
             leaf restore-count {
               type int32;
               description "Number of clients waiting to be restored";
             }
           }
           container dhcp-binding {
             description "Information about the address assigned to a Dynamic Host Configuration Protocol client";
             leaf allocated-address {
               type ipaddr;
               description "IPv4 or IPv6 address assigned to the DHCP client";
             }
             leaf session-id {
               type string;
               description "Session ID of the client";
             }
             leaf mac-address {
               type mac-addr;
               description "Media access control (hardware) address of the DHCP client";
             }
             leaf lease-expires {
               type int32;
               description "Number of seconds lease will expire in";
             }
             leaf lease-state {
               type string;
               description "Status of the address assignment";
             }
             leaf interface-name {
               type string;
               description "Name of the interface via which the DHCP server transmitted the address assignment";
             }
             leaf dhcpv6-relay-id-len {
               type int32;
               description "Number of bytes in client id";
             }
             leaf dhcpv6-relay-id {
               type string;
               description "DHCPv6 relay-id";
             }
           }
         }
         container detail {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf releasing-count {
               type int32;
             }
             leaf restore-count {
               type int32;
               description "Number of clients waiting to be restored";
             }
           }
           container dhcp-binding {
             description "Information about the address assigned to a Dynamic Host Configuration Protocol client";
             leaf allocated-address {
               type ipaddr;
               description "IPv4 or IPv6 address assigned to the DHCP client";
             }
             leaf mac-address {
               type mac-addr;
               description "Media access control (hardware) address of the DHCP client";
             }
             leaf lease-state {
               type string;
               description "Status of the address assignment";
             }
             leaf protocol-used {
               type string;
               description "Protocol used by client to perform this binding BOOTP/DHCP";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf lease-start-time {
               type string;
               description "Time when the client obtained the address assignment, in the format YYYY-MM-DD hh:mm:ss TZ (year, month, date, hour in 24-hour format, minute, second, time zone)";
             }
             leaf lease-time-violated {
               type string;
               description "Status of binding wrt lease time validation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf bootp-relay-address {
               type ipaddr;
               description "IP address of the bootstrap protocol server that relayed the address assigned by the DHCP server";
             }
             leaf previous-bootp-relay-address {
               type ipaddr;
               description "Previous IP address of the bootstrap protocol server that relayed the address assigned by the DHCP server";
             }
             leaf session-id {
               type string;
               description "Session ID of the client";
             }
             leaf pool-name {
               type string;
               description "Client pool name";
             }
             leaf profile-name {
               type string;
               description "Client profile name";
             }
             leaf liveness-detection-state {
               type string;
               description "Status of the liveness detection session with the client";
             }
             leaf dhcp-lease-binding-type {
               type string;
               description "Type of the address assignment";
             }
             leaf client-id-len {
               type int32;
               description "Number of bytes in client id";
             }
             leaf client-id {
               type string;
               description "Client id";
             }
             leaf alt-client-id-len {
               type int32;
               description "Number of bytes in alternate client id";
             }
             leaf alt-client-id {
               type string;
               description "Alternate client id";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-82-length-from-client {
               type int32;
               description "Option 82 length from client";
             }
             leaf option-82-data-from-client {
               type string;
               description "Option 82 data from client";
             }
             leaf hardware-type {
               type string;
               description "Client hardware type";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf retail-bridge-domain {
               type string;
               description "L3 wholesale retail client router context bridge domain";
             }
             leaf wholesale-logical-system-routing-instance {
               type string;
               description "L3 wholesale client router context logical system and routing instance";
             }
             leaf wholesale-bridge-domain {
               type string;
               description "L3 wholesale client router context bridge domain";
             }
             leaf antispoof-filter-name {
               type string;
               description "Antispoof filter name";
             }
             leaf antispoof-filter-flags {
               type string;
               description "Antispoof filter flags";
             }
             leaf antispoof-filter-state {
               type string;
               description "Antispoof filter state";
             }
             leaf antispoof-filter-type {
               type string;
               description "Antispoof filter type";
             }
             leaf antispoof-filter-term-id {
               type string;
               description "Antispoof filter term id";
             }
             leaf antispoof-filter-action {
               type string;
               description "Antispoof filter type";
             }
             leaf antispoof-filter-parent {
               type string;
               description "Antispoof filter parent pointer";
             }
             leaf antispoof-filter-owner {
               type string;
               description "Antispoof filter owner pointer";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
             leaf dhcpv6-relay-id-len {
               type int32;
               description "Number of bytes in client id";
             }
             leaf dhcpv6-relay-id {
               type string;
               description "DHCPv6 relay-id";
             }
           }
         }
       }
     }
   }
   rpc get-dhcp-relay-binding-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       container dhcp-relay-binding-information {
         container brief {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf rebinding-count {
               type int32;
             }
             leaf releasing-count {
               type int32;
             }
             leaf restore-count {
               type int32;
               description "Number of clients waiting to be restored";
             }
           }
           container binding-internal-states {
             leaf init {
               type int32;
               description "Number of clients init state";
             }
             leaf selecting {
               type int32;
               description "Number of clients in selecting state";
             }
             leaf requesting {
               type int32;
               description "Number of clients in requesting state";
             }
             leaf bound {
               type int32;
               description "Number of clients in bound state";
             }
             leaf renewing {
               type int32;
               description "Number of clients in renewing state";
             }
             leaf rebinding {
               type int32;
               description "Number of clients in rebinding state";
             }
             leaf wait-cm-add {
               type int32;
               description "Number of clients in wait-cm-add state";
             }
             leaf wait-cm-add-delete {
               type int32;
               description "Number of clients in wait-cm-add-delete state";
             }
             leaf wait-cm-delete {
               type int32;
               description "Number of clients in wait-cm-delete state";
             }
             leaf wait-subscr-add {
               type int32;
               description "Number of clients in wait-subscr-add state";
             }
             leaf wait-subscr-add-delete {
               type int32;
               description "Number of clients in wait-subscr-add-delete state";
             }
             leaf wait-subscr-delete {
               type int32;
               description "Number of clients in wait-subscr-delete state";
             }
             leaf wait-cm-update {
               type int32;
               description "Number of clients in wait-cm-update state";
             }
             leaf wait-cm-update-delete {
               type int32;
               description "Number of clients in wait-cm-update-delete state";
             }
             leaf wait-auth-req {
               type int32;
               description "Number of clients in wait-auth-req state";
             }
             leaf wait-auth-req-delete {
               type int32;
               description "Number of clients in wait-auth-req-delete state";
             }
             leaf wait-auth-req-release {
               type int32;
               description "Number of clients in wait-auth-req-release state";
             }
             leaf wait-auth-req-release-terminated {
               type int32;
               description "Number of clients in wait-auth-req-release-terminated state";
             }
             leaf wait-auth-act-prof {
               type int32;
               description "Number of clients in wait-auth-act-prof state";
             }
             leaf wait-auth-act-prof-delete {
               type int32;
               description "Number of clients in wait-auth-act-prof-delete state";
             }
             leaf wait-service-deactivation {
               type int32;
               description "Number of clients in wait-service-deactivation state";
             }
             leaf wait-dual-stack-peer-logout {
               type int32;
               description "Number of clients in wait-dual-stack-peer-logout state";
             }
             leaf wait-prof-inst {
               type int32;
               description "Number of clients in wait-prof-inst state";
             }
             leaf wait-prof-inst-delete {
               type int32;
               description "Number of clients in wait-prof-inst-delete state";
             }
             leaf wait-prof-delete {
               type int32;
               description "Number of clients in wait-prof-delete state";
             }
             leaf wait-interface {
               type int32;
               description "Number of clients in wait-interface state";
             }
             leaf wait-sdb-init-mirror-req {
               type int32;
               description "Number of clients in wait-sdb-init-mirror-req state";
             }
             leaf wait-sdb-init-mirror-req-delete {
               type int32;
               description "Number of clients in wait-sdb-init-mirror-req-delete state";
             }
             leaf wait-sdb-active-mirror-req {
               type int32;
               description "Number of clients in wait-sdb-active-mirror-req state";
             }
             leaf wait-sdb-active-mirror-req-delete {
               type int32;
               description "Number of clients in wait-sdb-active-mirror-req-delete state";
             }
             leaf wait-sdb-terminated-mirror-req {
               type int32;
               description "Number of clients in wait-sdb-terminated-mirror-req state";
             }
             leaf wait-sdb-dual-stack-terminating {
               type int32;
               description "Number of clients in wait-sdb-dual-stack-terminating state";
             }
             leaf wait-sdb-dual-stack-clear {
               type int32;
               description "Number of clients in wait-sdb-dual-stack-clear state";
             }
             leaf bound-on-intf-delete {
               type int32;
               description "Number of clients in bound-on-intf-delete state";
             }
           }
           container dhcp-binding {
             description "Information about the address assigned to a Dynamic Host Configuration Protocol client";
             leaf allocated-address {
               type ipaddr;
               description "IPv4 or IPv6 address assigned to the DHCP client";
             }
             leaf session-id {
               type string;
               description "Session ID of the client";
             }
             leaf mac-address {
               type mac-addr;
               description "Media access control (hardware) address of the DHCP client";
             }
             leaf lease-expires {
               type int32;
               description "Number of seconds lease will expire in";
             }
             leaf lease-state {
               type string;
               description "Status of the address assignment";
             }
             leaf interface-name {
               type string;
               description "Name of the interface via which the DHCP server transmitted the address assignment";
             }
           }
         }
         container detail {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf rebinding-count {
               type int32;
             }
             leaf releasing-count {
               type int32;
             }
             leaf restore-count {
               type int32;
               description "Number of clients waiting to be restored";
             }
           }
           container binding-internal-states {
             leaf init {
               type int32;
               description "Number of clients init state";
             }
             leaf selecting {
               type int32;
               description "Number of clients in selecting state";
             }
             leaf requesting {
               type int32;
               description "Number of clients in requesting state";
             }
             leaf bound {
               type int32;
               description "Number of clients in bound state";
             }
             leaf renewing {
               type int32;
               description "Number of clients in renewing state";
             }
             leaf rebinding {
               type int32;
               description "Number of clients in rebinding state";
             }
             leaf wait-cm-add {
               type int32;
               description "Number of clients in wait-cm-add state";
             }
             leaf wait-cm-add-delete {
               type int32;
               description "Number of clients in wait-cm-add-delete state";
             }
             leaf wait-cm-delete {
               type int32;
               description "Number of clients in wait-cm-delete state";
             }
             leaf wait-subscr-add {
               type int32;
               description "Number of clients in wait-subscr-add state";
             }
             leaf wait-subscr-add-delete {
               type int32;
               description "Number of clients in wait-subscr-add-delete state";
             }
             leaf wait-subscr-delete {
               type int32;
               description "Number of clients in wait-subscr-delete state";
             }
             leaf wait-cm-update {
               type int32;
               description "Number of clients in wait-cm-update state";
             }
             leaf wait-cm-update-delete {
               type int32;
               description "Number of clients in wait-cm-update-delete state";
             }
             leaf wait-auth-req {
               type int32;
               description "Number of clients in wait-auth-req state";
             }
             leaf wait-auth-req-delete {
               type int32;
               description "Number of clients in wait-auth-req-delete state";
             }
             leaf wait-auth-req-release {
               type int32;
               description "Number of clients in wait-auth-req-release state";
             }
             leaf wait-auth-req-release-terminated {
               type int32;
               description "Number of clients in wait-auth-req-release-terminated state";
             }
             leaf wait-auth-act-prof {
               type int32;
               description "Number of clients in wait-auth-act-prof state";
             }
             leaf wait-auth-act-prof-delete {
               type int32;
               description "Number of clients in wait-auth-act-prof-delete state";
             }
             leaf wait-service-deactivation {
               type int32;
               description "Number of clients in wait-service-deactivation state";
             }
             leaf wait-dual-stack-peer-logout {
               type int32;
               description "Number of clients in wait-dual-stack-peer-logout state";
             }
             leaf wait-prof-inst {
               type int32;
               description "Number of clients in wait-prof-inst state";
             }
             leaf wait-prof-inst-delete {
               type int32;
               description "Number of clients in wait-prof-inst-delete state";
             }
             leaf wait-prof-delete {
               type int32;
               description "Number of clients in wait-prof-delete state";
             }
             leaf wait-interface {
               type int32;
               description "Number of clients in wait-interface state";
             }
             leaf wait-sdb-init-mirror-req {
               type int32;
               description "Number of clients in wait-sdb-init-mirror-req state";
             }
             leaf wait-sdb-init-mirror-req-delete {
               type int32;
               description "Number of clients in wait-sdb-init-mirror-req-delete state";
             }
             leaf wait-sdb-active-mirror-req {
               type int32;
               description "Number of clients in wait-sdb-active-mirror-req state";
             }
             leaf wait-sdb-active-mirror-req-delete {
               type int32;
               description "Number of clients in wait-sdb-active-mirror-req-delete state";
             }
             leaf wait-sdb-terminated-mirror-req {
               type int32;
               description "Number of clients in wait-sdb-terminated-mirror-req state";
             }
             leaf wait-sdb-dual-stack-terminating {
               type int32;
               description "Number of clients in wait-sdb-dual-stack-terminating state";
             }
             leaf wait-sdb-dual-stack-clear {
               type int32;
               description "Number of clients in wait-sdb-dual-stack-clear state";
             }
             leaf bound-on-intf-delete {
               type int32;
               description "Number of clients in bound-on-intf-delete state";
             }
           }
           container dhcp-binding {
             description "Information about the address assigned to a Dynamic Host Configuration Protocol client";
             leaf allocated-address {
               type ipaddr;
               description "IPv4 or IPv6 address assigned to the DHCP client";
             }
             leaf mac-address {
               type mac-addr;
               description "Media access control (hardware) address of the DHCP client";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf lease-start-time {
               type string;
               description "Time when the client obtained the address assignment, in the format YYYY-MM-DD hh:mm:ss TZ (year, month, date, hour in 24-hour format, minute, second, time zone)";
             }
             leaf lease-time-violated {
               type string;
               description "Status of lease time validation violation";
             }
             leaf last-packet-received-time {
               type string;
               description "Time at which the most recent packet from the client was received, in the format YYYY-MM-DD hh:mm:ss TZ (year, month, date, hour in 24-hour format, minute, second, time zone)";
             }
             leaf interface-name {
               type string;
               description "Name of the interface via which the DHCP server transmitted the address assignment";
             }
             leaf vlan-id {
               type int32;
               description "Vlan id of the client interface";
             }
             leaf svlan-id {
               type int32;
               description "Svlan id of the client interface";
             }
             leaf demux-interface-name {
               type string;
               description "Demux interface name";
             }
             leaf server-ip-address {
               type ipaddr;
               description "IP address of the DHCP server";
             }
             leaf server-interface-name {
               type string;
               description "Interface that server was from";
             }
             leaf bootp-relay-address {
               type ipaddr;
               description "IP address of the bootstrap protocol server that relayed the address assigned by the DHCP server";
             }
             leaf previous-bootp-relay-address {
               type ipaddr;
               description "Previous IP address of the bootstrap protocol server that relayed the address assigned by the DHCP server";
             }
             leaf session-id {
               type string;
               description "Session ID of the client";
             }
             leaf pool-name {
               type string;
               description "Client pool name";
             }
             leaf profile-name {
               type string;
               description "Client profile name";
             }
             leaf liveness-detection-state {
               type string;
               description "Status of the liveness detection session with the client";
             }
             leaf dual-stack-group {
               type string;
               description "Dual stack group referenece by this client";
             }
             leaf dual-stack-peer-address {
               type ipaddr;
               description "Peer IP or IPV6 address for this dual stack client";
             }
             leaf dual-stack-peer-prefix {
               type ipaddr;
               description "Peer IPV6 prefix for this dual stack client";
             }
             leaf generated-circuit-id {
               type string;
               description "Generated circuit id";
             }
             leaf generated-remote-id {
               type string;
               description "Generated remote id";
             }
             leaf dhcp-lease-binding-type {
               type string;
               description "Type of the address assignment";
             }
             leaf client-id-len {
               type int32;
               description "Number of bytes in client id";
             }
             leaf client-id {
               type string;
               description "Four bytes of the client id";
             }
             leaf alt-client-id-len {
               type int32;
               description "Number of bytes in alternate client id";
             }
             leaf alt-client-id {
               type string;
               description "Four byte of the alternate client id";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-82-length-from-client {
               type int32;
               description "Option 82 length from client";
             }
             leaf option-82-data-from-client {
               type string;
               description "Option 82 data from client";
             }
             leaf hardware-type {
               type string;
               description "Client hardware type";
             }
             leaf logical-system-routing-instance {
               type string;
               description "Client router context logical system and routing instance";
             }
             leaf bridge-domain {
               type string;
               description "Client router context bridge domain";
             }
             leaf client-info {
               type string;
               description "General information about the client";
             }
             leaf retail-logical-system-routing-instance {
               type string;
               description "L3 wholesale retail client router context logical system and routing instance";
             }
             leaf wholesale-logical-system-routing-instance {
               type string;
               description "L3 wholesale client router context logical system and routing instance";
             }
             leaf antispoof-filter-name {
               type string;
               description "Antispoof filter name";
             }
             leaf antispoof-filter-flags {
               type string;
               description "Antispoof filter flags";
             }
             leaf antispoof-filter-state {
               type string;
               description "Antispoof filter state";
             }
             leaf antispoof-filter-type {
               type string;
               description "Antispoof filter type";
             }
             leaf antispoof-filter-term-id {
               type string;
               description "Antispoof filter term id";
             }
             leaf antispoof-filter-action {
               type string;
               description "Antispoof filter type";
             }
             leaf antispoof-filter-parent {
               type string;
               description "Antispoof filter parent pointer";
             }
             leaf antispoof-filter-owner {
               type string;
               description "Antispoof filter owner pointer";
             }
             leaf authentication-num-servers {
               type int32;
               description "Number of servers in authentication group";
             }
             leaf client-stale-count {
               type int32;
               description "Number of clients in stale list";
             }
             leaf auth-client-limit {
               type int32;
               description "Client limit from authentication daemon";
             }
             leaf auth-relay-server-group {
               type string;
               description "Value of pointer to authentication daemon server group";
             }
             leaf aci-iflset-name {
               type string;
               description "ACI-VLAN iflset name";
             }
             leaf aci-iflset-index {
               type int32;
               description "ACI-VLAN iflset index";
             }
             leaf aci-iflset-session-id {
               type string;
               description "ACI-VLAN iflset Session ID";
             }
           }
         }
       }
     }
   }
   rpc get-dhcp-server-statistics-information {
     description "Show DHCP server statistics";
     input {
       leaf level {
         default "summary";
         type enumeration {
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-server-statistics-information {
         leaf dropped-packet-total {
           type uint32;
           description "Total number of packets discarded by the DHCP server because of errors";
         }
         leaf dropped-packet-bad-hardware {
           type uint32;
           description "Number of packets discarded by the DHCP server because they specified an invalid hardware address";
         }
         leaf dropped-packet-bootp-packet {
           type uint32;
           description "Number of packets discarded by the DHCP server because they are bootp packets";
         }
         leaf dropped-packet-bad-bootp-opcode {
           type uint32;
           description "Number of packets discarded by the DHCP server because they specified an invalid operation code in bootp";
         }
         leaf dropped-packet-bad-options {
           type uint32;
           description "Number of packets discarded by the DHCP server because they specified invalid options";
         }
         leaf dropped-packet-invalid-server-address {
           type uint32;
           description "Number of packets discarded by the DHCP server because they specified an invalid server address";
         }
         leaf dropped-packet-no-addresses {
           type uint32;
           description "Number of packets discarded by the DHCP server because there were no addresses available for it to assign";
         }
         leaf dropped-packet-no-interface-cfg {
           type uint32;
           description "Number of packets discarded by the DHCP server because packets arrived on unconfigured interface";
         }
         leaf dropped-packet-no-local-address {
           type uint32;
           description "Number of packets discarded by the DHCP server because there was no valid local address";
         }
         leaf dropped-packet-too-short {
           type uint32;
           description "Number of packets discarded by the DHCP server because they were too short";
         }
         leaf dropped-packet-send-error {
           type uint32;
           description "Number of packets that the DHCP server could not send";
         }
         leaf dropped-packet-option-60 {
           type uint32;
           description "Number of packets discarded with no matching option-60";
         }
         leaf dropped-packet-option-82 {
           type uint32;
           description "Number of packets discarded because option-82 could not be added";
         }
         leaf dropped-packet-authentication {
           type uint32;
           description "Number of packets discarded because authentication failed";
         }
         leaf dropped-packet-dynamic-profile {
           type uint32;
           description "Number of packets discarded because a dynamic profile failed";
         }
         leaf dropped-packet-license {
           type uint32;
           description "Number of packets discarded because of a license failure";
         }
         leaf dropped-packet-bad-dhcp-opcode {
           type uint32;
           description "Number of packets discarded because of bad DHCP opcode";
         }
         leaf dropped-packet-no-options {
           type uint32;
           description "Number of packets discarded because of no options";
         }
         leaf dropped-packet-hop-limit {
           type uint32;
           description "Number of packets discarded because of hop limit reached";
         }
         leaf dropped-packet-ttl-expired {
           type uint32;
           description "Number of packets discarded because of ttl expired";
         }
         leaf dropped-packet-bad-udp-checksum {
           type uint32;
           description "Number of packets discarded because of bad udp checksum";
         }
         leaf dropped-packet-inactive-vlan {
           type uint32;
           description "Number of packets discarded because of inactive VLAN";
         }
         leaf dropped-packet-event-rate-analyzer {
           type uint32;
           description "Number of packets discarded because of ERA throttling";
         }
         leaf dropped-packet-client-lookup {
           type uint32;
           description "Number of packets discarded because no client binding was found";
         }
         leaf lease-time-violations-drop {
           type uint32;
           description "Packets dropped because of lease time violation";
         }
         leaf dropped-packet-dhcp-service-total {
           type uint32;
           description "Number of packets discarded at dhcp-service level";
         }
         leaf forwarded-packets-total {
           type uint32;
           description "Total number of packets forwarded";
         }
         leaf forwarded-bootrequest-packets {
           type uint32;
           description "Number of bootrequest packets forwarded";
         }
         leaf forwarded-bootreply-packets {
           type uint32;
           description "Number of bootreply packets forwarded";
         }
         container offer-delay-info {
           description "Information about offer delay queue status of the DHCP server";
           leaf delay-string {
             type string;
             description "Indicator of offer delay";
           }
           container queue {
             description "Information about the Delay Queue status";
             leaf delay-status {
               type string;
               description "Status of packets in delay queue";
             }
             leaf delay-count {
               type uint32;
               description "Number of packets in this status";
             }
           }
         }
         container message-table {
           description "Information about one or more DHCP or bootstrap protocol (BOOTP) messages sent or received by the DHCP server";
           leaf message-direction {
             type string;
             description "Indicator of whether the DHCP server sent or received the messages";
           }
           container message {
             description "Information about a DHCP or BOOTP message";
             leaf message-name {
               type string;
               description "Name of the message";
             }
             leaf message-count {
               type uint32;
               description "Number of times the DCHP server received or sent the message";
             }
           }
         }
       }
     }
   }
   rpc get-dhcp-server-bulk-leasequery-conn-statistics {
     description "Show DHCP server bulk leasequeery conn statistics";
     input {
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-server-bulk-leasequery-conn-statistics {
         leaf total-accepted-tcp-connections {
           type uint32;
           description "Number of accepted TCP connections";
         }
         leaf total-not-accepted-tcp-connections {
           type uint32;
           description "Number of not accepted TCP connections";
         }
         leaf tcp-connections-closed-due-to-error {
           type uint32;
           description "Number of connections closed due to error";
         }
         leaf tcp-connections-closed-due-to-max-empty-replies {
           type uint32;
           description "Number of connections closed due to max-empty-replies";
         }
         leaf in-flight-tcp-connections {
           type uint32;
           description "In-flight TCP connections";
         }
       }
     }
   }
   rpc get-dhcp-proxy-client-binding-information {
     description "Show DHCP proxy-client binding information";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-client-binding-information {
         container brief {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf releasing-count {
               type int32;
             }
             leaf declining-count {
               type int32;
             }
             leaf arpcheck-count {
               type int32;
             }
             leaf restore-count {
               type int32;
               description "Number of clients waiting to be restored";
             }
           }
           container dhcp-binding {
             description "Information about the address assigned to a Dynamic Host Configuration Protocol client";
             leaf allocated-address {
               type ipaddr;
               description "IPv4 or IPv6 address assigned to the DHCP client";
             }
             leaf mac-address {
               type mac-addr;
               description "Media access control (hardware) address of the DHCP client";
             }
             leaf lease-expires {
               type int32;
               description "Number of seconds lease will expire in";
             }
             leaf lease-state {
               type string;
               description "Status of the address assignment";
             }
             leaf interface-name {
               type string;
               description "Name of the interface via which the DHCP server transmitted the address assignment";
             }
             container dhcp-option-table {
               description "Information about one or more Dynamic Host Configuration Protocol options that are associated with the address assignment";
               container dhcp-option {
                 description "Information about a Dynamic Host Configuration Protocol option that is associated with the address assignment";
                 leaf dhcp-option-code {
                   type int32;
                   description "Numeric code assigned to the DHCP option";
                 }
                 leaf dhcp-option-name {
                   type string;
                   description "Name of the DHCP option";
                 }
                 leaf dhcp-option-type {
                   type string;
                   description "Type of value for the DHCP option (for example, string [word], integer, IP address)";
                 }
                 leaf dhcp-option-value {
                   type string;
                   description "Value of the DHCP option";
                 }
               }
             }
           }
         }
         container dhcpv6-client-brief {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf releasing-count {
               type int32;
             }
             leaf declining-count {
               type int32;
             }
             leaf arpcheck-count {
               type int32;
             }
             leaf restore-count {
               type int32;
               description "Number of clients waiting to be restored";
             }
           }
           container dhcp-binding {
             description "Information about the address assigned to a Dynamic Host Configuration Protocol client";
             leaf allocated-prefix {
               type string;
               description "IPv4 or IPv6 address assigned to the DHCP client";
             }
             leaf lease-expires {
               type int32;
               description "Number of seconds lease will expire in";
             }
             leaf lease-state {
               type string;
               description "Status of the address assignment";
             }
             leaf client-type {
               type string;
               description "Client type for the interface";
             }
             leaf interface-name {
               type string;
               description "Name of the interface via which the DHCP server transmitted the address assignment";
             }
             leaf client-duid {
               type string;
               description "Client duid of the client interface";
             }
             container dhcp-option-table {
               description "Information about one or more Dynamic Host Configuration Protocol options that are associated with the address assignment";
               container dhcp-option {
                 description "Information about a Dynamic Host Configuration Protocol option that is associated with the address assignment";
                 leaf dhcp-option-code {
                   type int32;
                   description "Numeric code assigned to the DHCP option";
                 }
                 leaf dhcp-option-name {
                   type string;
                   description "Name of the DHCP option";
                 }
                 leaf dhcp-option-type {
                   type string;
                   description "Type of value for the DHCP option (for example, string [word], integer, IP address)";
                 }
                 leaf dhcp-option-value {
                   type string;
                   description "Value of the DHCP option";
                 }
               }
             }
           }
         }
         container dhcpv6-client-brief-stateless {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf releasing-count {
               type int32;
             }
             leaf declining-count {
               type int32;
             }
             leaf arpcheck-count {
               type int32;
             }
             leaf restore-count {
               type int32;
               description "Number of clients waiting to be restored";
             }
           }
           container dhcp-binding {
             description "Information about the address assigned to a Dynamic Host Configuration Protocol client";
             leaf client-type {
               type string;
               description "Client type for the interface";
             }
             leaf lease-state {
               type string;
               description "Status of the address assignment";
             }
             leaf interface-name {
               type string;
               description "Name of the interface via which the DHCP server transmitted the address assignment";
             }
             leaf server-ip {
               type ipaddr;
               description "IP address of the DHCPV6 server";
             }
             leaf client-duid {
               type string;
               description "Client duid of the client interface";
             }
             container dhcp-option-table {
               description "Information about one or more Dynamic Host Configuration Protocol options that are associated with the address assignment";
               container dhcp-option {
                 description "Information about a Dynamic Host Configuration Protocol option that is associated with the address assignment";
                 leaf dhcp-option-code {
                   type int32;
                   description "Numeric code assigned to the DHCP option";
                 }
                 leaf dhcp-option-name {
                   type string;
                   description "Name of the DHCP option";
                 }
                 leaf dhcp-option-type {
                   type string;
                   description "Type of value for the DHCP option (for example, string [word], integer, IP address)";
                 }
                 leaf dhcp-option-value {
                   type string;
                   description "Value of the DHCP option";
                 }
               }
             }
           }
         }
         container detail {
           description "Information about the address assigned to each of one or more Dynamic Host Configuration Protocol clients";
           container binding-summary {
             leaf binding-count {
               type int32;
               description "Number of bindings in this routing instance";
             }
             leaf init-count {
               type int32;
             }
             leaf bound-count {
               type int32;
             }
             leaf selecting-count {
               type int32;
             }
             leaf requesting-count {
               type int32;
             }
             leaf renewing-count {
               type int32;
             }
             leaf releasing-count {
               type int32;
             }
             leaf declining-count {
               type int32;
             }
             leaf arpcheck-count {
               type int32;
             }
             leaf restore-count {
               type int32;
               description "Number of clients waiting to be restored";
             }
           }
           container dhcp-binding {
             description "Information about the address assigned to a Dynamic Host Configuration Protocol client";
             leaf interface-name {
               type string;
               description "Name of the interface via which the DHCP server transmitted the address assignment";
             }
             leaf mac-address {
               type mac-addr;
               description "Media access control (hardware) address of the DHCP client";
             }
             leaf lease-state {
               type string;
               description "Status of the address assignment";
             }
             leaf lease-end-time {
               type string;
               description "Time when the address assignment will expire, in the format YYYY-MM-DD hh:mm:ss TZ (year, month, date, hour in 24-hour format, minute, second, time zone). The value 'never' indicates that the lease does not expire";
             }
             leaf lease-expires {
               type int32;
               description "Number of seconds lease will expire in";
             }
             leaf lease-start-time {
               type string;
               description "Time when the client obtained the address assignment, in the format YYYY-MM-DD hh:mm:ss TZ (year, month, date, hour in 24-hour format, minute, second, time zone)";
             }
             leaf vlan-id {
               type int32;
               description "Vlan id of the client interface";
             }
             leaf svlan-id {
               type int32;
               description "Svlan id of the client interface";
             }
             leaf vendor-id {
               type string;
               description "Vendor identifier of the client interface";
             }
             leaf server-ip-address {
               type ipaddr;
               description "IP address of the DHCP server";
             }
             leaf client-duid {
               type string;
               description "Client duid of the client interface";
             }
             leaf client-type {
               type string;
               description "Client type for the interface";
             }
             leaf bind-type {
               type string;
               description "Client bind type for the interface";
             }
             leaf rapid-commit {
               type string;
               description "Rapid commit two msg exchange flag";
             }
             leaf server-ip {
               type ipaddr;
               description "IP address of the DHCPV6 server";
             }
             leaf allocated-address {
               type ipaddr;
               description "IPv4 or IPv6 address assigned to the DHCP client";
             }
             leaf requested-prefix {
               type string;
               description "IPv4 or IPv6 address assigned to the DHCP client";
             }
             leaf allocated-prefix {
               type string;
               description "IPv4 or IPv6 address assigned to the DHCP client";
             }
             leaf update-server {
               type string;
               description "Update server flag to update TCP/IP settings downstream";
             }
             leaf bootp-relay-address {
               type ipaddr;
               description "IP address of the bootstrap protocol server that relayed the address assigned by the DHCP server";
             }
             leaf previous-bootp-relay-address {
               type ipaddr;
               description "Previous IP address of the bootstrap protocol server that relayed the address assigned by the DHCP server";
             }
             leaf dhcp-lease-binding-type {
               type string;
               description "Type of the address assignment";
             }
             leaf client-id-len {
               type int32;
               description "Number of bytes in client id";
             }
             leaf client-id {
               type string;
               description "Client id";
             }
             leaf alt-client-id-len {
               type int32;
               description "Number of bytes in alternate client id";
             }
             leaf alt-client-id {
               type string;
               description "Alternate client id";
             }
             leaf client-option-type {
               type string;
               description "Type option 60 or option 82";
             }
             leaf client-option-len {
               type int32;
               description "Number of bytes in client option 60 / option 82 data";
             }
             leaf client-option-data {
               type string;
               description "Hex dump of client option 60 / option 82 data";
             }
             leaf option-82-length-from-client {
               type int32;
               description "Option 82 length from client";
             }
             leaf option-82-data-from-client {
               type string;
               description "Option 82 data from client";
             }
             leaf hardware-type {
               type string;
               description "Client hardware type";
             }
             leaf logical-system-routing-instance {
               type string;
               description "Client router context logical system and routing instance";
             }
             leaf bridge-domain {
               type string;
               description "Client router context bridge domain";
             }
             container dhcp-option-table {
               description "Information about one or more Dynamic Host Configuration Protocol options that are associated with the address assignment";
               container dhcp-option {
                 description "Information about a Dynamic Host Configuration Protocol option that is associated with the address assignment";
                 leaf dhcp-option-code {
                   type int32;
                   description "Numeric code assigned to the DHCP option";
                 }
                 leaf dhcp-option-name {
                   type string;
                   description "Name of the DHCP option";
                 }
                 leaf dhcp-option-type {
                   type string;
                   description "Type of value for the DHCP option (for example, string [word], integer, IP address)";
                 }
                 leaf dhcp-option-value {
                   type string;
                   description "Value of the DHCP option";
                 }
               }
             }
           }
         }
       }
     }
   }
   rpc get-proxy-dhcp-client-statistics-information {
     description "Show DHCP proxy-client statistics";
     input {
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container dhcp-proxy-client-statistics-information {
         container dhcp-client-statistics-information {
           description "Statistics from the Dynamic Host Configuration Protocol Client";
           leaf dropped-packet-total {
             type uint32;
             description "Total packet discard count for the DHCP interface";
           }
           leaf dropped-packet-bad-hardware {
             type uint32;
             description "Packets discarded due to invalid hardware address";
           }
           leaf dropped-packet-bad-bootp-opcode {
             type uint32;
             description "Packets discarded due to invalid operation code in bootp";
           }
           leaf dropped-packet-bad-options {
             type uint32;
             description "Packets discarded due to invalid option";
           }
           leaf dropped-packet-invalid-server-address {
             type uint32;
             description "Packets discarded due to invalid server address";
           }
           leaf dropped-packet-no-addresses {
             type uint32;
             description "Packets discarded due to no addresses available";
           }
           leaf dropped-packet-no-interface-cfg {
             type uint32;
             description "Packets discarded due to unconfigured interface";
           }
           leaf dropped-packet-no-routing-instance {
             type uint32;
             description "Number of packets discarded by the DHCP client because of a routing-instance mismatch";
           }
           leaf dropped-packet-no-local-address {
             type uint32;
             description "Packets discarded due to invalid local address";
           }
           leaf dropped-packet-too-short {
             type uint32;
             description "Packets discarded due to runt packets";
           }
           leaf dropped-packet-read-error {
             type uint32;
             description "Number of packets discarded by the DHCP client because of a read error";
           }
           leaf dropped-packet-send-error {
             type uint32;
             description "Packets discarded due to transmit error";
           }
           leaf dropped-packet-authentication {
             type uint32;
             description "Packets discarded due to authentication failure";
           }
           leaf dropped-packet-dynamic-profile {
             type uint32;
             description "Packets discarded due to dynamic profile failure";
           }
           leaf dropped-packet-license {
             type uint32;
             description "Packets discarded due to license failure";
           }
           leaf dropped-packet-bad-dhcp-opcode {
             type uint32;
             description "Packets discarded due to bad DHCP opcode";
           }
           leaf dropped-packet-no-options {
             type uint32;
             description "Packets discarded due to no DHCP options";
           }
           leaf forwarded-packets-total {
             type uint32;
             description "Total number of packets forwarded";
           }
           leaf forwarded-bootrequest-packets {
             type uint32;
             description "Number of bootrequest packets forwarded";
           }
           leaf forwarded-bootreply-packets {
             type uint32;
             description "Number of bootreply packets forwarded";
           }
           container message-table {
             description "Packet counts for DHCP messages sent or received by the dhcp client";
             leaf message-direction {
               type string;
               description "Indicates send or receive operation";
             }
             container message {
               description "Information about a DHCP or BOOTP message";
               leaf message-name {
                 type string;
                 description "Name of the message";
               }
               leaf message-count {
                 type uint32;
                 description "Number of times the DHCP client received or sent the message";
               }
             }
           }
         }
       }
     }
   }
   rpc get-dhcp-proxy-client-profile-servers-info {
     description "Show DHCP-Proxy server list of profile";
     input {
       leaf logical-system {
         description "Name of logical system";
         type string;
         mandatory true;
       }
       leaf routing-instance {
         description "Name of routing instance";
         type string;
         mandatory true;
       }
       leaf profile-name {
         description "Name of profile name";
         type string;
         mandatory true;
       }
     }
     output {
       container dhcp-proxy-client-profile-servers-information {
         container servers {
           description "Information about confiuration parameters";
           leaf server-ip-address {
             type ipaddr;
             description "IP address of the DHCP server";
           }
           leaf server-priority {
             type uint32;
             description "Priority of the DHCP server";
           }
           leaf server-status {
             type string;
             description "Status of the DHCP server";
           }
           leaf server-dead-timer {
             type string;
             description "Dead timer of the DHCP server";
           }
           leaf server-retry-count {
             type uint32;
             description "Retry count of the DHCP server";
           }
         }
       }
     }
   }
 }
