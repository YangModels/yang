/*
 * Copyright (c) 2017 Juniper Networks, Inc.
 * All rights reserved.
 */

 module show-virtual-chassis {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-virtual-chassis-information {
     description "Virtual chassis information";
     input {
       leaf verbosity_level {
         default "brief";
         type enumeration {
           enum "brief" {
             description "Display brief output (default)";
           }
           enum "detail" {
             description "Display detailed output";
           }
         }
       }
     }
     output {
       container virtual-chassis-information {
         leaf virtual-chassis-id {
           type string;
           description "Virtual Chassis identifier";
         }
         container preprovisioned-virtual-chassis-information {
           leaf virtual-chassis-mode {
             type string;
             description "Virtual Chassis Mode";
           }
           container fabric {
           }
         }
         container virtual-chassis-id-information {
           leaf virtual-chassis-id {
             type string;
             description "Virtual Chassis identifier";
           }
           leaf virtual-chassis-mode {
             type string;
             description "Virtual Chassis Mode";
           }
           container fabric {
           }
           container fabric-pnp {
             leaf virtual-chassis-id {
               type string;
               description "Virtual Chassis identifier";
             }
             leaf virtual-chassis-mode {
               type string;
               description "Virtual Chassis Mode";
             }
           }
         }
         container member-list {
           container dcf-slot {
             container member {
               leaf member-id {
                 type int32;
                 description "Member identifier";
               }
               leaf fpc-slot {
                 type int32;
                 description "FPC Slot Number";
               }
               leaf member-status {
                 type string;
                 description "Member's status";
               }
               leaf member-model {
                 type string;
                 description "Member's model";
               }
               leaf member-priority {
                 type int32;
                 description "Member's mastership priority";
               }
               leaf member-role {
                 type string;
                 description "Member's role";
               }
               leaf member-serial-number {
                 type string;
                 description "Member's serial number";
               }
               container neighbor-list {
               }
             }
           }
           container single-slot-alias {
             container member {
               leaf member-id {
                 type int32;
                 description "Member identifier";
               }
               leaf fpc-slot {
                 type int32;
                 description "FPC Slot Number";
               }
               leaf member-status {
                 type string;
                 description "Member's status";
               }
               leaf member-serial-number {
                 type string;
                 description "Member's serial number";
               }
               leaf member-alias-name {
                 type string;
                 description "Member's alias name";
               }
               leaf member-model {
                 type string;
                 description "Member's model";
               }
               leaf member-priority {
                 type int32;
                 description "Member's mastership priority";
               }
               leaf member-role {
                 type string;
                 description "Member's role";
               }
               leaf member-mixed-mode {
                 type string;
                 description "Member's mixed mode value";
               }
               leaf member-route-mode {
                 type string;
                 description "Member's route mode value";
               }
               container neighbor-list {
                 container neighbor {
                 }
               }
             }
           }
           container single-slot {
             container member {
               leaf member-id {
                 type int32;
                 description "Member identifier";
               }
               leaf fpc-slot {
                 type int32;
                 description "FPC Slot Number";
               }
               leaf member-status {
                 type string;
                 description "Member's status";
               }
               leaf member-serial-number {
                 type string;
                 description "Member's serial number";
               }
               leaf member-model {
                 type string;
                 description "Member's model";
               }
               leaf member-priority {
                 type int32;
                 description "Member's mastership priority";
               }
               leaf member-role {
                 type string;
                 description "Member's role";
               }
               leaf member-mixed-mode {
                 type string;
                 description "Member's mixed mode value";
               }
               leaf member-route-mode {
                 type string;
                 description "Member's route mode value";
               }
               container neighbor-list {
                 container neighbor {
                 }
               }
             }
           }
           container slot-range {
             container member {
               leaf member-id {
                 type int32;
                 description "Member identifier";
               }
               leaf fpc-slot-range {
                 type string;
                 description "FPC Slot Range";
               }
               leaf member-status {
                 type string;
                 description "Member's status";
               }
               leaf member-serial-number {
                 type string;
                 description "Member's serial number";
               }
               leaf member-model {
                 type string;
                 description "Member's model";
               }
               leaf member-priority {
                 type int32;
                 description "Member's mastership priority";
               }
               leaf member-role {
                 type string;
                 description "Member's role";
               }
               container neighbor-list {
                 container neighbor {
                 }
               }
             }
           }
           container detail {
             container member {
               leaf member-id {
                 type int32;
                 description "Member identifier";
               }
               leaf fpc-slot {
                 type int32;
                 description "FPC Slot Number";
               }
               leaf member-status {
                 type string;
                 description "Member's status";
               }
               leaf member-serial-number {
                 type string;
                 description "Member's serial number";
               }
               leaf member-model {
                 type string;
                 description "Member's model";
               }
               leaf member-priority {
                 type int32;
                 description "Member's mastership priority";
               }
               leaf member-role {
                 type string;
                 description "Member's role";
               }
               leaf member-mixed-mode {
                 type string;
                 description "Member's mixed mode value";
               }
               leaf member-route-mode {
                 type string;
                 description "Member's route mode value";
               }
               leaf member-location {
                 type string;
                 description "Member's location";
               }
               container neighbor-list {
                 container neighbor {
                 }
               }
             }
           }
           container detail-alias {
             container member {
               leaf member-id {
                 type int32;
                 description "Member identifier";
               }
               leaf fpc-slot {
                 type int32;
                 description "FPC Slot Number";
               }
               leaf member-status {
                 type string;
                 description "Member's status";
               }
               leaf member-serial-number {
                 type string;
                 description "Member's serial number";
               }
               leaf member-alias-name {
                 type string;
                 description "Member's alias name";
               }
               leaf member-model {
                 type string;
                 description "Member's model";
               }
               leaf member-priority {
                 type int32;
                 description "Member's mastership priority";
               }
               leaf member-role {
                 type string;
                 description "Member's role";
               }
               leaf member-mixed-mode {
                 type string;
                 description "Member's mixed mode value";
               }
               leaf member-route-mode {
                 type string;
                 description "Member's route mode value";
               }
               leaf member-location {
                 type string;
                 description "Member's location";
               }
               container neighbor-list {
                 container neighbor {
                 }
               }
             }
           }
           container detail-slot-range {
             container member {
               leaf member-id {
                 type int32;
                 description "Member identifier";
               }
               leaf fpc-slot-range {
                 type string;
                 description "FPC Slot Range";
               }
               leaf member-status {
                 type string;
                 description "Member's status";
               }
               leaf member-serial-number {
                 type string;
                 description "Member's serial number";
               }
               leaf member-model {
                 type string;
                 description "Member's model";
               }
               leaf member-priority {
                 type int32;
                 description "Member's mastership priority";
               }
               leaf member-role {
                 type string;
                 description "Member's role";
               }
               leaf member-location {
                 type string;
                 description "Member's location";
               }
               container neighbor-list {
                 container neighbor {
                 }
               }
             }
           }
         }
         container next-member-information {
           leaf next-member-id {
             type int32;
             description "Next member ID";
           }
           leaf next-fpc-slot {
             type int32;
             description "Next FPC Slot";
           }
         }
       }
     }
   }
   rpc get-virtual-chassis-adjacency-information {
     description "Show virtual chassis adjacency database";
     input {
       leaf verbosity_level {
         default "brief";
         type enumeration {
           enum "brief" {
             description "Display brief output (default)";
           }
           enum "detail" {
             description "Display detailed output";
           }
           enum "extensive" {
             description "Display extensive output";
           }
         }
       }
       leaf system-id {
         description "System ID of neighbor";
         type string;
       }
     }
     output {
       container virtual-chassis-adjacency-information {
         container brief {
           container vccp-adjacency {
             leaf interface-name {
               type string;
             }
             leaf system-name {
               type string;
               description "Hostname of a system";
             }
             leaf adjacency-state {
               type string;
               description "State of the adjacency";
             }
             leaf holdtime {
               type int32;
             }
             leaf adjacency-flag {
               type string;
             }
           }
         }
         container detail {
           container vccp-adjacency {
             leaf system-name {
               type string;
               description "Hostname of a system";
             }
             leaf interface-name {
               type string;
             }
             leaf adjacency-state {
               type string;
               description "State of the adjacency";
             }
             leaf holdtime {
               type int32;
             }
             leaf interface-priority {
               type int32;
             }
             leaf transition-count {
               type int32;
             }
             leaf last-transition-time {
               type string;
             }
             leaf adjacency-flag {
               type string;
             }
           }
         }
         container extensive {
           container vccp-adjacency {
             leaf system-name {
               type string;
               description "Hostname of a system";
             }
             leaf interface-name {
               type string;
             }
             leaf adjacency-state {
               type string;
               description "State of the adjacency";
             }
             leaf holdtime {
               type int32;
             }
             leaf interface-priority {
               type int32;
             }
             leaf transition-count {
               type int32;
             }
             leaf last-transition-time {
               type string;
             }
             leaf adjacency-flag {
               type string;
             }
             container vccp-adjacency-log {
               description "Entry describing adjacency transition";
               leaf adjacency-when {
                 type string;
                 description "Time at which the transition occurred";
               }
               leaf adjacency-event {
                 type string;
                 description "Event that triggered the transition";
               }
               leaf adjacency-down-reason {
                 type string;
                 description "Reason for the down transition event";
               }
             }
           }
         }
       }
     }
   }
   rpc get-virtual-chassis-database-information {
     description "Show virtual chassis link-state database";
     input {
       leaf verbosity_level {
         default "brief";
         type enumeration {
           enum "brief" {
             description "Display brief output (default)";
           }
           enum "detail" {
             description "Display detailed output";
           }
           enum "extensive" {
             description "Display extensive output";
           }
         }
       }
       leaf system-id {
         description "System ID of neighbor";
         type string;
       }
     }
     output {
       container virtual-chassis-database-information {
         container brief {
           container vccp-database {
             leaf lsp-count {
               type int32;
             }
             container vccp-database-entry {
               leaf lsp-id {
                 type string;
               }
               leaf sequence-number {
                 type int32;
               }
               leaf checksum {
                 type int32;
               }
               leaf remaining-lifetime {
                 type int32;
               }
               container vccp-tlv {
                 container vccp-tlv-overhead {
                   leaf tlv-type {
                     type int32;
                   }
                   leaf tlv-length {
                     type int32;
                   }
                   leaf bytes-left {
                     type int32;
                   }
                 }
                 container reachability-tlv {
                   leaf reachability-tlv.heading {
                     type string;
                   }
                   leaf system-name {
                     type string;
                     description "Hostname of a system";
                   }
                   leaf interface-name {
                     type string;
                   }
                   leaf metric {
                     type int32;
                   }
                   leaf tlv-length {
                     type int32;
                   }
                 }
                 container node-info-tlv {
                   leaf node-info-tlv.heading {
                     type string;
                   }
                   leaf member-id {
                     type int32;
                     description "Member identifier";
                   }
                   leaf vc-id {
                     type string;
                   }
                   leaf ni-flags {
                     type int32;
                   }
                   leaf mastership-priority {
                     type int32;
                   }
                   container device-info {
                     leaf system-name {
                       type string;
                       description "Hostname of a system";
                     }
                     leaf device-id {
                       type uint32;
                     }
                   }
                   container dcp-device-information {
                     leaf vc-mode {
                       type string;
                     }
                     leaf vc-size {
                       type uint32;
                     }
                     leaf my-master-id {
                       type string;
                     }
                     leaf device-physical-id {
                       type string;
                     }
                     leaf dcp-system-id {
                       type string;
                     }
                     leaf dcp-device-id {
                       type uint32;
                     }
                     leaf device-physical-type {
                       type string;
                     }
                     leaf dcp-vdcf-id {
                       type uint32;
                     }
                     leaf dcp-device-start-ppfe-id {
                       type uint32;
                     }
                     leaf dcp-device-ppfe-count {
                       type uint32;
                     }
                     leaf logical-function-bitmap {
                       type uint32;
                     }
                     leaf dcp-device-flags {
                       type string;
                     }
                     leaf dcp-device-name {
                       type string;
                     }
                   }
                 }
                 container dynamic-hostname-tlv {
                   leaf hostname {
                     type string;
                   }
                 }
                 container dcp-atomicity-tlv {
                   leaf dcp-atomicity-tlv.heading {
                     type string;
                   }
                   leaf fragment-offset {
                     type uint32;
                   }
                   leaf fragment-count {
                     type uint32;
                   }
                   container fragment-sequence-number-list {
                     leaf fragment-id {
                       type uint32;
                     }
                     leaf sequence-number {
                       type int32;
                     }
                   }
                 }
                 container dcp-vdcf-information-tlv {
                   leaf dcp-vdcf-information-tlv.heading {
                     type string;
                   }
                   leaf dcp-vdcf-id {
                     type uint32;
                   }
                   leaf dcp-vdcf-name {
                     type string;
                   }
                   leaf vdcf-flags {
                     type uint32;
                   }
                 }
                 container dcp-dynamic-device-tlv {
                   leaf dcp-dynamic-device-tlv.heading {
                     type string;
                   }
                   leaf dynamic-device-id {
                     type uint32;
                   }
                   leaf dynamic-device-name {
                     type string;
                   }
                   leaf dynamic-device-type {
                     type uint32;
                   }
                   leaf dynamic-device-physical-type {
                     type uint32;
                   }
                   leaf dynamic-flags {
                     type uint32;
                   }
                 }
                 container dcp-device-information-tlv {
                   leaf dcp-device-information-tlv.heading {
                     type string;
                   }
                   leaf device-system-id {
                     type string;
                   }
                   leaf device-vdcf-id {
                     type uint32;
                   }
                   leaf dcp-device-id {
                     type uint32;
                   }
                   leaf dcp-device-start-ppfe-id {
                     type uint32;
                   }
                   leaf dcp-device-ppfe-count {
                     type uint32;
                   }
                   leaf device-name {
                     type string;
                   }
                   leaf device-flags {
                     type uint32;
                   }
                   leaf device-physical-id {
                     type string;
                   }
                 }
                 container dcp-ine-information-tlv {
                   leaf dcp-ine-information-tlv.heading {
                     type string;
                   }
                   leaf vdcf-id {
                     type uint32;
                   }
                   leaf ine-id {
                     type uint32;
                   }
                   leaf ine-name {
                     type string;
                   }
                   leaf logical-function-bitmap {
                     type uint32;
                   }
                   leaf ine-flags {
                     type uint32;
                   }
                 }
                 container dcp-ine-membership-information-tlv {
                   leaf dcp-ine-membership-information-tlv.heading {
                     type string;
                   }
                   leaf ine-system-id {
                     type string;
                   }
                   leaf ine-id {
                     type uint32;
                   }
                   leaf ine-slot {
                     type uint32;
                   }
                   leaf ine-member-flags {
                     type uint32;
                   }
                 }
                 container dcp-product-category-tlv {
                   leaf dcp-product-category-tlv.heading {
                     type string;
                   }
                   leaf product-category {
                     type string;
                   }
                 }
                 container dcp-node-ic-connectivity-map-tlv {
                   leaf dcp-node-ic-connectivity-map-tlv.heading {
                     type string;
                   }
                   leaf chip-id {
                     type uint32;
                   }
                   leaf node-ic-connectivity-map {
                     type string;
                   }
                 }
                 container master-info-tlv {
                   leaf master-info-tlv.heading {
                     type string;
                   }
                   leaf system-name {
                     type string;
                     description "Hostname of a system";
                   }
                 }
                 container backup-info-tlv {
                   leaf backup-info-tlv.heading {
                     type string;
                   }
                   leaf system-name {
                     type string;
                     description "Hostname of a system";
                   }
                 }
                 container stable-state-tlv {
                   leaf stable-state-tlv.heading {
                     type string;
                   }
                   leaf stable-master {
                     type string;
                   }
                   leaf stable-backup {
                     type string;
                   }
                 }
                 container route-tlv {
                   leaf route-tlv.heading {
                     type string;
                   }
                   leaf unicast {
                     type string;
                   }
                   leaf multicast {
                     type string;
                   }
                   leaf vcf-route-mode {
                     type int32;
                   }
                   leaf vcf-provision-mode {
                     type int32;
                   }
                   leaf vcf-route-preference {
                     type int32;
                   }
                 }
                 container me-sync-tlv {
                   leaf me-sync-tlv.heading {
                     type string;
                   }
                   leaf state {
                     type int32;
                   }
                   leaf duration {
                     type int32;
                   }
                 }
                 container topology-hash-tlv {
                   leaf topology-hash-tlv.heading {
                     type string;
                   }
                   leaf vcf-topology-hash {
                     type int32;
                   }
                 }
                 container member-info-tlv {
                   leaf member-info-tlv.heading {
                     type string;
                   }
                   leaf system-name {
                     type string;
                     description "Hostname of a system";
                   }
                   leaf member-id {
                     type int32;
                     description "Member identifier";
                   }
                   leaf member-role {
                     type string;
                     description "Member's role";
                   }
                   container device-info {
                     leaf device-id {
                       type uint32;
                     }
                   }
                 }
                 container topology-tlv {
                   leaf topology-tlv.heading {
                     type string;
                   }
                   leaf system-name {
                     type string;
                     description "Hostname of a system";
                   }
                 }
                 container provision-tlv {
                   leaf provision-tlv.heading {
                     type string;
                   }
                   leaf member-id {
                     type int32;
                     description "Member identifier";
                   }
                   leaf serial-number {
                     type string;
                     description "Serial number of a system";
                   }
                 }
                 container dcf-fabric-device-information-tlv {
                 }
                 container iri-tlv {
                   leaf iri-tlv.heading {
                     type string;
                   }
                   leaf ip-address {
                     type ipaddr;
                     description "IRI IP address";
                   }
                 }
                 container me-link-status-tlv {
                   leaf me-link-status-tlv.heading {
                     type string;
                   }
                   leaf link-state {
                     type int32;
                   }
                 }
                 container port-info-tlv {
                   leaf port-info-tlv.heading {
                     type string;
                   }
                   leaf port-interface {
                     type string;
                   }
                   leaf port-state {
                     type int32;
                   }
                 }
                 container version-information-tlv {
                   leaf version-information-tlv.heading {
                     type string;
                   }
                   leaf software-major {
                     type int32;
                   }
                   leaf software-minor {
                     type int32;
                   }
                   leaf software-category {
                     type string;
                   }
                   leaf software-build {
                     type string;
                   }
                   leaf software-spin {
                     type int32;
                   }
                 }
                 container member-fpc-slots-tlv {
                   leaf member-fpc-slots-tlv.heading {
                     type string;
                   }
                   leaf member-fpc-slots {
                     type int32;
                   }
                 }
                 container unknown-tlv {
                   leaf tlv-type {
                     type int32;
                   }
                   leaf tlv-length {
                     type int32;
                   }
                 }
                 container tlv-stragglers {
                   leaf bytes-left {
                     type int32;
                   }
                 }
               }
             }
           }
         }
         container detail {
           container vccp-database {
             container vccp-database-entry {
               leaf lsp-id {
                 type string;
               }
               leaf sequence-number {
                 type int32;
               }
               leaf checksum {
                 type int32;
               }
               leaf remaining-lifetime {
                 type int32;
               }
               leaf lsp-stub {
                 type empty;
               }
               container vccp-isis-neighbor {
                 leaf is-neighbor-id {
                   type string;
                 }
                 leaf interface-name {
                   type string;
                 }
                 leaf metric {
                   type int32;
                 }
               }
               container vccp-tlv {
                 container vccp-tlv-overhead {
                   leaf tlv-type {
                     type int32;
                   }
                   leaf tlv-length {
                     type int32;
                   }
                   leaf bytes-left {
                     type int32;
                   }
                 }
                 container reachability-tlv {
                   leaf reachability-tlv.heading {
                     type string;
                   }
                   leaf system-name {
                     type string;
                     description "Hostname of a system";
                   }
                   leaf interface-name {
                     type string;
                   }
                   leaf metric {
                     type int32;
                   }
                   leaf tlv-length {
                     type int32;
                   }
                 }
                 container node-info-tlv {
                   leaf node-info-tlv.heading {
                     type string;
                   }
                   leaf member-id {
                     type int32;
                     description "Member identifier";
                   }
                   leaf vc-id {
                     type string;
                   }
                   leaf ni-flags {
                     type int32;
                   }
                   leaf mastership-priority {
                     type int32;
                   }
                   container device-info {
                     leaf system-name {
                       type string;
                       description "Hostname of a system";
                     }
                     leaf device-id {
                       type uint32;
                     }
                   }
                   container dcp-device-information {
                     leaf vc-mode {
                       type string;
                     }
                     leaf vc-size {
                       type uint32;
                     }
                     leaf my-master-id {
                       type string;
                     }
                     leaf device-physical-id {
                       type string;
                     }
                     leaf dcp-system-id {
                       type string;
                     }
                     leaf dcp-device-id {
                       type uint32;
                     }
                     leaf device-physical-type {
                       type string;
                     }
                     leaf dcp-vdcf-id {
                       type uint32;
                     }
                     leaf dcp-device-start-ppfe-id {
                       type uint32;
                     }
                     leaf dcp-device-ppfe-count {
                       type uint32;
                     }
                     leaf logical-function-bitmap {
                       type uint32;
                     }
                     leaf dcp-device-flags {
                       type string;
                     }
                     leaf dcp-device-name {
                       type string;
                     }
                   }
                 }
                 container dynamic-hostname-tlv {
                   leaf hostname {
                     type string;
                   }
                 }
                 container dcp-atomicity-tlv {
                   leaf dcp-atomicity-tlv.heading {
                     type string;
                   }
                   leaf fragment-offset {
                     type uint32;
                   }
                   leaf fragment-count {
                     type uint32;
                   }
                   container fragment-sequence-number-list {
                     leaf fragment-id {
                       type uint32;
                     }
                     leaf sequence-number {
                       type int32;
                     }
                   }
                 }
                 container dcp-vdcf-information-tlv {
                   leaf dcp-vdcf-information-tlv.heading {
                     type string;
                   }
                   leaf dcp-vdcf-id {
                     type uint32;
                   }
                   leaf dcp-vdcf-name {
                     type string;
                   }
                   leaf vdcf-flags {
                     type uint32;
                   }
                 }
                 container dcp-dynamic-device-tlv {
                   leaf dcp-dynamic-device-tlv.heading {
                     type string;
                   }
                   leaf dynamic-device-id {
                     type uint32;
                   }
                   leaf dynamic-device-name {
                     type string;
                   }
                   leaf dynamic-device-type {
                     type uint32;
                   }
                   leaf dynamic-device-physical-type {
                     type uint32;
                   }
                   leaf dynamic-flags {
                     type uint32;
                   }
                 }
                 container dcp-device-information-tlv {
                   leaf dcp-device-information-tlv.heading {
                     type string;
                   }
                   leaf device-system-id {
                     type string;
                   }
                   leaf device-vdcf-id {
                     type uint32;
                   }
                   leaf dcp-device-id {
                     type uint32;
                   }
                   leaf dcp-device-start-ppfe-id {
                     type uint32;
                   }
                   leaf dcp-device-ppfe-count {
                     type uint32;
                   }
                   leaf device-name {
                     type string;
                   }
                   leaf device-flags {
                     type uint32;
                   }
                   leaf device-physical-id {
                     type string;
                   }
                 }
                 container dcp-ine-information-tlv {
                   leaf dcp-ine-information-tlv.heading {
                     type string;
                   }
                   leaf vdcf-id {
                     type uint32;
                   }
                   leaf ine-id {
                     type uint32;
                   }
                   leaf ine-name {
                     type string;
                   }
                   leaf logical-function-bitmap {
                     type uint32;
                   }
                   leaf ine-flags {
                     type uint32;
                   }
                 }
                 container dcp-ine-membership-information-tlv {
                   leaf dcp-ine-membership-information-tlv.heading {
                     type string;
                   }
                   leaf ine-system-id {
                     type string;
                   }
                   leaf ine-id {
                     type uint32;
                   }
                   leaf ine-slot {
                     type uint32;
                   }
                   leaf ine-member-flags {
                     type uint32;
                   }
                 }
                 container dcp-product-category-tlv {
                   leaf dcp-product-category-tlv.heading {
                     type string;
                   }
                   leaf product-category {
                     type string;
                   }
                 }
                 container dcp-node-ic-connectivity-map-tlv {
                   leaf dcp-node-ic-connectivity-map-tlv.heading {
                     type string;
                   }
                   leaf chip-id {
                     type uint32;
                   }
                   leaf node-ic-connectivity-map {
                     type string;
                   }
                 }
                 container master-info-tlv {
                   leaf master-info-tlv.heading {
                     type string;
                   }
                   leaf system-name {
                     type string;
                     description "Hostname of a system";
                   }
                 }
                 container backup-info-tlv {
                   leaf backup-info-tlv.heading {
                     type string;
                   }
                   leaf system-name {
                     type string;
                     description "Hostname of a system";
                   }
                 }
                 container stable-state-tlv {
                   leaf stable-state-tlv.heading {
                     type string;
                   }
                   leaf stable-master {
                     type string;
                   }
                   leaf stable-backup {
                     type string;
                   }
                 }
                 container route-tlv {
                   leaf route-tlv.heading {
                     type string;
                   }
                   leaf unicast {
                     type string;
                   }
                   leaf multicast {
                     type string;
                   }
                   leaf vcf-route-mode {
                     type int32;
                   }
                   leaf vcf-provision-mode {
                     type int32;
                   }
                   leaf vcf-route-preference {
                     type int32;
                   }
                 }
                 container me-sync-tlv {
                   leaf me-sync-tlv.heading {
                     type string;
                   }
                   leaf state {
                     type int32;
                   }
                   leaf duration {
                     type int32;
                   }
                 }
                 container topology-hash-tlv {
                   leaf topology-hash-tlv.heading {
                     type string;
                   }
                   leaf vcf-topology-hash {
                     type int32;
                   }
                 }
                 container member-info-tlv {
                   leaf member-info-tlv.heading {
                     type string;
                   }
                   leaf system-name {
                     type string;
                     description "Hostname of a system";
                   }
                   leaf member-id {
                     type int32;
                     description "Member identifier";
                   }
                   leaf member-role {
                     type string;
                     description "Member's role";
                   }
                   container device-info {
                     leaf device-id {
                       type uint32;
                     }
                   }
                 }
                 container topology-tlv {
                   leaf topology-tlv.heading {
                     type string;
                   }
                   leaf system-name {
                     type string;
                     description "Hostname of a system";
                   }
                 }
                 container provision-tlv {
                   leaf provision-tlv.heading {
                     type string;
                   }
                   leaf member-id {
                     type int32;
                     description "Member identifier";
                   }
                   leaf serial-number {
                     type string;
                     description "Serial number of a system";
                   }
                 }
                 container dcf-fabric-device-information-tlv {
                 }
                 container iri-tlv {
                   leaf iri-tlv.heading {
                     type string;
                   }
                   leaf ip-address {
                     type ipaddr;
                     description "IRI IP address";
                   }
                 }
                 container me-link-status-tlv {
                   leaf me-link-status-tlv.heading {
                     type string;
                   }
                   leaf link-state {
                     type int32;
                   }
                 }
                 container port-info-tlv {
                   leaf port-info-tlv.heading {
                     type string;
                   }
                   leaf port-interface {
                     type string;
                   }
                   leaf port-state {
                     type int32;
                   }
                 }
                 container version-information-tlv {
                   leaf version-information-tlv.heading {
                     type string;
                   }
                   leaf software-major {
                     type int32;
                   }
                   leaf software-minor {
                     type int32;
                   }
                   leaf software-category {
                     type string;
                   }
                   leaf software-build {
                     type string;
                   }
                   leaf software-spin {
                     type int32;
                   }
                 }
                 container member-fpc-slots-tlv {
                   leaf member-fpc-slots-tlv.heading {
                     type string;
                   }
                   leaf member-fpc-slots {
                     type int32;
                   }
                 }
                 container unknown-tlv {
                   leaf tlv-type {
                     type int32;
                   }
                   leaf tlv-length {
                     type int32;
                   }
                 }
                 container tlv-stragglers {
                   leaf bytes-left {
                     type int32;
                   }
                 }
               }
             }
           }
         }
         container extensive {
           container vccp-database {
             container vccp-database-entry {
               leaf lsp-id {
                 type string;
               }
               leaf sequence-number {
                 type int32;
               }
               leaf checksum {
                 type int32;
               }
               leaf remaining-lifetime {
                 type int32;
               }
               leaf lsp-stub {
                 type empty;
               }
               container vccp-isis-neighbor {
                 leaf is-neighbor-id {
                   type string;
                 }
                 leaf interface-name {
                   type string;
                 }
                 leaf metric {
                   type int32;
                 }
               }
               container vccp-header {
                 leaf lsp-id {
                   type string;
                 }
                 leaf pdu-length {
                   type int32;
                 }
                 leaf allocated-length {
                   type int32;
                 }
                 leaf remaining-lifetime {
                   type int32;
                 }
                 leaf interface-index {
                   type int32;
                 }
                 leaf estimated-free-bytes {
                   type int32;
                 }
                 leaf actual-free-bytes {
                   type int32;
                 }
                 leaf lsdb-timer-type {
                   type string;
                 }
                 leaf lsdb-expiration-time {
                   type int32;
                 }
                 leaf needs-rebuild {
                   type empty;
                 }
               }
               container vccp-packet {
                 leaf lsp-id {
                   type string;
                 }
                 leaf pdu-length {
                   type int32;
                 }
                 leaf pdu-lifetime {
                   type int32;
                 }
                 leaf checksum {
                   type int32;
                 }
                 leaf sequence-number {
                   type int32;
                 }
                 leaf lsp-length {
                   type int32;
                 }
                 leaf pdu-version {
                   type int32;
                 }
                 leaf system-id-length {
                   type int32;
                 }
                 leaf vccp-packet-type {
                   type int32;
                 }
                 leaf software-major-version {
                   type int32;
                 }
                 leaf software-minor-version {
                   type int32;
                 }
               }
               container vccp-tlv {
                 leaf vccp-tlv.heading {
                   type string;
                 }
                 container vccp-tlv-overhead {
                   leaf tlv-type {
                     type int32;
                   }
                   leaf tlv-length {
                     type int32;
                   }
                   leaf bytes-left {
                     type int32;
                   }
                 }
                 container reachability-tlv {
                   leaf reachability-tlv.heading {
                     type string;
                   }
                   leaf system-name {
                     type string;
                     description "Hostname of a system";
                   }
                   leaf interface-name {
                     type string;
                   }
                   leaf metric {
                     type int32;
                   }
                   leaf tlv-length {
                     type int32;
                   }
                 }
                 container node-info-tlv {
                   leaf node-info-tlv.heading {
                     type string;
                   }
                   leaf member-id {
                     type int32;
                     description "Member identifier";
                   }
                   leaf vc-id {
                     type string;
                   }
                   leaf ni-flags {
                     type int32;
                   }
                   leaf mastership-priority {
                     type int32;
                   }
                   container device-info {
                     leaf system-name {
                       type string;
                       description "Hostname of a system";
                     }
                     leaf device-id {
                       type uint32;
                     }
                   }
                   container dcp-device-information {
                     leaf vc-mode {
                       type string;
                     }
                     leaf vc-size {
                       type uint32;
                     }
                     leaf my-master-id {
                       type string;
                     }
                     leaf device-physical-id {
                       type string;
                     }
                     leaf dcp-system-id {
                       type string;
                     }
                     leaf dcp-device-id {
                       type uint32;
                     }
                     leaf device-physical-type {
                       type string;
                     }
                     leaf dcp-vdcf-id {
                       type uint32;
                     }
                     leaf dcp-device-start-ppfe-id {
                       type uint32;
                     }
                     leaf dcp-device-ppfe-count {
                       type uint32;
                     }
                     leaf logical-function-bitmap {
                       type uint32;
                     }
                     leaf dcp-device-flags {
                       type string;
                     }
                     leaf dcp-device-name {
                       type string;
                     }
                   }
                 }
                 container dynamic-hostname-tlv {
                   leaf hostname {
                     type string;
                   }
                 }
                 container dcp-atomicity-tlv {
                   leaf dcp-atomicity-tlv.heading {
                     type string;
                   }
                   leaf fragment-offset {
                     type uint32;
                   }
                   leaf fragment-count {
                     type uint32;
                   }
                   container fragment-sequence-number-list {
                     leaf fragment-id {
                       type uint32;
                     }
                     leaf sequence-number {
                       type int32;
                     }
                   }
                 }
                 container dcp-vdcf-information-tlv {
                   leaf dcp-vdcf-information-tlv.heading {
                     type string;
                   }
                   leaf dcp-vdcf-id {
                     type uint32;
                   }
                   leaf dcp-vdcf-name {
                     type string;
                   }
                   leaf vdcf-flags {
                     type uint32;
                   }
                 }
                 container dcp-dynamic-device-tlv {
                   leaf dcp-dynamic-device-tlv.heading {
                     type string;
                   }
                   leaf dynamic-device-id {
                     type uint32;
                   }
                   leaf dynamic-device-name {
                     type string;
                   }
                   leaf dynamic-device-type {
                     type uint32;
                   }
                   leaf dynamic-device-physical-type {
                     type uint32;
                   }
                   leaf dynamic-flags {
                     type uint32;
                   }
                 }
                 container dcp-device-information-tlv {
                   leaf dcp-device-information-tlv.heading {
                     type string;
                   }
                   leaf device-system-id {
                     type string;
                   }
                   leaf device-vdcf-id {
                     type uint32;
                   }
                   leaf dcp-device-id {
                     type uint32;
                   }
                   leaf dcp-device-start-ppfe-id {
                     type uint32;
                   }
                   leaf dcp-device-ppfe-count {
                     type uint32;
                   }
                   leaf device-name {
                     type string;
                   }
                   leaf device-flags {
                     type uint32;
                   }
                   leaf device-physical-id {
                     type string;
                   }
                 }
                 container dcp-ine-information-tlv {
                   leaf dcp-ine-information-tlv.heading {
                     type string;
                   }
                   leaf vdcf-id {
                     type uint32;
                   }
                   leaf ine-id {
                     type uint32;
                   }
                   leaf ine-name {
                     type string;
                   }
                   leaf logical-function-bitmap {
                     type uint32;
                   }
                   leaf ine-flags {
                     type uint32;
                   }
                 }
                 container dcp-ine-membership-information-tlv {
                   leaf dcp-ine-membership-information-tlv.heading {
                     type string;
                   }
                   leaf ine-system-id {
                     type string;
                   }
                   leaf ine-id {
                     type uint32;
                   }
                   leaf ine-slot {
                     type uint32;
                   }
                   leaf ine-member-flags {
                     type uint32;
                   }
                 }
                 container dcp-product-category-tlv {
                   leaf dcp-product-category-tlv.heading {
                     type string;
                   }
                   leaf product-category {
                     type string;
                   }
                 }
                 container dcp-node-ic-connectivity-map-tlv {
                   leaf dcp-node-ic-connectivity-map-tlv.heading {
                     type string;
                   }
                   leaf chip-id {
                     type uint32;
                   }
                   leaf node-ic-connectivity-map {
                     type string;
                   }
                 }
                 container master-info-tlv {
                   leaf master-info-tlv.heading {
                     type string;
                   }
                   leaf system-name {
                     type string;
                     description "Hostname of a system";
                   }
                 }
                 container backup-info-tlv {
                   leaf backup-info-tlv.heading {
                     type string;
                   }
                   leaf system-name {
                     type string;
                     description "Hostname of a system";
                   }
                 }
                 container stable-state-tlv {
                   leaf stable-state-tlv.heading {
                     type string;
                   }
                   leaf stable-master {
                     type string;
                   }
                   leaf stable-backup {
                     type string;
                   }
                 }
                 container route-tlv {
                   leaf route-tlv.heading {
                     type string;
                   }
                   leaf unicast {
                     type string;
                   }
                   leaf multicast {
                     type string;
                   }
                   leaf vcf-route-mode {
                     type int32;
                   }
                   leaf vcf-provision-mode {
                     type int32;
                   }
                   leaf vcf-route-preference {
                     type int32;
                   }
                 }
                 container me-sync-tlv {
                   leaf me-sync-tlv.heading {
                     type string;
                   }
                   leaf state {
                     type int32;
                   }
                   leaf duration {
                     type int32;
                   }
                 }
                 container topology-hash-tlv {
                   leaf topology-hash-tlv.heading {
                     type string;
                   }
                   leaf vcf-topology-hash {
                     type int32;
                   }
                 }
                 container member-info-tlv {
                   leaf member-info-tlv.heading {
                     type string;
                   }
                   leaf system-name {
                     type string;
                     description "Hostname of a system";
                   }
                   leaf member-id {
                     type int32;
                     description "Member identifier";
                   }
                   leaf member-role {
                     type string;
                     description "Member's role";
                   }
                   container device-info {
                     leaf device-id {
                       type uint32;
                     }
                   }
                 }
                 container topology-tlv {
                   leaf topology-tlv.heading {
                     type string;
                   }
                   leaf system-name {
                     type string;
                     description "Hostname of a system";
                   }
                 }
                 container provision-tlv {
                   leaf provision-tlv.heading {
                     type string;
                   }
                   leaf member-id {
                     type int32;
                     description "Member identifier";
                   }
                   leaf serial-number {
                     type string;
                     description "Serial number of a system";
                   }
                 }
                 container dcf-fabric-device-information-tlv {
                 }
                 container iri-tlv {
                   leaf iri-tlv.heading {
                     type string;
                   }
                   leaf ip-address {
                     type ipaddr;
                     description "IRI IP address";
                   }
                 }
                 container me-link-status-tlv {
                   leaf me-link-status-tlv.heading {
                     type string;
                   }
                   leaf link-state {
                     type int32;
                   }
                 }
                 container port-info-tlv {
                   leaf port-info-tlv.heading {
                     type string;
                   }
                   leaf port-interface {
                     type string;
                   }
                   leaf port-state {
                     type int32;
                   }
                 }
                 container version-information-tlv {
                   leaf version-information-tlv.heading {
                     type string;
                   }
                   leaf software-major {
                     type int32;
                   }
                   leaf software-minor {
                     type int32;
                   }
                   leaf software-category {
                     type string;
                   }
                   leaf software-build {
                     type string;
                   }
                   leaf software-spin {
                     type int32;
                   }
                 }
                 container member-fpc-slots-tlv {
                   leaf member-fpc-slots-tlv.heading {
                     type string;
                   }
                   leaf member-fpc-slots {
                     type int32;
                   }
                 }
                 container unknown-tlv {
                   leaf tlv-type {
                     type int32;
                   }
                   leaf tlv-length {
                     type int32;
                   }
                 }
                 container tlv-stragglers {
                   leaf bytes-left {
                     type int32;
                   }
                 }
               }
               container transmission-status {
                 leaf transmit-count {
                   type int32;
                 }
                 leaf message {
                   type string;
                 }
                 leaf interface-name {
                   type string;
                 }
                 leaf transmit-time {
                   type string;
                   description "Time to queue this message for transmission";
                 }
               }
             }
           }
         }
       }
     }
   }
   rpc get-virtual-chassis-interface-information {
     description "Show virtual chassis protocol interface information";
     input {
       leaf verbosity_level {
         default "brief";
         type enumeration {
           enum "brief" {
             description "Display brief output (default)";
           }
           enum "detail" {
             description "Display detailed output";
           }
         }
       }
       leaf interface-name {
         description "Name of interface";
         type string;
       }
     }
     output {
       container virtual-chassis-interface-information {
         container brief {
           container vccp-interface {
             leaf interface-name {
               type string;
             }
             leaf vccp-interface-state {
               type string;
             }
             leaf metric {
               type int32;
             }
           }
         }
         container detail {
           container vccp-interface {
             leaf vccp-interface.heading {
               type string;
             }
             leaf interface-name {
               type string;
             }
             leaf interface-index {
               type int32;
             }
             leaf interface-state-value {
               type int32;
             }
             leaf interface-disabled-flag {
               type empty;
             }
             leaf lsp-interval {
               type int32;
             }
             leaf hello-padding {
               type string;
             }
             leaf system-name {
               type string;
               description "Hostname of a system";
             }
             container interface-level-data {
               leaf adjacency-count {
                 type int32;
               }
               leaf metric {
                 type int32;
               }
               leaf hello-time {
                 type int32;
               }
               leaf holdtime {
                 type int32;
               }
             }
           }
         }
       }
     }
   }
   rpc get-virtual-chassis-route-information {
     description "Show virtual chassis routing table";
     input {
       leaf destination {
         description "System ID of destination";
         type string;
       }
     }
     output {
       container virtual-chassis-route-information {
         container vccp-routing-table {
           leaf system-name {
             type string;
             description "Hostname of a system";
           }
           leaf vccp-rtttype {
             type int32;
           }
           leaf table-version {
             type int32;
           }
           container vccp-route {
             leaf route-version {
               type int32;
             }
             leaf metric {
               type int32;
             }
             leaf interface-name {
               type string;
             }
             leaf vccp-next-hop {
               type string;
             }
           }
         }
       }
     }
   }
   rpc get-virtual-chassis-statistics-information {
     description "Show virtual chassis performance statistics";
     input {
       leaf interface-name {
         description "Name of logical interface";
         type string;
       }
     }
     output {
       container virtual-chassis-statistics-information {
         container vccp-statistics {
           leaf system-name {
             type string;
             description "Hostname of a system";
           }
           leaf lsp-queue-length {
             type int32;
           }
           leaf lsp-queue-drops {
             type int32;
           }
           leaf spf-runs {
             type int32;
           }
           leaf fragments-rebuilt {
             type int32;
           }
           leaf lsps-regenerated {
             type int32;
           }
           leaf purges-initiated {
             type int32;
           }
           container vccp-pdu-statistics {
             leaf vccp-pdu-type {
               type string;
             }
             leaf packets-received {
               type uint64;
             }
             leaf packets-processed {
               type uint64;
             }
             leaf packets-dropped {
               type uint64;
             }
             leaf packets-sent {
               type uint64;
             }
             leaf packets-retransmitted {
               type uint64;
             }
           }
           container totals-information {
             leaf packets-received {
               type uint64;
             }
             leaf packets-sent {
               type uint64;
             }
           }
         }
       }
     }
   }
 }
