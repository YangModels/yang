/*
 * Copyright (c) 2017 Juniper Networks, Inc.
 * All rights reserved.
 */

 module show-mpls {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-mpls-abstract-hop-membership-information {
     description "Show MPLS abstract hop membership tables";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
       leaf abstract-hop {
         description "Name of abstract hop";
         type string;
       }
     }
     output {
       container mpls-abstract-hop-membership-information {
         container mpls-abstract-hop-membership {
           leaf abstract-hop-name {
             type string;
           }
           container mpls-abstract-hop-credibility-table {
             container mpls-abstract-hop-credibility-info {
               container mpls-abstract-hop-member-table {
                 leaf member-address {
                   type ipaddr;
                 }
               }
             }
           }
         }
       }
     }
   }
   rpc get-mpls-admin-group-information {
     description "Show MPLS administrative groups";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
     }
     output {
       container mpls-admin-group-information {
         container mpls-admin-group {
           leaf admin-group-name {
             type string;
             description "Name of the admin group";
           }
           leaf index {
             type int32;
           }
         }
       }
     }
   }
   rpc get-mpls-admin-group-extended-information {
     description "Show MPLS extended administrative groups";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
     }
     output {
       container mpls-admin-group-extended-information {
         container mpls-admin-group-extended {
           leaf admin-group-name {
             type string;
             description "Name of the admin group";
           }
           leaf admin-group-index {
             type uint32;
           }
           leaf range {
             type string;
           }
         }
       }
     }
   }
   rpc get-mpls-association-path-information {
     description "Display all LSPs that share same path";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf path-name {
         description "Name of path";
         type string;
         mandatory true;
       }
     }
   }
   rpc get-mpls-association-iif-information {
     description "Display all LSPs that share same incoming interface";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface-name {
         description "Name of incoming interface";
         type string;
         mandatory true;
       }
     }
   }
   rpc get-mpls-association-oif-information {
     description "Display all LSPs that share same outgoing interface";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface-name {
         description "Name of outgoing interface";
         type string;
         mandatory true;
       }
     }
   }
   rpc get-mpls-correlation-nexthop-information {
     description "Display MPLS LSP info for the owner of this nexthop";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf nhid {
         description "NH-ID";
         type int32;
         mandatory true;
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
     }
   }
   rpc get-mpls-correlation-label-information {
     description "Display MPLS LSP info for the owner of this label";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf nhid {
         description "Label value";
         type int32;
         mandatory true;
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
     }
   }
   rpc get-mpls-cspf-information {
     description "Show Constrained Shortest Path First statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
     }
     output {
       container mpls-cspf-information {
         container mpls-cspf {
           leaf mpls-cspf.heading {
             type string;
           }
           container cspf-queue {
             description "CSPF queue statistics";
             leaf current {
               type int32;
             }
             leaf maximum {
               type int32;
             }
             leaf dequeued {
               type int32;
             }
           }
           container cspf-paths {
             description "CSPF path computations statistics";
             leaf total-paths {
               type int32;
             }
             leaf successful {
               type int32;
             }
             leaf no-route {
               type int32;
             }
             leaf sys-error {
               type int32;
             }
             leaf cspfs {
               type int32;
             }
           }
           container cspf-timing {
             description "CSPF timing statistics";
             leaf total-time {
               type string;
             }
             leaf cspf-time {
               type string;
             }
             leaf average-time {
               type string;
             }
             leaf rpd-time {
               type string;
             }
           }
         }
       }
     }
   }
   rpc get-mpls-path-information {
     description "Show configured named paths";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
       leaf path {
         description "Name of label-switched path";
         type string;
       }
     }
     output {
       container mpls-path-information {
         container mpls-path {
           leaf name {
             type string;
           }
           leaf address {
             type ipaddr;
           }
           leaf path-type {
             type string;
           }
           leaf telink-id {
             type int32;
             description "Link identifier of unnumbered link";
           }
           leaf is-abstract-hop {
             type string;
             description "Indicates if the hop is an abstract hop or a real hop";
           }
         }
       }
     }
   }
   rpc get-mpls-interface-information {
     description "Show MPLS interfaces";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf instance {
         description "Name of routing instance";
         type string;
       }
     }
     output {
       container mpls-interface-information {
         container mpls-interface {
           leaf interface-name {
             type string;
             description "Name of interface";
           }
           leaf mpls-interface-state {
             type string;
           }
           leaf no-group-flag {
             type empty;
           }
           leaf admin-group-name {
             type string;
             description "Name of the admin group";
           }
           leaf admin-group-number {
             type int32;
             description "Number of the admin group";
           }
         }
         container mpls-interface-detail {
           leaf interface-name {
             type string;
             description "Name of interface";
           }
           leaf mpls-interface-state {
             type string;
           }
           leaf no-group-flag {
             type empty;
           }
           leaf admin-group-name {
             type string;
             description "Name of the admin group";
           }
           leaf admin-group-number {
             type int32;
             description "Number of the admin group";
           }
           leaf admin-group-extended-name {
             type string;
             description "Name of the extended admin group";
           }
           leaf admin-group-extended-number {
             type uint32;
             description "Number of the extended admin group";
           }
           leaf srlg-name {
             type string;
             description "Name of the srlg";
           }
           leaf maximum-labels {
             type string;
             description "Maximum label";
           }
           leaf static-revert-time {
             type string;
             description "Static LSP revert wait time";
           }
           leaf always-mark-connection-protection-tlv {
             type string;
             description "Always-mark-connection-protection-tlv status on a MPLS interface";
           }
           leaf mpls-interface-switch-away-lsps {
             type string;
             description "Switch-away-lsps knob status of a MPLS interface";
           }
         }
       }
     }
   }
   rpc get-mpls-diffserv-te-information {
     description "Show MPLS Differentiated Services traffic engineering global properties";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
     }
     output {
       container mpls-diffserv-te-information {
         leaf bandwidth-model {
           type string;
           description "Bandwidth model in use";
         }
         container te-class-map {
           leaf te-class {
             type string;
             description "TE class";
           }
           leaf traffic-class {
             type string;
             description "Traffic class";
           }
           leaf te-prio {
             type int32;
             description "Priority associated with a particular traffic class";
           }
         }
       }
     }
   }
   rpc get-mpls-lsp-information {
     description "Show configured label-switched paths";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
       leaf lsp-type {
         type enumeration {
           enum "ingress" {
             description "Display LSPs originating at this router";
           }
           enum "egress" {
             description "Display LSPs ending at this router";
           }
           enum "transit" {
             description "Display LSPs transiting this router";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
       leaf lsp-state {
         type enumeration {
           enum "up" {
             description "Display active LSPs";
           }
           enum "down" {
             description "Display inactive LSPs";
           }
         }
       }
       leaf lsp-direction {
         type enumeration {
           enum "unidirectional" {
             description "Display unidirectional LSPs";
           }
           enum "bidirectional" {
             description "Display bidirectional LSPs";
           }
           enum "p2mp" {
             description "Display point-to-multipoint LSPs";
           }
           enum "externally-controlled" {
             description "Display externally controlled LSPs";
           }
         }
       }
       leaf lsp-provisioning {
         type enumeration {
           enum "externally-provisioned" {
             description "Display externally provisioned LSPs";
           }
           enum "locally-provisioned" {
             description "Display locally provisioned LSPs";
           }
         }
       }
       leaf lsp-stat {
         type enumeration {
           enum "statistics" {
             description "Display packet statistics for LSPs";
           }
           enum "reverse-statistics" {
             description "Display packet statistics for reverse direction of LSPs";
           }
         }
       }
       leaf bypass-lsp {
         type enumeration {
           enum "bypass" {
             description "Display LSPs used for protecting other LSPs";
           }
         }
       }
       leaf activeroutes {
         type enumeration {
           enum "count-active-routes" {
             description "Show active routes for LSPs";
           }
         }
       }
       leaf regex {
         description "Regular expression for LSP names to match";
         type string;
       }
     }
     output {
       container mpls-lsp-information {
         container rsvp-session-data {
           leaf session-type {
             type string;
             description "Type of session with respect to this router";
           }
           leaf count {
             type int32;
           }
           leaf detours {
             type int32;
             description "Number of detour sessions";
           }
           leaf display-count {
             type int32;
             description "Number of sessions displayed";
           }
           leaf up-count {
             type int32;
             description "Number of sessions in up state";
           }
           leaf down-count {
             type int32;
             description "Number of sessions in down state";
           }
           container rsvp-session {
             description "Single RSVP session";
             container brief {
               description "Single RSVP session";
               leaf destination-address {
                 type ipaddr;
                 description "Session destination address";
               }
               leaf source-address {
                 type ipaddr;
               }
               leaf lsp-state {
                 type string;
                 description "State of an LSP";
               }
               leaf route-count {
                 type int32;
                 description "Number of active routes";
               }
               leaf rsb-count {
                 type int32;
                 description "Number of RSBs";
               }
               leaf resv-style {
                 type string;
               }
               leaf label-in {
                 type string;
                 description "Incoming label";
               }
               leaf label-out {
                 type string;
                 description "Outgoing label";
               }
               leaf name {
                 type string;
               }
               leaf bidirectional {
                 type empty;
                 description "LSP is bidirectional";
               }
               leaf associated-bidirectional {
                 type empty;
                 description "LSP is associated-bidirectional";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf is-primary {
                   type empty;
                   description "Path is a primary path";
                 }
                 leaf active-path {
                   type string;
                   description "Path that the LSP is currently using";
                 }
                 leaf name {
                   type string;
                 }
                 leaf bidirectional {
                   type empty;
                   description "LSP is bidirectional";
                 }
                 leaf associated-bidirectional {
                   type empty;
                   description "LSP is associated-bidirectional";
                 }
                 leaf ext-assoc-bidir {
                   type empty;
                   description "Extended associated bidirectional LSP";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container descriptions {
               description "Single RSVP session";
               leaf destination-address {
                 type ipaddr;
                 description "Session destination address";
               }
               leaf source-address {
                 type ipaddr;
               }
               leaf name {
                 type string;
               }
               leaf lsp-description {
                 type string;
                 description "LSP description string (up to 80 characters)";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf name {
                   type string;
                 }
                 leaf lsp-description {
                   type string;
                   description "LSP description string (up to 80 characters)";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container brief_stats {
               description "Single RSVP session";
               leaf destination-address {
                 type ipaddr;
                 description "Session destination address";
               }
               leaf source-address {
                 type ipaddr;
               }
               leaf lsp-state {
                 type string;
                 description "State of an LSP";
               }
               leaf lsp-pktbytes {
                 type string;
                 description "LSP packet and byte counters";
               }
               leaf name {
                 type string;
               }
               leaf bidirectional {
                 type empty;
                 description "LSP is bidirectional";
               }
               leaf associated-bidirectional {
                 type empty;
                 description "LSP is associated-bidirectional";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 leaf ext-assoc-bidir {
                   type empty;
                   description "Extended associated bidirectional LSP";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container brief_xc {
               description "Single RSVP session";
               leaf source-address {
                 type ipaddr;
               }
               leaf lsp-id {
                 type string;
               }
               leaf p2mp-branch-id {
                 type uint32;
               }
               leaf lsp-state {
                 type string;
                 description "State of an LSP";
               }
               leaf xc-psb-list {
                 type string;
                 description "List of PSBs part of the RSVP xc";
               }
               leaf xc-rsb-list {
                 type string;
                 description "List of RSBs part of the RSVP xc";
               }
               leaf name {
                 type string;
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   leaf name {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container detail {
               description "Single RSVP session";
               leaf destination-address {
                 type ipaddr;
                 description "Session destination address";
               }
               leaf is-detour {
                 type empty;
                 description "Session is a detour session";
               }
               leaf source-address {
                 type ipaddr;
               }
               leaf lsp-state {
                 type string;
                 description "State of an LSP";
               }
               leaf route-count {
                 type int32;
                 description "Number of active routes";
               }
               leaf name {
                 type string;
               }
               leaf lsp-path-type {
                 type string;
                 description "Primary or secondary LSP path";
               }
               leaf graceful-deletion-triggered {
                 type empty;
                 description "Initiated graceful deletion procedure for the LSP";
               }
               leaf mpls-lsp-type {
                 type string;
                 description "Type of LSP";
               }
               leaf lsp-description {
                 type string;
                 description "LSP description string (up to 80 characters)";
               }
               leaf source-tna-address {
                 type ipaddr;
                 description "Source TNA address for the connection";
               }
               leaf destination-tna-address {
                 type ipaddr;
                 description "Destination TNA address for the connection";
               }
               leaf bidirectional {
                 type empty;
                 description "LSP is bidirectional";
               }
               leaf associated-bidirectional {
                 type empty;
                 description "LSP is associated-bidirectional";
               }
               leaf upstream-label-in {
                 type string;
                 description "Incoming upstream label";
               }
               leaf upstream-label-out {
                 type string;
                 description "Outgoing upstream label";
               }
               leaf lsp-associated-lspname {
                 type string;
                 description "Associated LSP name";
               }
               leaf lsp-associated-lspsrc {
                 type string;
                 description "Associated LSP source address";
               }
               leaf mpls-p2mp-lsp-name {
                 type string;
               }
               leaf p2mp-remerge-state {
                 type string;
                 description "Re-merge status of the P2MP sub-LSP";
               }
               leaf lsp-aggregation {
                 type string;
                 description "Supports LSP aggregation";
               }
               leaf suggested-label-in {
                 type int32;
                 description "Suggested label received";
               }
               leaf suggested-label-out {
                 type int32;
                 description "Suggested label sent";
               }
               leaf recovery-label-in {
                 type int32;
               }
               leaf recovery-label-out {
                 type int32;
               }
               leaf lsp-pktbytes {
                 type string;
                 description "LSP packet and byte counters";
               }
               leaf no-statistics {
                 type empty;
                 description "No statistics are available for this session";
               }
               leaf rsb-count {
                 type int32;
                 description "Number of RSBs";
               }
               leaf resv-style {
                 type string;
               }
               leaf label-in {
                 type string;
                 description "Incoming label";
               }
               leaf label-out {
                 type string;
                 description "Outgoing label";
               }
               leaf psb-lifetime {
                 type int32;
                 description "Lifetime for a PSB after which the entry expires";
               }
               leaf psb-creation-time {
                 type string;
                 description "Time when this PSB was created";
               }
               leaf path-mtu {
                 type int32;
                 description "The value of the path MTU, as negotiated by the network";
               }
               leaf path-mtu-in-kernel {
                 type int32;
                 description "The value of the MTU used locally for forwarding";
               }
               leaf sender-tspec {
                 type string;
                 description "Sender TSpec";
               }
               leaf adspec {
                 type string;
                 description "Adspec data element in an RSVP Path message";
               }
               leaf lsp-diffserv-info {
                 type string;
                 description "LSP DiffServ info";
               }
               leaf ct-bw {
                 type string;
                 description "Per-class bandwidth requested for E-LSPs and L-LSPs";
               }
               leaf lsp-id {
                 type string;
               }
               leaf tunnel-id {
                 type int32;
               }
               leaf proto-id {
                 type int32;
               }
               leaf p2mp-branch-id {
                 type uint32;
               }
               leaf p2mp-subgroup-orig {
                 type ipaddr;
               }
               leaf self-id {
                 type string;
                 description "Statistics identifier for RSVP path state control block";
               }
               leaf nh-statistics-id {
                 type string;
                 description "Nexthop statistics identifier for RSVP path at ingress";
               }
               leaf route-statistics-id {
                 type string;
                 description "Route statistics identifier for RSVP path at egress";
               }
               leaf nh-traffic-class-statistics {
                 type empty;
                 description "Traffic class statistics are enabled at ingress";
               }
               leaf route-traffic-class-statistics {
                 type empty;
                 description "Traffic class statistics are enabled at egress";
               }
               leaf session-id {
                 type int32;
                 description "Unique identifier for RSVP session";
               }
               leaf is-fastreroute {
                 type empty;
                 description "Fast reroute (one-to-one backup) is desired";
               }
               leaf is-linkprotection {
                 type empty;
                 description "Link protection (facility backup) is desired";
               }
               leaf is-nodeprotection {
                 type empty;
                 description "Link-Node protection (facility backup) is desired";
               }
               leaf ep-plr-protector {
                 type string;
               }
               leaf is-soft-preemption {
                 type empty;
                 description "Soft-preemption is desired";
               }
               leaf rsvp-path-status {
                 type string;
               }
               leaf bypass-name {
                 type string;
                 description "Name of the bypass";
               }
               leaf rsvp-lp-backup-route-cnt {
                 type int32;
                 description "Number of routes tunneled through this bypass";
               }
               leaf rsvp-lp-backup-lsp-cnt {
                 type int32;
                 description "Number of backup RSVP LSPs tunneled through this bypass";
               }
               leaf entropy-label {
                 type string;
                 description "Entropy label";
               }
               leaf p2mp-self-id {
                 type string;
                 description "Statistics identifier for RSVP P2MP path state control block";
               }
               container layer2-tspec {
                 description "Layer 2 TSpec";
                 leaf switching-granularity {
                   type string;
                   description "Layer 2 switching granularity";
                 }
                 leaf mtu {
                   type int32;
                   description "MTU along an interface";
                 }
                 leaf atm-vp-bundle-size {
                   type int32;
                   description "VP bundle size";
                 }
                 leaf atm-cell-bundle-size {
                   type int32;
                   description "Maximum cell bundle size";
                 }
               }
               container rsvp-lsp-enh-local-prot-status {
                 description "Enhanced FRR local protection status";
                 leaf rsvp-lsp-enh-local-prot-admin-status {
                   type string;
                   description "Enhanced FRR local protection admin status";
                 }
                 leaf rsvp-lsp-enh-local-prot-disabled-reason {
                   type string;
                   description "Enhanced FRR local protection disabled reason";
                 }
                 leaf rsvp-lsp-enh-local-prot-refresh-interval {
                   type string;
                   description "Enhanced FRR refresh interval set for LSP";
                 }
               }
               container rsvp-lsp-enh-local-prot-upstream {
                 description "Enhanced FRR local protection upstream information";
                 leaf rsvp-lsp-enh-lp-upstream-status {
                   type string;
                   description "Enhanced FRR local protection status upstream";
                 }
                 leaf rsvp-lsp-enh-lp-upstream-lp {
                   type string;
                   description "The node is LP-MP for Phop";
                 }
                 leaf rsvp-lsp-enh-lp-phop-addr {
                   type ipaddr;
                   description "Phop PLR for which this node is LP-MP";
                 }
                 leaf rsvp-lsp-enh-lp-upstream-lp-status {
                   type string;
                   description "Current upstream LP-MP status";
                 }
                 leaf rsvp-lsp-enh-lp-upstream-np {
                   type string;
                   description "The node is NP-MP for PPhop";
                 }
                 leaf rsvp-lsp-enh-lp-pphop-addr {
                   type ipaddr;
                   description "PPhop PLR for which this node is NP-MP";
                 }
                 leaf rsvp-lsp-enh-lp-upstream-np-status {
                   type string;
                   description "Current upstream NP-MP status";
                 }
                 leaf rsvp-lsp-enh-lp-upstream-disabled-reason {
                   type string;
                   description "Reason enhanced local protection is disabled upstream";
                 }
                 leaf rsvp-lsp-enh-local-prot-refresh-interval {
                   type string;
                   description "Enhanced FRR refresh interval set for LSP";
                 }
               }
               container rsvp-lsp-enh-local-prot-downstream {
                 description "Enhanced FRR local protection downstream information";
                 leaf rsvp-lsp-enh-lp-downstream-status {
                   type string;
                   description "Enhanced FRR local protection status downstream";
                 }
                 leaf rsvp-lsp-enh-lp-downstream-lp {
                   type string;
                   description "The node has made link protection available";
                 }
                 leaf rsvp-lsp-enh-lp-nhop-addr {
                   type ipaddr;
                   description "Nhop MP neigbor address";
                 }
                 leaf rsvp-lsp-enh-lp-downstream-np {
                   type string;
                   description "The node has made node protection available";
                 }
                 leaf rsvp-lsp-enh-lp-nnhop-addr {
                   type ipaddr;
                   description "NNhop MP neighbor address";
                 }
                 leaf rsvp-lsp-enh-lp-current-status {
                   type string;
                   description "Current downstream protection status";
                 }
                 leaf rsvp-lsp-enh-lp-downstream-disabled-reason {
                   type string;
                   description "Reason enhanced local protection is disabled downstream";
                 }
                 leaf rsvp-lsp-enh-local-prot-refresh-interval {
                   type string;
                   description "Enhanced FRR refresh interval set for LSP";
                 }
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf entropy-label {
                   type string;
                   description "Entropy label";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container record-route {
                 description "Record Route Object (RRO)";
                 leaf record-route.heading {
                   type string;
                   description "Record Route Object (RRO)";
                 }
                 leaf address {
                   type ipaddr;
                 }
                 leaf telink-id {
                   type int32;
                   description "Link identifier of unnumbered link";
                 }
                 leaf self {
                   type empty;
                 }
                 leaf incomplete {
                   type empty;
                 }
               }
               container lsp-attribute-flags {
                 description "LSP attribute flags";
                 leaf non-php {
                   type empty;
                   description "Non-PHP";
                 }
                 leaf oob {
                   type empty;
                   description "Out-of-band mapping";
                 }
               }
               container lp-history {
                 description "Log of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container rsvp-telink {
                 leaf active-reservation {
                   type int32;
                   description "Number of active reservations";
                 }
                 leaf preemption-count {
                   type int32;
                   description "Number of preemptions that occurred on an interface";
                 }
                 leaf update-threshold {
                   type int32;
                   description "Percentage change in reserved bandwidth to trigger IGP update";
                 }
                 leaf subscription {
                   type int32;
                   description "Percentage of link capacity available for bandwidth reservations";
                 }
                 leaf bc {
                   type int32;
                   description "Bandwidth constraint (0..7)";
                 }
                 leaf bc-description {
                   type string;
                   description "Description of the bandwidth constraint";
                 }
                 leaf static-bc-bandwidth {
                   type int32;
                   description "Static bandwidth capacity for a bandwidth constraint";
                 }
                 leaf ct-class {
                   type int32;
                   description "Class type (0..7)";
                 }
                 leaf static-bandwidth {
                   type int32;
                   description "Static bandwidth capacity of the link";
                 }
                 leaf available-bandwidth {
                   type int32;
                   description "Amount of bandwidth available for reservations";
                 }
                 leaf ct-subscription {
                   type int32;
                   description "Subscription percentage per traffic class";
                 }
                 leaf max-available-bandwidth {
                   type int32;
                   description "Maximum amount of bandwidth available for reservations, including the subscription factor";
                 }
                 leaf max-available-description {
                   type string;
                   description "Description of the computation of the maximum available bandwidth";
                 }
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                 }
               }
               container protection-attribute {
                 description "Protection attributes of RSVP session";
                 leaf protect-lsp-type {
                   type string;
                   description "Type of LSP for protection purposes";
                 }
                 leaf protect-lsp-role {
                   type string;
                   description "Role of LSP for protection purposes";
                 }
                 leaf protect-protection-type {
                   type string;
                   description "Type of protection being used";
                 }
                 leaf protect-secondary-operational {
                   type empty;
                   description "Protecting LSP is operational and carrying protected traffic";
                 }
               }
               container association-attribute {
                 description "Association attributes of RSVP session";
                 leaf association-type {
                   type string;
                   description "Type of association object";
                 }
                 leaf association-source {
                   type ipaddr;
                   description "Source node defining the association";
                 }
                 leaf association-id {
                   type int32;
                   description "Identifier for the association";
                 }
               }
               container detour {
                 description "Detour session";
                 leaf lsp-state {
                   type string;
                   description "State of an LSP";
                 }
                 leaf sender-tspec {
                   type string;
                   description "Sender TSpec";
                 }
                 leaf lsp-diffserv-info {
                   type string;
                   description "LSP DiffServ info";
                 }
                 leaf ct-bw {
                   type string;
                   description "Per-class bandwidth requested for E-LSPs and L-LSPs";
                 }
                 leaf adspec {
                   type string;
                   description "Adspec data element in an RSVP Path message";
                 }
                 leaf path-mtu {
                   type int32;
                   description "The value of the path MTU, as negotiated by the network";
                 }
                 leaf path-mtu-in-kernel {
                   type int32;
                   description "The value of the MTU used locally for forwarding";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container record-route {
                   description "Record Route Object (RRO)";
                   leaf record-route.heading {
                     type string;
                     description "Record Route Object (RRO)";
                   }
                   leaf address {
                     type ipaddr;
                   }
                   leaf telink-id {
                     type int32;
                     description "Link identifier of unnumbered link";
                   }
                   leaf self {
                     type empty;
                   }
                   leaf incomplete {
                     type empty;
                   }
                 }
               }
               container detour-branch {
                 description "Branch of some detour session";
                 leaf source-address {
                   type ipaddr;
                 }
                 leaf skip-address {
                   type ipaddr;
                   description "Address of node or link to be skipped";
                 }
                 leaf lsp-state {
                   type string;
                   description "State of an LSP";
                 }
                 leaf sender-tspec {
                   type string;
                   description "Sender TSpec";
                 }
                 leaf adspec {
                   type string;
                   description "Adspec data element in an RSVP Path message";
                 }
                 leaf path-mtu {
                   type int32;
                   description "The value of the path MTU, as negotiated by the network";
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container record-route {
                   description "Record Route Object (RRO)";
                   leaf record-route.heading {
                     type string;
                     description "Record Route Object (RRO)";
                   }
                   leaf address {
                     type ipaddr;
                   }
                   leaf telink-id {
                     type int32;
                     description "Link identifier of unnumbered link";
                   }
                   leaf self {
                     type empty;
                   }
                   leaf incomplete {
                     type empty;
                   }
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container detour-branch-labels {
                   leaf label-in {
                     type string;
                     description "Incoming label";
                   }
                   leaf label-out {
                     type string;
                     description "Outgoing label";
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf name {
                   type string;
                 }
                 leaf lsp-type {
                   type string;
                   description "Type of LSP";
                 }
                 leaf egress-label-operation {
                   type string;
                   description "Label advertised by egress";
                 }
                 leaf lsp-control-status {
                   type string;
                   description "Control status of LSP configured to be externally controlled";
                 }
                 leaf lsp-diffserv-te-info {
                   type string;
                   description "LSP support of DiffServ-TE extensions";
                 }
                 leaf bidirectional {
                   type empty;
                   description "LSP is bidirectional";
                 }
                 leaf associated-bidirectional {
                   type empty;
                   description "LSP is associated-bidirectional";
                 }
                 leaf lsp-associated-lspname {
                   type string;
                   description "Associated LSP name";
                 }
                 leaf lsp-associated-lspsrc {
                   type string;
                   description "Associated LSP source address";
                 }
                 leaf ext-assoc-bidir {
                   type empty;
                   description "Extended associated bidirectional LSP";
                 }
                 leaf ext-assoc-bidir-direction {
                   type string;
                   description "Ext-Assoc-Bidir direction";
                 }
                 leaf lsp-description {
                   type string;
                   description "LSP description string (up to 80 characters)";
                 }
                 leaf lsp-pktbytes {
                   type string;
                   description "LSP packet and byte counters";
                 }
                 leaf aggregate-lsp-pktbytes {
                   type string;
                   description "Aggregate LSP packet and byte counters";
                 }
                 leaf no-statistics {
                   type empty;
                   description "No statistics are available for this session";
                 }
                 leaf active-path {
                   type string;
                   description "Path that the LSP is currently using";
                 }
                 leaf mpls-p2mp-name {
                   type string;
                 }
                 leaf is-fastreroute {
                   type empty;
                   description "Fast reroute (one-to-one backup) is desired";
                 }
                 leaf is-linkprotection {
                   type empty;
                   description "Link protection (facility backup) is desired";
                 }
                 leaf is-nodeprotection {
                   type empty;
                   description "Link-Node protection (facility backup) is desired";
                 }
                 leaf is-inter-domain-path {
                   type empty;
                   description "Inter-domain LSP";
                 }
                 leaf load-balance {
                   type string;
                   description "Load-balancing algorithm chosen";
                 }
                 leaf metric {
                   type int32;
                 }
                 leaf actual-metric {
                   type int32;
                 }
                 leaf revert-timer {
                   type string;
                   description "Hold-down time before reverting to primary path.";
                 }
                 leaf revert-timer-remain {
                   type string;
                   description "Time remaining before reverting:";
                 }
                 leaf optimize-protection-timer {
                   type int32;
                   description "Optimize protection timer";
                 }
                 leaf lsp-creation-time {
                   type string;
                   description "Time when the LSP was created";
                 }
                 leaf lsp-soft-preemption-counter {
                   type int32;
                   description "Number of times the LSP was soft preempted";
                 }
                 leaf lsp-soft-preemption-time {
                   type string;
                   description "Time when the LSP was last soft preempted";
                 }
                 leaf retry-timer {
                   type int32;
                 }
                 leaf retry-limit {
                   type int32;
                 }
                 leaf lsp-packets {
                   type string;
                   description "LSP packet counters";
                 }
                 leaf lsp-bytes {
                   type string;
                   description "LSP byte counters";
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container mpls-srlg {
                   leaf srlg-name {
                     type string;
                     description "Name of the srlg";
                   }
                   leaf srlg-value {
                     type uint32;
                     description "Value of the srlg";
                   }
                   leaf srlg-cost {
                     type uint32;
                     description "Cost of the srlg";
                   }
                 }
                 container mpls-lsp-autobandwidth {
                   leaf monitor-lsp-bandwidth {
                     type empty;
                     description "Enable the bandwidth monitoring mode";
                   }
                   leaf minimum-bandwidth {
                     type int32;
                     description "Configured LSP minimum bandwidth";
                   }
                   leaf maximum-bandwidth {
                     type int32;
                     description "Configured LSP maximum bandwidth";
                   }
                   leaf dynamic-minimum-bandwidth {
                     type int32;
                     description "LSP dynamic minimum bandwidth (or last Max Avg Bw)";
                   }
                   leaf adjust-timer {
                     type int32;
                     description "Configured LSP adjust timer";
                   }
                   leaf adjust-threshold {
                     type int32;
                     description "Percentage change in average LSP utilization to trigger autoadjustment";
                   }
                   leaf adjust-threshold-activate-bandwidth {
                     type int32;
                     description "Configured LSP adjust threshold bandwidth";
                   }
                   leaf maximum-average-bandwidth {
                     type int32;
                     description "Maximum Average BW";
                   }
                   leaf time-to-adjust {
                     type int32;
                     description "Time in which LSP will autoadjust bandwidth";
                   }
                   leaf autobw-minimum-bandwidth-adjust-interval {
                     type int32;
                   }
                   leaf autobw-minimum-bandwidth-adjust-threshold-percent {
                     type int32;
                   }
                   leaf autobw-minimum-bandwidth-adjust-threshold-value {
                     type int32;
                   }
                   leaf time-to-expire-minimum-bandwidth-adjust {
                     type int32;
                     description "Time in which LSP will start changing minimum bandwidth";
                   }
                   leaf overflow-limit {
                     type int32;
                     description "Configured limit of consecutive overflow samples for LSP";
                   }
                   leaf overflow-sample-count {
                     type int32;
                     description "Number of consecutive overflow samples encountered";
                   }
                   leaf underflow-limit {
                     type int32;
                     description "Configured limit of consecutive underflow samples for LSP";
                   }
                   leaf underflow-sample-count {
                     type int32;
                     description "Number of consecutive underflow samples encountered";
                   }
                   leaf underflow-max-avg-bandwidth {
                     type int32;
                     description "Highest average bandwidth recorded so far for underflow samples";
                   }
                 }
                 container mpls-lsp-path {
                   description "Primary or secondary LSP path";
                   leaf path-active {
                     type empty;
                     description "Whether the path is active or not";
                   }
                   leaf title {
                     type string;
                   }
                   leaf name {
                     type string;
                   }
                   leaf path-state {
                     type string;
                     description "State of the MPLS path";
                   }
                   leaf cos {
                     type int32;
                     description "CoS value";
                   }
                   leaf no-decrement-ttl {
                     type empty;
                     description "TTL";
                   }
                   leaf preference {
                     type int32;
                     description "Preference for the route";
                   }
                   leaf path-soft-preemption-pending {
                     type empty;
                     description "Soft preemption pending for this path";
                   }
                   leaf setup-priority {
                     type int32;
                     description "Priority with respect to taking resources";
                   }
                   leaf hold-priority {
                     type int32;
                     description "Priority with respect to holding resources";
                   }
                   leaf actual-setup-priority {
                     type int32;
                   }
                   leaf actual-hold-priority {
                     type int32;
                   }
                   leaf external-lsp-cspf-type {
                     type string;
                   }
                   leaf bandwidth {
                     type int32;
                   }
                   leaf actual-bandwidth {
                     type int32;
                   }
                   leaf per-class-bandwidth-heading {
                     type string;
                   }
                   leaf bandwidth_ct0 {
                     type int32;
                   }
                   leaf bandwidth_ct1 {
                     type int32;
                   }
                   leaf bandwidth_ct2 {
                     type int32;
                   }
                   leaf bandwidth_ct3 {
                     type int32;
                   }
                   leaf path-adaptive {
                     type empty;
                     description "LSP is adaptive";
                   }
                   leaf path-no-recordroute {
                     type empty;
                     description "Record route disabled";
                   }
                   leaf hoplimit {
                     type int32;
                     description "Maximum number of hops that can be traversed";
                   }
                   leaf optimize-timer {
                     type int32;
                     description "Optimize timer";
                   }
                   leaf smart-optimize-timer {
                     type int32;
                     description "Smart optimize timer";
                   }
                   leaf retry-timer {
                     type int32;
                   }
                   leaf retry-limit {
                     type int32;
                   }
                   leaf external-cspf-status {
                     type string;
                     description "Status provided by External CSPF computation";
                   }
                   leaf cspf-status {
                     type string;
                     description "Status returned by CSPF computation";
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                   container mpls-srlg {
                     leaf srlg-name {
                       type string;
                       description "Name of the srlg";
                     }
                     leaf srlg-value {
                       type uint32;
                       description "Value of the srlg";
                     }
                     leaf srlg-cost {
                       type uint32;
                       description "Cost of the srlg";
                     }
                   }
                 }
                 container mpls-lsp-attributes {
                   leaf signal-type {
                     type string;
                   }
                   leaf encoding-type {
                     type string;
                     description "LSP encoding type";
                   }
                   leaf switching-type {
                     type string;
                     description "LSP switching capability";
                   }
                   leaf gpid {
                     type string;
                     description "LSP generalized PID";
                   }
                   leaf protection-type {
                     type string;
                     description "LSP protection desired";
                   }
                 }
               }
             }
           }
           container mpls-p2mp-lsp {
             leaf mpls-p2mp-name {
               type string;
             }
             leaf mpls-p2mp-branch-count {
               type string;
             }
           }
           container mpls-container-lsp {
             description "MPLS container-label-switched path information";
             leaf mpls-container-lsp-name {
               type string;
             }
             leaf mpls-container-lsp-state {
               type string;
             }
             leaf mpls-container-member-count {
               type string;
             }
             leaf container-active-path {
               type string;
               description "Path that the member LSP is currently using";
             }
             leaf container-is-primary {
               type empty;
               description "Path is a primary path";
             }
             leaf lsp-packets {
               type string;
               description "LSP packet counters";
             }
             leaf lsp-bytes {
               type string;
               description "LSP byte counters";
             }
             leaf lsp-control-status {
               type string;
               description "Control status of LSP configured to be externally controlled";
             }
             container mpls-lsp-path {
               description "Primary or secondary LSP path";
               container admin-groups {
                 leaf admin-groups.heading {
                   type string;
                 }
                 leaf color {
                   type int32;
                 }
                 leaf no-group-flag {
                   type empty;
                 }
                 leaf admin-group-name {
                   type string;
                   description "Name of the admin group";
                 }
                 leaf admin-group-number {
                   type int32;
                   description "Number of the admin group";
                 }
               }
               container admin-groups-extended {
                 leaf admin-groups-extended.heading {
                   type string;
                 }
                 leaf admin-group-name {
                   type string;
                   description "Name of the admin group";
                 }
                 leaf admin-group-number {
                   type int32;
                   description "Number of the admin group";
                 }
               }
               container srlg {
                 leaf srlg.heading {
                   type string;
                 }
                 leaf srlg-name {
                   type string;
                   description "Name of the srlg";
                 }
               }
               container mpls-lsp-upstream-label {
                 description "Upstream label configured for the LSP";
                 leaf vlan-id-label {
                   type uint32;
                   description "VLAN ID label configured for the LSP";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container oam-state {
                 description "OAM state information";
                 leaf oam-bfd-session-state {
                   type string;
                 }
                 leaf oam-lsp-ping-state {
                   type string;
                 }
               }
               container path-history {
                 description "Log over time of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container path-available-bandwidth {
                 description "Available bandwidth on an LSP path";
                 leaf path-available-bandwidth.heading {
                   type string;
                   description "Available bandwidth on an LSP path";
                 }
                 leaf bandwidth {
                   type int32;
                 }
                 leaf class-type {
                   type int32;
                 }
                 leaf class-bandwidth {
                   type int32;
                 }
               }
               container layer2-connection {
                 description "Layer 2 connection using the LSP path";
                 leaf neighbor-address {
                   type ipaddr;
                   description "IP address of this neighbor";
                 }
                 leaf interface-name {
                   type string;
                   description "Name of interface";
                 }
                 leaf vc-id {
                   type int32;
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
               }
             }
             container mpls-container-lsp-splitting-merging {
               leaf minimum-member-lsps {
                 type int32;
                 description "Configured minimum LSPs";
               }
               leaf maximum-member-lsps {
                 type int32;
                 description "Configured maximum LSPs";
               }
               leaf aggregate-bandwidth {
                 type int32;
                 description "Aggregate bandwidth";
               }
               leaf current-bandwidth {
                 type int32;
                 description "Sampled Aggregate bandwidth";
               }
               leaf normalize-interval {
                 type int32;
                 description "Configured LSP normalize timer";
               }
               leaf splitting-merging-threshold {
                 type int32;
                 description "Percentage change in aggregate LSP utilization to trigger normalization";
               }
               leaf maximum-signaling-bandwidth {
                 type int32;
                 description "Configured signaling maximum bandwidth";
               }
               leaf minimum-signaling-bandwidth {
                 type int32;
                 description "Configured signaling minimum bandwidth";
               }
               leaf maximum-splitting-bandwidth {
                 type int32;
                 description "Configured splitting maximum bandwidth";
               }
               leaf minimum-splitting-bandwidth {
                 type int32;
                 description "Configured splitting minimum bandwidth";
               }
               leaf normalization-mode {
                 type string;
               }
               leaf sampling-mode {
                 type string;
                 description "Sampling Attributes";
               }
               leaf time-to-normalize {
                 type int32;
                 description "Time in which LSP will normalize";
               }
               leaf aggregate-packets {
                 type int32;
                 description "Aggregate packets";
               }
               leaf aggregate-bytes {
                 type int32;
                 description "Aggregate bytes";
               }
             }
             container mpls-container-lsp-history {
               description "Log over time of container LSP related events";
               leaf sequence-number {
                 type int32;
                 description "History event number";
               }
               leaf time {
                 type string;
                 description "Time of the event";
               }
               leaf log {
                 type string;
                 description "Supplemental information of the event";
               }
               leaf route {
                 type string;
                 description "Latest RRO contents, as reported by RSVP";
               }
             }
           }
           container mpls-container-lsp-member-summary {
             container mpls-container-lsp {
               description "MPLS container-label-switched path information";
               leaf mpls-container-lsp-name {
                 type string;
               }
               leaf mpls-container-lsp-state {
                 type string;
               }
               leaf mpls-container-member-count {
                 type string;
               }
               leaf container-active-path {
                 type string;
                 description "Path that the member LSP is currently using";
               }
               leaf container-is-primary {
                 type empty;
                 description "Path is a primary path";
               }
               leaf lsp-packets {
                 type string;
                 description "LSP packet counters";
               }
               leaf lsp-bytes {
                 type string;
                 description "LSP byte counters";
               }
               leaf lsp-control-status {
                 type string;
                 description "Control status of LSP configured to be externally controlled";
               }
               container mpls-lsp-path {
                 description "Primary or secondary LSP path";
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container srlg {
                   leaf srlg.heading {
                     type string;
                   }
                   leaf srlg-name {
                     type string;
                     description "Name of the srlg";
                   }
                 }
                 container mpls-lsp-upstream-label {
                   description "Upstream label configured for the LSP";
                   leaf vlan-id-label {
                     type uint32;
                     description "VLAN ID label configured for the LSP";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container oam-state {
                   description "OAM state information";
                   leaf oam-bfd-session-state {
                     type string;
                   }
                   leaf oam-lsp-ping-state {
                     type string;
                   }
                 }
                 container path-history {
                   description "Log over time of LSP path-related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
                 container path-available-bandwidth {
                   description "Available bandwidth on an LSP path";
                   leaf path-available-bandwidth.heading {
                     type string;
                     description "Available bandwidth on an LSP path";
                   }
                   leaf bandwidth {
                     type int32;
                   }
                   leaf class-type {
                     type int32;
                   }
                   leaf class-bandwidth {
                     type int32;
                   }
                 }
                 container layer2-connection {
                   description "Layer 2 connection using the LSP path";
                   leaf neighbor-address {
                     type ipaddr;
                     description "IP address of this neighbor";
                   }
                   leaf interface-name {
                     type string;
                     description "Name of interface";
                   }
                   leaf vc-id {
                     type int32;
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                 }
               }
               container mpls-container-lsp-splitting-merging {
                 leaf minimum-member-lsps {
                   type int32;
                   description "Configured minimum LSPs";
                 }
                 leaf maximum-member-lsps {
                   type int32;
                   description "Configured maximum LSPs";
                 }
                 leaf aggregate-bandwidth {
                   type int32;
                   description "Aggregate bandwidth";
                 }
                 leaf current-bandwidth {
                   type int32;
                   description "Sampled Aggregate bandwidth";
                 }
                 leaf normalize-interval {
                   type int32;
                   description "Configured LSP normalize timer";
                 }
                 leaf splitting-merging-threshold {
                   type int32;
                   description "Percentage change in aggregate LSP utilization to trigger normalization";
                 }
                 leaf maximum-signaling-bandwidth {
                   type int32;
                   description "Configured signaling maximum bandwidth";
                 }
                 leaf minimum-signaling-bandwidth {
                   type int32;
                   description "Configured signaling minimum bandwidth";
                 }
                 leaf maximum-splitting-bandwidth {
                   type int32;
                   description "Configured splitting maximum bandwidth";
                 }
                 leaf minimum-splitting-bandwidth {
                   type int32;
                   description "Configured splitting minimum bandwidth";
                 }
                 leaf normalization-mode {
                   type string;
                 }
                 leaf sampling-mode {
                   type string;
                   description "Sampling Attributes";
                 }
                 leaf time-to-normalize {
                   type int32;
                   description "Time in which LSP will normalize";
                 }
                 leaf aggregate-packets {
                   type int32;
                   description "Aggregate packets";
                 }
                 leaf aggregate-bytes {
                   type int32;
                   description "Aggregate bytes";
                 }
               }
               container mpls-container-lsp-history {
                 description "Log over time of container LSP related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
             }
           }
           container container-rsvp-session {
             container brief {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf is-primary {
                   type empty;
                   description "Path is a primary path";
                 }
                 leaf active-path {
                   type string;
                   description "Path that the LSP is currently using";
                 }
                 leaf container-member-name {
                   type string;
                   description "Path that the member LSP is currently using";
                 }
                 leaf label-out {
                   type string;
                   description "Outgoing label";
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf label-out {
                   type string;
                   description "Outgoing label";
                 }
               }
               container detour {
                 description "Detour session";
                 leaf lsp-state {
                   type string;
                   description "State of an LSP";
                 }
                 leaf label-out {
                   type string;
                   description "Outgoing label";
                 }
               }
               container detour-branch {
                 description "Branch of some detour session";
                 container detour-branch-labels {
                 }
               }
             }
             container descriptions {
               container mpls-container-lsp {
                 description "MPLS container-label-switched path information";
                 leaf destination-address {
                   type ipaddr;
                   description "Session destination address";
                 }
                 leaf source-address {
                   type ipaddr;
                 }
                 leaf lsp-description {
                   type string;
                   description "LSP description string (up to 80 characters)";
                 }
                 leaf container-active-path {
                   type string;
                   description "Path that the member LSP is currently using";
                 }
                 leaf container-is-primary {
                   type empty;
                   description "Path is a primary path";
                 }
                 leaf lsp-packets {
                   type string;
                   description "LSP packet counters";
                 }
                 leaf lsp-bytes {
                   type string;
                   description "LSP byte counters";
                 }
                 leaf lsp-control-status {
                   type string;
                   description "Control status of LSP configured to be externally controlled";
                 }
                 container mpls-lsp-path {
                   description "Primary or secondary LSP path";
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
                 container mpls-container-lsp-splitting-merging {
                   leaf minimum-member-lsps {
                     type int32;
                     description "Configured minimum LSPs";
                   }
                   leaf maximum-member-lsps {
                     type int32;
                     description "Configured maximum LSPs";
                   }
                   leaf aggregate-bandwidth {
                     type int32;
                     description "Aggregate bandwidth";
                   }
                   leaf current-bandwidth {
                     type int32;
                     description "Sampled Aggregate bandwidth";
                   }
                   leaf normalize-interval {
                     type int32;
                     description "Configured LSP normalize timer";
                   }
                   leaf splitting-merging-threshold {
                     type int32;
                     description "Percentage change in aggregate LSP utilization to trigger normalization";
                   }
                   leaf maximum-signaling-bandwidth {
                     type int32;
                     description "Configured signaling maximum bandwidth";
                   }
                   leaf minimum-signaling-bandwidth {
                     type int32;
                     description "Configured signaling minimum bandwidth";
                   }
                   leaf maximum-splitting-bandwidth {
                     type int32;
                     description "Configured splitting maximum bandwidth";
                   }
                   leaf minimum-splitting-bandwidth {
                     type int32;
                     description "Configured splitting minimum bandwidth";
                   }
                   leaf normalization-mode {
                     type string;
                   }
                   leaf sampling-mode {
                     type string;
                     description "Sampling Attributes";
                   }
                   leaf time-to-normalize {
                     type int32;
                     description "Time in which LSP will normalize";
                   }
                   leaf aggregate-packets {
                     type int32;
                     description "Aggregate packets";
                   }
                   leaf aggregate-bytes {
                     type int32;
                     description "Aggregate bytes";
                   }
                 }
                 container mpls-container-lsp-history {
                   description "Log over time of container LSP related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
               }
               container mpls-lsp {
                 description "MPLS label-switched path information";
                 leaf destination-address {
                   type ipaddr;
                   description "Session destination address";
                 }
                 leaf name {
                   type string;
                 }
                 leaf lsp-description {
                   type string;
                   description "LSP description string (up to 80 characters)";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container detour {
                 description "Detour session";
               }
               container detour-branch {
                 description "Branch of some detour session";
               }
             }
             container brief_stats {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container detour {
                 description "Detour session";
               }
               container detour-branch {
                 description "Branch of some detour session";
               }
             }
             container detail {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf lsp-type {
                   type string;
                   description "Type of LSP";
                 }
                 leaf egress-label-operation {
                   type string;
                   description "Label advertised by egress";
                 }
                 leaf lsp-diffserv-te-info {
                   type string;
                   description "LSP support of DiffServ-TE extensions";
                 }
                 leaf lsp-description {
                   type string;
                   description "LSP description string (up to 80 characters)";
                 }
                 leaf lsp-pktbytes {
                   type string;
                   description "LSP packet and byte counters";
                 }
                 leaf aggregate-lsp-pktbytes {
                   type string;
                   description "Aggregate LSP packet and byte counters";
                 }
                 leaf no-statistics {
                   type empty;
                   description "No statistics are available for this session";
                 }
                 leaf active-path {
                   type string;
                   description "Path that the LSP is currently using";
                 }
                 leaf mpls-container-name {
                   type string;
                   description "Name of the container LSP";
                 }
                 leaf is-fastreroute {
                   type empty;
                   description "Fast reroute (one-to-one backup) is desired";
                 }
                 leaf is-linkprotection {
                   type empty;
                   description "Link protection (facility backup) is desired";
                 }
                 leaf is-nodeprotection {
                   type empty;
                   description "Link-Node protection (facility backup) is desired";
                 }
                 leaf is-inter-domain-path {
                   type empty;
                   description "Inter-domain LSP";
                 }
                 leaf load-balance {
                   type string;
                   description "Load-balancing algorithm chosen";
                 }
                 leaf metric {
                   type int32;
                 }
                 leaf optimize-protection-timer {
                   type int32;
                   description "Optimize protection timer";
                 }
                 leaf lsp-creation-time {
                   type string;
                   description "Time when the LSP was created";
                 }
                 leaf lsp-soft-preemption-counter {
                   type int32;
                   description "Number of times the LSP was soft preempted";
                 }
                 leaf lsp-soft-preemption-time {
                   type string;
                   description "Time when the LSP was last soft preempted";
                 }
                 leaf retry-timer {
                   type int32;
                 }
                 leaf retry-limit {
                   type int32;
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container srlg {
                   leaf srlg.heading {
                     type string;
                   }
                   leaf srlg-name {
                     type string;
                     description "Name of the srlg";
                   }
                 }
                 container mpls-lsp-upstream-label {
                   description "Upstream label configured for the LSP";
                   leaf vlan-id-label {
                     type uint32;
                     description "VLAN ID label configured for the LSP";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container oam-state {
                   description "OAM state information";
                   leaf oam-bfd-session-state {
                     type string;
                   }
                   leaf oam-lsp-ping-state {
                     type string;
                   }
                 }
                 container path-history {
                   description "Log over time of LSP path-related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
                 container path-available-bandwidth {
                   description "Available bandwidth on an LSP path";
                   leaf path-available-bandwidth.heading {
                     type string;
                     description "Available bandwidth on an LSP path";
                   }
                   leaf bandwidth {
                     type int32;
                   }
                   leaf class-type {
                     type int32;
                   }
                   leaf class-bandwidth {
                     type int32;
                   }
                 }
                 container layer2-connection {
                   description "Layer 2 connection using the LSP path";
                   leaf neighbor-address {
                     type ipaddr;
                     description "IP address of this neighbor";
                   }
                   leaf interface-name {
                     type string;
                     description "Name of interface";
                   }
                   leaf vc-id {
                     type int32;
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                 }
                 container mpls-srlg {
                   leaf srlg-name {
                     type string;
                     description "Name of the srlg";
                   }
                   leaf srlg-value {
                     type uint32;
                     description "Value of the srlg";
                   }
                   leaf srlg-cost {
                     type uint32;
                     description "Cost of the srlg";
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf label-out {
                   type string;
                   description "Outgoing label";
                 }
                 leaf path-mtu {
                   type int32;
                   description "The value of the path MTU, as negotiated by the network";
                 }
                 leaf path-mtu-in-kernel {
                   type int32;
                   description "The value of the MTU used locally for forwarding";
                 }
                 leaf sender-tspec {
                   type string;
                   description "Sender TSpec";
                 }
                 leaf adspec {
                   type string;
                   description "Adspec data element in an RSVP Path message";
                 }
                 leaf lsp-diffserv-info {
                   type string;
                   description "LSP DiffServ info";
                 }
                 leaf ct-bw {
                   type string;
                   description "Per-class bandwidth requested for E-LSPs and L-LSPs";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf entropy-label {
                   type string;
                   description "Entropy label";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container detour {
                 description "Detour session";
                 leaf lsp-state {
                   type string;
                   description "State of an LSP";
                 }
                 leaf sender-tspec {
                   type string;
                   description "Sender TSpec";
                 }
                 leaf lsp-diffserv-info {
                   type string;
                   description "LSP DiffServ info";
                 }
                 leaf ct-bw {
                   type string;
                   description "Per-class bandwidth requested for E-LSPs and L-LSPs";
                 }
                 leaf adspec {
                   type string;
                   description "Adspec data element in an RSVP Path message";
                 }
                 leaf path-mtu {
                   type int32;
                   description "The value of the path MTU, as negotiated by the network";
                 }
                 leaf path-mtu-in-kernel {
                   type int32;
                   description "The value of the MTU used locally for forwarding";
                 }
                 leaf label-out {
                   type string;
                   description "Outgoing label";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
               }
               container detour-branch {
                 description "Branch of some detour session";
                 leaf source-address {
                   type ipaddr;
                 }
                 leaf skip-address {
                   type ipaddr;
                   description "Address of node or link to be skipped";
                 }
                 leaf lsp-state {
                   type string;
                   description "State of an LSP";
                 }
                 leaf sender-tspec {
                   type string;
                   description "Sender TSpec";
                 }
                 leaf adspec {
                   type string;
                   description "Adspec data element in an RSVP Path message";
                 }
                 leaf path-mtu {
                   type int32;
                   description "The value of the path MTU, as negotiated by the network";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container detour-branch-labels {
                   container packet-information {
                     description "RSVP packets sent or received per session";
                     leaf packet-information.heading {
                       type string;
                       description "RSVP packets sent or received per session";
                     }
                     leaf previous-hop {
                       type ipaddr;
                       description "Previous-hop address";
                     }
                     leaf next-hop {
                       type ipaddr;
                       description "Next-hop address";
                     }
                     leaf interface-name {
                       type string;
                       description "Name of interface";
                     }
                     leaf count {
                       type int32;
                     }
                     leaf notify-destination {
                       type ipaddr;
                       description "Notify address";
                     }
                     leaf entropy-label {
                       type string;
                       description "Entropy label";
                     }
                     leaf in-message-handle {
                       type string;
                       description "RSVP I/O handle for incoming message";
                     }
                     leaf in-message-id {
                       type uint32;
                       description "Incoming Message ID";
                     }
                     leaf in-epoch {
                       type uint32;
                       description "Incoming Epoch";
                     }
                     leaf out-message-state {
                       type string;
                       description "RSVP I/O state for outgoing message";
                     }
                     leaf out-message-id {
                       type uint32;
                       description "Outgoing Message ID";
                     }
                     leaf out-epoch {
                       type uint32;
                       description "Outgoing Epoch";
                     }
                   }
                 }
               }
             }
           }
         }
       }
     }
   }
   rpc get-mpls-lsp-defaults-information {
     description "Display LSP defaults";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
     }
     output {
       container mpls-lsp-defaults-information {
         container mpls-lsp-defaults {
           leaf lsp-hold-priority {
             type int32;
             description "Default priority for holding resources";
           }
           leaf lsp-setup-priority {
             type int32;
             description "Default priority for taking resources";
           }
           leaf lsp-hoplimit {
             type int32;
             description "Maximum number of hops that can be traversed";
           }
           leaf lsp-bandwidth {
             type int32;
             description "Default LSP Bandwidth";
           }
           leaf lsp-retry-timer {
             type int32;
           }
         }
       }
     }
   }
   rpc get-mpls-lsp-autobandwidth {
     description "Display autobandwidth statistics for LSPs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf level {
         default "brief";
         type enumeration {
           enum "brief" {
             description "Display brief output (default)";
           }
           enum "detail" {
             description "Display detailed output";
           }
           enum "extensive" {
             description "Display extensive output";
           }
         }
       }
     }
     output {
       container mpls-lsp-information {
         container rsvp-session-data {
           leaf session-type {
             type string;
             description "Type of session with respect to this router";
           }
           leaf count {
             type int32;
           }
           leaf detours {
             type int32;
             description "Number of detour sessions";
           }
           leaf display-count {
             type int32;
             description "Number of sessions displayed";
           }
           leaf up-count {
             type int32;
             description "Number of sessions in up state";
           }
           leaf down-count {
             type int32;
             description "Number of sessions in down state";
           }
           container rsvp-session {
             description "Single RSVP session";
             container brief {
               description "Single RSVP session";
               leaf destination-address {
                 type ipaddr;
                 description "Session destination address";
               }
               leaf source-address {
                 type ipaddr;
               }
               leaf lsp-state {
                 type string;
                 description "State of an LSP";
               }
               leaf route-count {
                 type int32;
                 description "Number of active routes";
               }
               leaf rsb-count {
                 type int32;
                 description "Number of RSBs";
               }
               leaf resv-style {
                 type string;
               }
               leaf label-in {
                 type string;
                 description "Incoming label";
               }
               leaf label-out {
                 type string;
                 description "Outgoing label";
               }
               leaf name {
                 type string;
               }
               leaf bidirectional {
                 type empty;
                 description "LSP is bidirectional";
               }
               leaf associated-bidirectional {
                 type empty;
                 description "LSP is associated-bidirectional";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf is-primary {
                   type empty;
                   description "Path is a primary path";
                 }
                 leaf active-path {
                   type string;
                   description "Path that the LSP is currently using";
                 }
                 leaf name {
                   type string;
                 }
                 leaf bidirectional {
                   type empty;
                   description "LSP is bidirectional";
                 }
                 leaf associated-bidirectional {
                   type empty;
                   description "LSP is associated-bidirectional";
                 }
                 leaf ext-assoc-bidir {
                   type empty;
                   description "Extended associated bidirectional LSP";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container descriptions {
               description "Single RSVP session";
               leaf destination-address {
                 type ipaddr;
                 description "Session destination address";
               }
               leaf source-address {
                 type ipaddr;
               }
               leaf name {
                 type string;
               }
               leaf lsp-description {
                 type string;
                 description "LSP description string (up to 80 characters)";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf name {
                   type string;
                 }
                 leaf lsp-description {
                   type string;
                   description "LSP description string (up to 80 characters)";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container brief_stats {
               description "Single RSVP session";
               leaf destination-address {
                 type ipaddr;
                 description "Session destination address";
               }
               leaf source-address {
                 type ipaddr;
               }
               leaf lsp-state {
                 type string;
                 description "State of an LSP";
               }
               leaf lsp-pktbytes {
                 type string;
                 description "LSP packet and byte counters";
               }
               leaf name {
                 type string;
               }
               leaf bidirectional {
                 type empty;
                 description "LSP is bidirectional";
               }
               leaf associated-bidirectional {
                 type empty;
                 description "LSP is associated-bidirectional";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 leaf ext-assoc-bidir {
                   type empty;
                   description "Extended associated bidirectional LSP";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container brief_xc {
               description "Single RSVP session";
               leaf source-address {
                 type ipaddr;
               }
               leaf lsp-id {
                 type string;
               }
               leaf p2mp-branch-id {
                 type uint32;
               }
               leaf lsp-state {
                 type string;
                 description "State of an LSP";
               }
               leaf xc-psb-list {
                 type string;
                 description "List of PSBs part of the RSVP xc";
               }
               leaf xc-rsb-list {
                 type string;
                 description "List of RSBs part of the RSVP xc";
               }
               leaf name {
                 type string;
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   leaf name {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container detail {
               description "Single RSVP session";
               leaf destination-address {
                 type ipaddr;
                 description "Session destination address";
               }
               leaf is-detour {
                 type empty;
                 description "Session is a detour session";
               }
               leaf source-address {
                 type ipaddr;
               }
               leaf lsp-state {
                 type string;
                 description "State of an LSP";
               }
               leaf route-count {
                 type int32;
                 description "Number of active routes";
               }
               leaf name {
                 type string;
               }
               leaf lsp-path-type {
                 type string;
                 description "Primary or secondary LSP path";
               }
               leaf graceful-deletion-triggered {
                 type empty;
                 description "Initiated graceful deletion procedure for the LSP";
               }
               leaf mpls-lsp-type {
                 type string;
                 description "Type of LSP";
               }
               leaf lsp-description {
                 type string;
                 description "LSP description string (up to 80 characters)";
               }
               leaf source-tna-address {
                 type ipaddr;
                 description "Source TNA address for the connection";
               }
               leaf destination-tna-address {
                 type ipaddr;
                 description "Destination TNA address for the connection";
               }
               leaf bidirectional {
                 type empty;
                 description "LSP is bidirectional";
               }
               leaf associated-bidirectional {
                 type empty;
                 description "LSP is associated-bidirectional";
               }
               leaf upstream-label-in {
                 type string;
                 description "Incoming upstream label";
               }
               leaf upstream-label-out {
                 type string;
                 description "Outgoing upstream label";
               }
               leaf lsp-associated-lspname {
                 type string;
                 description "Associated LSP name";
               }
               leaf lsp-associated-lspsrc {
                 type string;
                 description "Associated LSP source address";
               }
               leaf mpls-p2mp-lsp-name {
                 type string;
               }
               leaf p2mp-remerge-state {
                 type string;
                 description "Re-merge status of the P2MP sub-LSP";
               }
               leaf lsp-aggregation {
                 type string;
                 description "Supports LSP aggregation";
               }
               leaf suggested-label-in {
                 type int32;
                 description "Suggested label received";
               }
               leaf suggested-label-out {
                 type int32;
                 description "Suggested label sent";
               }
               leaf recovery-label-in {
                 type int32;
               }
               leaf recovery-label-out {
                 type int32;
               }
               leaf lsp-pktbytes {
                 type string;
                 description "LSP packet and byte counters";
               }
               leaf no-statistics {
                 type empty;
                 description "No statistics are available for this session";
               }
               leaf rsb-count {
                 type int32;
                 description "Number of RSBs";
               }
               leaf resv-style {
                 type string;
               }
               leaf label-in {
                 type string;
                 description "Incoming label";
               }
               leaf label-out {
                 type string;
                 description "Outgoing label";
               }
               leaf psb-lifetime {
                 type int32;
                 description "Lifetime for a PSB after which the entry expires";
               }
               leaf psb-creation-time {
                 type string;
                 description "Time when this PSB was created";
               }
               leaf path-mtu {
                 type int32;
                 description "The value of the path MTU, as negotiated by the network";
               }
               leaf path-mtu-in-kernel {
                 type int32;
                 description "The value of the MTU used locally for forwarding";
               }
               leaf sender-tspec {
                 type string;
                 description "Sender TSpec";
               }
               leaf adspec {
                 type string;
                 description "Adspec data element in an RSVP Path message";
               }
               leaf lsp-diffserv-info {
                 type string;
                 description "LSP DiffServ info";
               }
               leaf ct-bw {
                 type string;
                 description "Per-class bandwidth requested for E-LSPs and L-LSPs";
               }
               leaf lsp-id {
                 type string;
               }
               leaf tunnel-id {
                 type int32;
               }
               leaf proto-id {
                 type int32;
               }
               leaf p2mp-branch-id {
                 type uint32;
               }
               leaf p2mp-subgroup-orig {
                 type ipaddr;
               }
               leaf self-id {
                 type string;
                 description "Statistics identifier for RSVP path state control block";
               }
               leaf nh-statistics-id {
                 type string;
                 description "Nexthop statistics identifier for RSVP path at ingress";
               }
               leaf route-statistics-id {
                 type string;
                 description "Route statistics identifier for RSVP path at egress";
               }
               leaf nh-traffic-class-statistics {
                 type empty;
                 description "Traffic class statistics are enabled at ingress";
               }
               leaf route-traffic-class-statistics {
                 type empty;
                 description "Traffic class statistics are enabled at egress";
               }
               leaf session-id {
                 type int32;
                 description "Unique identifier for RSVP session";
               }
               leaf is-fastreroute {
                 type empty;
                 description "Fast reroute (one-to-one backup) is desired";
               }
               leaf is-linkprotection {
                 type empty;
                 description "Link protection (facility backup) is desired";
               }
               leaf is-nodeprotection {
                 type empty;
                 description "Link-Node protection (facility backup) is desired";
               }
               leaf ep-plr-protector {
                 type string;
               }
               leaf is-soft-preemption {
                 type empty;
                 description "Soft-preemption is desired";
               }
               leaf rsvp-path-status {
                 type string;
               }
               leaf bypass-name {
                 type string;
                 description "Name of the bypass";
               }
               leaf rsvp-lp-backup-route-cnt {
                 type int32;
                 description "Number of routes tunneled through this bypass";
               }
               leaf rsvp-lp-backup-lsp-cnt {
                 type int32;
                 description "Number of backup RSVP LSPs tunneled through this bypass";
               }
               leaf entropy-label {
                 type string;
                 description "Entropy label";
               }
               leaf p2mp-self-id {
                 type string;
                 description "Statistics identifier for RSVP P2MP path state control block";
               }
               container layer2-tspec {
                 description "Layer 2 TSpec";
                 leaf switching-granularity {
                   type string;
                   description "Layer 2 switching granularity";
                 }
                 leaf mtu {
                   type int32;
                   description "MTU along an interface";
                 }
                 leaf atm-vp-bundle-size {
                   type int32;
                   description "VP bundle size";
                 }
                 leaf atm-cell-bundle-size {
                   type int32;
                   description "Maximum cell bundle size";
                 }
               }
               container rsvp-lsp-enh-local-prot-status {
                 description "Enhanced FRR local protection status";
                 leaf rsvp-lsp-enh-local-prot-admin-status {
                   type string;
                   description "Enhanced FRR local protection admin status";
                 }
                 leaf rsvp-lsp-enh-local-prot-disabled-reason {
                   type string;
                   description "Enhanced FRR local protection disabled reason";
                 }
                 leaf rsvp-lsp-enh-local-prot-refresh-interval {
                   type string;
                   description "Enhanced FRR refresh interval set for LSP";
                 }
               }
               container rsvp-lsp-enh-local-prot-upstream {
                 description "Enhanced FRR local protection upstream information";
                 leaf rsvp-lsp-enh-lp-upstream-status {
                   type string;
                   description "Enhanced FRR local protection status upstream";
                 }
                 leaf rsvp-lsp-enh-lp-upstream-lp {
                   type string;
                   description "The node is LP-MP for Phop";
                 }
                 leaf rsvp-lsp-enh-lp-phop-addr {
                   type ipaddr;
                   description "Phop PLR for which this node is LP-MP";
                 }
                 leaf rsvp-lsp-enh-lp-upstream-lp-status {
                   type string;
                   description "Current upstream LP-MP status";
                 }
                 leaf rsvp-lsp-enh-lp-upstream-np {
                   type string;
                   description "The node is NP-MP for PPhop";
                 }
                 leaf rsvp-lsp-enh-lp-pphop-addr {
                   type ipaddr;
                   description "PPhop PLR for which this node is NP-MP";
                 }
                 leaf rsvp-lsp-enh-lp-upstream-np-status {
                   type string;
                   description "Current upstream NP-MP status";
                 }
                 leaf rsvp-lsp-enh-lp-upstream-disabled-reason {
                   type string;
                   description "Reason enhanced local protection is disabled upstream";
                 }
                 leaf rsvp-lsp-enh-local-prot-refresh-interval {
                   type string;
                   description "Enhanced FRR refresh interval set for LSP";
                 }
               }
               container rsvp-lsp-enh-local-prot-downstream {
                 description "Enhanced FRR local protection downstream information";
                 leaf rsvp-lsp-enh-lp-downstream-status {
                   type string;
                   description "Enhanced FRR local protection status downstream";
                 }
                 leaf rsvp-lsp-enh-lp-downstream-lp {
                   type string;
                   description "The node has made link protection available";
                 }
                 leaf rsvp-lsp-enh-lp-nhop-addr {
                   type ipaddr;
                   description "Nhop MP neigbor address";
                 }
                 leaf rsvp-lsp-enh-lp-downstream-np {
                   type string;
                   description "The node has made node protection available";
                 }
                 leaf rsvp-lsp-enh-lp-nnhop-addr {
                   type ipaddr;
                   description "NNhop MP neighbor address";
                 }
                 leaf rsvp-lsp-enh-lp-current-status {
                   type string;
                   description "Current downstream protection status";
                 }
                 leaf rsvp-lsp-enh-lp-downstream-disabled-reason {
                   type string;
                   description "Reason enhanced local protection is disabled downstream";
                 }
                 leaf rsvp-lsp-enh-local-prot-refresh-interval {
                   type string;
                   description "Enhanced FRR refresh interval set for LSP";
                 }
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf entropy-label {
                   type string;
                   description "Entropy label";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container record-route {
                 description "Record Route Object (RRO)";
                 leaf record-route.heading {
                   type string;
                   description "Record Route Object (RRO)";
                 }
                 leaf address {
                   type ipaddr;
                 }
                 leaf telink-id {
                   type int32;
                   description "Link identifier of unnumbered link";
                 }
                 leaf self {
                   type empty;
                 }
                 leaf incomplete {
                   type empty;
                 }
               }
               container lsp-attribute-flags {
                 description "LSP attribute flags";
                 leaf non-php {
                   type empty;
                   description "Non-PHP";
                 }
                 leaf oob {
                   type empty;
                   description "Out-of-band mapping";
                 }
               }
               container lp-history {
                 description "Log of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container rsvp-telink {
                 leaf active-reservation {
                   type int32;
                   description "Number of active reservations";
                 }
                 leaf preemption-count {
                   type int32;
                   description "Number of preemptions that occurred on an interface";
                 }
                 leaf update-threshold {
                   type int32;
                   description "Percentage change in reserved bandwidth to trigger IGP update";
                 }
                 leaf subscription {
                   type int32;
                   description "Percentage of link capacity available for bandwidth reservations";
                 }
                 leaf bc {
                   type int32;
                   description "Bandwidth constraint (0..7)";
                 }
                 leaf bc-description {
                   type string;
                   description "Description of the bandwidth constraint";
                 }
                 leaf static-bc-bandwidth {
                   type int32;
                   description "Static bandwidth capacity for a bandwidth constraint";
                 }
                 leaf ct-class {
                   type int32;
                   description "Class type (0..7)";
                 }
                 leaf static-bandwidth {
                   type int32;
                   description "Static bandwidth capacity of the link";
                 }
                 leaf available-bandwidth {
                   type int32;
                   description "Amount of bandwidth available for reservations";
                 }
                 leaf ct-subscription {
                   type int32;
                   description "Subscription percentage per traffic class";
                 }
                 leaf max-available-bandwidth {
                   type int32;
                   description "Maximum amount of bandwidth available for reservations, including the subscription factor";
                 }
                 leaf max-available-description {
                   type string;
                   description "Description of the computation of the maximum available bandwidth";
                 }
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                 }
               }
               container protection-attribute {
                 description "Protection attributes of RSVP session";
                 leaf protect-lsp-type {
                   type string;
                   description "Type of LSP for protection purposes";
                 }
                 leaf protect-lsp-role {
                   type string;
                   description "Role of LSP for protection purposes";
                 }
                 leaf protect-protection-type {
                   type string;
                   description "Type of protection being used";
                 }
                 leaf protect-secondary-operational {
                   type empty;
                   description "Protecting LSP is operational and carrying protected traffic";
                 }
               }
               container association-attribute {
                 description "Association attributes of RSVP session";
                 leaf association-type {
                   type string;
                   description "Type of association object";
                 }
                 leaf association-source {
                   type ipaddr;
                   description "Source node defining the association";
                 }
                 leaf association-id {
                   type int32;
                   description "Identifier for the association";
                 }
               }
               container detour {
                 description "Detour session";
                 leaf lsp-state {
                   type string;
                   description "State of an LSP";
                 }
                 leaf sender-tspec {
                   type string;
                   description "Sender TSpec";
                 }
                 leaf lsp-diffserv-info {
                   type string;
                   description "LSP DiffServ info";
                 }
                 leaf ct-bw {
                   type string;
                   description "Per-class bandwidth requested for E-LSPs and L-LSPs";
                 }
                 leaf adspec {
                   type string;
                   description "Adspec data element in an RSVP Path message";
                 }
                 leaf path-mtu {
                   type int32;
                   description "The value of the path MTU, as negotiated by the network";
                 }
                 leaf path-mtu-in-kernel {
                   type int32;
                   description "The value of the MTU used locally for forwarding";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container record-route {
                   description "Record Route Object (RRO)";
                   leaf record-route.heading {
                     type string;
                     description "Record Route Object (RRO)";
                   }
                   leaf address {
                     type ipaddr;
                   }
                   leaf telink-id {
                     type int32;
                     description "Link identifier of unnumbered link";
                   }
                   leaf self {
                     type empty;
                   }
                   leaf incomplete {
                     type empty;
                   }
                 }
               }
               container detour-branch {
                 description "Branch of some detour session";
                 leaf source-address {
                   type ipaddr;
                 }
                 leaf skip-address {
                   type ipaddr;
                   description "Address of node or link to be skipped";
                 }
                 leaf lsp-state {
                   type string;
                   description "State of an LSP";
                 }
                 leaf sender-tspec {
                   type string;
                   description "Sender TSpec";
                 }
                 leaf adspec {
                   type string;
                   description "Adspec data element in an RSVP Path message";
                 }
                 leaf path-mtu {
                   type int32;
                   description "The value of the path MTU, as negotiated by the network";
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container record-route {
                   description "Record Route Object (RRO)";
                   leaf record-route.heading {
                     type string;
                     description "Record Route Object (RRO)";
                   }
                   leaf address {
                     type ipaddr;
                   }
                   leaf telink-id {
                     type int32;
                     description "Link identifier of unnumbered link";
                   }
                   leaf self {
                     type empty;
                   }
                   leaf incomplete {
                     type empty;
                   }
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container detour-branch-labels {
                   leaf label-in {
                     type string;
                     description "Incoming label";
                   }
                   leaf label-out {
                     type string;
                     description "Outgoing label";
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf name {
                   type string;
                 }
                 leaf lsp-type {
                   type string;
                   description "Type of LSP";
                 }
                 leaf egress-label-operation {
                   type string;
                   description "Label advertised by egress";
                 }
                 leaf lsp-control-status {
                   type string;
                   description "Control status of LSP configured to be externally controlled";
                 }
                 leaf lsp-diffserv-te-info {
                   type string;
                   description "LSP support of DiffServ-TE extensions";
                 }
                 leaf bidirectional {
                   type empty;
                   description "LSP is bidirectional";
                 }
                 leaf associated-bidirectional {
                   type empty;
                   description "LSP is associated-bidirectional";
                 }
                 leaf lsp-associated-lspname {
                   type string;
                   description "Associated LSP name";
                 }
                 leaf lsp-associated-lspsrc {
                   type string;
                   description "Associated LSP source address";
                 }
                 leaf ext-assoc-bidir {
                   type empty;
                   description "Extended associated bidirectional LSP";
                 }
                 leaf ext-assoc-bidir-direction {
                   type string;
                   description "Ext-Assoc-Bidir direction";
                 }
                 leaf lsp-description {
                   type string;
                   description "LSP description string (up to 80 characters)";
                 }
                 leaf lsp-pktbytes {
                   type string;
                   description "LSP packet and byte counters";
                 }
                 leaf aggregate-lsp-pktbytes {
                   type string;
                   description "Aggregate LSP packet and byte counters";
                 }
                 leaf no-statistics {
                   type empty;
                   description "No statistics are available for this session";
                 }
                 leaf active-path {
                   type string;
                   description "Path that the LSP is currently using";
                 }
                 leaf mpls-p2mp-name {
                   type string;
                 }
                 leaf is-fastreroute {
                   type empty;
                   description "Fast reroute (one-to-one backup) is desired";
                 }
                 leaf is-linkprotection {
                   type empty;
                   description "Link protection (facility backup) is desired";
                 }
                 leaf is-nodeprotection {
                   type empty;
                   description "Link-Node protection (facility backup) is desired";
                 }
                 leaf is-inter-domain-path {
                   type empty;
                   description "Inter-domain LSP";
                 }
                 leaf load-balance {
                   type string;
                   description "Load-balancing algorithm chosen";
                 }
                 leaf metric {
                   type int32;
                 }
                 leaf actual-metric {
                   type int32;
                 }
                 leaf revert-timer {
                   type string;
                   description "Hold-down time before reverting to primary path.";
                 }
                 leaf revert-timer-remain {
                   type string;
                   description "Time remaining before reverting:";
                 }
                 leaf optimize-protection-timer {
                   type int32;
                   description "Optimize protection timer";
                 }
                 leaf lsp-creation-time {
                   type string;
                   description "Time when the LSP was created";
                 }
                 leaf lsp-soft-preemption-counter {
                   type int32;
                   description "Number of times the LSP was soft preempted";
                 }
                 leaf lsp-soft-preemption-time {
                   type string;
                   description "Time when the LSP was last soft preempted";
                 }
                 leaf retry-timer {
                   type int32;
                 }
                 leaf retry-limit {
                   type int32;
                 }
                 leaf lsp-packets {
                   type string;
                   description "LSP packet counters";
                 }
                 leaf lsp-bytes {
                   type string;
                   description "LSP byte counters";
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container mpls-srlg {
                   leaf srlg-name {
                     type string;
                     description "Name of the srlg";
                   }
                   leaf srlg-value {
                     type uint32;
                     description "Value of the srlg";
                   }
                   leaf srlg-cost {
                     type uint32;
                     description "Cost of the srlg";
                   }
                 }
                 container mpls-lsp-autobandwidth {
                   leaf monitor-lsp-bandwidth {
                     type empty;
                     description "Enable the bandwidth monitoring mode";
                   }
                   leaf minimum-bandwidth {
                     type int32;
                     description "Configured LSP minimum bandwidth";
                   }
                   leaf maximum-bandwidth {
                     type int32;
                     description "Configured LSP maximum bandwidth";
                   }
                   leaf dynamic-minimum-bandwidth {
                     type int32;
                     description "LSP dynamic minimum bandwidth (or last Max Avg Bw)";
                   }
                   leaf adjust-timer {
                     type int32;
                     description "Configured LSP adjust timer";
                   }
                   leaf adjust-threshold {
                     type int32;
                     description "Percentage change in average LSP utilization to trigger autoadjustment";
                   }
                   leaf adjust-threshold-activate-bandwidth {
                     type int32;
                     description "Configured LSP adjust threshold bandwidth";
                   }
                   leaf maximum-average-bandwidth {
                     type int32;
                     description "Maximum Average BW";
                   }
                   leaf time-to-adjust {
                     type int32;
                     description "Time in which LSP will autoadjust bandwidth";
                   }
                   leaf autobw-minimum-bandwidth-adjust-interval {
                     type int32;
                   }
                   leaf autobw-minimum-bandwidth-adjust-threshold-percent {
                     type int32;
                   }
                   leaf autobw-minimum-bandwidth-adjust-threshold-value {
                     type int32;
                   }
                   leaf time-to-expire-minimum-bandwidth-adjust {
                     type int32;
                     description "Time in which LSP will start changing minimum bandwidth";
                   }
                   leaf overflow-limit {
                     type int32;
                     description "Configured limit of consecutive overflow samples for LSP";
                   }
                   leaf overflow-sample-count {
                     type int32;
                     description "Number of consecutive overflow samples encountered";
                   }
                   leaf underflow-limit {
                     type int32;
                     description "Configured limit of consecutive underflow samples for LSP";
                   }
                   leaf underflow-sample-count {
                     type int32;
                     description "Number of consecutive underflow samples encountered";
                   }
                   leaf underflow-max-avg-bandwidth {
                     type int32;
                     description "Highest average bandwidth recorded so far for underflow samples";
                   }
                 }
                 container mpls-lsp-path {
                   description "Primary or secondary LSP path";
                   leaf path-active {
                     type empty;
                     description "Whether the path is active or not";
                   }
                   leaf title {
                     type string;
                   }
                   leaf name {
                     type string;
                   }
                   leaf path-state {
                     type string;
                     description "State of the MPLS path";
                   }
                   leaf cos {
                     type int32;
                     description "CoS value";
                   }
                   leaf no-decrement-ttl {
                     type empty;
                     description "TTL";
                   }
                   leaf preference {
                     type int32;
                     description "Preference for the route";
                   }
                   leaf path-soft-preemption-pending {
                     type empty;
                     description "Soft preemption pending for this path";
                   }
                   leaf setup-priority {
                     type int32;
                     description "Priority with respect to taking resources";
                   }
                   leaf hold-priority {
                     type int32;
                     description "Priority with respect to holding resources";
                   }
                   leaf actual-setup-priority {
                     type int32;
                   }
                   leaf actual-hold-priority {
                     type int32;
                   }
                   leaf external-lsp-cspf-type {
                     type string;
                   }
                   leaf bandwidth {
                     type int32;
                   }
                   leaf actual-bandwidth {
                     type int32;
                   }
                   leaf per-class-bandwidth-heading {
                     type string;
                   }
                   leaf bandwidth_ct0 {
                     type int32;
                   }
                   leaf bandwidth_ct1 {
                     type int32;
                   }
                   leaf bandwidth_ct2 {
                     type int32;
                   }
                   leaf bandwidth_ct3 {
                     type int32;
                   }
                   leaf path-adaptive {
                     type empty;
                     description "LSP is adaptive";
                   }
                   leaf path-no-recordroute {
                     type empty;
                     description "Record route disabled";
                   }
                   leaf hoplimit {
                     type int32;
                     description "Maximum number of hops that can be traversed";
                   }
                   leaf optimize-timer {
                     type int32;
                     description "Optimize timer";
                   }
                   leaf smart-optimize-timer {
                     type int32;
                     description "Smart optimize timer";
                   }
                   leaf retry-timer {
                     type int32;
                   }
                   leaf retry-limit {
                     type int32;
                   }
                   leaf external-cspf-status {
                     type string;
                     description "Status provided by External CSPF computation";
                   }
                   leaf cspf-status {
                     type string;
                     description "Status returned by CSPF computation";
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                   container mpls-srlg {
                     leaf srlg-name {
                       type string;
                       description "Name of the srlg";
                     }
                     leaf srlg-value {
                       type uint32;
                       description "Value of the srlg";
                     }
                     leaf srlg-cost {
                       type uint32;
                       description "Cost of the srlg";
                     }
                   }
                 }
                 container mpls-lsp-attributes {
                   leaf signal-type {
                     type string;
                   }
                   leaf encoding-type {
                     type string;
                     description "LSP encoding type";
                   }
                   leaf switching-type {
                     type string;
                     description "LSP switching capability";
                   }
                   leaf gpid {
                     type string;
                     description "LSP generalized PID";
                   }
                   leaf protection-type {
                     type string;
                     description "LSP protection desired";
                   }
                 }
               }
             }
           }
           container mpls-p2mp-lsp {
             leaf mpls-p2mp-name {
               type string;
             }
             leaf mpls-p2mp-branch-count {
               type string;
             }
           }
           container mpls-container-lsp {
             description "MPLS container-label-switched path information";
             leaf mpls-container-lsp-name {
               type string;
             }
             leaf mpls-container-lsp-state {
               type string;
             }
             leaf mpls-container-member-count {
               type string;
             }
             leaf container-active-path {
               type string;
               description "Path that the member LSP is currently using";
             }
             leaf container-is-primary {
               type empty;
               description "Path is a primary path";
             }
             leaf lsp-packets {
               type string;
               description "LSP packet counters";
             }
             leaf lsp-bytes {
               type string;
               description "LSP byte counters";
             }
             leaf lsp-control-status {
               type string;
               description "Control status of LSP configured to be externally controlled";
             }
             container mpls-lsp-path {
               description "Primary or secondary LSP path";
               container admin-groups {
                 leaf admin-groups.heading {
                   type string;
                 }
                 leaf color {
                   type int32;
                 }
                 leaf no-group-flag {
                   type empty;
                 }
                 leaf admin-group-name {
                   type string;
                   description "Name of the admin group";
                 }
                 leaf admin-group-number {
                   type int32;
                   description "Number of the admin group";
                 }
               }
               container admin-groups-extended {
                 leaf admin-groups-extended.heading {
                   type string;
                 }
                 leaf admin-group-name {
                   type string;
                   description "Name of the admin group";
                 }
                 leaf admin-group-number {
                   type int32;
                   description "Number of the admin group";
                 }
               }
               container srlg {
                 leaf srlg.heading {
                   type string;
                 }
                 leaf srlg-name {
                   type string;
                   description "Name of the srlg";
                 }
               }
               container mpls-lsp-upstream-label {
                 description "Upstream label configured for the LSP";
                 leaf vlan-id-label {
                   type uint32;
                   description "VLAN ID label configured for the LSP";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container oam-state {
                 description "OAM state information";
                 leaf oam-bfd-session-state {
                   type string;
                 }
                 leaf oam-lsp-ping-state {
                   type string;
                 }
               }
               container path-history {
                 description "Log over time of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container path-available-bandwidth {
                 description "Available bandwidth on an LSP path";
                 leaf path-available-bandwidth.heading {
                   type string;
                   description "Available bandwidth on an LSP path";
                 }
                 leaf bandwidth {
                   type int32;
                 }
                 leaf class-type {
                   type int32;
                 }
                 leaf class-bandwidth {
                   type int32;
                 }
               }
               container layer2-connection {
                 description "Layer 2 connection using the LSP path";
                 leaf neighbor-address {
                   type ipaddr;
                   description "IP address of this neighbor";
                 }
                 leaf interface-name {
                   type string;
                   description "Name of interface";
                 }
                 leaf vc-id {
                   type int32;
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
               }
             }
             container mpls-container-lsp-splitting-merging {
               leaf minimum-member-lsps {
                 type int32;
                 description "Configured minimum LSPs";
               }
               leaf maximum-member-lsps {
                 type int32;
                 description "Configured maximum LSPs";
               }
               leaf aggregate-bandwidth {
                 type int32;
                 description "Aggregate bandwidth";
               }
               leaf current-bandwidth {
                 type int32;
                 description "Sampled Aggregate bandwidth";
               }
               leaf normalize-interval {
                 type int32;
                 description "Configured LSP normalize timer";
               }
               leaf splitting-merging-threshold {
                 type int32;
                 description "Percentage change in aggregate LSP utilization to trigger normalization";
               }
               leaf maximum-signaling-bandwidth {
                 type int32;
                 description "Configured signaling maximum bandwidth";
               }
               leaf minimum-signaling-bandwidth {
                 type int32;
                 description "Configured signaling minimum bandwidth";
               }
               leaf maximum-splitting-bandwidth {
                 type int32;
                 description "Configured splitting maximum bandwidth";
               }
               leaf minimum-splitting-bandwidth {
                 type int32;
                 description "Configured splitting minimum bandwidth";
               }
               leaf normalization-mode {
                 type string;
               }
               leaf sampling-mode {
                 type string;
                 description "Sampling Attributes";
               }
               leaf time-to-normalize {
                 type int32;
                 description "Time in which LSP will normalize";
               }
               leaf aggregate-packets {
                 type int32;
                 description "Aggregate packets";
               }
               leaf aggregate-bytes {
                 type int32;
                 description "Aggregate bytes";
               }
             }
             container mpls-container-lsp-history {
               description "Log over time of container LSP related events";
               leaf sequence-number {
                 type int32;
                 description "History event number";
               }
               leaf time {
                 type string;
                 description "Time of the event";
               }
               leaf log {
                 type string;
                 description "Supplemental information of the event";
               }
               leaf route {
                 type string;
                 description "Latest RRO contents, as reported by RSVP";
               }
             }
           }
           container mpls-container-lsp-member-summary {
             container mpls-container-lsp {
               description "MPLS container-label-switched path information";
               leaf mpls-container-lsp-name {
                 type string;
               }
               leaf mpls-container-lsp-state {
                 type string;
               }
               leaf mpls-container-member-count {
                 type string;
               }
               leaf container-active-path {
                 type string;
                 description "Path that the member LSP is currently using";
               }
               leaf container-is-primary {
                 type empty;
                 description "Path is a primary path";
               }
               leaf lsp-packets {
                 type string;
                 description "LSP packet counters";
               }
               leaf lsp-bytes {
                 type string;
                 description "LSP byte counters";
               }
               leaf lsp-control-status {
                 type string;
                 description "Control status of LSP configured to be externally controlled";
               }
               container mpls-lsp-path {
                 description "Primary or secondary LSP path";
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container srlg {
                   leaf srlg.heading {
                     type string;
                   }
                   leaf srlg-name {
                     type string;
                     description "Name of the srlg";
                   }
                 }
                 container mpls-lsp-upstream-label {
                   description "Upstream label configured for the LSP";
                   leaf vlan-id-label {
                     type uint32;
                     description "VLAN ID label configured for the LSP";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container oam-state {
                   description "OAM state information";
                   leaf oam-bfd-session-state {
                     type string;
                   }
                   leaf oam-lsp-ping-state {
                     type string;
                   }
                 }
                 container path-history {
                   description "Log over time of LSP path-related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
                 container path-available-bandwidth {
                   description "Available bandwidth on an LSP path";
                   leaf path-available-bandwidth.heading {
                     type string;
                     description "Available bandwidth on an LSP path";
                   }
                   leaf bandwidth {
                     type int32;
                   }
                   leaf class-type {
                     type int32;
                   }
                   leaf class-bandwidth {
                     type int32;
                   }
                 }
                 container layer2-connection {
                   description "Layer 2 connection using the LSP path";
                   leaf neighbor-address {
                     type ipaddr;
                     description "IP address of this neighbor";
                   }
                   leaf interface-name {
                     type string;
                     description "Name of interface";
                   }
                   leaf vc-id {
                     type int32;
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                 }
               }
               container mpls-container-lsp-splitting-merging {
                 leaf minimum-member-lsps {
                   type int32;
                   description "Configured minimum LSPs";
                 }
                 leaf maximum-member-lsps {
                   type int32;
                   description "Configured maximum LSPs";
                 }
                 leaf aggregate-bandwidth {
                   type int32;
                   description "Aggregate bandwidth";
                 }
                 leaf current-bandwidth {
                   type int32;
                   description "Sampled Aggregate bandwidth";
                 }
                 leaf normalize-interval {
                   type int32;
                   description "Configured LSP normalize timer";
                 }
                 leaf splitting-merging-threshold {
                   type int32;
                   description "Percentage change in aggregate LSP utilization to trigger normalization";
                 }
                 leaf maximum-signaling-bandwidth {
                   type int32;
                   description "Configured signaling maximum bandwidth";
                 }
                 leaf minimum-signaling-bandwidth {
                   type int32;
                   description "Configured signaling minimum bandwidth";
                 }
                 leaf maximum-splitting-bandwidth {
                   type int32;
                   description "Configured splitting maximum bandwidth";
                 }
                 leaf minimum-splitting-bandwidth {
                   type int32;
                   description "Configured splitting minimum bandwidth";
                 }
                 leaf normalization-mode {
                   type string;
                 }
                 leaf sampling-mode {
                   type string;
                   description "Sampling Attributes";
                 }
                 leaf time-to-normalize {
                   type int32;
                   description "Time in which LSP will normalize";
                 }
                 leaf aggregate-packets {
                   type int32;
                   description "Aggregate packets";
                 }
                 leaf aggregate-bytes {
                   type int32;
                   description "Aggregate bytes";
                 }
               }
               container mpls-container-lsp-history {
                 description "Log over time of container LSP related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
             }
           }
           container container-rsvp-session {
             container brief {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf is-primary {
                   type empty;
                   description "Path is a primary path";
                 }
                 leaf active-path {
                   type string;
                   description "Path that the LSP is currently using";
                 }
                 leaf container-member-name {
                   type string;
                   description "Path that the member LSP is currently using";
                 }
                 leaf label-out {
                   type string;
                   description "Outgoing label";
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf label-out {
                   type string;
                   description "Outgoing label";
                 }
               }
               container detour {
                 description "Detour session";
                 leaf lsp-state {
                   type string;
                   description "State of an LSP";
                 }
                 leaf label-out {
                   type string;
                   description "Outgoing label";
                 }
               }
               container detour-branch {
                 description "Branch of some detour session";
                 container detour-branch-labels {
                 }
               }
             }
             container descriptions {
               container mpls-container-lsp {
                 description "MPLS container-label-switched path information";
                 leaf destination-address {
                   type ipaddr;
                   description "Session destination address";
                 }
                 leaf source-address {
                   type ipaddr;
                 }
                 leaf lsp-description {
                   type string;
                   description "LSP description string (up to 80 characters)";
                 }
                 leaf container-active-path {
                   type string;
                   description "Path that the member LSP is currently using";
                 }
                 leaf container-is-primary {
                   type empty;
                   description "Path is a primary path";
                 }
                 leaf lsp-packets {
                   type string;
                   description "LSP packet counters";
                 }
                 leaf lsp-bytes {
                   type string;
                   description "LSP byte counters";
                 }
                 leaf lsp-control-status {
                   type string;
                   description "Control status of LSP configured to be externally controlled";
                 }
                 container mpls-lsp-path {
                   description "Primary or secondary LSP path";
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
                 container mpls-container-lsp-splitting-merging {
                   leaf minimum-member-lsps {
                     type int32;
                     description "Configured minimum LSPs";
                   }
                   leaf maximum-member-lsps {
                     type int32;
                     description "Configured maximum LSPs";
                   }
                   leaf aggregate-bandwidth {
                     type int32;
                     description "Aggregate bandwidth";
                   }
                   leaf current-bandwidth {
                     type int32;
                     description "Sampled Aggregate bandwidth";
                   }
                   leaf normalize-interval {
                     type int32;
                     description "Configured LSP normalize timer";
                   }
                   leaf splitting-merging-threshold {
                     type int32;
                     description "Percentage change in aggregate LSP utilization to trigger normalization";
                   }
                   leaf maximum-signaling-bandwidth {
                     type int32;
                     description "Configured signaling maximum bandwidth";
                   }
                   leaf minimum-signaling-bandwidth {
                     type int32;
                     description "Configured signaling minimum bandwidth";
                   }
                   leaf maximum-splitting-bandwidth {
                     type int32;
                     description "Configured splitting maximum bandwidth";
                   }
                   leaf minimum-splitting-bandwidth {
                     type int32;
                     description "Configured splitting minimum bandwidth";
                   }
                   leaf normalization-mode {
                     type string;
                   }
                   leaf sampling-mode {
                     type string;
                     description "Sampling Attributes";
                   }
                   leaf time-to-normalize {
                     type int32;
                     description "Time in which LSP will normalize";
                   }
                   leaf aggregate-packets {
                     type int32;
                     description "Aggregate packets";
                   }
                   leaf aggregate-bytes {
                     type int32;
                     description "Aggregate bytes";
                   }
                 }
                 container mpls-container-lsp-history {
                   description "Log over time of container LSP related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
               }
               container mpls-lsp {
                 description "MPLS label-switched path information";
                 leaf destination-address {
                   type ipaddr;
                   description "Session destination address";
                 }
                 leaf name {
                   type string;
                 }
                 leaf lsp-description {
                   type string;
                   description "LSP description string (up to 80 characters)";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container detour {
                 description "Detour session";
               }
               container detour-branch {
                 description "Branch of some detour session";
               }
             }
             container brief_stats {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container detour {
                 description "Detour session";
               }
               container detour-branch {
                 description "Branch of some detour session";
               }
             }
             container detail {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf lsp-type {
                   type string;
                   description "Type of LSP";
                 }
                 leaf egress-label-operation {
                   type string;
                   description "Label advertised by egress";
                 }
                 leaf lsp-diffserv-te-info {
                   type string;
                   description "LSP support of DiffServ-TE extensions";
                 }
                 leaf lsp-description {
                   type string;
                   description "LSP description string (up to 80 characters)";
                 }
                 leaf lsp-pktbytes {
                   type string;
                   description "LSP packet and byte counters";
                 }
                 leaf aggregate-lsp-pktbytes {
                   type string;
                   description "Aggregate LSP packet and byte counters";
                 }
                 leaf no-statistics {
                   type empty;
                   description "No statistics are available for this session";
                 }
                 leaf active-path {
                   type string;
                   description "Path that the LSP is currently using";
                 }
                 leaf mpls-container-name {
                   type string;
                   description "Name of the container LSP";
                 }
                 leaf is-fastreroute {
                   type empty;
                   description "Fast reroute (one-to-one backup) is desired";
                 }
                 leaf is-linkprotection {
                   type empty;
                   description "Link protection (facility backup) is desired";
                 }
                 leaf is-nodeprotection {
                   type empty;
                   description "Link-Node protection (facility backup) is desired";
                 }
                 leaf is-inter-domain-path {
                   type empty;
                   description "Inter-domain LSP";
                 }
                 leaf load-balance {
                   type string;
                   description "Load-balancing algorithm chosen";
                 }
                 leaf metric {
                   type int32;
                 }
                 leaf optimize-protection-timer {
                   type int32;
                   description "Optimize protection timer";
                 }
                 leaf lsp-creation-time {
                   type string;
                   description "Time when the LSP was created";
                 }
                 leaf lsp-soft-preemption-counter {
                   type int32;
                   description "Number of times the LSP was soft preempted";
                 }
                 leaf lsp-soft-preemption-time {
                   type string;
                   description "Time when the LSP was last soft preempted";
                 }
                 leaf retry-timer {
                   type int32;
                 }
                 leaf retry-limit {
                   type int32;
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container srlg {
                   leaf srlg.heading {
                     type string;
                   }
                   leaf srlg-name {
                     type string;
                     description "Name of the srlg";
                   }
                 }
                 container mpls-lsp-upstream-label {
                   description "Upstream label configured for the LSP";
                   leaf vlan-id-label {
                     type uint32;
                     description "VLAN ID label configured for the LSP";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container oam-state {
                   description "OAM state information";
                   leaf oam-bfd-session-state {
                     type string;
                   }
                   leaf oam-lsp-ping-state {
                     type string;
                   }
                 }
                 container path-history {
                   description "Log over time of LSP path-related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
                 container path-available-bandwidth {
                   description "Available bandwidth on an LSP path";
                   leaf path-available-bandwidth.heading {
                     type string;
                     description "Available bandwidth on an LSP path";
                   }
                   leaf bandwidth {
                     type int32;
                   }
                   leaf class-type {
                     type int32;
                   }
                   leaf class-bandwidth {
                     type int32;
                   }
                 }
                 container layer2-connection {
                   description "Layer 2 connection using the LSP path";
                   leaf neighbor-address {
                     type ipaddr;
                     description "IP address of this neighbor";
                   }
                   leaf interface-name {
                     type string;
                     description "Name of interface";
                   }
                   leaf vc-id {
                     type int32;
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                 }
                 container mpls-srlg {
                   leaf srlg-name {
                     type string;
                     description "Name of the srlg";
                   }
                   leaf srlg-value {
                     type uint32;
                     description "Value of the srlg";
                   }
                   leaf srlg-cost {
                     type uint32;
                     description "Cost of the srlg";
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf label-out {
                   type string;
                   description "Outgoing label";
                 }
                 leaf path-mtu {
                   type int32;
                   description "The value of the path MTU, as negotiated by the network";
                 }
                 leaf path-mtu-in-kernel {
                   type int32;
                   description "The value of the MTU used locally for forwarding";
                 }
                 leaf sender-tspec {
                   type string;
                   description "Sender TSpec";
                 }
                 leaf adspec {
                   type string;
                   description "Adspec data element in an RSVP Path message";
                 }
                 leaf lsp-diffserv-info {
                   type string;
                   description "LSP DiffServ info";
                 }
                 leaf ct-bw {
                   type string;
                   description "Per-class bandwidth requested for E-LSPs and L-LSPs";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf entropy-label {
                   type string;
                   description "Entropy label";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container detour {
                 description "Detour session";
                 leaf lsp-state {
                   type string;
                   description "State of an LSP";
                 }
                 leaf sender-tspec {
                   type string;
                   description "Sender TSpec";
                 }
                 leaf lsp-diffserv-info {
                   type string;
                   description "LSP DiffServ info";
                 }
                 leaf ct-bw {
                   type string;
                   description "Per-class bandwidth requested for E-LSPs and L-LSPs";
                 }
                 leaf adspec {
                   type string;
                   description "Adspec data element in an RSVP Path message";
                 }
                 leaf path-mtu {
                   type int32;
                   description "The value of the path MTU, as negotiated by the network";
                 }
                 leaf path-mtu-in-kernel {
                   type int32;
                   description "The value of the MTU used locally for forwarding";
                 }
                 leaf label-out {
                   type string;
                   description "Outgoing label";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
               }
               container detour-branch {
                 description "Branch of some detour session";
                 leaf source-address {
                   type ipaddr;
                 }
                 leaf skip-address {
                   type ipaddr;
                   description "Address of node or link to be skipped";
                 }
                 leaf lsp-state {
                   type string;
                   description "State of an LSP";
                 }
                 leaf sender-tspec {
                   type string;
                   description "Sender TSpec";
                 }
                 leaf adspec {
                   type string;
                   description "Adspec data element in an RSVP Path message";
                 }
                 leaf path-mtu {
                   type int32;
                   description "The value of the path MTU, as negotiated by the network";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container detour-branch-labels {
                   container packet-information {
                     description "RSVP packets sent or received per session";
                     leaf packet-information.heading {
                       type string;
                       description "RSVP packets sent or received per session";
                     }
                     leaf previous-hop {
                       type ipaddr;
                       description "Previous-hop address";
                     }
                     leaf next-hop {
                       type ipaddr;
                       description "Next-hop address";
                     }
                     leaf interface-name {
                       type string;
                       description "Name of interface";
                     }
                     leaf count {
                       type int32;
                     }
                     leaf notify-destination {
                       type ipaddr;
                       description "Notify address";
                     }
                     leaf entropy-label {
                       type string;
                       description "Entropy label";
                     }
                     leaf in-message-handle {
                       type string;
                       description "RSVP I/O handle for incoming message";
                     }
                     leaf in-message-id {
                       type uint32;
                       description "Incoming Message ID";
                     }
                     leaf in-epoch {
                       type uint32;
                       description "Incoming Epoch";
                     }
                     leaf out-message-state {
                       type string;
                       description "RSVP I/O state for outgoing message";
                     }
                     leaf out-message-id {
                       type uint32;
                       description "Outgoing Message ID";
                     }
                     leaf out-epoch {
                       type uint32;
                       description "Outgoing Epoch";
                     }
                   }
                 }
               }
             }
           }
         }
       }
     }
   }
   rpc get-mpls-lsp-abstract-computation {
     description "Display abstract computation preprocessing for LSPs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf level {
         default "brief";
         type enumeration {
           enum "brief" {
             description "Display brief output (default)";
           }
           enum "detail" {
             description "Display detailed output";
           }
           enum "extensive" {
             description "Display extensive output";
           }
         }
       }
       leaf regex {
         description "Regular expression for LSP names to match";
         type string;
       }
     }
     output {
       container mpls-lsp-information {
         container rsvp-session-data {
           leaf session-type {
             type string;
             description "Type of session with respect to this router";
           }
           leaf count {
             type int32;
           }
           leaf detours {
             type int32;
             description "Number of detour sessions";
           }
           leaf display-count {
             type int32;
             description "Number of sessions displayed";
           }
           leaf up-count {
             type int32;
             description "Number of sessions in up state";
           }
           leaf down-count {
             type int32;
             description "Number of sessions in down state";
           }
           container rsvp-session {
             description "Single RSVP session";
             container brief {
               description "Single RSVP session";
               leaf destination-address {
                 type ipaddr;
                 description "Session destination address";
               }
               leaf source-address {
                 type ipaddr;
               }
               leaf lsp-state {
                 type string;
                 description "State of an LSP";
               }
               leaf route-count {
                 type int32;
                 description "Number of active routes";
               }
               leaf rsb-count {
                 type int32;
                 description "Number of RSBs";
               }
               leaf resv-style {
                 type string;
               }
               leaf label-in {
                 type string;
                 description "Incoming label";
               }
               leaf label-out {
                 type string;
                 description "Outgoing label";
               }
               leaf name {
                 type string;
               }
               leaf bidirectional {
                 type empty;
                 description "LSP is bidirectional";
               }
               leaf associated-bidirectional {
                 type empty;
                 description "LSP is associated-bidirectional";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf is-primary {
                   type empty;
                   description "Path is a primary path";
                 }
                 leaf active-path {
                   type string;
                   description "Path that the LSP is currently using";
                 }
                 leaf name {
                   type string;
                 }
                 leaf bidirectional {
                   type empty;
                   description "LSP is bidirectional";
                 }
                 leaf associated-bidirectional {
                   type empty;
                   description "LSP is associated-bidirectional";
                 }
                 leaf ext-assoc-bidir {
                   type empty;
                   description "Extended associated bidirectional LSP";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container descriptions {
               description "Single RSVP session";
               leaf destination-address {
                 type ipaddr;
                 description "Session destination address";
               }
               leaf source-address {
                 type ipaddr;
               }
               leaf name {
                 type string;
               }
               leaf lsp-description {
                 type string;
                 description "LSP description string (up to 80 characters)";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf name {
                   type string;
                 }
                 leaf lsp-description {
                   type string;
                   description "LSP description string (up to 80 characters)";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container brief_stats {
               description "Single RSVP session";
               leaf destination-address {
                 type ipaddr;
                 description "Session destination address";
               }
               leaf source-address {
                 type ipaddr;
               }
               leaf lsp-state {
                 type string;
                 description "State of an LSP";
               }
               leaf lsp-pktbytes {
                 type string;
                 description "LSP packet and byte counters";
               }
               leaf name {
                 type string;
               }
               leaf bidirectional {
                 type empty;
                 description "LSP is bidirectional";
               }
               leaf associated-bidirectional {
                 type empty;
                 description "LSP is associated-bidirectional";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 leaf ext-assoc-bidir {
                   type empty;
                   description "Extended associated bidirectional LSP";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container brief_xc {
               description "Single RSVP session";
               leaf source-address {
                 type ipaddr;
               }
               leaf lsp-id {
                 type string;
               }
               leaf p2mp-branch-id {
                 type uint32;
               }
               leaf lsp-state {
                 type string;
                 description "State of an LSP";
               }
               leaf xc-psb-list {
                 type string;
                 description "List of PSBs part of the RSVP xc";
               }
               leaf xc-rsb-list {
                 type string;
                 description "List of RSBs part of the RSVP xc";
               }
               leaf name {
                 type string;
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   leaf name {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container detail {
               description "Single RSVP session";
               leaf destination-address {
                 type ipaddr;
                 description "Session destination address";
               }
               leaf is-detour {
                 type empty;
                 description "Session is a detour session";
               }
               leaf source-address {
                 type ipaddr;
               }
               leaf lsp-state {
                 type string;
                 description "State of an LSP";
               }
               leaf route-count {
                 type int32;
                 description "Number of active routes";
               }
               leaf name {
                 type string;
               }
               leaf lsp-path-type {
                 type string;
                 description "Primary or secondary LSP path";
               }
               leaf graceful-deletion-triggered {
                 type empty;
                 description "Initiated graceful deletion procedure for the LSP";
               }
               leaf mpls-lsp-type {
                 type string;
                 description "Type of LSP";
               }
               leaf lsp-description {
                 type string;
                 description "LSP description string (up to 80 characters)";
               }
               leaf source-tna-address {
                 type ipaddr;
                 description "Source TNA address for the connection";
               }
               leaf destination-tna-address {
                 type ipaddr;
                 description "Destination TNA address for the connection";
               }
               leaf bidirectional {
                 type empty;
                 description "LSP is bidirectional";
               }
               leaf associated-bidirectional {
                 type empty;
                 description "LSP is associated-bidirectional";
               }
               leaf upstream-label-in {
                 type string;
                 description "Incoming upstream label";
               }
               leaf upstream-label-out {
                 type string;
                 description "Outgoing upstream label";
               }
               leaf lsp-associated-lspname {
                 type string;
                 description "Associated LSP name";
               }
               leaf lsp-associated-lspsrc {
                 type string;
                 description "Associated LSP source address";
               }
               leaf mpls-p2mp-lsp-name {
                 type string;
               }
               leaf p2mp-remerge-state {
                 type string;
                 description "Re-merge status of the P2MP sub-LSP";
               }
               leaf lsp-aggregation {
                 type string;
                 description "Supports LSP aggregation";
               }
               leaf suggested-label-in {
                 type int32;
                 description "Suggested label received";
               }
               leaf suggested-label-out {
                 type int32;
                 description "Suggested label sent";
               }
               leaf recovery-label-in {
                 type int32;
               }
               leaf recovery-label-out {
                 type int32;
               }
               leaf lsp-pktbytes {
                 type string;
                 description "LSP packet and byte counters";
               }
               leaf no-statistics {
                 type empty;
                 description "No statistics are available for this session";
               }
               leaf rsb-count {
                 type int32;
                 description "Number of RSBs";
               }
               leaf resv-style {
                 type string;
               }
               leaf label-in {
                 type string;
                 description "Incoming label";
               }
               leaf label-out {
                 type string;
                 description "Outgoing label";
               }
               leaf psb-lifetime {
                 type int32;
                 description "Lifetime for a PSB after which the entry expires";
               }
               leaf psb-creation-time {
                 type string;
                 description "Time when this PSB was created";
               }
               leaf path-mtu {
                 type int32;
                 description "The value of the path MTU, as negotiated by the network";
               }
               leaf path-mtu-in-kernel {
                 type int32;
                 description "The value of the MTU used locally for forwarding";
               }
               leaf sender-tspec {
                 type string;
                 description "Sender TSpec";
               }
               leaf adspec {
                 type string;
                 description "Adspec data element in an RSVP Path message";
               }
               leaf lsp-diffserv-info {
                 type string;
                 description "LSP DiffServ info";
               }
               leaf ct-bw {
                 type string;
                 description "Per-class bandwidth requested for E-LSPs and L-LSPs";
               }
               leaf lsp-id {
                 type string;
               }
               leaf tunnel-id {
                 type int32;
               }
               leaf proto-id {
                 type int32;
               }
               leaf p2mp-branch-id {
                 type uint32;
               }
               leaf p2mp-subgroup-orig {
                 type ipaddr;
               }
               leaf self-id {
                 type string;
                 description "Statistics identifier for RSVP path state control block";
               }
               leaf nh-statistics-id {
                 type string;
                 description "Nexthop statistics identifier for RSVP path at ingress";
               }
               leaf route-statistics-id {
                 type string;
                 description "Route statistics identifier for RSVP path at egress";
               }
               leaf nh-traffic-class-statistics {
                 type empty;
                 description "Traffic class statistics are enabled at ingress";
               }
               leaf route-traffic-class-statistics {
                 type empty;
                 description "Traffic class statistics are enabled at egress";
               }
               leaf session-id {
                 type int32;
                 description "Unique identifier for RSVP session";
               }
               leaf is-fastreroute {
                 type empty;
                 description "Fast reroute (one-to-one backup) is desired";
               }
               leaf is-linkprotection {
                 type empty;
                 description "Link protection (facility backup) is desired";
               }
               leaf is-nodeprotection {
                 type empty;
                 description "Link-Node protection (facility backup) is desired";
               }
               leaf ep-plr-protector {
                 type string;
               }
               leaf is-soft-preemption {
                 type empty;
                 description "Soft-preemption is desired";
               }
               leaf rsvp-path-status {
                 type string;
               }
               leaf bypass-name {
                 type string;
                 description "Name of the bypass";
               }
               leaf rsvp-lp-backup-route-cnt {
                 type int32;
                 description "Number of routes tunneled through this bypass";
               }
               leaf rsvp-lp-backup-lsp-cnt {
                 type int32;
                 description "Number of backup RSVP LSPs tunneled through this bypass";
               }
               leaf entropy-label {
                 type string;
                 description "Entropy label";
               }
               leaf p2mp-self-id {
                 type string;
                 description "Statistics identifier for RSVP P2MP path state control block";
               }
               container layer2-tspec {
                 description "Layer 2 TSpec";
                 leaf switching-granularity {
                   type string;
                   description "Layer 2 switching granularity";
                 }
                 leaf mtu {
                   type int32;
                   description "MTU along an interface";
                 }
                 leaf atm-vp-bundle-size {
                   type int32;
                   description "VP bundle size";
                 }
                 leaf atm-cell-bundle-size {
                   type int32;
                   description "Maximum cell bundle size";
                 }
               }
               container rsvp-lsp-enh-local-prot-status {
                 description "Enhanced FRR local protection status";
                 leaf rsvp-lsp-enh-local-prot-admin-status {
                   type string;
                   description "Enhanced FRR local protection admin status";
                 }
                 leaf rsvp-lsp-enh-local-prot-disabled-reason {
                   type string;
                   description "Enhanced FRR local protection disabled reason";
                 }
                 leaf rsvp-lsp-enh-local-prot-refresh-interval {
                   type string;
                   description "Enhanced FRR refresh interval set for LSP";
                 }
               }
               container rsvp-lsp-enh-local-prot-upstream {
                 description "Enhanced FRR local protection upstream information";
                 leaf rsvp-lsp-enh-lp-upstream-status {
                   type string;
                   description "Enhanced FRR local protection status upstream";
                 }
                 leaf rsvp-lsp-enh-lp-upstream-lp {
                   type string;
                   description "The node is LP-MP for Phop";
                 }
                 leaf rsvp-lsp-enh-lp-phop-addr {
                   type ipaddr;
                   description "Phop PLR for which this node is LP-MP";
                 }
                 leaf rsvp-lsp-enh-lp-upstream-lp-status {
                   type string;
                   description "Current upstream LP-MP status";
                 }
                 leaf rsvp-lsp-enh-lp-upstream-np {
                   type string;
                   description "The node is NP-MP for PPhop";
                 }
                 leaf rsvp-lsp-enh-lp-pphop-addr {
                   type ipaddr;
                   description "PPhop PLR for which this node is NP-MP";
                 }
                 leaf rsvp-lsp-enh-lp-upstream-np-status {
                   type string;
                   description "Current upstream NP-MP status";
                 }
                 leaf rsvp-lsp-enh-lp-upstream-disabled-reason {
                   type string;
                   description "Reason enhanced local protection is disabled upstream";
                 }
                 leaf rsvp-lsp-enh-local-prot-refresh-interval {
                   type string;
                   description "Enhanced FRR refresh interval set for LSP";
                 }
               }
               container rsvp-lsp-enh-local-prot-downstream {
                 description "Enhanced FRR local protection downstream information";
                 leaf rsvp-lsp-enh-lp-downstream-status {
                   type string;
                   description "Enhanced FRR local protection status downstream";
                 }
                 leaf rsvp-lsp-enh-lp-downstream-lp {
                   type string;
                   description "The node has made link protection available";
                 }
                 leaf rsvp-lsp-enh-lp-nhop-addr {
                   type ipaddr;
                   description "Nhop MP neigbor address";
                 }
                 leaf rsvp-lsp-enh-lp-downstream-np {
                   type string;
                   description "The node has made node protection available";
                 }
                 leaf rsvp-lsp-enh-lp-nnhop-addr {
                   type ipaddr;
                   description "NNhop MP neighbor address";
                 }
                 leaf rsvp-lsp-enh-lp-current-status {
                   type string;
                   description "Current downstream protection status";
                 }
                 leaf rsvp-lsp-enh-lp-downstream-disabled-reason {
                   type string;
                   description "Reason enhanced local protection is disabled downstream";
                 }
                 leaf rsvp-lsp-enh-local-prot-refresh-interval {
                   type string;
                   description "Enhanced FRR refresh interval set for LSP";
                 }
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf entropy-label {
                   type string;
                   description "Entropy label";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container record-route {
                 description "Record Route Object (RRO)";
                 leaf record-route.heading {
                   type string;
                   description "Record Route Object (RRO)";
                 }
                 leaf address {
                   type ipaddr;
                 }
                 leaf telink-id {
                   type int32;
                   description "Link identifier of unnumbered link";
                 }
                 leaf self {
                   type empty;
                 }
                 leaf incomplete {
                   type empty;
                 }
               }
               container lsp-attribute-flags {
                 description "LSP attribute flags";
                 leaf non-php {
                   type empty;
                   description "Non-PHP";
                 }
                 leaf oob {
                   type empty;
                   description "Out-of-band mapping";
                 }
               }
               container lp-history {
                 description "Log of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container rsvp-telink {
                 leaf active-reservation {
                   type int32;
                   description "Number of active reservations";
                 }
                 leaf preemption-count {
                   type int32;
                   description "Number of preemptions that occurred on an interface";
                 }
                 leaf update-threshold {
                   type int32;
                   description "Percentage change in reserved bandwidth to trigger IGP update";
                 }
                 leaf subscription {
                   type int32;
                   description "Percentage of link capacity available for bandwidth reservations";
                 }
                 leaf bc {
                   type int32;
                   description "Bandwidth constraint (0..7)";
                 }
                 leaf bc-description {
                   type string;
                   description "Description of the bandwidth constraint";
                 }
                 leaf static-bc-bandwidth {
                   type int32;
                   description "Static bandwidth capacity for a bandwidth constraint";
                 }
                 leaf ct-class {
                   type int32;
                   description "Class type (0..7)";
                 }
                 leaf static-bandwidth {
                   type int32;
                   description "Static bandwidth capacity of the link";
                 }
                 leaf available-bandwidth {
                   type int32;
                   description "Amount of bandwidth available for reservations";
                 }
                 leaf ct-subscription {
                   type int32;
                   description "Subscription percentage per traffic class";
                 }
                 leaf max-available-bandwidth {
                   type int32;
                   description "Maximum amount of bandwidth available for reservations, including the subscription factor";
                 }
                 leaf max-available-description {
                   type string;
                   description "Description of the computation of the maximum available bandwidth";
                 }
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                 }
               }
               container protection-attribute {
                 description "Protection attributes of RSVP session";
                 leaf protect-lsp-type {
                   type string;
                   description "Type of LSP for protection purposes";
                 }
                 leaf protect-lsp-role {
                   type string;
                   description "Role of LSP for protection purposes";
                 }
                 leaf protect-protection-type {
                   type string;
                   description "Type of protection being used";
                 }
                 leaf protect-secondary-operational {
                   type empty;
                   description "Protecting LSP is operational and carrying protected traffic";
                 }
               }
               container association-attribute {
                 description "Association attributes of RSVP session";
                 leaf association-type {
                   type string;
                   description "Type of association object";
                 }
                 leaf association-source {
                   type ipaddr;
                   description "Source node defining the association";
                 }
                 leaf association-id {
                   type int32;
                   description "Identifier for the association";
                 }
               }
               container detour {
                 description "Detour session";
                 leaf lsp-state {
                   type string;
                   description "State of an LSP";
                 }
                 leaf sender-tspec {
                   type string;
                   description "Sender TSpec";
                 }
                 leaf lsp-diffserv-info {
                   type string;
                   description "LSP DiffServ info";
                 }
                 leaf ct-bw {
                   type string;
                   description "Per-class bandwidth requested for E-LSPs and L-LSPs";
                 }
                 leaf adspec {
                   type string;
                   description "Adspec data element in an RSVP Path message";
                 }
                 leaf path-mtu {
                   type int32;
                   description "The value of the path MTU, as negotiated by the network";
                 }
                 leaf path-mtu-in-kernel {
                   type int32;
                   description "The value of the MTU used locally for forwarding";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container record-route {
                   description "Record Route Object (RRO)";
                   leaf record-route.heading {
                     type string;
                     description "Record Route Object (RRO)";
                   }
                   leaf address {
                     type ipaddr;
                   }
                   leaf telink-id {
                     type int32;
                     description "Link identifier of unnumbered link";
                   }
                   leaf self {
                     type empty;
                   }
                   leaf incomplete {
                     type empty;
                   }
                 }
               }
               container detour-branch {
                 description "Branch of some detour session";
                 leaf source-address {
                   type ipaddr;
                 }
                 leaf skip-address {
                   type ipaddr;
                   description "Address of node or link to be skipped";
                 }
                 leaf lsp-state {
                   type string;
                   description "State of an LSP";
                 }
                 leaf sender-tspec {
                   type string;
                   description "Sender TSpec";
                 }
                 leaf adspec {
                   type string;
                   description "Adspec data element in an RSVP Path message";
                 }
                 leaf path-mtu {
                   type int32;
                   description "The value of the path MTU, as negotiated by the network";
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container record-route {
                   description "Record Route Object (RRO)";
                   leaf record-route.heading {
                     type string;
                     description "Record Route Object (RRO)";
                   }
                   leaf address {
                     type ipaddr;
                   }
                   leaf telink-id {
                     type int32;
                     description "Link identifier of unnumbered link";
                   }
                   leaf self {
                     type empty;
                   }
                   leaf incomplete {
                     type empty;
                   }
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container detour-branch-labels {
                   leaf label-in {
                     type string;
                     description "Incoming label";
                   }
                   leaf label-out {
                     type string;
                     description "Outgoing label";
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf name {
                   type string;
                 }
                 leaf lsp-type {
                   type string;
                   description "Type of LSP";
                 }
                 leaf egress-label-operation {
                   type string;
                   description "Label advertised by egress";
                 }
                 leaf lsp-control-status {
                   type string;
                   description "Control status of LSP configured to be externally controlled";
                 }
                 leaf lsp-diffserv-te-info {
                   type string;
                   description "LSP support of DiffServ-TE extensions";
                 }
                 leaf bidirectional {
                   type empty;
                   description "LSP is bidirectional";
                 }
                 leaf associated-bidirectional {
                   type empty;
                   description "LSP is associated-bidirectional";
                 }
                 leaf lsp-associated-lspname {
                   type string;
                   description "Associated LSP name";
                 }
                 leaf lsp-associated-lspsrc {
                   type string;
                   description "Associated LSP source address";
                 }
                 leaf ext-assoc-bidir {
                   type empty;
                   description "Extended associated bidirectional LSP";
                 }
                 leaf ext-assoc-bidir-direction {
                   type string;
                   description "Ext-Assoc-Bidir direction";
                 }
                 leaf lsp-description {
                   type string;
                   description "LSP description string (up to 80 characters)";
                 }
                 leaf lsp-pktbytes {
                   type string;
                   description "LSP packet and byte counters";
                 }
                 leaf aggregate-lsp-pktbytes {
                   type string;
                   description "Aggregate LSP packet and byte counters";
                 }
                 leaf no-statistics {
                   type empty;
                   description "No statistics are available for this session";
                 }
                 leaf active-path {
                   type string;
                   description "Path that the LSP is currently using";
                 }
                 leaf mpls-p2mp-name {
                   type string;
                 }
                 leaf is-fastreroute {
                   type empty;
                   description "Fast reroute (one-to-one backup) is desired";
                 }
                 leaf is-linkprotection {
                   type empty;
                   description "Link protection (facility backup) is desired";
                 }
                 leaf is-nodeprotection {
                   type empty;
                   description "Link-Node protection (facility backup) is desired";
                 }
                 leaf is-inter-domain-path {
                   type empty;
                   description "Inter-domain LSP";
                 }
                 leaf load-balance {
                   type string;
                   description "Load-balancing algorithm chosen";
                 }
                 leaf metric {
                   type int32;
                 }
                 leaf actual-metric {
                   type int32;
                 }
                 leaf revert-timer {
                   type string;
                   description "Hold-down time before reverting to primary path.";
                 }
                 leaf revert-timer-remain {
                   type string;
                   description "Time remaining before reverting:";
                 }
                 leaf optimize-protection-timer {
                   type int32;
                   description "Optimize protection timer";
                 }
                 leaf lsp-creation-time {
                   type string;
                   description "Time when the LSP was created";
                 }
                 leaf lsp-soft-preemption-counter {
                   type int32;
                   description "Number of times the LSP was soft preempted";
                 }
                 leaf lsp-soft-preemption-time {
                   type string;
                   description "Time when the LSP was last soft preempted";
                 }
                 leaf retry-timer {
                   type int32;
                 }
                 leaf retry-limit {
                   type int32;
                 }
                 leaf lsp-packets {
                   type string;
                   description "LSP packet counters";
                 }
                 leaf lsp-bytes {
                   type string;
                   description "LSP byte counters";
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container mpls-srlg {
                   leaf srlg-name {
                     type string;
                     description "Name of the srlg";
                   }
                   leaf srlg-value {
                     type uint32;
                     description "Value of the srlg";
                   }
                   leaf srlg-cost {
                     type uint32;
                     description "Cost of the srlg";
                   }
                 }
                 container mpls-lsp-autobandwidth {
                   leaf monitor-lsp-bandwidth {
                     type empty;
                     description "Enable the bandwidth monitoring mode";
                   }
                   leaf minimum-bandwidth {
                     type int32;
                     description "Configured LSP minimum bandwidth";
                   }
                   leaf maximum-bandwidth {
                     type int32;
                     description "Configured LSP maximum bandwidth";
                   }
                   leaf dynamic-minimum-bandwidth {
                     type int32;
                     description "LSP dynamic minimum bandwidth (or last Max Avg Bw)";
                   }
                   leaf adjust-timer {
                     type int32;
                     description "Configured LSP adjust timer";
                   }
                   leaf adjust-threshold {
                     type int32;
                     description "Percentage change in average LSP utilization to trigger autoadjustment";
                   }
                   leaf adjust-threshold-activate-bandwidth {
                     type int32;
                     description "Configured LSP adjust threshold bandwidth";
                   }
                   leaf maximum-average-bandwidth {
                     type int32;
                     description "Maximum Average BW";
                   }
                   leaf time-to-adjust {
                     type int32;
                     description "Time in which LSP will autoadjust bandwidth";
                   }
                   leaf autobw-minimum-bandwidth-adjust-interval {
                     type int32;
                   }
                   leaf autobw-minimum-bandwidth-adjust-threshold-percent {
                     type int32;
                   }
                   leaf autobw-minimum-bandwidth-adjust-threshold-value {
                     type int32;
                   }
                   leaf time-to-expire-minimum-bandwidth-adjust {
                     type int32;
                     description "Time in which LSP will start changing minimum bandwidth";
                   }
                   leaf overflow-limit {
                     type int32;
                     description "Configured limit of consecutive overflow samples for LSP";
                   }
                   leaf overflow-sample-count {
                     type int32;
                     description "Number of consecutive overflow samples encountered";
                   }
                   leaf underflow-limit {
                     type int32;
                     description "Configured limit of consecutive underflow samples for LSP";
                   }
                   leaf underflow-sample-count {
                     type int32;
                     description "Number of consecutive underflow samples encountered";
                   }
                   leaf underflow-max-avg-bandwidth {
                     type int32;
                     description "Highest average bandwidth recorded so far for underflow samples";
                   }
                 }
                 container mpls-lsp-path {
                   description "Primary or secondary LSP path";
                   leaf path-active {
                     type empty;
                     description "Whether the path is active or not";
                   }
                   leaf title {
                     type string;
                   }
                   leaf name {
                     type string;
                   }
                   leaf path-state {
                     type string;
                     description "State of the MPLS path";
                   }
                   leaf cos {
                     type int32;
                     description "CoS value";
                   }
                   leaf no-decrement-ttl {
                     type empty;
                     description "TTL";
                   }
                   leaf preference {
                     type int32;
                     description "Preference for the route";
                   }
                   leaf path-soft-preemption-pending {
                     type empty;
                     description "Soft preemption pending for this path";
                   }
                   leaf setup-priority {
                     type int32;
                     description "Priority with respect to taking resources";
                   }
                   leaf hold-priority {
                     type int32;
                     description "Priority with respect to holding resources";
                   }
                   leaf actual-setup-priority {
                     type int32;
                   }
                   leaf actual-hold-priority {
                     type int32;
                   }
                   leaf external-lsp-cspf-type {
                     type string;
                   }
                   leaf bandwidth {
                     type int32;
                   }
                   leaf actual-bandwidth {
                     type int32;
                   }
                   leaf per-class-bandwidth-heading {
                     type string;
                   }
                   leaf bandwidth_ct0 {
                     type int32;
                   }
                   leaf bandwidth_ct1 {
                     type int32;
                   }
                   leaf bandwidth_ct2 {
                     type int32;
                   }
                   leaf bandwidth_ct3 {
                     type int32;
                   }
                   leaf path-adaptive {
                     type empty;
                     description "LSP is adaptive";
                   }
                   leaf path-no-recordroute {
                     type empty;
                     description "Record route disabled";
                   }
                   leaf hoplimit {
                     type int32;
                     description "Maximum number of hops that can be traversed";
                   }
                   leaf optimize-timer {
                     type int32;
                     description "Optimize timer";
                   }
                   leaf smart-optimize-timer {
                     type int32;
                     description "Smart optimize timer";
                   }
                   leaf retry-timer {
                     type int32;
                   }
                   leaf retry-limit {
                     type int32;
                   }
                   leaf external-cspf-status {
                     type string;
                     description "Status provided by External CSPF computation";
                   }
                   leaf cspf-status {
                     type string;
                     description "Status returned by CSPF computation";
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                   container mpls-srlg {
                     leaf srlg-name {
                       type string;
                       description "Name of the srlg";
                     }
                     leaf srlg-value {
                       type uint32;
                       description "Value of the srlg";
                     }
                     leaf srlg-cost {
                       type uint32;
                       description "Cost of the srlg";
                     }
                   }
                 }
                 container mpls-lsp-attributes {
                   leaf signal-type {
                     type string;
                   }
                   leaf encoding-type {
                     type string;
                     description "LSP encoding type";
                   }
                   leaf switching-type {
                     type string;
                     description "LSP switching capability";
                   }
                   leaf gpid {
                     type string;
                     description "LSP generalized PID";
                   }
                   leaf protection-type {
                     type string;
                     description "LSP protection desired";
                   }
                 }
               }
             }
           }
           container mpls-p2mp-lsp {
             leaf mpls-p2mp-name {
               type string;
             }
             leaf mpls-p2mp-branch-count {
               type string;
             }
           }
           container mpls-container-lsp {
             description "MPLS container-label-switched path information";
             leaf mpls-container-lsp-name {
               type string;
             }
             leaf mpls-container-lsp-state {
               type string;
             }
             leaf mpls-container-member-count {
               type string;
             }
             leaf container-active-path {
               type string;
               description "Path that the member LSP is currently using";
             }
             leaf container-is-primary {
               type empty;
               description "Path is a primary path";
             }
             leaf lsp-packets {
               type string;
               description "LSP packet counters";
             }
             leaf lsp-bytes {
               type string;
               description "LSP byte counters";
             }
             leaf lsp-control-status {
               type string;
               description "Control status of LSP configured to be externally controlled";
             }
             container mpls-lsp-path {
               description "Primary or secondary LSP path";
               container admin-groups {
                 leaf admin-groups.heading {
                   type string;
                 }
                 leaf color {
                   type int32;
                 }
                 leaf no-group-flag {
                   type empty;
                 }
                 leaf admin-group-name {
                   type string;
                   description "Name of the admin group";
                 }
                 leaf admin-group-number {
                   type int32;
                   description "Number of the admin group";
                 }
               }
               container admin-groups-extended {
                 leaf admin-groups-extended.heading {
                   type string;
                 }
                 leaf admin-group-name {
                   type string;
                   description "Name of the admin group";
                 }
                 leaf admin-group-number {
                   type int32;
                   description "Number of the admin group";
                 }
               }
               container srlg {
                 leaf srlg.heading {
                   type string;
                 }
                 leaf srlg-name {
                   type string;
                   description "Name of the srlg";
                 }
               }
               container mpls-lsp-upstream-label {
                 description "Upstream label configured for the LSP";
                 leaf vlan-id-label {
                   type uint32;
                   description "VLAN ID label configured for the LSP";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container oam-state {
                 description "OAM state information";
                 leaf oam-bfd-session-state {
                   type string;
                 }
                 leaf oam-lsp-ping-state {
                   type string;
                 }
               }
               container path-history {
                 description "Log over time of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container path-available-bandwidth {
                 description "Available bandwidth on an LSP path";
                 leaf path-available-bandwidth.heading {
                   type string;
                   description "Available bandwidth on an LSP path";
                 }
                 leaf bandwidth {
                   type int32;
                 }
                 leaf class-type {
                   type int32;
                 }
                 leaf class-bandwidth {
                   type int32;
                 }
               }
               container layer2-connection {
                 description "Layer 2 connection using the LSP path";
                 leaf neighbor-address {
                   type ipaddr;
                   description "IP address of this neighbor";
                 }
                 leaf interface-name {
                   type string;
                   description "Name of interface";
                 }
                 leaf vc-id {
                   type int32;
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
               }
             }
             container mpls-container-lsp-splitting-merging {
               leaf minimum-member-lsps {
                 type int32;
                 description "Configured minimum LSPs";
               }
               leaf maximum-member-lsps {
                 type int32;
                 description "Configured maximum LSPs";
               }
               leaf aggregate-bandwidth {
                 type int32;
                 description "Aggregate bandwidth";
               }
               leaf current-bandwidth {
                 type int32;
                 description "Sampled Aggregate bandwidth";
               }
               leaf normalize-interval {
                 type int32;
                 description "Configured LSP normalize timer";
               }
               leaf splitting-merging-threshold {
                 type int32;
                 description "Percentage change in aggregate LSP utilization to trigger normalization";
               }
               leaf maximum-signaling-bandwidth {
                 type int32;
                 description "Configured signaling maximum bandwidth";
               }
               leaf minimum-signaling-bandwidth {
                 type int32;
                 description "Configured signaling minimum bandwidth";
               }
               leaf maximum-splitting-bandwidth {
                 type int32;
                 description "Configured splitting maximum bandwidth";
               }
               leaf minimum-splitting-bandwidth {
                 type int32;
                 description "Configured splitting minimum bandwidth";
               }
               leaf normalization-mode {
                 type string;
               }
               leaf sampling-mode {
                 type string;
                 description "Sampling Attributes";
               }
               leaf time-to-normalize {
                 type int32;
                 description "Time in which LSP will normalize";
               }
               leaf aggregate-packets {
                 type int32;
                 description "Aggregate packets";
               }
               leaf aggregate-bytes {
                 type int32;
                 description "Aggregate bytes";
               }
             }
             container mpls-container-lsp-history {
               description "Log over time of container LSP related events";
               leaf sequence-number {
                 type int32;
                 description "History event number";
               }
               leaf time {
                 type string;
                 description "Time of the event";
               }
               leaf log {
                 type string;
                 description "Supplemental information of the event";
               }
               leaf route {
                 type string;
                 description "Latest RRO contents, as reported by RSVP";
               }
             }
           }
           container mpls-container-lsp-member-summary {
             container mpls-container-lsp {
               description "MPLS container-label-switched path information";
               leaf mpls-container-lsp-name {
                 type string;
               }
               leaf mpls-container-lsp-state {
                 type string;
               }
               leaf mpls-container-member-count {
                 type string;
               }
               leaf container-active-path {
                 type string;
                 description "Path that the member LSP is currently using";
               }
               leaf container-is-primary {
                 type empty;
                 description "Path is a primary path";
               }
               leaf lsp-packets {
                 type string;
                 description "LSP packet counters";
               }
               leaf lsp-bytes {
                 type string;
                 description "LSP byte counters";
               }
               leaf lsp-control-status {
                 type string;
                 description "Control status of LSP configured to be externally controlled";
               }
               container mpls-lsp-path {
                 description "Primary or secondary LSP path";
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container srlg {
                   leaf srlg.heading {
                     type string;
                   }
                   leaf srlg-name {
                     type string;
                     description "Name of the srlg";
                   }
                 }
                 container mpls-lsp-upstream-label {
                   description "Upstream label configured for the LSP";
                   leaf vlan-id-label {
                     type uint32;
                     description "VLAN ID label configured for the LSP";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container oam-state {
                   description "OAM state information";
                   leaf oam-bfd-session-state {
                     type string;
                   }
                   leaf oam-lsp-ping-state {
                     type string;
                   }
                 }
                 container path-history {
                   description "Log over time of LSP path-related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
                 container path-available-bandwidth {
                   description "Available bandwidth on an LSP path";
                   leaf path-available-bandwidth.heading {
                     type string;
                     description "Available bandwidth on an LSP path";
                   }
                   leaf bandwidth {
                     type int32;
                   }
                   leaf class-type {
                     type int32;
                   }
                   leaf class-bandwidth {
                     type int32;
                   }
                 }
                 container layer2-connection {
                   description "Layer 2 connection using the LSP path";
                   leaf neighbor-address {
                     type ipaddr;
                     description "IP address of this neighbor";
                   }
                   leaf interface-name {
                     type string;
                     description "Name of interface";
                   }
                   leaf vc-id {
                     type int32;
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                 }
               }
               container mpls-container-lsp-splitting-merging {
                 leaf minimum-member-lsps {
                   type int32;
                   description "Configured minimum LSPs";
                 }
                 leaf maximum-member-lsps {
                   type int32;
                   description "Configured maximum LSPs";
                 }
                 leaf aggregate-bandwidth {
                   type int32;
                   description "Aggregate bandwidth";
                 }
                 leaf current-bandwidth {
                   type int32;
                   description "Sampled Aggregate bandwidth";
                 }
                 leaf normalize-interval {
                   type int32;
                   description "Configured LSP normalize timer";
                 }
                 leaf splitting-merging-threshold {
                   type int32;
                   description "Percentage change in aggregate LSP utilization to trigger normalization";
                 }
                 leaf maximum-signaling-bandwidth {
                   type int32;
                   description "Configured signaling maximum bandwidth";
                 }
                 leaf minimum-signaling-bandwidth {
                   type int32;
                   description "Configured signaling minimum bandwidth";
                 }
                 leaf maximum-splitting-bandwidth {
                   type int32;
                   description "Configured splitting maximum bandwidth";
                 }
                 leaf minimum-splitting-bandwidth {
                   type int32;
                   description "Configured splitting minimum bandwidth";
                 }
                 leaf normalization-mode {
                   type string;
                 }
                 leaf sampling-mode {
                   type string;
                   description "Sampling Attributes";
                 }
                 leaf time-to-normalize {
                   type int32;
                   description "Time in which LSP will normalize";
                 }
                 leaf aggregate-packets {
                   type int32;
                   description "Aggregate packets";
                 }
                 leaf aggregate-bytes {
                   type int32;
                   description "Aggregate bytes";
                 }
               }
               container mpls-container-lsp-history {
                 description "Log over time of container LSP related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
             }
           }
           container container-rsvp-session {
             container brief {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf is-primary {
                   type empty;
                   description "Path is a primary path";
                 }
                 leaf active-path {
                   type string;
                   description "Path that the LSP is currently using";
                 }
                 leaf container-member-name {
                   type string;
                   description "Path that the member LSP is currently using";
                 }
                 leaf label-out {
                   type string;
                   description "Outgoing label";
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf label-out {
                   type string;
                   description "Outgoing label";
                 }
               }
               container detour {
                 description "Detour session";
                 leaf lsp-state {
                   type string;
                   description "State of an LSP";
                 }
                 leaf label-out {
                   type string;
                   description "Outgoing label";
                 }
               }
               container detour-branch {
                 description "Branch of some detour session";
                 container detour-branch-labels {
                 }
               }
             }
             container descriptions {
               container mpls-container-lsp {
                 description "MPLS container-label-switched path information";
                 leaf destination-address {
                   type ipaddr;
                   description "Session destination address";
                 }
                 leaf source-address {
                   type ipaddr;
                 }
                 leaf lsp-description {
                   type string;
                   description "LSP description string (up to 80 characters)";
                 }
                 leaf container-active-path {
                   type string;
                   description "Path that the member LSP is currently using";
                 }
                 leaf container-is-primary {
                   type empty;
                   description "Path is a primary path";
                 }
                 leaf lsp-packets {
                   type string;
                   description "LSP packet counters";
                 }
                 leaf lsp-bytes {
                   type string;
                   description "LSP byte counters";
                 }
                 leaf lsp-control-status {
                   type string;
                   description "Control status of LSP configured to be externally controlled";
                 }
                 container mpls-lsp-path {
                   description "Primary or secondary LSP path";
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
                 container mpls-container-lsp-splitting-merging {
                   leaf minimum-member-lsps {
                     type int32;
                     description "Configured minimum LSPs";
                   }
                   leaf maximum-member-lsps {
                     type int32;
                     description "Configured maximum LSPs";
                   }
                   leaf aggregate-bandwidth {
                     type int32;
                     description "Aggregate bandwidth";
                   }
                   leaf current-bandwidth {
                     type int32;
                     description "Sampled Aggregate bandwidth";
                   }
                   leaf normalize-interval {
                     type int32;
                     description "Configured LSP normalize timer";
                   }
                   leaf splitting-merging-threshold {
                     type int32;
                     description "Percentage change in aggregate LSP utilization to trigger normalization";
                   }
                   leaf maximum-signaling-bandwidth {
                     type int32;
                     description "Configured signaling maximum bandwidth";
                   }
                   leaf minimum-signaling-bandwidth {
                     type int32;
                     description "Configured signaling minimum bandwidth";
                   }
                   leaf maximum-splitting-bandwidth {
                     type int32;
                     description "Configured splitting maximum bandwidth";
                   }
                   leaf minimum-splitting-bandwidth {
                     type int32;
                     description "Configured splitting minimum bandwidth";
                   }
                   leaf normalization-mode {
                     type string;
                   }
                   leaf sampling-mode {
                     type string;
                     description "Sampling Attributes";
                   }
                   leaf time-to-normalize {
                     type int32;
                     description "Time in which LSP will normalize";
                   }
                   leaf aggregate-packets {
                     type int32;
                     description "Aggregate packets";
                   }
                   leaf aggregate-bytes {
                     type int32;
                     description "Aggregate bytes";
                   }
                 }
                 container mpls-container-lsp-history {
                   description "Log over time of container LSP related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
               }
               container mpls-lsp {
                 description "MPLS label-switched path information";
                 leaf destination-address {
                   type ipaddr;
                   description "Session destination address";
                 }
                 leaf name {
                   type string;
                 }
                 leaf lsp-description {
                   type string;
                   description "LSP description string (up to 80 characters)";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container detour {
                 description "Detour session";
               }
               container detour-branch {
                 description "Branch of some detour session";
               }
             }
             container brief_stats {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container detour {
                 description "Detour session";
               }
               container detour-branch {
                 description "Branch of some detour session";
               }
             }
             container detail {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf lsp-type {
                   type string;
                   description "Type of LSP";
                 }
                 leaf egress-label-operation {
                   type string;
                   description "Label advertised by egress";
                 }
                 leaf lsp-diffserv-te-info {
                   type string;
                   description "LSP support of DiffServ-TE extensions";
                 }
                 leaf lsp-description {
                   type string;
                   description "LSP description string (up to 80 characters)";
                 }
                 leaf lsp-pktbytes {
                   type string;
                   description "LSP packet and byte counters";
                 }
                 leaf aggregate-lsp-pktbytes {
                   type string;
                   description "Aggregate LSP packet and byte counters";
                 }
                 leaf no-statistics {
                   type empty;
                   description "No statistics are available for this session";
                 }
                 leaf active-path {
                   type string;
                   description "Path that the LSP is currently using";
                 }
                 leaf mpls-container-name {
                   type string;
                   description "Name of the container LSP";
                 }
                 leaf is-fastreroute {
                   type empty;
                   description "Fast reroute (one-to-one backup) is desired";
                 }
                 leaf is-linkprotection {
                   type empty;
                   description "Link protection (facility backup) is desired";
                 }
                 leaf is-nodeprotection {
                   type empty;
                   description "Link-Node protection (facility backup) is desired";
                 }
                 leaf is-inter-domain-path {
                   type empty;
                   description "Inter-domain LSP";
                 }
                 leaf load-balance {
                   type string;
                   description "Load-balancing algorithm chosen";
                 }
                 leaf metric {
                   type int32;
                 }
                 leaf optimize-protection-timer {
                   type int32;
                   description "Optimize protection timer";
                 }
                 leaf lsp-creation-time {
                   type string;
                   description "Time when the LSP was created";
                 }
                 leaf lsp-soft-preemption-counter {
                   type int32;
                   description "Number of times the LSP was soft preempted";
                 }
                 leaf lsp-soft-preemption-time {
                   type string;
                   description "Time when the LSP was last soft preempted";
                 }
                 leaf retry-timer {
                   type int32;
                 }
                 leaf retry-limit {
                   type int32;
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container srlg {
                   leaf srlg.heading {
                     type string;
                   }
                   leaf srlg-name {
                     type string;
                     description "Name of the srlg";
                   }
                 }
                 container mpls-lsp-upstream-label {
                   description "Upstream label configured for the LSP";
                   leaf vlan-id-label {
                     type uint32;
                     description "VLAN ID label configured for the LSP";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container oam-state {
                   description "OAM state information";
                   leaf oam-bfd-session-state {
                     type string;
                   }
                   leaf oam-lsp-ping-state {
                     type string;
                   }
                 }
                 container path-history {
                   description "Log over time of LSP path-related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
                 container path-available-bandwidth {
                   description "Available bandwidth on an LSP path";
                   leaf path-available-bandwidth.heading {
                     type string;
                     description "Available bandwidth on an LSP path";
                   }
                   leaf bandwidth {
                     type int32;
                   }
                   leaf class-type {
                     type int32;
                   }
                   leaf class-bandwidth {
                     type int32;
                   }
                 }
                 container layer2-connection {
                   description "Layer 2 connection using the LSP path";
                   leaf neighbor-address {
                     type ipaddr;
                     description "IP address of this neighbor";
                   }
                   leaf interface-name {
                     type string;
                     description "Name of interface";
                   }
                   leaf vc-id {
                     type int32;
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                 }
                 container mpls-srlg {
                   leaf srlg-name {
                     type string;
                     description "Name of the srlg";
                   }
                   leaf srlg-value {
                     type uint32;
                     description "Value of the srlg";
                   }
                   leaf srlg-cost {
                     type uint32;
                     description "Cost of the srlg";
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf label-out {
                   type string;
                   description "Outgoing label";
                 }
                 leaf path-mtu {
                   type int32;
                   description "The value of the path MTU, as negotiated by the network";
                 }
                 leaf path-mtu-in-kernel {
                   type int32;
                   description "The value of the MTU used locally for forwarding";
                 }
                 leaf sender-tspec {
                   type string;
                   description "Sender TSpec";
                 }
                 leaf adspec {
                   type string;
                   description "Adspec data element in an RSVP Path message";
                 }
                 leaf lsp-diffserv-info {
                   type string;
                   description "LSP DiffServ info";
                 }
                 leaf ct-bw {
                   type string;
                   description "Per-class bandwidth requested for E-LSPs and L-LSPs";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf entropy-label {
                   type string;
                   description "Entropy label";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container detour {
                 description "Detour session";
                 leaf lsp-state {
                   type string;
                   description "State of an LSP";
                 }
                 leaf sender-tspec {
                   type string;
                   description "Sender TSpec";
                 }
                 leaf lsp-diffserv-info {
                   type string;
                   description "LSP DiffServ info";
                 }
                 leaf ct-bw {
                   type string;
                   description "Per-class bandwidth requested for E-LSPs and L-LSPs";
                 }
                 leaf adspec {
                   type string;
                   description "Adspec data element in an RSVP Path message";
                 }
                 leaf path-mtu {
                   type int32;
                   description "The value of the path MTU, as negotiated by the network";
                 }
                 leaf path-mtu-in-kernel {
                   type int32;
                   description "The value of the MTU used locally for forwarding";
                 }
                 leaf label-out {
                   type string;
                   description "Outgoing label";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
               }
               container detour-branch {
                 description "Branch of some detour session";
                 leaf source-address {
                   type ipaddr;
                 }
                 leaf skip-address {
                   type ipaddr;
                   description "Address of node or link to be skipped";
                 }
                 leaf lsp-state {
                   type string;
                   description "State of an LSP";
                 }
                 leaf sender-tspec {
                   type string;
                   description "Sender TSpec";
                 }
                 leaf adspec {
                   type string;
                   description "Adspec data element in an RSVP Path message";
                 }
                 leaf path-mtu {
                   type int32;
                   description "The value of the path MTU, as negotiated by the network";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container detour-branch-labels {
                   container packet-information {
                     description "RSVP packets sent or received per session";
                     leaf packet-information.heading {
                       type string;
                       description "RSVP packets sent or received per session";
                     }
                     leaf previous-hop {
                       type ipaddr;
                       description "Previous-hop address";
                     }
                     leaf next-hop {
                       type ipaddr;
                       description "Next-hop address";
                     }
                     leaf interface-name {
                       type string;
                       description "Name of interface";
                     }
                     leaf count {
                       type int32;
                     }
                     leaf notify-destination {
                       type ipaddr;
                       description "Notify address";
                     }
                     leaf entropy-label {
                       type string;
                       description "Entropy label";
                     }
                     leaf in-message-handle {
                       type string;
                       description "RSVP I/O handle for incoming message";
                     }
                     leaf in-message-id {
                       type uint32;
                       description "Incoming Message ID";
                     }
                     leaf in-epoch {
                       type uint32;
                       description "Incoming Epoch";
                     }
                     leaf out-message-state {
                       type string;
                       description "RSVP I/O state for outgoing message";
                     }
                     leaf out-message-id {
                       type uint32;
                       description "Outgoing Message ID";
                     }
                     leaf out-epoch {
                       type uint32;
                       description "Outgoing Epoch";
                     }
                   }
                 }
               }
             }
           }
         }
       }
     }
   }
   rpc get-mpls-container-lsp-information {
     description "Show configured container-label-switched paths";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
       leaf lsp-type {
         type enumeration {
           enum "ingress" {
             description "Display LSPs originating at this router";
           }
           enum "egress" {
             description "Display LSPs ending at this router";
           }
           enum "transit" {
             description "Display LSPs transiting this router";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
       leaf lsp-state {
         type enumeration {
           enum "up" {
             description "Display active LSPs";
           }
           enum "down" {
             description "Display inactive LSPs";
           }
         }
       }
       leaf lsp-direction {
         type enumeration {
           enum "unidirectional" {
             description "Display unidirectional container LSPs";
           }
         }
       }
       leaf lsp-stat {
         type enumeration {
           enum "statistics" {
             description "Display packet statistics for LSPs";
           }
         }
       }
       leaf activeroutes {
         type enumeration {
           enum "count-active-routes" {
             description "Show active routes for LSPs";
           }
         }
       }
       leaf regex {
         description "Regular expression for LSP names to match";
         type string;
       }
     }
     output {
       container mpls-container-lsp-information {
         container rsvp-session-data {
           leaf session-type {
             type string;
             description "Type of session with respect to this router";
           }
           leaf count {
             type int32;
           }
           leaf detours {
             type int32;
             description "Number of detour sessions";
           }
           leaf display-count {
             type int32;
             description "Number of sessions displayed";
           }
           leaf up-count {
             type int32;
             description "Number of sessions in up state";
           }
           leaf down-count {
             type int32;
             description "Number of sessions in down state";
           }
           container rsvp-session {
             description "Single RSVP session";
             container brief {
               description "Single RSVP session";
               leaf destination-address {
                 type ipaddr;
                 description "Session destination address";
               }
               leaf source-address {
                 type ipaddr;
               }
               leaf lsp-state {
                 type string;
                 description "State of an LSP";
               }
               leaf route-count {
                 type int32;
                 description "Number of active routes";
               }
               leaf rsb-count {
                 type int32;
                 description "Number of RSBs";
               }
               leaf resv-style {
                 type string;
               }
               leaf label-in {
                 type string;
                 description "Incoming label";
               }
               leaf label-out {
                 type string;
                 description "Outgoing label";
               }
               leaf name {
                 type string;
               }
               leaf bidirectional {
                 type empty;
                 description "LSP is bidirectional";
               }
               leaf associated-bidirectional {
                 type empty;
                 description "LSP is associated-bidirectional";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf is-primary {
                   type empty;
                   description "Path is a primary path";
                 }
                 leaf active-path {
                   type string;
                   description "Path that the LSP is currently using";
                 }
                 leaf name {
                   type string;
                 }
                 leaf bidirectional {
                   type empty;
                   description "LSP is bidirectional";
                 }
                 leaf associated-bidirectional {
                   type empty;
                   description "LSP is associated-bidirectional";
                 }
                 leaf ext-assoc-bidir {
                   type empty;
                   description "Extended associated bidirectional LSP";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container descriptions {
               description "Single RSVP session";
               leaf destination-address {
                 type ipaddr;
                 description "Session destination address";
               }
               leaf source-address {
                 type ipaddr;
               }
               leaf name {
                 type string;
               }
               leaf lsp-description {
                 type string;
                 description "LSP description string (up to 80 characters)";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf name {
                   type string;
                 }
                 leaf lsp-description {
                   type string;
                   description "LSP description string (up to 80 characters)";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container brief_stats {
               description "Single RSVP session";
               leaf destination-address {
                 type ipaddr;
                 description "Session destination address";
               }
               leaf source-address {
                 type ipaddr;
               }
               leaf lsp-state {
                 type string;
                 description "State of an LSP";
               }
               leaf lsp-pktbytes {
                 type string;
                 description "LSP packet and byte counters";
               }
               leaf name {
                 type string;
               }
               leaf bidirectional {
                 type empty;
                 description "LSP is bidirectional";
               }
               leaf associated-bidirectional {
                 type empty;
                 description "LSP is associated-bidirectional";
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 leaf ext-assoc-bidir {
                   type empty;
                   description "Extended associated bidirectional LSP";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container brief_xc {
               description "Single RSVP session";
               leaf source-address {
                 type ipaddr;
               }
               leaf lsp-id {
                 type string;
               }
               leaf p2mp-branch-id {
                 type uint32;
               }
               leaf lsp-state {
                 type string;
                 description "State of an LSP";
               }
               leaf xc-psb-list {
                 type string;
                 description "List of PSBs part of the RSVP xc";
               }
               leaf xc-rsb-list {
                 type string;
                 description "List of RSBs part of the RSVP xc";
               }
               leaf name {
                 type string;
               }
               leaf entropy-label {
                 type string;
                 description "Entropy label";
               }
               leaf p2mp-self-id {
                 type string;
                 description "Statistics identifier for RSVP P2MP path state control block";
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container rsvp-telink {
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                   leaf ct-class {
                     type int32;
                     description "Class type (0..7)";
                   }
                 }
               }
               container detour {
                 description "Detour session";
               }
               container detour-branch {
                 description "Branch of some detour session";
               }
               container mpls-lsp {
                 description "MPLS label-switched path information";
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   leaf name {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
             }
             container detail {
               description "Single RSVP session";
               leaf destination-address {
                 type ipaddr;
                 description "Session destination address";
               }
               leaf is-detour {
                 type empty;
                 description "Session is a detour session";
               }
               leaf source-address {
                 type ipaddr;
               }
               leaf lsp-state {
                 type string;
                 description "State of an LSP";
               }
               leaf route-count {
                 type int32;
                 description "Number of active routes";
               }
               leaf name {
                 type string;
               }
               leaf lsp-path-type {
                 type string;
                 description "Primary or secondary LSP path";
               }
               leaf graceful-deletion-triggered {
                 type empty;
                 description "Initiated graceful deletion procedure for the LSP";
               }
               leaf mpls-lsp-type {
                 type string;
                 description "Type of LSP";
               }
               leaf lsp-description {
                 type string;
                 description "LSP description string (up to 80 characters)";
               }
               leaf source-tna-address {
                 type ipaddr;
                 description "Source TNA address for the connection";
               }
               leaf destination-tna-address {
                 type ipaddr;
                 description "Destination TNA address for the connection";
               }
               leaf bidirectional {
                 type empty;
                 description "LSP is bidirectional";
               }
               leaf associated-bidirectional {
                 type empty;
                 description "LSP is associated-bidirectional";
               }
               leaf upstream-label-in {
                 type string;
                 description "Incoming upstream label";
               }
               leaf upstream-label-out {
                 type string;
                 description "Outgoing upstream label";
               }
               leaf lsp-associated-lspname {
                 type string;
                 description "Associated LSP name";
               }
               leaf lsp-associated-lspsrc {
                 type string;
                 description "Associated LSP source address";
               }
               leaf mpls-p2mp-lsp-name {
                 type string;
               }
               leaf p2mp-remerge-state {
                 type string;
                 description "Re-merge status of the P2MP sub-LSP";
               }
               leaf lsp-aggregation {
                 type string;
                 description "Supports LSP aggregation";
               }
               leaf suggested-label-in {
                 type int32;
                 description "Suggested label received";
               }
               leaf suggested-label-out {
                 type int32;
                 description "Suggested label sent";
               }
               leaf recovery-label-in {
                 type int32;
               }
               leaf recovery-label-out {
                 type int32;
               }
               leaf lsp-pktbytes {
                 type string;
                 description "LSP packet and byte counters";
               }
               leaf no-statistics {
                 type empty;
                 description "No statistics are available for this session";
               }
               leaf rsb-count {
                 type int32;
                 description "Number of RSBs";
               }
               leaf resv-style {
                 type string;
               }
               leaf label-in {
                 type string;
                 description "Incoming label";
               }
               leaf label-out {
                 type string;
                 description "Outgoing label";
               }
               leaf psb-lifetime {
                 type int32;
                 description "Lifetime for a PSB after which the entry expires";
               }
               leaf psb-creation-time {
                 type string;
                 description "Time when this PSB was created";
               }
               leaf path-mtu {
                 type int32;
                 description "The value of the path MTU, as negotiated by the network";
               }
               leaf path-mtu-in-kernel {
                 type int32;
                 description "The value of the MTU used locally for forwarding";
               }
               leaf sender-tspec {
                 type string;
                 description "Sender TSpec";
               }
               leaf adspec {
                 type string;
                 description "Adspec data element in an RSVP Path message";
               }
               leaf lsp-diffserv-info {
                 type string;
                 description "LSP DiffServ info";
               }
               leaf ct-bw {
                 type string;
                 description "Per-class bandwidth requested for E-LSPs and L-LSPs";
               }
               leaf lsp-id {
                 type string;
               }
               leaf tunnel-id {
                 type int32;
               }
               leaf proto-id {
                 type int32;
               }
               leaf p2mp-branch-id {
                 type uint32;
               }
               leaf p2mp-subgroup-orig {
                 type ipaddr;
               }
               leaf self-id {
                 type string;
                 description "Statistics identifier for RSVP path state control block";
               }
               leaf nh-statistics-id {
                 type string;
                 description "Nexthop statistics identifier for RSVP path at ingress";
               }
               leaf route-statistics-id {
                 type string;
                 description "Route statistics identifier for RSVP path at egress";
               }
               leaf nh-traffic-class-statistics {
                 type empty;
                 description "Traffic class statistics are enabled at ingress";
               }
               leaf route-traffic-class-statistics {
                 type empty;
                 description "Traffic class statistics are enabled at egress";
               }
               leaf session-id {
                 type int32;
                 description "Unique identifier for RSVP session";
               }
               leaf is-fastreroute {
                 type empty;
                 description "Fast reroute (one-to-one backup) is desired";
               }
               leaf is-linkprotection {
                 type empty;
                 description "Link protection (facility backup) is desired";
               }
               leaf is-nodeprotection {
                 type empty;
                 description "Link-Node protection (facility backup) is desired";
               }
               leaf ep-plr-protector {
                 type string;
               }
               leaf is-soft-preemption {
                 type empty;
                 description "Soft-preemption is desired";
               }
               leaf rsvp-path-status {
                 type string;
               }
               leaf bypass-name {
                 type string;
                 description "Name of the bypass";
               }
               leaf rsvp-lp-backup-route-cnt {
                 type int32;
                 description "Number of routes tunneled through this bypass";
               }
               leaf rsvp-lp-backup-lsp-cnt {
                 type int32;
                 description "Number of backup RSVP LSPs tunneled through this bypass";
               }
               leaf entropy-label {
                 type string;
                 description "Entropy label";
               }
               leaf p2mp-self-id {
                 type string;
                 description "Statistics identifier for RSVP P2MP path state control block";
               }
               container layer2-tspec {
                 description "Layer 2 TSpec";
                 leaf switching-granularity {
                   type string;
                   description "Layer 2 switching granularity";
                 }
                 leaf mtu {
                   type int32;
                   description "MTU along an interface";
                 }
                 leaf atm-vp-bundle-size {
                   type int32;
                   description "VP bundle size";
                 }
                 leaf atm-cell-bundle-size {
                   type int32;
                   description "Maximum cell bundle size";
                 }
               }
               container rsvp-lsp-enh-local-prot-status {
                 description "Enhanced FRR local protection status";
                 leaf rsvp-lsp-enh-local-prot-admin-status {
                   type string;
                   description "Enhanced FRR local protection admin status";
                 }
                 leaf rsvp-lsp-enh-local-prot-disabled-reason {
                   type string;
                   description "Enhanced FRR local protection disabled reason";
                 }
                 leaf rsvp-lsp-enh-local-prot-refresh-interval {
                   type string;
                   description "Enhanced FRR refresh interval set for LSP";
                 }
               }
               container rsvp-lsp-enh-local-prot-upstream {
                 description "Enhanced FRR local protection upstream information";
                 leaf rsvp-lsp-enh-lp-upstream-status {
                   type string;
                   description "Enhanced FRR local protection status upstream";
                 }
                 leaf rsvp-lsp-enh-lp-upstream-lp {
                   type string;
                   description "The node is LP-MP for Phop";
                 }
                 leaf rsvp-lsp-enh-lp-phop-addr {
                   type ipaddr;
                   description "Phop PLR for which this node is LP-MP";
                 }
                 leaf rsvp-lsp-enh-lp-upstream-lp-status {
                   type string;
                   description "Current upstream LP-MP status";
                 }
                 leaf rsvp-lsp-enh-lp-upstream-np {
                   type string;
                   description "The node is NP-MP for PPhop";
                 }
                 leaf rsvp-lsp-enh-lp-pphop-addr {
                   type ipaddr;
                   description "PPhop PLR for which this node is NP-MP";
                 }
                 leaf rsvp-lsp-enh-lp-upstream-np-status {
                   type string;
                   description "Current upstream NP-MP status";
                 }
                 leaf rsvp-lsp-enh-lp-upstream-disabled-reason {
                   type string;
                   description "Reason enhanced local protection is disabled upstream";
                 }
                 leaf rsvp-lsp-enh-local-prot-refresh-interval {
                   type string;
                   description "Enhanced FRR refresh interval set for LSP";
                 }
               }
               container rsvp-lsp-enh-local-prot-downstream {
                 description "Enhanced FRR local protection downstream information";
                 leaf rsvp-lsp-enh-lp-downstream-status {
                   type string;
                   description "Enhanced FRR local protection status downstream";
                 }
                 leaf rsvp-lsp-enh-lp-downstream-lp {
                   type string;
                   description "The node has made link protection available";
                 }
                 leaf rsvp-lsp-enh-lp-nhop-addr {
                   type ipaddr;
                   description "Nhop MP neigbor address";
                 }
                 leaf rsvp-lsp-enh-lp-downstream-np {
                   type string;
                   description "The node has made node protection available";
                 }
                 leaf rsvp-lsp-enh-lp-nnhop-addr {
                   type ipaddr;
                   description "NNhop MP neighbor address";
                 }
                 leaf rsvp-lsp-enh-lp-current-status {
                   type string;
                   description "Current downstream protection status";
                 }
                 leaf rsvp-lsp-enh-lp-downstream-disabled-reason {
                   type string;
                   description "Reason enhanced local protection is disabled downstream";
                 }
                 leaf rsvp-lsp-enh-local-prot-refresh-interval {
                   type string;
                   description "Enhanced FRR refresh interval set for LSP";
                 }
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf entropy-label {
                   type string;
                   description "Entropy label";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container record-route {
                 description "Record Route Object (RRO)";
                 leaf record-route.heading {
                   type string;
                   description "Record Route Object (RRO)";
                 }
                 leaf address {
                   type ipaddr;
                 }
                 leaf telink-id {
                   type int32;
                   description "Link identifier of unnumbered link";
                 }
                 leaf self {
                   type empty;
                 }
                 leaf incomplete {
                   type empty;
                 }
               }
               container lsp-attribute-flags {
                 description "LSP attribute flags";
                 leaf non-php {
                   type empty;
                   description "Non-PHP";
                 }
                 leaf oob {
                   type empty;
                   description "Out-of-band mapping";
                 }
               }
               container lp-history {
                 description "Log of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container rsvp-telink {
                 leaf active-reservation {
                   type int32;
                   description "Number of active reservations";
                 }
                 leaf preemption-count {
                   type int32;
                   description "Number of preemptions that occurred on an interface";
                 }
                 leaf update-threshold {
                   type int32;
                   description "Percentage change in reserved bandwidth to trigger IGP update";
                 }
                 leaf subscription {
                   type int32;
                   description "Percentage of link capacity available for bandwidth reservations";
                 }
                 leaf bc {
                   type int32;
                   description "Bandwidth constraint (0..7)";
                 }
                 leaf bc-description {
                   type string;
                   description "Description of the bandwidth constraint";
                 }
                 leaf static-bc-bandwidth {
                   type int32;
                   description "Static bandwidth capacity for a bandwidth constraint";
                 }
                 leaf ct-class {
                   type int32;
                   description "Class type (0..7)";
                 }
                 leaf static-bandwidth {
                   type int32;
                   description "Static bandwidth capacity of the link";
                 }
                 leaf available-bandwidth {
                   type int32;
                   description "Amount of bandwidth available for reservations";
                 }
                 leaf ct-subscription {
                   type int32;
                   description "Subscription percentage per traffic class";
                 }
                 leaf max-available-bandwidth {
                   type int32;
                   description "Maximum amount of bandwidth available for reservations, including the subscription factor";
                 }
                 leaf max-available-description {
                   type string;
                   description "Description of the computation of the maximum available bandwidth";
                 }
                 leaf ct-bw0 {
                   type int32;
                 }
                 leaf ct-bw1 {
                   type int32;
                 }
                 leaf ct-bw2 {
                   type int32;
                 }
                 leaf ct-bw3 {
                   type int32;
                 }
                 leaf ct-bw4 {
                   type int32;
                 }
                 leaf ct-bw5 {
                   type int32;
                 }
                 leaf ct-bw6 {
                   type int32;
                 }
                 leaf ct-bw7 {
                   type int32;
                 }
                 container reserved-ct-bandwidth {
                   description "Bandwidth reserved at different class and priority levels";
                 }
               }
               container protection-attribute {
                 description "Protection attributes of RSVP session";
                 leaf protect-lsp-type {
                   type string;
                   description "Type of LSP for protection purposes";
                 }
                 leaf protect-lsp-role {
                   type string;
                   description "Role of LSP for protection purposes";
                 }
                 leaf protect-protection-type {
                   type string;
                   description "Type of protection being used";
                 }
                 leaf protect-secondary-operational {
                   type empty;
                   description "Protecting LSP is operational and carrying protected traffic";
                 }
               }
               container association-attribute {
                 description "Association attributes of RSVP session";
                 leaf association-type {
                   type string;
                   description "Type of association object";
                 }
                 leaf association-source {
                   type ipaddr;
                   description "Source node defining the association";
                 }
                 leaf association-id {
                   type int32;
                   description "Identifier for the association";
                 }
               }
               container detour {
                 description "Detour session";
                 leaf lsp-state {
                   type string;
                   description "State of an LSP";
                 }
                 leaf sender-tspec {
                   type string;
                   description "Sender TSpec";
                 }
                 leaf lsp-diffserv-info {
                   type string;
                   description "LSP DiffServ info";
                 }
                 leaf ct-bw {
                   type string;
                   description "Per-class bandwidth requested for E-LSPs and L-LSPs";
                 }
                 leaf adspec {
                   type string;
                   description "Adspec data element in an RSVP Path message";
                 }
                 leaf path-mtu {
                   type int32;
                   description "The value of the path MTU, as negotiated by the network";
                 }
                 leaf path-mtu-in-kernel {
                   type int32;
                   description "The value of the MTU used locally for forwarding";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container record-route {
                   description "Record Route Object (RRO)";
                   leaf record-route.heading {
                     type string;
                     description "Record Route Object (RRO)";
                   }
                   leaf address {
                     type ipaddr;
                   }
                   leaf telink-id {
                     type int32;
                     description "Link identifier of unnumbered link";
                   }
                   leaf self {
                     type empty;
                   }
                   leaf incomplete {
                     type empty;
                   }
                 }
               }
               container detour-branch {
                 description "Branch of some detour session";
                 leaf source-address {
                   type ipaddr;
                 }
                 leaf skip-address {
                   type ipaddr;
                   description "Address of node or link to be skipped";
                 }
                 leaf lsp-state {
                   type string;
                   description "State of an LSP";
                 }
                 leaf sender-tspec {
                   type string;
                   description "Sender TSpec";
                 }
                 leaf adspec {
                   type string;
                   description "Adspec data element in an RSVP Path message";
                 }
                 leaf path-mtu {
                   type int32;
                   description "The value of the path MTU, as negotiated by the network";
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container record-route {
                   description "Record Route Object (RRO)";
                   leaf record-route.heading {
                     type string;
                     description "Record Route Object (RRO)";
                   }
                   leaf address {
                     type ipaddr;
                   }
                   leaf telink-id {
                     type int32;
                     description "Link identifier of unnumbered link";
                   }
                   leaf self {
                     type empty;
                   }
                   leaf incomplete {
                     type empty;
                   }
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container detour-branch-labels {
                   leaf label-in {
                     type string;
                     description "Incoming label";
                   }
                   leaf label-out {
                     type string;
                     description "Outgoing label";
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf name {
                   type string;
                 }
                 leaf lsp-type {
                   type string;
                   description "Type of LSP";
                 }
                 leaf egress-label-operation {
                   type string;
                   description "Label advertised by egress";
                 }
                 leaf lsp-control-status {
                   type string;
                   description "Control status of LSP configured to be externally controlled";
                 }
                 leaf lsp-diffserv-te-info {
                   type string;
                   description "LSP support of DiffServ-TE extensions";
                 }
                 leaf bidirectional {
                   type empty;
                   description "LSP is bidirectional";
                 }
                 leaf associated-bidirectional {
                   type empty;
                   description "LSP is associated-bidirectional";
                 }
                 leaf lsp-associated-lspname {
                   type string;
                   description "Associated LSP name";
                 }
                 leaf lsp-associated-lspsrc {
                   type string;
                   description "Associated LSP source address";
                 }
                 leaf ext-assoc-bidir {
                   type empty;
                   description "Extended associated bidirectional LSP";
                 }
                 leaf ext-assoc-bidir-direction {
                   type string;
                   description "Ext-Assoc-Bidir direction";
                 }
                 leaf lsp-description {
                   type string;
                   description "LSP description string (up to 80 characters)";
                 }
                 leaf lsp-pktbytes {
                   type string;
                   description "LSP packet and byte counters";
                 }
                 leaf aggregate-lsp-pktbytes {
                   type string;
                   description "Aggregate LSP packet and byte counters";
                 }
                 leaf no-statistics {
                   type empty;
                   description "No statistics are available for this session";
                 }
                 leaf active-path {
                   type string;
                   description "Path that the LSP is currently using";
                 }
                 leaf mpls-p2mp-name {
                   type string;
                 }
                 leaf is-fastreroute {
                   type empty;
                   description "Fast reroute (one-to-one backup) is desired";
                 }
                 leaf is-linkprotection {
                   type empty;
                   description "Link protection (facility backup) is desired";
                 }
                 leaf is-nodeprotection {
                   type empty;
                   description "Link-Node protection (facility backup) is desired";
                 }
                 leaf is-inter-domain-path {
                   type empty;
                   description "Inter-domain LSP";
                 }
                 leaf load-balance {
                   type string;
                   description "Load-balancing algorithm chosen";
                 }
                 leaf metric {
                   type int32;
                 }
                 leaf actual-metric {
                   type int32;
                 }
                 leaf revert-timer {
                   type string;
                   description "Hold-down time before reverting to primary path.";
                 }
                 leaf revert-timer-remain {
                   type string;
                   description "Time remaining before reverting:";
                 }
                 leaf optimize-protection-timer {
                   type int32;
                   description "Optimize protection timer";
                 }
                 leaf lsp-creation-time {
                   type string;
                   description "Time when the LSP was created";
                 }
                 leaf lsp-soft-preemption-counter {
                   type int32;
                   description "Number of times the LSP was soft preempted";
                 }
                 leaf lsp-soft-preemption-time {
                   type string;
                   description "Time when the LSP was last soft preempted";
                 }
                 leaf retry-timer {
                   type int32;
                 }
                 leaf retry-limit {
                   type int32;
                 }
                 leaf lsp-packets {
                   type string;
                   description "LSP packet counters";
                 }
                 leaf lsp-bytes {
                   type string;
                   description "LSP byte counters";
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container mpls-srlg {
                   leaf srlg-name {
                     type string;
                     description "Name of the srlg";
                   }
                   leaf srlg-value {
                     type uint32;
                     description "Value of the srlg";
                   }
                   leaf srlg-cost {
                     type uint32;
                     description "Cost of the srlg";
                   }
                 }
                 container mpls-lsp-autobandwidth {
                   leaf monitor-lsp-bandwidth {
                     type empty;
                     description "Enable the bandwidth monitoring mode";
                   }
                   leaf minimum-bandwidth {
                     type int32;
                     description "Configured LSP minimum bandwidth";
                   }
                   leaf maximum-bandwidth {
                     type int32;
                     description "Configured LSP maximum bandwidth";
                   }
                   leaf dynamic-minimum-bandwidth {
                     type int32;
                     description "LSP dynamic minimum bandwidth (or last Max Avg Bw)";
                   }
                   leaf adjust-timer {
                     type int32;
                     description "Configured LSP adjust timer";
                   }
                   leaf adjust-threshold {
                     type int32;
                     description "Percentage change in average LSP utilization to trigger autoadjustment";
                   }
                   leaf adjust-threshold-activate-bandwidth {
                     type int32;
                     description "Configured LSP adjust threshold bandwidth";
                   }
                   leaf maximum-average-bandwidth {
                     type int32;
                     description "Maximum Average BW";
                   }
                   leaf time-to-adjust {
                     type int32;
                     description "Time in which LSP will autoadjust bandwidth";
                   }
                   leaf autobw-minimum-bandwidth-adjust-interval {
                     type int32;
                   }
                   leaf autobw-minimum-bandwidth-adjust-threshold-percent {
                     type int32;
                   }
                   leaf autobw-minimum-bandwidth-adjust-threshold-value {
                     type int32;
                   }
                   leaf time-to-expire-minimum-bandwidth-adjust {
                     type int32;
                     description "Time in which LSP will start changing minimum bandwidth";
                   }
                   leaf overflow-limit {
                     type int32;
                     description "Configured limit of consecutive overflow samples for LSP";
                   }
                   leaf overflow-sample-count {
                     type int32;
                     description "Number of consecutive overflow samples encountered";
                   }
                   leaf underflow-limit {
                     type int32;
                     description "Configured limit of consecutive underflow samples for LSP";
                   }
                   leaf underflow-sample-count {
                     type int32;
                     description "Number of consecutive underflow samples encountered";
                   }
                   leaf underflow-max-avg-bandwidth {
                     type int32;
                     description "Highest average bandwidth recorded so far for underflow samples";
                   }
                 }
                 container mpls-lsp-path {
                   description "Primary or secondary LSP path";
                   leaf path-active {
                     type empty;
                     description "Whether the path is active or not";
                   }
                   leaf title {
                     type string;
                   }
                   leaf name {
                     type string;
                   }
                   leaf path-state {
                     type string;
                     description "State of the MPLS path";
                   }
                   leaf cos {
                     type int32;
                     description "CoS value";
                   }
                   leaf no-decrement-ttl {
                     type empty;
                     description "TTL";
                   }
                   leaf preference {
                     type int32;
                     description "Preference for the route";
                   }
                   leaf path-soft-preemption-pending {
                     type empty;
                     description "Soft preemption pending for this path";
                   }
                   leaf setup-priority {
                     type int32;
                     description "Priority with respect to taking resources";
                   }
                   leaf hold-priority {
                     type int32;
                     description "Priority with respect to holding resources";
                   }
                   leaf actual-setup-priority {
                     type int32;
                   }
                   leaf actual-hold-priority {
                     type int32;
                   }
                   leaf external-lsp-cspf-type {
                     type string;
                   }
                   leaf bandwidth {
                     type int32;
                   }
                   leaf actual-bandwidth {
                     type int32;
                   }
                   leaf per-class-bandwidth-heading {
                     type string;
                   }
                   leaf bandwidth_ct0 {
                     type int32;
                   }
                   leaf bandwidth_ct1 {
                     type int32;
                   }
                   leaf bandwidth_ct2 {
                     type int32;
                   }
                   leaf bandwidth_ct3 {
                     type int32;
                   }
                   leaf path-adaptive {
                     type empty;
                     description "LSP is adaptive";
                   }
                   leaf path-no-recordroute {
                     type empty;
                     description "Record route disabled";
                   }
                   leaf hoplimit {
                     type int32;
                     description "Maximum number of hops that can be traversed";
                   }
                   leaf optimize-timer {
                     type int32;
                     description "Optimize timer";
                   }
                   leaf smart-optimize-timer {
                     type int32;
                     description "Smart optimize timer";
                   }
                   leaf retry-timer {
                     type int32;
                   }
                   leaf retry-limit {
                     type int32;
                   }
                   leaf external-cspf-status {
                     type string;
                     description "Status provided by External CSPF computation";
                   }
                   leaf cspf-status {
                     type string;
                     description "Status returned by CSPF computation";
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                   container mpls-srlg {
                     leaf srlg-name {
                       type string;
                       description "Name of the srlg";
                     }
                     leaf srlg-value {
                       type uint32;
                       description "Value of the srlg";
                     }
                     leaf srlg-cost {
                       type uint32;
                       description "Cost of the srlg";
                     }
                   }
                 }
                 container mpls-lsp-attributes {
                   leaf signal-type {
                     type string;
                   }
                   leaf encoding-type {
                     type string;
                     description "LSP encoding type";
                   }
                   leaf switching-type {
                     type string;
                     description "LSP switching capability";
                   }
                   leaf gpid {
                     type string;
                     description "LSP generalized PID";
                   }
                   leaf protection-type {
                     type string;
                     description "LSP protection desired";
                   }
                 }
               }
             }
           }
           container mpls-p2mp-lsp {
             leaf mpls-p2mp-name {
               type string;
             }
             leaf mpls-p2mp-branch-count {
               type string;
             }
           }
           container mpls-container-lsp {
             description "MPLS container-label-switched path information";
             leaf mpls-container-lsp-name {
               type string;
             }
             leaf mpls-container-lsp-state {
               type string;
             }
             leaf mpls-container-member-count {
               type string;
             }
             leaf container-active-path {
               type string;
               description "Path that the member LSP is currently using";
             }
             leaf container-is-primary {
               type empty;
               description "Path is a primary path";
             }
             leaf lsp-packets {
               type string;
               description "LSP packet counters";
             }
             leaf lsp-bytes {
               type string;
               description "LSP byte counters";
             }
             leaf lsp-control-status {
               type string;
               description "Control status of LSP configured to be externally controlled";
             }
             container mpls-lsp-path {
               description "Primary or secondary LSP path";
               container admin-groups {
                 leaf admin-groups.heading {
                   type string;
                 }
                 leaf color {
                   type int32;
                 }
                 leaf no-group-flag {
                   type empty;
                 }
                 leaf admin-group-name {
                   type string;
                   description "Name of the admin group";
                 }
                 leaf admin-group-number {
                   type int32;
                   description "Number of the admin group";
                 }
               }
               container admin-groups-extended {
                 leaf admin-groups-extended.heading {
                   type string;
                 }
                 leaf admin-group-name {
                   type string;
                   description "Name of the admin group";
                 }
                 leaf admin-group-number {
                   type int32;
                   description "Number of the admin group";
                 }
               }
               container srlg {
                 leaf srlg.heading {
                   type string;
                 }
                 leaf srlg-name {
                   type string;
                   description "Name of the srlg";
                 }
               }
               container mpls-lsp-upstream-label {
                 description "Upstream label configured for the LSP";
                 leaf vlan-id-label {
                   type uint32;
                   description "VLAN ID label configured for the LSP";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container oam-state {
                 description "OAM state information";
                 leaf oam-bfd-session-state {
                   type string;
                 }
                 leaf oam-lsp-ping-state {
                   type string;
                 }
               }
               container path-history {
                 description "Log over time of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container path-available-bandwidth {
                 description "Available bandwidth on an LSP path";
                 leaf path-available-bandwidth.heading {
                   type string;
                   description "Available bandwidth on an LSP path";
                 }
                 leaf bandwidth {
                   type int32;
                 }
                 leaf class-type {
                   type int32;
                 }
                 leaf class-bandwidth {
                   type int32;
                 }
               }
               container layer2-connection {
                 description "Layer 2 connection using the LSP path";
                 leaf neighbor-address {
                   type ipaddr;
                   description "IP address of this neighbor";
                 }
                 leaf interface-name {
                   type string;
                   description "Name of interface";
                 }
                 leaf vc-id {
                   type int32;
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
               }
             }
             container mpls-container-lsp-splitting-merging {
               leaf minimum-member-lsps {
                 type int32;
                 description "Configured minimum LSPs";
               }
               leaf maximum-member-lsps {
                 type int32;
                 description "Configured maximum LSPs";
               }
               leaf aggregate-bandwidth {
                 type int32;
                 description "Aggregate bandwidth";
               }
               leaf current-bandwidth {
                 type int32;
                 description "Sampled Aggregate bandwidth";
               }
               leaf normalize-interval {
                 type int32;
                 description "Configured LSP normalize timer";
               }
               leaf splitting-merging-threshold {
                 type int32;
                 description "Percentage change in aggregate LSP utilization to trigger normalization";
               }
               leaf maximum-signaling-bandwidth {
                 type int32;
                 description "Configured signaling maximum bandwidth";
               }
               leaf minimum-signaling-bandwidth {
                 type int32;
                 description "Configured signaling minimum bandwidth";
               }
               leaf maximum-splitting-bandwidth {
                 type int32;
                 description "Configured splitting maximum bandwidth";
               }
               leaf minimum-splitting-bandwidth {
                 type int32;
                 description "Configured splitting minimum bandwidth";
               }
               leaf normalization-mode {
                 type string;
               }
               leaf sampling-mode {
                 type string;
                 description "Sampling Attributes";
               }
               leaf time-to-normalize {
                 type int32;
                 description "Time in which LSP will normalize";
               }
               leaf aggregate-packets {
                 type int32;
                 description "Aggregate packets";
               }
               leaf aggregate-bytes {
                 type int32;
                 description "Aggregate bytes";
               }
             }
             container mpls-container-lsp-history {
               description "Log over time of container LSP related events";
               leaf sequence-number {
                 type int32;
                 description "History event number";
               }
               leaf time {
                 type string;
                 description "Time of the event";
               }
               leaf log {
                 type string;
                 description "Supplemental information of the event";
               }
               leaf route {
                 type string;
                 description "Latest RRO contents, as reported by RSVP";
               }
             }
           }
           container mpls-container-lsp-member-summary {
             container mpls-container-lsp {
               description "MPLS container-label-switched path information";
               leaf mpls-container-lsp-name {
                 type string;
               }
               leaf mpls-container-lsp-state {
                 type string;
               }
               leaf mpls-container-member-count {
                 type string;
               }
               leaf container-active-path {
                 type string;
                 description "Path that the member LSP is currently using";
               }
               leaf container-is-primary {
                 type empty;
                 description "Path is a primary path";
               }
               leaf lsp-packets {
                 type string;
                 description "LSP packet counters";
               }
               leaf lsp-bytes {
                 type string;
                 description "LSP byte counters";
               }
               leaf lsp-control-status {
                 type string;
                 description "Control status of LSP configured to be externally controlled";
               }
               container mpls-lsp-path {
                 description "Primary or secondary LSP path";
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container srlg {
                   leaf srlg.heading {
                     type string;
                   }
                   leaf srlg-name {
                     type string;
                     description "Name of the srlg";
                   }
                 }
                 container mpls-lsp-upstream-label {
                   description "Upstream label configured for the LSP";
                   leaf vlan-id-label {
                     type uint32;
                     description "VLAN ID label configured for the LSP";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container oam-state {
                   description "OAM state information";
                   leaf oam-bfd-session-state {
                     type string;
                   }
                   leaf oam-lsp-ping-state {
                     type string;
                   }
                 }
                 container path-history {
                   description "Log over time of LSP path-related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
                 container path-available-bandwidth {
                   description "Available bandwidth on an LSP path";
                   leaf path-available-bandwidth.heading {
                     type string;
                     description "Available bandwidth on an LSP path";
                   }
                   leaf bandwidth {
                     type int32;
                   }
                   leaf class-type {
                     type int32;
                   }
                   leaf class-bandwidth {
                     type int32;
                   }
                 }
                 container layer2-connection {
                   description "Layer 2 connection using the LSP path";
                   leaf neighbor-address {
                     type ipaddr;
                     description "IP address of this neighbor";
                   }
                   leaf interface-name {
                     type string;
                     description "Name of interface";
                   }
                   leaf vc-id {
                     type int32;
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                 }
               }
               container mpls-container-lsp-splitting-merging {
                 leaf minimum-member-lsps {
                   type int32;
                   description "Configured minimum LSPs";
                 }
                 leaf maximum-member-lsps {
                   type int32;
                   description "Configured maximum LSPs";
                 }
                 leaf aggregate-bandwidth {
                   type int32;
                   description "Aggregate bandwidth";
                 }
                 leaf current-bandwidth {
                   type int32;
                   description "Sampled Aggregate bandwidth";
                 }
                 leaf normalize-interval {
                   type int32;
                   description "Configured LSP normalize timer";
                 }
                 leaf splitting-merging-threshold {
                   type int32;
                   description "Percentage change in aggregate LSP utilization to trigger normalization";
                 }
                 leaf maximum-signaling-bandwidth {
                   type int32;
                   description "Configured signaling maximum bandwidth";
                 }
                 leaf minimum-signaling-bandwidth {
                   type int32;
                   description "Configured signaling minimum bandwidth";
                 }
                 leaf maximum-splitting-bandwidth {
                   type int32;
                   description "Configured splitting maximum bandwidth";
                 }
                 leaf minimum-splitting-bandwidth {
                   type int32;
                   description "Configured splitting minimum bandwidth";
                 }
                 leaf normalization-mode {
                   type string;
                 }
                 leaf sampling-mode {
                   type string;
                   description "Sampling Attributes";
                 }
                 leaf time-to-normalize {
                   type int32;
                   description "Time in which LSP will normalize";
                 }
                 leaf aggregate-packets {
                   type int32;
                   description "Aggregate packets";
                 }
                 leaf aggregate-bytes {
                   type int32;
                   description "Aggregate bytes";
                 }
               }
               container mpls-container-lsp-history {
                 description "Log over time of container LSP related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
             }
           }
           container container-rsvp-session {
             container brief {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf is-primary {
                   type empty;
                   description "Path is a primary path";
                 }
                 leaf active-path {
                   type string;
                   description "Path that the LSP is currently using";
                 }
                 leaf container-member-name {
                   type string;
                   description "Path that the member LSP is currently using";
                 }
                 leaf label-out {
                   type string;
                   description "Outgoing label";
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf label-out {
                   type string;
                   description "Outgoing label";
                 }
               }
               container detour {
                 description "Detour session";
                 leaf lsp-state {
                   type string;
                   description "State of an LSP";
                 }
                 leaf label-out {
                   type string;
                   description "Outgoing label";
                 }
               }
               container detour-branch {
                 description "Branch of some detour session";
                 container detour-branch-labels {
                 }
               }
             }
             container descriptions {
               container mpls-container-lsp {
                 description "MPLS container-label-switched path information";
                 leaf destination-address {
                   type ipaddr;
                   description "Session destination address";
                 }
                 leaf source-address {
                   type ipaddr;
                 }
                 leaf lsp-description {
                   type string;
                   description "LSP description string (up to 80 characters)";
                 }
                 leaf container-active-path {
                   type string;
                   description "Path that the member LSP is currently using";
                 }
                 leaf container-is-primary {
                   type empty;
                   description "Path is a primary path";
                 }
                 leaf lsp-packets {
                   type string;
                   description "LSP packet counters";
                 }
                 leaf lsp-bytes {
                   type string;
                   description "LSP byte counters";
                 }
                 leaf lsp-control-status {
                   type string;
                   description "Control status of LSP configured to be externally controlled";
                 }
                 container mpls-lsp-path {
                   description "Primary or secondary LSP path";
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
                 container mpls-container-lsp-splitting-merging {
                   leaf minimum-member-lsps {
                     type int32;
                     description "Configured minimum LSPs";
                   }
                   leaf maximum-member-lsps {
                     type int32;
                     description "Configured maximum LSPs";
                   }
                   leaf aggregate-bandwidth {
                     type int32;
                     description "Aggregate bandwidth";
                   }
                   leaf current-bandwidth {
                     type int32;
                     description "Sampled Aggregate bandwidth";
                   }
                   leaf normalize-interval {
                     type int32;
                     description "Configured LSP normalize timer";
                   }
                   leaf splitting-merging-threshold {
                     type int32;
                     description "Percentage change in aggregate LSP utilization to trigger normalization";
                   }
                   leaf maximum-signaling-bandwidth {
                     type int32;
                     description "Configured signaling maximum bandwidth";
                   }
                   leaf minimum-signaling-bandwidth {
                     type int32;
                     description "Configured signaling minimum bandwidth";
                   }
                   leaf maximum-splitting-bandwidth {
                     type int32;
                     description "Configured splitting maximum bandwidth";
                   }
                   leaf minimum-splitting-bandwidth {
                     type int32;
                     description "Configured splitting minimum bandwidth";
                   }
                   leaf normalization-mode {
                     type string;
                   }
                   leaf sampling-mode {
                     type string;
                     description "Sampling Attributes";
                   }
                   leaf time-to-normalize {
                     type int32;
                     description "Time in which LSP will normalize";
                   }
                   leaf aggregate-packets {
                     type int32;
                     description "Aggregate packets";
                   }
                   leaf aggregate-bytes {
                     type int32;
                     description "Aggregate bytes";
                   }
                 }
                 container mpls-container-lsp-history {
                   description "Log over time of container LSP related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
               }
               container mpls-lsp {
                 description "MPLS label-switched path information";
                 leaf destination-address {
                   type ipaddr;
                   description "Session destination address";
                 }
                 leaf name {
                   type string;
                 }
                 leaf lsp-description {
                   type string;
                   description "LSP description string (up to 80 characters)";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container detour {
                 description "Detour session";
               }
               container detour-branch {
                 description "Branch of some detour session";
               }
             }
             container brief_stats {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf lsp-pktbytes {
                   type string;
                   description "LSP packet and byte counters";
                 }
                 leaf name {
                   type string;
                 }
                 leaf bidirectional {
                   type empty;
                   description "LSP is bidirectional";
                 }
                 leaf associated-bidirectional {
                   type empty;
                   description "LSP is associated-bidirectional";
                 }
                 leaf lsp-packets {
                   type string;
                   description "LSP packet counters";
                 }
                 leaf lsp-bytes {
                   type string;
                   description "LSP byte counters";
                 }
                 container mpls-lsp-path {
                   description "Primary or secondary LSP path";
                   leaf path-active {
                     type empty;
                     description "Whether the path is active or not";
                   }
                   leaf title {
                     type string;
                   }
                   container admin-groups {
                     leaf admin-groups.heading {
                       type string;
                     }
                     leaf color {
                       type int32;
                     }
                     leaf no-group-flag {
                       type empty;
                     }
                     leaf admin-group-name {
                       type string;
                       description "Name of the admin group";
                     }
                     leaf admin-group-number {
                       type int32;
                       description "Number of the admin group";
                     }
                   }
                   container admin-groups-extended {
                     leaf admin-groups-extended.heading {
                       type string;
                     }
                     leaf admin-group-name {
                       type string;
                       description "Name of the admin group";
                     }
                     leaf admin-group-number {
                       type int32;
                       description "Number of the admin group";
                     }
                   }
                   container srlg {
                     leaf srlg.heading {
                       type string;
                     }
                     leaf srlg-name {
                       type string;
                       description "Name of the srlg";
                     }
                   }
                   container mpls-lsp-upstream-label {
                     description "Upstream label configured for the LSP";
                     leaf vlan-id-label {
                       type uint32;
                       description "VLAN ID label configured for the LSP";
                     }
                   }
                   container explicit-route {
                     description "Explicit Route Object (ERO)";
                     leaf explicit-route.heading {
                       type string;
                       description "Explicit Route Object (ERO)";
                     }
                     leaf address {
                       type ipaddr;
                     }
                     leaf explicit-route-type {
                       type string;
                     }
                     leaf telink-id {
                       type int32;
                       description "Link identifier of unnumbered link";
                     }
                   }
                   container oam-state {
                     description "OAM state information";
                     leaf oam-bfd-session-state {
                       type string;
                     }
                     leaf oam-lsp-ping-state {
                       type string;
                     }
                   }
                   container path-history {
                     description "Log over time of LSP path-related events";
                     leaf sequence-number {
                       type int32;
                       description "History event number";
                     }
                     leaf time {
                       type string;
                       description "Time of the event";
                     }
                     leaf log {
                       type string;
                       description "Supplemental information of the event";
                     }
                     leaf route {
                       type string;
                       description "Latest RRO contents, as reported by RSVP";
                     }
                   }
                   container path-available-bandwidth {
                     description "Available bandwidth on an LSP path";
                     leaf path-available-bandwidth.heading {
                       type string;
                       description "Available bandwidth on an LSP path";
                     }
                     leaf bandwidth {
                       type int32;
                     }
                     leaf class-type {
                       type int32;
                     }
                     leaf class-bandwidth {
                       type int32;
                     }
                   }
                   container layer2-connection {
                     description "Layer 2 connection using the LSP path";
                     leaf neighbor-address {
                       type ipaddr;
                       description "IP address of this neighbor";
                     }
                     leaf interface-name {
                       type string;
                       description "Name of interface";
                     }
                     leaf vc-id {
                       type int32;
                     }
                     container connection-bandwidth {
                       description "Bandwidth of a layer 2 connection";
                       leaf connection-bandwidth.heading {
                         type string;
                         description "Bandwidth of a layer 2 connection";
                       }
                       leaf bandwidth {
                         type int32;
                       }
                       leaf class-type {
                         type int32;
                       }
                       leaf class-bandwidth {
                         type int32;
                       }
                     }
                   }
                 }
               }
               container detour {
                 description "Detour session";
               }
               container detour-branch {
                 description "Branch of some detour session";
               }
             }
             container detail {
               container mpls-container-lsp {
                 description "MPLS container-label-switched path information";
                 leaf destination-address {
                   type ipaddr;
                   description "Session destination address";
                 }
                 leaf source-address {
                   type ipaddr;
                 }
                 leaf lsp-state {
                   type string;
                   description "State of an LSP";
                 }
                 leaf route-count {
                   type int32;
                   description "Number of active routes";
                 }
                 leaf lsp-type {
                   type string;
                   description "Type of LSP";
                 }
                 leaf egress-label-operation {
                   type string;
                   description "Label advertised by egress";
                 }
                 leaf lsp-diffserv-te-info {
                   type string;
                   description "LSP support of DiffServ-TE extensions";
                 }
                 leaf lsp-description {
                   type string;
                   description "LSP description string (up to 80 characters)";
                 }
                 leaf lsp-pktbytes {
                   type string;
                   description "LSP packet and byte counters";
                 }
                 leaf aggregate-lsp-pktbytes {
                   type string;
                   description "Aggregate LSP packet and byte counters";
                 }
                 leaf no-statistics {
                   type empty;
                   description "No statistics are available for this session";
                 }
                 leaf active-path {
                   type string;
                   description "Path that the LSP is currently using";
                 }
                 leaf mpls-container-name {
                   type string;
                   description "Name of the container LSP";
                 }
                 leaf is-fastreroute {
                   type empty;
                   description "Fast reroute (one-to-one backup) is desired";
                 }
                 leaf is-linkprotection {
                   type empty;
                   description "Link protection (facility backup) is desired";
                 }
                 leaf is-nodeprotection {
                   type empty;
                   description "Link-Node protection (facility backup) is desired";
                 }
                 leaf is-inter-domain-path {
                   type empty;
                   description "Inter-domain LSP";
                 }
                 leaf load-balance {
                   type string;
                   description "Load-balancing algorithm chosen";
                 }
                 leaf metric {
                   type int32;
                 }
                 leaf optimize-protection-timer {
                   type int32;
                   description "Optimize protection timer";
                 }
                 leaf lsp-creation-time {
                   type string;
                   description "Time when the LSP was created";
                 }
                 leaf lsp-soft-preemption-counter {
                   type int32;
                   description "Number of times the LSP was soft preempted";
                 }
                 leaf lsp-soft-preemption-time {
                   type string;
                   description "Time when the LSP was last soft preempted";
                 }
                 leaf retry-timer {
                   type int32;
                 }
                 leaf retry-limit {
                   type int32;
                 }
                 container admin-groups {
                   leaf admin-groups.heading {
                     type string;
                   }
                   leaf color {
                     type int32;
                   }
                   leaf no-group-flag {
                     type empty;
                   }
                   leaf admin-group-name {
                     type string;
                     description "Name of the admin group";
                   }
                   leaf admin-group-number {
                     type int32;
                     description "Number of the admin group";
                   }
                 }
                 container admin-groups-extended {
                   leaf admin-groups-extended.heading {
                     type string;
                   }
                   leaf admin-group-name {
                     type string;
                     description "Name of the admin group";
                   }
                   leaf admin-group-number {
                     type int32;
                     description "Number of the admin group";
                   }
                 }
                 container srlg {
                   leaf srlg.heading {
                     type string;
                   }
                   leaf srlg-name {
                     type string;
                     description "Name of the srlg";
                   }
                 }
                 container mpls-lsp-upstream-label {
                   description "Upstream label configured for the LSP";
                   leaf vlan-id-label {
                     type uint32;
                     description "VLAN ID label configured for the LSP";
                   }
                 }
                 container explicit-route {
                   description "Explicit Route Object (ERO)";
                   leaf explicit-route.heading {
                     type string;
                     description "Explicit Route Object (ERO)";
                   }
                   leaf address {
                     type ipaddr;
                   }
                   leaf explicit-route-type {
                     type string;
                   }
                   leaf telink-id {
                     type int32;
                     description "Link identifier of unnumbered link";
                   }
                 }
                 container oam-state {
                   description "OAM state information";
                   leaf oam-bfd-session-state {
                     type string;
                   }
                   leaf oam-lsp-ping-state {
                     type string;
                   }
                 }
                 container path-history {
                   description "Log over time of LSP path-related events";
                   leaf sequence-number {
                     type int32;
                     description "History event number";
                   }
                   leaf time {
                     type string;
                     description "Time of the event";
                   }
                   leaf log {
                     type string;
                     description "Supplemental information of the event";
                   }
                   leaf route {
                     type string;
                     description "Latest RRO contents, as reported by RSVP";
                   }
                 }
                 container path-available-bandwidth {
                   description "Available bandwidth on an LSP path";
                   leaf path-available-bandwidth.heading {
                     type string;
                     description "Available bandwidth on an LSP path";
                   }
                   leaf bandwidth {
                     type int32;
                   }
                   leaf class-type {
                     type int32;
                   }
                   leaf class-bandwidth {
                     type int32;
                   }
                 }
                 container layer2-connection {
                   description "Layer 2 connection using the LSP path";
                   leaf neighbor-address {
                     type ipaddr;
                     description "IP address of this neighbor";
                   }
                   leaf interface-name {
                     type string;
                     description "Name of interface";
                   }
                   leaf vc-id {
                     type int32;
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                 }
                 container mpls-srlg {
                   leaf srlg-name {
                     type string;
                     description "Name of the srlg";
                   }
                   leaf srlg-value {
                     type uint32;
                     description "Value of the srlg";
                   }
                   leaf srlg-cost {
                     type uint32;
                     description "Cost of the srlg";
                   }
                 }
               }
               container mpls-lsp {
                 description "MPLS label-switched path information";
                 leaf destination-address {
                   type ipaddr;
                   description "Session destination address";
                 }
                 leaf source-address {
                   type ipaddr;
                 }
                 leaf lsp-state {
                   type string;
                   description "State of an LSP";
                 }
                 leaf label-out {
                   type string;
                   description "Outgoing label";
                 }
                 leaf path-mtu {
                   type int32;
                   description "The value of the path MTU, as negotiated by the network";
                 }
                 leaf path-mtu-in-kernel {
                   type int32;
                   description "The value of the MTU used locally for forwarding";
                 }
                 leaf sender-tspec {
                   type string;
                   description "Sender TSpec";
                 }
                 leaf adspec {
                   type string;
                   description "Adspec data element in an RSVP Path message";
                 }
                 leaf lsp-diffserv-info {
                   type string;
                   description "LSP DiffServ info";
                 }
                 leaf ct-bw {
                   type string;
                   description "Per-class bandwidth requested for E-LSPs and L-LSPs";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
               }
               container packet-information {
                 description "RSVP packets sent or received per session";
                 leaf packet-information.heading {
                   type string;
                   description "RSVP packets sent or received per session";
                 }
                 leaf previous-hop {
                   type ipaddr;
                   description "Previous-hop address";
                 }
                 leaf next-hop {
                   type ipaddr;
                   description "Next-hop address";
                 }
                 leaf interface-name {
                   type string;
                   description "Name of interface";
                 }
                 leaf count {
                   type int32;
                 }
                 leaf notify-destination {
                   type ipaddr;
                   description "Notify address";
                 }
                 leaf entropy-label {
                   type string;
                   description "Entropy label";
                 }
                 leaf in-message-handle {
                   type string;
                   description "RSVP I/O handle for incoming message";
                 }
                 leaf in-message-id {
                   type uint32;
                   description "Incoming Message ID";
                 }
                 leaf in-epoch {
                   type uint32;
                   description "Incoming Epoch";
                 }
                 leaf out-message-state {
                   type string;
                   description "RSVP I/O state for outgoing message";
                 }
                 leaf out-message-id {
                   type uint32;
                   description "Outgoing Message ID";
                 }
                 leaf out-epoch {
                   type uint32;
                   description "Outgoing Epoch";
                 }
               }
               container detour {
                 description "Detour session";
                 leaf lsp-state {
                   type string;
                   description "State of an LSP";
                 }
                 leaf sender-tspec {
                   type string;
                   description "Sender TSpec";
                 }
                 leaf lsp-diffserv-info {
                   type string;
                   description "LSP DiffServ info";
                 }
                 leaf ct-bw {
                   type string;
                   description "Per-class bandwidth requested for E-LSPs and L-LSPs";
                 }
                 leaf adspec {
                   type string;
                   description "Adspec data element in an RSVP Path message";
                 }
                 leaf path-mtu {
                   type int32;
                   description "The value of the path MTU, as negotiated by the network";
                 }
                 leaf path-mtu-in-kernel {
                   type int32;
                   description "The value of the MTU used locally for forwarding";
                 }
                 leaf label-out {
                   type string;
                   description "Outgoing label";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
               }
               container detour-branch {
                 description "Branch of some detour session";
                 leaf source-address {
                   type ipaddr;
                 }
                 leaf skip-address {
                   type ipaddr;
                   description "Address of node or link to be skipped";
                 }
                 leaf lsp-state {
                   type string;
                   description "State of an LSP";
                 }
                 leaf sender-tspec {
                   type string;
                   description "Sender TSpec";
                 }
                 leaf adspec {
                   type string;
                   description "Adspec data element in an RSVP Path message";
                 }
                 leaf path-mtu {
                   type int32;
                   description "The value of the path MTU, as negotiated by the network";
                 }
                 container packet-information {
                   description "RSVP packets sent or received per session";
                   leaf packet-information.heading {
                     type string;
                     description "RSVP packets sent or received per session";
                   }
                   leaf previous-hop {
                     type ipaddr;
                     description "Previous-hop address";
                   }
                   leaf next-hop {
                     type ipaddr;
                     description "Next-hop address";
                   }
                   leaf interface-name {
                     type string;
                     description "Name of interface";
                   }
                   leaf count {
                     type int32;
                   }
                   leaf notify-destination {
                     type ipaddr;
                     description "Notify address";
                   }
                   leaf entropy-label {
                     type string;
                     description "Entropy label";
                   }
                   leaf in-message-handle {
                     type string;
                     description "RSVP I/O handle for incoming message";
                   }
                   leaf in-message-id {
                     type uint32;
                     description "Incoming Message ID";
                   }
                   leaf in-epoch {
                     type uint32;
                     description "Incoming Epoch";
                   }
                   leaf out-message-state {
                     type string;
                     description "RSVP I/O state for outgoing message";
                   }
                   leaf out-message-id {
                     type uint32;
                     description "Outgoing Message ID";
                   }
                   leaf out-epoch {
                     type uint32;
                     description "Outgoing Epoch";
                   }
                 }
                 container detour-branch-labels {
                   container packet-information {
                     description "RSVP packets sent or received per session";
                     leaf packet-information.heading {
                       type string;
                       description "RSVP packets sent or received per session";
                     }
                     leaf previous-hop {
                       type ipaddr;
                       description "Previous-hop address";
                     }
                     leaf next-hop {
                       type ipaddr;
                       description "Next-hop address";
                     }
                     leaf interface-name {
                       type string;
                       description "Name of interface";
                     }
                     leaf count {
                       type int32;
                     }
                     leaf notify-destination {
                       type ipaddr;
                       description "Notify address";
                     }
                     leaf entropy-label {
                       type string;
                       description "Entropy label";
                     }
                     leaf in-message-handle {
                       type string;
                       description "RSVP I/O handle for incoming message";
                     }
                     leaf in-message-id {
                       type uint32;
                       description "Incoming Message ID";
                     }
                     leaf in-epoch {
                       type uint32;
                       description "Incoming Epoch";
                     }
                     leaf out-message-state {
                       type string;
                       description "RSVP I/O state for outgoing message";
                     }
                     leaf out-message-id {
                       type uint32;
                       description "Outgoing Message ID";
                     }
                     leaf out-epoch {
                       type uint32;
                       description "Outgoing Epoch";
                     }
                   }
                 }
               }
             }
           }
         }
       }
     }
   }
   rpc get-mpls-container-lsp-defaults-information {
     description "Display container LSP defaults";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       container mpls-container-lsp-defaults-information {
         container mpls-container-lsp-defaults {
           leaf minimum-splitting-bandwidth {
             type int32;
             description "Configured splitting minimum bandwidth";
           }
           leaf maximum-splitting-bandwidth {
             type int32;
             description "Configured splitting maximum bandwidth";
           }
           leaf minimum-signaling-bandwidth {
             type int32;
             description "Configured signaling minimum bandwidth";
           }
           leaf maximum-signaling-bandwidth {
             type int32;
             description "Configured signaling maximum bandwidth";
           }
           leaf maximum-member-lsps {
             type int32;
             description "Configured maximum LSPs";
           }
           leaf minimum-member-lsps {
             type int32;
             description "Configured minimum LSPs";
           }
           leaf splitting-merging-threshold {
             type int32;
             description "Percentage change in aggregate LSP utilization to trigger normalization";
           }
           leaf normalize-interval {
             type int32;
             description "Configured LSP normalize timer";
           }
           leaf normalization-mode {
             type string;
           }
           leaf normalize-retry-duration {
             type int32;
             description "Default normalize retry duration";
           }
           leaf normalize-retry-limit {
             type int32;
             description "Default normalize retry limit";
           }
           leaf sampling-mode {
             type string;
             description "Sampling Attributes";
           }
           leaf failover-normalization {
             type string;
             description "Default failover normalization";
           }
           leaf stats-sampling-interval {
             type int32;
             description "Default statistics collection interval";
           }
         }
       }
     }
   }
   rpc get-mpls-static-lsp-information {
     description "Show configured static label-switched paths";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
       leaf lsp-type {
         type enumeration {
           enum "bypass" {
             description "Display bypass LSPs originating at this router";
           }
           enum "ingress" {
             description "Display LSPs originating at this router";
           }
           enum "transit" {
             description "Display LSPs transiting this router";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
           enum "statistics" {
             description "Display packet statistics for LSPs";
           }
         }
       }
       leaf lsp-state {
         type enumeration {
           enum "up" {
             description "Display active LSPs";
           }
           enum "down" {
             description "Display inactive LSPs";
           }
         }
       }
       leaf regex {
         description "Regular expression for LSP names to match";
         type string;
       }
     }
     output {
       container mpls-static-lsp-information {
         container mpls-static-lsp-summary {
           leaf session-type {
             type string;
             description "Type of session with respect to this router";
           }
           leaf count {
             type int32;
           }
           leaf display-count {
             type int32;
             description "Number of sessions displayed";
           }
           leaf up-count {
             type int32;
             description "Number of sessions in up state";
           }
           leaf down-count {
             type int32;
             description "Number of sessions in down state";
           }
         }
         container mpls-static-ingress-lsp-brief {
           leaf lsp-name {
             type string;
             description "Tunneled into an RSVP LSP";
           }
           leaf destination-address {
             type ipaddr;
             description "Session destination address";
           }
           leaf lsp-state {
             type string;
             description "State of an LSP";
           }
         }
         container mpls-static-transit-lsp-brief {
           leaf lsp-name {
             type string;
             description "Tunneled into an RSVP LSP";
           }
           leaf label-in {
             type string;
             description "Incoming label";
           }
           leaf lsp-state {
             type string;
             description "State of an LSP";
           }
         }
         container mpls-static-ingress-lsp-descriptions {
           leaf lsp-name {
             type string;
             description "Tunneled into an RSVP LSP";
           }
           leaf destination-address {
             type ipaddr;
             description "Session destination address";
           }
           leaf lsp-description {
             type string;
             description "LSP description string (up to 80 characters)";
           }
         }
         container mpls-static-transit-lsp-descriptions {
           leaf lsp-name {
             type string;
             description "Tunneled into an RSVP LSP";
           }
           leaf label-in {
             type string;
             description "Incoming label";
           }
           leaf lsp-description {
             type string;
             description "LSP description string (up to 80 characters)";
           }
         }
         container mpls-static-ingress-lsp-statistics {
           leaf lsp-name {
             type string;
             description "Tunneled into an RSVP LSP";
           }
           leaf destination-address {
             type ipaddr;
             description "Session destination address";
           }
           leaf lsp-state {
             type string;
             description "State of an LSP";
           }
           leaf lsp-pktbytes {
             type string;
             description "LSP packet and byte counters";
           }
           leaf lsp-packets {
             type string;
             description "LSP packet counters";
           }
           leaf lsp-bytes {
             type string;
             description "LSP byte counters";
           }
         }
         container mpls-static-transit-lsp-statistics {
           leaf lsp-name {
             type string;
             description "Tunneled into an RSVP LSP";
           }
           leaf label-in {
             type string;
             description "Incoming label";
           }
           leaf lsp-state {
             type string;
             description "State of an LSP";
           }
           leaf lsp-pktbytes {
             type string;
             description "LSP packet and byte counters";
           }
           leaf lsp-packets {
             type string;
             description "LSP packet counters";
           }
           leaf lsp-bytes {
             type string;
             description "LSP byte counters";
           }
         }
         container mpls-static-lsp-detail {
           leaf lsp-name {
             type string;
             description "Tunneled into an RSVP LSP";
           }
           leaf destination-address {
             type ipaddr;
             description "Session destination address";
           }
           leaf label-in {
             type string;
             description "Incoming label";
           }
           leaf lsp-description {
             type string;
             description "LSP description string (up to 80 characters)";
           }
           leaf lsp-state {
             type string;
             description "State of an LSP";
           }
           leaf lsp-sub-state {
             type string;
             description "LSP sub state";
           }
           leaf next-hop {
             type ipaddr;
             description "Next-hop address";
           }
           leaf interface-name {
             type string;
             description "Name of interface";
           }
           leaf label-operation {
             type string;
             description "Label operation";
           }
           leaf label-out {
             type string;
             description "Outgoing label";
           }
           leaf creation-time {
             type string;
             description "Creation time";
           }
           leaf lp-bypass-name {
             type string;
             description "Link protection bypass LSP name";
           }
           leaf np-bypass-name {
             type string;
             description "Node protection bypass LSP name";
           }
           leaf next-next-label {
             type string;
             description "Node protection next-next label";
           }
           leaf bandwidth_ct0 {
             type int32;
           }
           leaf spvc-id {
             type string;
             description "Unique id for the static lsp structure";
           }
           leaf self-id {
             type string;
             description "Statistics identifier for RSVP path state control block";
           }
           leaf lsp-pktbytes {
             type string;
             description "LSP packet and byte counters";
           }
           leaf lsp-packets {
             type string;
             description "LSP packet counters";
           }
           leaf lsp-bytes {
             type string;
             description "LSP byte counters";
           }
         }
       }
     }
   }
   rpc get-mpls-call-admission-control-information {
     description "Show CAC information for MPLS LSPs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf lsp-name {
         description "Name of LSP";
         type string {
           length "1 .. 64";
         }
       }
       leaf instance {
         description "Name of routing instance";
         type string;
       }
     }
     output {
       container mpls-call-admission-control-information {
         container mpls-call-admission-control {
           container mpls-lsp {
             description "MPLS label-switched path information";
             leaf name {
               type string;
             }
             leaf lsp-packets {
               type string;
               description "LSP packet counters";
             }
             leaf lsp-bytes {
               type string;
               description "LSP byte counters";
             }
             container mpls-lsp-path {
               description "Primary or secondary LSP path";
               leaf path-active {
                 type empty;
                 description "Whether the path is active or not";
               }
               leaf title {
                 type string;
               }
               container admin-groups {
                 leaf admin-groups.heading {
                   type string;
                 }
                 leaf color {
                   type int32;
                 }
                 leaf no-group-flag {
                   type empty;
                 }
                 leaf admin-group-name {
                   type string;
                   description "Name of the admin group";
                 }
                 leaf admin-group-number {
                   type int32;
                   description "Number of the admin group";
                 }
               }
               container admin-groups-extended {
                 leaf admin-groups-extended.heading {
                   type string;
                 }
                 leaf admin-group-name {
                   type string;
                   description "Name of the admin group";
                 }
                 leaf admin-group-number {
                   type int32;
                   description "Number of the admin group";
                 }
               }
               container srlg {
                 leaf srlg.heading {
                   type string;
                 }
                 leaf srlg-name {
                   type string;
                   description "Name of the srlg";
                 }
               }
               container mpls-lsp-upstream-label {
                 description "Upstream label configured for the LSP";
                 leaf vlan-id-label {
                   type uint32;
                   description "VLAN ID label configured for the LSP";
                 }
               }
               container explicit-route {
                 description "Explicit Route Object (ERO)";
                 leaf explicit-route.heading {
                   type string;
                   description "Explicit Route Object (ERO)";
                 }
                 leaf address {
                   type ipaddr;
                 }
                 leaf explicit-route-type {
                   type string;
                 }
                 leaf telink-id {
                   type int32;
                   description "Link identifier of unnumbered link";
                 }
               }
               container oam-state {
                 description "OAM state information";
                 leaf oam-bfd-session-state {
                   type string;
                 }
                 leaf oam-lsp-ping-state {
                   type string;
                 }
               }
               container path-history {
                 description "Log over time of LSP path-related events";
                 leaf sequence-number {
                   type int32;
                   description "History event number";
                 }
                 leaf time {
                   type string;
                   description "Time of the event";
                 }
                 leaf log {
                   type string;
                   description "Supplemental information of the event";
                 }
                 leaf route {
                   type string;
                   description "Latest RRO contents, as reported by RSVP";
                 }
               }
               container path-available-bandwidth {
                 description "Available bandwidth on an LSP path";
                 leaf path-available-bandwidth.heading {
                   type string;
                   description "Available bandwidth on an LSP path";
                 }
                 leaf bandwidth {
                   type int32;
                 }
                 leaf class-type {
                   type int32;
                 }
                 leaf class-bandwidth {
                   type int32;
                 }
               }
               container layer2-connection {
                 description "Layer 2 connection using the LSP path";
                 leaf neighbor-address {
                   type ipaddr;
                   description "IP address of this neighbor";
                 }
                 leaf interface-name {
                   type string;
                   description "Name of interface";
                 }
                 leaf vc-id {
                   type int32;
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
               }
             }
           }
         }
       }
     }
   }
   rpc get-mpls-context-identifier-information {
     description "Show configured egress protection context identifiers";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
       leaf context-type {
         type enumeration {
           enum "primary" {
             description "Display primary context identifier(s)";
           }
           enum "protector" {
             description "Display protector context identifier(s)";
           }
         }
       }
       leaf level {
         default "brief";
         type enumeration {
           enum "brief" {
             description "Display brief output (default)";
           }
           enum "detail" {
             description "Display detailed output";
           }
         }
       }
       leaf id {
         description "Identifier";
         type string;
       }
     }
     output {
       container mpls-context-identifier-information {
         leaf context-total-count {
           type int32;
           description "Number context identifiers";
         }
         leaf primary-context-count {
           type int32;
           description "Number primary context identifiers";
         }
         leaf protector-context-count {
           type int32;
           description "Number primary context identifiers";
         }
         container mpls-context-identifier {
           description "Egress protection context identifier";
           container brief {
             description "Egress protection context identifier";
             leaf context-identifier {
               type ipaddr;
               description "IP address";
             }
             leaf context-type {
               type string;
               description "Type";
             }
             leaf metric {
               type int32;
             }
             leaf context-table {
               type string;
               description "Context table name";
             }
             container context-lsps {
               description "LSPs destined for this context";
               leaf context-lsp-name {
                 type string;
                 description "Context LSP's name";
               }
               leaf context-lsp-ingress-router {
                 type ipaddr;
                 description "Context LSP's ingress router";
               }
               leaf context-lsp-is-detour {
                 type empty;
                 description "LSP is a detour";
               }
             }
           }
           container detail {
             description "Egress protection context identifier";
             leaf context-identifier {
               type ipaddr;
               description "IP address";
             }
             leaf context-type {
               type string;
               description "Type";
             }
             leaf metric {
               type int32;
             }
             leaf advertise-mode {
               type string;
               description "Context-id advertise mode";
             }
             leaf context-table {
               type string;
               description "Context table name";
             }
             leaf label-out {
               type string;
               description "Outgoing label";
             }
             leaf admin-group-name {
               type string;
               description "Name of the admin group";
             }
             container context-lsps {
               description "LSPs destined for this context";
               leaf context-lsp-name {
                 type string;
                 description "Context LSP's name";
               }
               leaf context-lsp-ingress-router {
                 type ipaddr;
                 description "Context LSP's ingress router";
               }
               leaf context-lsp-is-detour {
                 type empty;
                 description "LSP is a detour";
               }
             }
           }
         }
       }
     }
   }
   rpc get-mpls-srlg-information {
     description "Show MPLS SRLG";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of routing instance";
         type string;
       }
     }
     output {
       container mpls-srlg-information {
         container mpls-srlg {
           leaf srlg-name {
             type string;
             description "Name of the srlg";
           }
           leaf srlg-value {
             type uint32;
             description "Value of the srlg";
           }
           leaf srlg-cost {
             type uint32;
             description "Cost of the srlg";
           }
         }
       }
     }
   }
   rpc mpls-label-space {
     description "Mpls label space";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc mpls-label-space-usage {
     description "Show MPLS label space usage statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
   }
   rpc get-mpls-traceroute-database-ldp {
     description "Show FECs";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf fec {
         description "IP address and optional prefix length of FEC";
         type ipprefix;
       }
       leaf detail {
         description "Display detailed output";
         type empty;
       }
       leaf no-resolve {
         description "Don't attempt to print addresses symbolically";
         type empty;
       }
       leaf routing-instance {
         description "Name of routing instance, or 'all'";
         type string {
           junos:posix-pattern "!^((__.*__)|(all)|(.*[ ].*)|(\"\")|(.{129,}))$";
           junos:pattern-message "Must be a non-reserved string of 128 characters or less with no spaces.";
         }
       }
     }
   }
   rpc get-egress-protection-information {
     description "Show egress-protection information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
     }
   }
 }
