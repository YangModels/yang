/*
 * Copyright (c) 2017 Juniper Networks, Inc.
 * All rights reserved.
 */

 module show-dynamic-tunnels {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-dynamic-tunnels-database {
     description "Show the dynamic tunnel database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf table {
         description "Show all the tunnels belonging to this table";
         type string;
       }
       leaf destination {
         description "IP address and optional prefix length of destination";
         type ipprefix-optional;
       }
       leaf level {
         type enumeration {
           enum "summary" {
             description "Summary of dynamic tunnel";
           }
           enum "terse" {
             description "Display terse output";
           }
         }
       }
     }
     output {
       container dynamic-tunnels-information {
         container dynamic-tunnel-statistics {
           leaf dyn-total-count {
             type int32;
           }
           leaf dyn-ifl-type {
             type empty;
           }
           leaf dyn-tunnel-mode-gre {
             type string;
           }
           leaf dyn-total-count-ifl {
             type int32;
           }
           leaf dyn-up-count-ifl {
             type int32;
           }
           leaf dyn-down-count-ifl {
             type int32;
           }
           leaf dyn-total-count-gre-nhb {
             type int32;
           }
           leaf dyn-up-count-gre-nhb {
             type int32;
           }
           leaf dyn-down-count-gre-nhb {
             type string;
           }
           leaf dyn-rsvp-auto {
             type empty;
           }
           leaf dyn-total-count-rsvp {
             type int32;
           }
           leaf dyn-nhb-udp {
             type empty;
           }
           leaf dyn-tunnel-mode-udp {
             type string;
           }
           leaf dyn-total-count-udp-nhb {
             type int32;
           }
           leaf dyn-up-count-udp-nhb {
             type int32;
           }
           leaf dyn-down-count-udp-nhb {
             type string;
           }
         }
         container dynamic-tunnel-table {
           leaf table-name {
             type string;
             description "Unicast routing table";
           }
           container destination-network {
             leaf prefix {
               type ipaddr;
             }
             leaf destination-network-deleted {
               type empty;
               description "Whether this destination network has been unconfigured";
             }
             container dynamic-tunnel {
               leaf tunnel-destination {
                 type ipaddr;
                 description "Tunnel destination";
               }
               leaf tunnel-state {
                 type string;
                 description "State of the tunnel";
               }
               leaf tunnel-expiry {
                 type int32;
                 description "Time after which the tunnel will be removed";
               }
               leaf tunnel-reference-count {
                 type int32;
                 description "Number of references on this tunnel";
               }
               container tunnel-nexthop {
                 leaf tunnel-nh-type {
                   type string;
                   description "Type of next hop";
                 }
                 leaf via {
                   type string;
                   description "Reachable via a local interface";
                 }
                 leaf tunnel-nh-src {
                   type ipaddr;
                   description "Source address for this tunnel next hop";
                 }
                 leaf tunnel-id-index {
                   type int32;
                   description "Tunnel Index";
                 }
                 leaf tunnel-attr-vpn-label {
                   type string;
                   description "VPN label for L3VPN over dynamic tunnel";
                 }
                 leaf tunnel-attr-reference-count {
                   type int32;
                   description "Number of references on this tunnel-attr";
                 }
                 leaf tunnel-traffic-stats {
                   type string;
                   description "Nexthop based tunnel out-going traffic statistics";
                 }
                 leaf tunnel-nh-state {
                   type string;
                   description "State of the tunnel next hop";
                 }
                 leaf tunnel-nh-reason {
                   type string;
                   description "Reason why the tunnel next hop is not up";
                 }
                 leaf tunnel-nh-lsp-name {
                   type string;
                   description "Name of the LSP nexthop of this tunnel";
                 }
               }
             }
             container dynamic-tunnel-terse {
               container terse {
                 leaf tunnel-dest-terse {
                   type ipaddr;
                 }
                 leaf tunnel-src-terse {
                   type ipaddr;
                 }
                 leaf tunnel-nh-terse {
                   type string;
                 }
                 leaf tunnel-type-terse {
                   type string;
                 }
                 leaf tunnel-state-terse {
                   type string;
                 }
                 leaf tunnel-nh-reason-terse {
                   type string;
                 }
               }
             }
           }
         }
       }
     }
   }
 }
