/*
 * Copyright (c) 2017 Juniper Networks, Inc.
 * All rights reserved.
 */

 module show-class-of-service {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-cos-information {
     description "Show class-of-service (CoS) information";
     output {
       container cos-information {
         container cos-forwarding-class-information {
           container fc-map {
             description "Class-of-service forwarding class to queue mapping";
             container fx-series-fc-map-format {
               description "Class-of-service forwarding class to queue mapping";
               container fc-map-item {
                 leaf fc-name {
                   type string;
                   description "Class-of-service forwarding class name";
                 }
                 leaf fc-number {
                   type uint32;
                   description "Identifier for Class-of-service forwarding class";
                 }
               }
             }
             container t-series-fc-information {
               description "Class-of-service forwarding class to queue mapping";
               container fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-rqueue-number {
                   type uint32;
                   description "Class-of-service forwarding class restricted queue number";
                 }
                 leaf fc-priority {
                   type string;
                   description "Class-of-service forwarding class queue priority";
                 }
                 leaf fc-policing-priority {
                   type string;
                   description "Class-of-service forwarding class policing priority";
                 }
                 leaf fc-spu-priority {
                   type string;
                   description "Class-of-service forwarding class spu priority";
                 }
               }
             }
             container m-series-fc-information {
               description "Class-of-service forwarding class to queue mapping";
               container fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-policing-priority {
                   type string;
                   description "Class-of-service forwarding class policing priority";
                 }
                 leaf fc-spu-priority {
                   type string;
                   description "Class-of-service forwarding class spu priority";
                 }
               }
             }
             container ex82-series-fc-information {
               description "Class-of-service forwarding class to queue mapping";
               container fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-priority {
                   type string;
                   description "Class-of-service forwarding class queue priority";
                 }
               }
             }
             container fx-series-fc-information {
               description "Class-of-service forwarding class to queue mapping";
               container fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-policing-priority {
                   type string;
                   description "Class-of-service forwarding class policing priority";
                 }
                 leaf fc-no-loss {
                   type string;
                   description "Class-of-service forwarding class no-loss";
                 }
               }
             }
             container fc-map-information {
               description "Class-of-service forwarding class to queue mapping";
               container fc-map-item {
                 leaf fc-name {
                   type string;
                   description "Class-of-service forwarding class name";
                 }
                 leaf fc-queue-number {
                   type uint32;
                   description "Class-of-service forwarding class queue number";
                 }
                 leaf fc-rqueue-number {
                   type uint32;
                   description "Class-of-service forwarding class restricted queue number";
                 }
               }
             }
           }
         }
         container cos-forwarding-class-map-information {
           container fc-map {
             description "Class-of-service forwarding class to queue mapping";
             container fx-series-fc-map-format {
               description "Class-of-service forwarding class to queue mapping";
               container fc-map-item {
                 leaf fc-name {
                   type string;
                   description "Class-of-service forwarding class name";
                 }
                 leaf fc-number {
                   type uint32;
                   description "Identifier for Class-of-service forwarding class";
                 }
               }
             }
             container t-series-fc-information {
               description "Class-of-service forwarding class to queue mapping";
               container fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-rqueue-number {
                   type uint32;
                   description "Class-of-service forwarding class restricted queue number";
                 }
                 leaf fc-priority {
                   type string;
                   description "Class-of-service forwarding class queue priority";
                 }
                 leaf fc-policing-priority {
                   type string;
                   description "Class-of-service forwarding class policing priority";
                 }
                 leaf fc-spu-priority {
                   type string;
                   description "Class-of-service forwarding class spu priority";
                 }
               }
             }
             container m-series-fc-information {
               description "Class-of-service forwarding class to queue mapping";
               container fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-policing-priority {
                   type string;
                   description "Class-of-service forwarding class policing priority";
                 }
                 leaf fc-spu-priority {
                   type string;
                   description "Class-of-service forwarding class spu priority";
                 }
               }
             }
             container ex82-series-fc-information {
               description "Class-of-service forwarding class to queue mapping";
               container fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-priority {
                   type string;
                   description "Class-of-service forwarding class queue priority";
                 }
               }
             }
             container fx-series-fc-information {
               description "Class-of-service forwarding class to queue mapping";
               container fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-policing-priority {
                   type string;
                   description "Class-of-service forwarding class policing priority";
                 }
                 leaf fc-no-loss {
                   type string;
                   description "Class-of-service forwarding class no-loss";
                 }
               }
             }
             container fc-map-information {
               description "Class-of-service forwarding class to queue mapping";
               container fc-map-item {
                 leaf fc-name {
                   type string;
                   description "Class-of-service forwarding class name";
                 }
                 leaf fc-queue-number {
                   type uint32;
                   description "Class-of-service forwarding class queue number";
                 }
                 leaf fc-rqueue-number {
                   type uint32;
                   description "Class-of-service forwarding class restricted queue number";
                 }
               }
             }
           }
         }
         container cos-classifier-information {
           container classifier {
             description "Class-of-service code point classifier";
             leaf classifier-name {
               type string;
               description "Class-of-service classifier name";
             }
             leaf code-point-type {
               type string;
               description "Class-of-service code point type";
             }
             leaf table-index {
               type uint32;
               description "Table index";
             }
             container classifier-map {
               container classifier-map-item {
                 leaf code-point {
                   type string;
                   description "Class-of-service code point alias name or bits";
                 }
                 leaf fc-name {
                   type string;
                   description "Class-of-service forwarding class name";
                 }
                 leaf loss-priority {
                   type string;
                   description "Class-of-service loss priority";
                 }
                 leaf cntag-present {
                   type string;
                   description "Class-of-service cntag present";
                 }
               }
             }
           }
         }
         container cos-loss-priority-map-information {
           container loss-priority-map {
             description "Class-of-service code point loss priority map";
             leaf loss-priority-map-name {
               type string;
               description "Name of class-of-service loss priority map";
             }
             leaf code-point-type {
               type string;
               description "Class-of-service code point type";
             }
             leaf table-index {
               type uint32;
               description "Table index";
             }
             container loss-priority-map-table {
               container loss-priority-map-item {
                 leaf code-point {
                   type string;
                   description "Class-of-service code point alias name or bits";
                 }
                 leaf loss-priority {
                   type string;
                   description "Class-of-service loss priority";
                 }
               }
               container loss-priority-map-table-entry {
                 leaf table-index {
                   type uint32;
                   description "Table index";
                 }
                 leaf code-point {
                   type string;
                   description "Class-of-service code point alias name or bits";
                 }
                 leaf loss-priority {
                   type string;
                   description "Class-of-service loss priority";
                 }
               }
             }
           }
         }
         container cos-drop-profile-information {
           container drop-profile {
             description "Class-of-service drop profile";
             leaf profile-name {
               type string;
               description "Class-of-service drop profile name";
             }
             leaf profile-type {
               type string;
               description "Class-of-service drop profile type";
             }
             leaf table-index {
               type uint32;
               description "Table index";
             }
             container profile-map {
               container profile-map-item {
                 container m-t-mx-j-series-drop-profile-information {
                   leaf fill-level {
                     type uint32;
                     description "Class-of-service drop profile fill level value";
                   }
                   leaf probability {
                     type uint32;
                     description "Class-of-service drop profile probability value";
                   }
                 }
                 container ex-series-drop-profile-information {
                   leaf fill-level {
                     type uint32;
                     description "Class-of-service drop profile fill level value";
                   }
                 }
               }
             }
           }
         }
         container cos-rewrite-information {
           container rewrite {
             description "Class-of-service drop profile";
             leaf rewrite-name {
               type string;
               description "Class-of-service rewrite rule name";
             }
             leaf code-point-type {
               type string;
               description "Class-of-service code point type";
             }
             leaf table-index {
               type uint32;
               description "Table index";
             }
             container rewrite-map {
               container rewrite-map-item {
                 leaf fc-name {
                   type string;
                   description "Class-of-service forwarding class name";
                 }
                 leaf loss-priority {
                   type string;
                   description "Class-of-service loss priority";
                 }
                 leaf code-point {
                   type string;
                   description "Class-of-service code point alias name or bits";
                 }
               }
             }
           }
         }
         container cos-loss-priority-rewrite-information {
           container loss-priority-rewrite {
             description "Class-of-service loss priority to code point rewrite";
             leaf loss-priority-rewrite-name {
               type string;
               description "Name of class-of-service loss priority rewrite";
             }
             leaf code-point-type {
               type string;
               description "Class-of-service code point type";
             }
             leaf table-index {
               type uint32;
               description "Table index";
             }
             container loss-priority-rewrite-table {
               container loss-priority-rewrite-item {
                 leaf loss-priority {
                   type string;
                   description "Class-of-service loss priority";
                 }
                 leaf code-point {
                   type string;
                   description "Class-of-service code point alias name or bits";
                 }
               }
               container loss-priority-rewrite-table-entry {
                 leaf table-index {
                   type uint32;
                   description "Table index";
                 }
                 leaf loss-priority {
                   type string;
                   description "Class-of-service loss priority";
                 }
                 leaf code-point {
                   type string;
                   description "Class-of-service code point alias name or bits";
                 }
               }
             }
           }
         }
         container cos-code-point-map-information {
           container code-point-map {
             description "Class-of-service code point alias map";
             leaf code-point-type {
               type string;
               description "Class-of-service code point type";
             }
             container alias-map {
               container alias-map-item {
                 leaf code-point-alias {
                   type string;
                   description "Class-of-service code point alias name";
                 }
                 leaf code-point-bits {
                   type string;
                   description "Class-of-service code point bit sequence";
                 }
               }
             }
           }
         }
         container cos-fragmentation-map-information {
           container fragmentation-map {
             description "Class-of-service fragmentation map";
             leaf fragmentation-map-name {
               type string;
               description "Class-of-service fragmentation map name";
             }
             leaf fragmentation-map-index {
               type uint32;
               description "Index number for Class-of-service fragmentation map";
             }
             container fragment-map {
               container no-fragmentation {
                 leaf fc-name {
                   type string;
                   description "Class-of-service forwarding class name";
                 }
               }
               container fragmentation {
                 leaf fc-name {
                   type string;
                   description "Class-of-service forwarding class name";
                 }
                 leaf fragment-threshold {
                   type string;
                   description "Fragmentation threshold";
                 }
               }
               container multilink_class {
                 leaf fc-name {
                   type string;
                   description "Class-of-service forwarding class name";
                 }
                 leaf fragment-threshold {
                   type string;
                   description "Fragmentation threshold";
                 }
                 leaf fragment-multilink-class {
                   type int32;
                   description "Identifier for multilink class";
                 }
               }
             }
           }
         }
         container cos-translation-table-map-information {
           container translation-table {
             description "Class-of-service code point translation table";
             leaf translation-table-name {
               type string;
               description "Class-of-service translation table name";
             }
             leaf translation-table-type {
               type string;
               description "Class-of-service translation table type";
             }
             leaf table-index {
               type uint32;
               description "Table index";
             }
             container translation-table-map {
               container translation-table-map-item {
                 leaf from-code-point {
                   type string;
                   description "Class-of-service code point alias name or bits";
                 }
                 leaf to-code-point {
                   type string;
                   description "Class-of-service code point alias name or bits";
                 }
               }
             }
             container translation-table-entry {
               leaf table-index {
                 type uint32;
                 description "Table index";
               }
               leaf from-code-point {
                 type string;
                 description "Class-of-service code point alias name or bits";
               }
               leaf to-code-point {
                 type string;
                 description "Class-of-service code point alias name or bits";
               }
             }
           }
         }
         container cos-multi-destination-information {
           container sm-md-map {
             leaf scheduler-map-name {
               type string;
               description "Class-of-service scheduler map name";
             }
             leaf scheduler-map-index {
               type uint64;
               description "Class-of-service scheduler map index";
             }
           }
           container fc-md-map {
             leaf fc-name {
               type string;
               description "Class-of-service forwarding class name";
             }
             leaf fc-queue-number {
               type uint32;
               description "Class-of-service forwarding class queue number";
             }
           }
           container cls-md-map {
             container md-inet-classifier {
               leaf multidest-classifier-name {
                 type string;
                 description "Multi destination classifier name";
               }
               leaf multidest-classifier-type {
                 type string;
                 description "Multi destination classifier type";
               }
               leaf multidest-classifier-index {
                 type uint32;
                 description "Multi destination classifier id";
               }
             }
             container md-ethernet-classifier {
               leaf multidest-classifier-name {
                 type string;
                 description "Multi destination classifier name";
               }
               leaf multidest-classifier-type {
                 type string;
                 description "Multi destination classifier type";
               }
               leaf multidest-classifier-index {
                 type uint32;
                 description "Multi destination classifier id";
               }
             }
           }
         }
         container cos-forwarding-class-set-information {
           container forwarding-class-set {
             description "Class-of-service forwarding class set information";
             container fx-series {
               description "Class-of-service forwarding class set information";
               container forwarding-class-set-entry {
                 leaf forwarding-class-set-name {
                   type string;
                   description "Class-of-service forwarding class set name";
                 }
                 leaf forwarding-class-set-type {
                   type string;
                   description "Identifier for Class-of-service forwarding class set type";
                 }
                 leaf forwarding-class-set-index {
                   type uint32;
                   description "Identifier for Class-of-service forwarding class set";
                 }
                 container fc-map {
                   description "Class-of-service forwarding class to queue mapping";
                   container fx-series-fc-map-format {
                     description "Class-of-service forwarding class to queue mapping";
                     container fc-map-item {
                       leaf fc-name {
                         type string;
                         description "Class-of-service forwarding class name";
                       }
                       leaf fc-number {
                         type uint32;
                         description "Identifier for Class-of-service forwarding class";
                       }
                     }
                   }
                   container t-series-fc-information {
                     description "Class-of-service forwarding class to queue mapping";
                     container fc-map-item {
                       leaf fc-name {
                         type string;
                         description "Class-of-service forwarding class name";
                       }
                       leaf fc-number {
                         type uint32;
                         description "Identifier for Class-of-service forwarding class";
                       }
                       leaf fc-queue-number {
                         type uint32;
                         description "Class-of-service forwarding class queue number";
                       }
                       leaf fc-rqueue-number {
                         type uint32;
                         description "Class-of-service forwarding class restricted queue number";
                       }
                       leaf fc-priority {
                         type string;
                         description "Class-of-service forwarding class queue priority";
                       }
                       leaf fc-policing-priority {
                         type string;
                         description "Class-of-service forwarding class policing priority";
                       }
                       leaf fc-spu-priority {
                         type string;
                         description "Class-of-service forwarding class spu priority";
                       }
                     }
                   }
                   container m-series-fc-information {
                     description "Class-of-service forwarding class to queue mapping";
                     container fc-map-item {
                       leaf fc-name {
                         type string;
                         description "Class-of-service forwarding class name";
                       }
                       leaf fc-number {
                         type uint32;
                         description "Identifier for Class-of-service forwarding class";
                       }
                       leaf fc-queue-number {
                         type uint32;
                         description "Class-of-service forwarding class queue number";
                       }
                       leaf fc-policing-priority {
                         type string;
                         description "Class-of-service forwarding class policing priority";
                       }
                       leaf fc-spu-priority {
                         type string;
                         description "Class-of-service forwarding class spu priority";
                       }
                     }
                   }
                   container ex82-series-fc-information {
                     description "Class-of-service forwarding class to queue mapping";
                     container fc-map-item {
                       leaf fc-name {
                         type string;
                         description "Class-of-service forwarding class name";
                       }
                       leaf fc-number {
                         type uint32;
                         description "Identifier for Class-of-service forwarding class";
                       }
                       leaf fc-queue-number {
                         type uint32;
                         description "Class-of-service forwarding class queue number";
                       }
                       leaf fc-priority {
                         type string;
                         description "Class-of-service forwarding class queue priority";
                       }
                     }
                   }
                   container fx-series-fc-information {
                     description "Class-of-service forwarding class to queue mapping";
                     container fc-map-item {
                       leaf fc-name {
                         type string;
                         description "Class-of-service forwarding class name";
                       }
                       leaf fc-number {
                         type uint32;
                         description "Identifier for Class-of-service forwarding class";
                       }
                       leaf fc-queue-number {
                         type uint32;
                         description "Class-of-service forwarding class queue number";
                       }
                       leaf fc-policing-priority {
                         type string;
                         description "Class-of-service forwarding class policing priority";
                       }
                       leaf fc-no-loss {
                         type string;
                         description "Class-of-service forwarding class no-loss";
                       }
                     }
                   }
                   container fc-map-information {
                     description "Class-of-service forwarding class to queue mapping";
                     container fc-map-item {
                       leaf fc-name {
                         type string;
                         description "Class-of-service forwarding class name";
                       }
                       leaf fc-queue-number {
                         type uint32;
                         description "Class-of-service forwarding class queue number";
                       }
                       leaf fc-rqueue-number {
                         type uint32;
                         description "Class-of-service forwarding class restricted queue number";
                       }
                     }
                   }
                 }
               }
             }
           }
         }
         container cos-policy-map-information {
           container policy-map {
             description "Class-of-service Policy-map";
             leaf policy-map-name {
               type string;
               description "Class-of-service Policy-map name";
             }
             leaf table-index {
               type uint32;
               description "Table index";
             }
             container policy-map-cp-entries {
               leaf code-point-type {
                 type string;
                 description "Class-of-service code point type";
               }
               leaf code-point {
                 type string;
                 description "Class-of-service code point alias name or bits";
               }
               leaf code-point-option {
                 type string;
                 description "Class-of-service code point option flag";
               }
             }
           }
         }
       }
     }
   }
   rpc get-cos-forwarding-class-information {
     description "Show mapping of forwarding class names to queue numbers";
     output {
       container cos-forwarding-class-information {
         container fc-map {
           description "Class-of-service forwarding class to queue mapping";
           container fx-series-fc-map-format {
             description "Class-of-service forwarding class to queue mapping";
             container fc-map-item {
               leaf fc-name {
                 type string;
                 description "Class-of-service forwarding class name";
               }
               leaf fc-number {
                 type uint32;
                 description "Identifier for Class-of-service forwarding class";
               }
             }
           }
           container t-series-fc-information {
             description "Class-of-service forwarding class to queue mapping";
             container fc-map-item {
               leaf fc-name {
                 type string;
                 description "Class-of-service forwarding class name";
               }
               leaf fc-number {
                 type uint32;
                 description "Identifier for Class-of-service forwarding class";
               }
               leaf fc-queue-number {
                 type uint32;
                 description "Class-of-service forwarding class queue number";
               }
               leaf fc-rqueue-number {
                 type uint32;
                 description "Class-of-service forwarding class restricted queue number";
               }
               leaf fc-priority {
                 type string;
                 description "Class-of-service forwarding class queue priority";
               }
               leaf fc-policing-priority {
                 type string;
                 description "Class-of-service forwarding class policing priority";
               }
               leaf fc-spu-priority {
                 type string;
                 description "Class-of-service forwarding class spu priority";
               }
             }
           }
           container m-series-fc-information {
             description "Class-of-service forwarding class to queue mapping";
             container fc-map-item {
               leaf fc-name {
                 type string;
                 description "Class-of-service forwarding class name";
               }
               leaf fc-number {
                 type uint32;
                 description "Identifier for Class-of-service forwarding class";
               }
               leaf fc-queue-number {
                 type uint32;
                 description "Class-of-service forwarding class queue number";
               }
               leaf fc-policing-priority {
                 type string;
                 description "Class-of-service forwarding class policing priority";
               }
               leaf fc-spu-priority {
                 type string;
                 description "Class-of-service forwarding class spu priority";
               }
             }
           }
           container ex82-series-fc-information {
             description "Class-of-service forwarding class to queue mapping";
             container fc-map-item {
               leaf fc-name {
                 type string;
                 description "Class-of-service forwarding class name";
               }
               leaf fc-number {
                 type uint32;
                 description "Identifier for Class-of-service forwarding class";
               }
               leaf fc-queue-number {
                 type uint32;
                 description "Class-of-service forwarding class queue number";
               }
               leaf fc-priority {
                 type string;
                 description "Class-of-service forwarding class queue priority";
               }
             }
           }
           container fx-series-fc-information {
             description "Class-of-service forwarding class to queue mapping";
             container fc-map-item {
               leaf fc-name {
                 type string;
                 description "Class-of-service forwarding class name";
               }
               leaf fc-number {
                 type uint32;
                 description "Identifier for Class-of-service forwarding class";
               }
               leaf fc-queue-number {
                 type uint32;
                 description "Class-of-service forwarding class queue number";
               }
               leaf fc-policing-priority {
                 type string;
                 description "Class-of-service forwarding class policing priority";
               }
               leaf fc-no-loss {
                 type string;
                 description "Class-of-service forwarding class no-loss";
               }
             }
           }
           container fc-map-information {
             description "Class-of-service forwarding class to queue mapping";
             container fc-map-item {
               leaf fc-name {
                 type string;
                 description "Class-of-service forwarding class name";
               }
               leaf fc-queue-number {
                 type uint32;
                 description "Class-of-service forwarding class queue number";
               }
               leaf fc-rqueue-number {
                 type uint32;
                 description "Class-of-service forwarding class restricted queue number";
               }
             }
           }
         }
       }
     }
   }
   rpc get-cos-forwarding-class-set-information {
     description "Show forwarding-class-sets that are active";
     input {
       leaf forwarding-class-set-name {
         description "Name of forwarding class set";
         type string;
       }
     }
     output {
       container cos-forwarding-class-set-information {
         container forwarding-class-set {
           description "Class-of-service forwarding class set information";
           container fx-series {
             description "Class-of-service forwarding class set information";
             container forwarding-class-set-entry {
               leaf forwarding-class-set-name {
                 type string;
                 description "Class-of-service forwarding class set name";
               }
               leaf forwarding-class-set-type {
                 type string;
                 description "Identifier for Class-of-service forwarding class set type";
               }
               leaf forwarding-class-set-index {
                 type uint32;
                 description "Identifier for Class-of-service forwarding class set";
               }
               container fc-map {
                 description "Class-of-service forwarding class to queue mapping";
                 container fx-series-fc-map-format {
                   description "Class-of-service forwarding class to queue mapping";
                   container fc-map-item {
                     leaf fc-name {
                       type string;
                       description "Class-of-service forwarding class name";
                     }
                     leaf fc-number {
                       type uint32;
                       description "Identifier for Class-of-service forwarding class";
                     }
                   }
                 }
                 container t-series-fc-information {
                   description "Class-of-service forwarding class to queue mapping";
                   container fc-map-item {
                     leaf fc-name {
                       type string;
                       description "Class-of-service forwarding class name";
                     }
                     leaf fc-number {
                       type uint32;
                       description "Identifier for Class-of-service forwarding class";
                     }
                     leaf fc-queue-number {
                       type uint32;
                       description "Class-of-service forwarding class queue number";
                     }
                     leaf fc-rqueue-number {
                       type uint32;
                       description "Class-of-service forwarding class restricted queue number";
                     }
                     leaf fc-priority {
                       type string;
                       description "Class-of-service forwarding class queue priority";
                     }
                     leaf fc-policing-priority {
                       type string;
                       description "Class-of-service forwarding class policing priority";
                     }
                     leaf fc-spu-priority {
                       type string;
                       description "Class-of-service forwarding class spu priority";
                     }
                   }
                 }
                 container m-series-fc-information {
                   description "Class-of-service forwarding class to queue mapping";
                   container fc-map-item {
                     leaf fc-name {
                       type string;
                       description "Class-of-service forwarding class name";
                     }
                     leaf fc-number {
                       type uint32;
                       description "Identifier for Class-of-service forwarding class";
                     }
                     leaf fc-queue-number {
                       type uint32;
                       description "Class-of-service forwarding class queue number";
                     }
                     leaf fc-policing-priority {
                       type string;
                       description "Class-of-service forwarding class policing priority";
                     }
                     leaf fc-spu-priority {
                       type string;
                       description "Class-of-service forwarding class spu priority";
                     }
                   }
                 }
                 container ex82-series-fc-information {
                   description "Class-of-service forwarding class to queue mapping";
                   container fc-map-item {
                     leaf fc-name {
                       type string;
                       description "Class-of-service forwarding class name";
                     }
                     leaf fc-number {
                       type uint32;
                       description "Identifier for Class-of-service forwarding class";
                     }
                     leaf fc-queue-number {
                       type uint32;
                       description "Class-of-service forwarding class queue number";
                     }
                     leaf fc-priority {
                       type string;
                       description "Class-of-service forwarding class queue priority";
                     }
                   }
                 }
                 container fx-series-fc-information {
                   description "Class-of-service forwarding class to queue mapping";
                   container fc-map-item {
                     leaf fc-name {
                       type string;
                       description "Class-of-service forwarding class name";
                     }
                     leaf fc-number {
                       type uint32;
                       description "Identifier for Class-of-service forwarding class";
                     }
                     leaf fc-queue-number {
                       type uint32;
                       description "Class-of-service forwarding class queue number";
                     }
                     leaf fc-policing-priority {
                       type string;
                       description "Class-of-service forwarding class policing priority";
                     }
                     leaf fc-no-loss {
                       type string;
                       description "Class-of-service forwarding class no-loss";
                     }
                   }
                 }
                 container fc-map-information {
                   description "Class-of-service forwarding class to queue mapping";
                   container fc-map-item {
                     leaf fc-name {
                       type string;
                       description "Class-of-service forwarding class name";
                     }
                     leaf fc-queue-number {
                       type uint32;
                       description "Class-of-service forwarding class queue number";
                     }
                     leaf fc-rqueue-number {
                       type uint32;
                       description "Class-of-service forwarding class restricted queue number";
                     }
                   }
                 }
               }
             }
           }
         }
       }
     }
   }
   rpc get-cos-drop-profile-information {
     description "Show interpolated data points of named drop profile";
     input {
       leaf profile-name {
         description "Name of drop profile";
         type string;
       }
     }
     output {
       container cos-drop-profile-information {
         container drop-profile {
           description "Class-of-service drop profile";
           leaf profile-name {
             type string;
             description "Class-of-service drop profile name";
           }
           leaf profile-type {
             type string;
             description "Class-of-service drop profile type";
           }
           leaf table-index {
             type uint32;
             description "Table index";
           }
           container profile-map {
             container profile-map-item {
               container m-t-mx-j-series-drop-profile-information {
                 leaf fill-level {
                   type uint32;
                   description "Class-of-service drop profile fill level value";
                 }
                 leaf probability {
                   type uint32;
                   description "Class-of-service drop profile probability value";
                 }
               }
               container ex-series-drop-profile-information {
                 leaf fill-level {
                   type uint32;
                   description "Class-of-service drop profile fill level value";
                 }
               }
             }
           }
         }
       }
     }
   }
   rpc get-cos-classifier-information {
     description "Show mapping of code point to forwarding class/loss priority";
     input {
       leaf classifier-name {
         description "Name of classifier";
         type string;
       }
       leaf type {
         description "Type of classifier";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "ieee-802.1ad" {
             description "IEEE-802.1ad (DEI) code point";
           }
         }
       }
     }
     output {
       container cos-classifier-information {
         container classifier {
           description "Class-of-service code point classifier";
           leaf classifier-name {
             type string;
             description "Class-of-service classifier name";
           }
           leaf code-point-type {
             type string;
             description "Class-of-service code point type";
           }
           leaf table-index {
             type uint32;
             description "Table index";
           }
           container classifier-map {
             container classifier-map-item {
               leaf code-point {
                 type string;
                 description "Class-of-service code point alias name or bits";
               }
               leaf fc-name {
                 type string;
                 description "Class-of-service forwarding class name";
               }
               leaf loss-priority {
                 type string;
                 description "Class-of-service loss priority";
               }
               leaf cntag-present {
                 type string;
                 description "Class-of-service cntag present";
               }
             }
           }
         }
       }
     }
   }
   rpc get-cos-loss-priority-rewrite-information {
     description "Show mapping of loss priority to code point";
     input {
       leaf loss-priority-rewrite-name {
         description "Name of loss priority rewrite";
         type string;
       }
       leaf type {
         type enumeration {
           enum "frame-relay-de" {
             description "Frame Relay discard eligible code point";
           }
         }
       }
     }
     output {
       container cos-loss-priority-rewrite-information {
         container loss-priority-rewrite {
           description "Class-of-service loss priority to code point rewrite";
           leaf loss-priority-rewrite-name {
             type string;
             description "Name of class-of-service loss priority rewrite";
           }
           leaf code-point-type {
             type string;
             description "Class-of-service code point type";
           }
           leaf table-index {
             type uint32;
             description "Table index";
           }
           container loss-priority-rewrite-table {
             container loss-priority-rewrite-item {
               leaf loss-priority {
                 type string;
                 description "Class-of-service loss priority";
               }
               leaf code-point {
                 type string;
                 description "Class-of-service code point alias name or bits";
               }
             }
             container loss-priority-rewrite-table-entry {
               leaf table-index {
                 type uint32;
                 description "Table index";
               }
               leaf loss-priority {
                 type string;
                 description "Class-of-service loss priority";
               }
               leaf code-point {
                 type string;
                 description "Class-of-service code point alias name or bits";
               }
             }
           }
         }
       }
     }
   }
   rpc get-cos-rewrite-information {
     description "Show mapping of forwarding class/loss priority to code point";
     input {
       leaf rewrite-rule-name {
         description "Name of rewrite rule";
         type string;
       }
       leaf type {
         description "Type of rewrite rule";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "frame-relay-de" {
             description "Frame relay discard eligible bit code point";
           }
           enum "ieee-802.1ad" {
             description "IEEE-802.1ad (DEI) code point";
           }
         }
       }
     }
     output {
       container cos-rewrite-information {
         container rewrite {
           description "Class-of-service drop profile";
           leaf rewrite-name {
             type string;
             description "Class-of-service rewrite rule name";
           }
           leaf code-point-type {
             type string;
             description "Class-of-service code point type";
           }
           leaf table-index {
             type uint32;
             description "Table index";
           }
           container rewrite-map {
             container rewrite-map-item {
               leaf fc-name {
                 type string;
                 description "Class-of-service forwarding class name";
               }
               leaf loss-priority {
                 type string;
                 description "Class-of-service loss priority";
               }
               leaf code-point {
                 type string;
                 description "Class-of-service code point alias name or bits";
               }
             }
           }
         }
       }
     }
   }
   rpc get-cos-code-point-map-information {
     description "Show mapping of symbolic name to code point bit pattern";
     input {
       leaf type {
         description "Type of code point alias";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "ieee-802.1ad" {
             description "IEEE-802.1ad (DEI) code point";
           }
         }
       }
     }
     output {
       container cos-code-point-map-information {
         container code-point-map {
           description "Class-of-service code point alias map";
           leaf code-point-type {
             type string;
             description "Class-of-service code point type";
           }
           container alias-map {
             container alias-map-item {
               leaf code-point-alias {
                 type string;
                 description "Class-of-service code point alias name";
               }
               leaf code-point-bits {
                 type string;
                 description "Class-of-service code point bit sequence";
               }
             }
           }
         }
       }
     }
   }
   rpc get-cos-scheduler-map-information {
     description "Show mapping of forwarding classes to schedulers";
     input {
       leaf scheduler-map-name {
         description "Name of scheduler map";
         type string;
       }
     }
     output {
       container cos-scheduler-map-information {
         container scheduler-map {
           description "Class-of-service scheduler map";
           leaf scheduler-map-name {
             type string;
             description "Class-of-service scheduler map name";
           }
           leaf scheduler-map-index {
             type uint64;
             description "Class-of-service scheduler map index";
           }
           container scheduler {
             leaf scheduler-name {
               type string;
               description "Class-of-service scheduler name";
             }
             leaf fc-name {
               type string;
               description "Class-of-service forwarding class name";
             }
             leaf scheduler-index {
               type uint64;
               description "Class of service scheduler index";
             }
             leaf scheduler-tx-rate {
               type string;
               description "Class-of-service scheduler transmit rate";
             }
             leaf scheduler-tx-limit {
               type string;
               description "Class-of-service scheduler transmit limit";
             }
             leaf scheduler-buffer-size {
               type string;
               description "Class-of-service scheduler buffer size";
             }
             leaf scheduler-buffer-multicast-share {
               type uint32;
               description "Class-of-service scheduler multicast buffer share";
             }
             leaf scheduler-buffer-limit {
               type string;
               description "Class-of-service scheduler buffer limit";
             }
             leaf scheduler-shared-buffer-maximum-percentage {
               type uint32;
               description "Shared Buffer maximum percentage";
             }
             leaf scheduler-shared-buffer-multicast-maximum-percentage {
               type uint32;
               description "Shared Buffer multicast maximum percentage";
             }
             leaf scheduler-priority {
               type string;
               description "Class-of-service scheduler priority";
             }
             leaf scheduler-shaping-rate {
               type string;
               description "Class-of-service scheduler shaping rate";
             }
             leaf scheduler-shaping-rate-burst {
               type string;
               description "Class-of-service scheduler shaping rate burst";
             }
             leaf scheduler-adjust-minimum {
               type int32;
               description "Class-of-service scheduler adjustment minimum rate";
             }
             leaf scheduler-adjust-percent {
               type int32;
               description "Class-of-service scheduler percent adjustment for a queue";
             }
             leaf scheduler-excess-priority {
               type string;
               description "Class-of-service scheduler excess priority";
             }
             leaf scheduler-excess-rate {
               type string;
               description "Class-of-service scheduler excess rate";
             }
             leaf scheduler-explicit-congestion-notification {
               type string;
               description "Class-of-service ECN status of queue";
             }
             leaf scheduler-drop-profile-ln-index {
               type uint32;
               description "Class-of-service scheduler drop profile index low, non-TCP";
             }
             leaf scheduler-drop-profile-ln {
               type string;
               description "Class-of-service scheduler drop profile low, non-TCP";
             }
             leaf scheduler-drop-profile-lt-index {
               type uint32;
               description "Class-of-service scheduler drop profile index low, TCP";
             }
             leaf scheduler-drop-profile-lt {
               type string;
               description "Class-of-service scheduler drop profile low, TCP";
             }
             leaf scheduler-drop-profile-hn-index {
               type uint32;
               description "Class-of-service scheduler drop profile index high, non-TCP";
             }
             leaf scheduler-drop-profile-hn {
               type string;
               description "Class-of-service scheduler drop profile high, non-TCP";
             }
             leaf scheduler-drop-profile-ht-index {
               type uint32;
               description "Class-of-service scheduler drop profile index high, TCP";
             }
             leaf scheduler-drop-profile-ht {
               type string;
               description "Class-of-service scheduler drop profile high, TCP";
             }
             leaf scheduler-drop-profile-la-index {
               type uint32;
               description "Class-of-service scheduler drop profile index low";
             }
             leaf scheduler-drop-profile-la {
               type string;
               description "Class-of-service scheduler drop profile low";
             }
             leaf scheduler-drop-profile-ma-index {
               type uint32;
               description "Class-of-service scheduler drop profile index medium";
             }
             leaf scheduler-drop-profile-ma {
               type string;
               description "Class-of-service scheduler drop profile medium";
             }
             leaf scheduler-drop-profile-mla-index {
               type uint32;
               description "Class-of-service scheduler drop profile index medium-low";
             }
             leaf scheduler-drop-profile-mla {
               type string;
               description "Class-of-service scheduler drop profile medium-low";
             }
             leaf scheduler-drop-profile-mha-index {
               type uint32;
               description "Class-of-service scheduler drop profile index medium-high";
             }
             leaf scheduler-drop-profile-mha {
               type string;
               description "Class-of-service scheduler drop profile medium-high";
             }
             leaf scheduler-drop-profile-ha-index {
               type uint32;
               description "Class-of-service scheduler drop profile index high";
             }
             leaf scheduler-drop-profile-ha {
               type string;
               description "Class-of-service scheduler drop profile high";
             }
           }
         }
       }
     }
   }
   rpc get-cos-traffic-control-profile-information {
     description "Show traffic control profiles";
     input {
       leaf traffic-control-profile-name {
         description "Name of traffic control profile";
         type string;
       }
     }
     output {
       container cos-traffic-control-profile-information {
         container traffic-control-profile {
           description "Information about one or more traffic control profiles";
           leaf traffic-control-profile-name {
             type string;
             description "Class-of-service traffic control profile name";
           }
           leaf traffic-control-profile-index {
             type uint64;
             description "Index number for Class-of-service traffic control profile";
           }
           leaf scheduler-map-name {
             type string;
             description "Class-of-service scheduler map name";
           }
           leaf atm-service {
             type string;
             description "Class-of-service traffic control profile atm service";
           }
           leaf shaping-rate {
             type uint64;
             description "Class-of-service shaping rate";
           }
           leaf shaping-rate-burst {
             type uint32;
             description "Class-of-service shaping rate burst, in bytes";
           }
           leaf shaping-rate-priority-strict-high {
             type uint64;
             description "Class-of-service shaping rate for priority strict high";
           }
           leaf shaping-rate-priority-strict-high-burst {
             type uint32;
             description "Class-of-service shaping rate burst for priority strict-high";
           }
           leaf shaping-rate-priority-high {
             type uint64;
             description "Class-of-service shaping rate for priority high";
           }
           leaf shaping-rate-priority-high-burst {
             type uint32;
             description "Class-of-service shaping rate for priority high burst";
           }
           leaf shaping-rate-priority-medium {
             type uint64;
             description "Class-of-service shaping rate for priority medium";
           }
           leaf shaping-rate-priority-medium-burst {
             type uint32;
             description "Class-of-service shaping rate for priority medium burst";
           }
           leaf shaping-rate-priority-medium-low {
             type uint64;
             description "Class-of-service shaping rate for priority medium-low";
           }
           leaf shaping-rate-priority-medium-low-burst {
             type uint32;
             description "Class-of-service shaping rate burst for priority medium-low";
           }
           leaf shaping-rate-priority-low {
             type uint64;
             description "Class-of-service shaping rate for priority low";
           }
           leaf shaping-rate-priority-low-burst {
             type uint32;
             description "Class-of-service shaping rate for priority low burst";
           }
           leaf shaping-rate-excess-high {
             type uint64;
             description "Class-of-service shaping rate for excess high";
           }
           leaf shaping-rate-excess-high-burst {
             type uint32;
             description "Class-of-service shaping rate for excess high burst";
           }
           leaf shaping-rate-excess-medium-high {
             type uint64;
             description "Class-of-service shaping rate for excess medium-high";
           }
           leaf shaping-rate-excess-medium-high-burst {
             type uint32;
             description "Class-of-service shaping rate burst for excess medium-high";
           }
           leaf shaping-rate-excess-medium-low {
             type uint64;
             description "Class-of-service shaping rate for excess medium-low";
           }
           leaf shaping-rate-excess-medium-low-burst {
             type uint32;
             description "Class-of-service shaping rate burst for excess medium-low";
           }
           leaf shaping-rate-excess-low {
             type uint64;
             description "Class-of-service shaping rate for excess low";
           }
           leaf shaping-rate-excess-low-burst {
             type uint32;
             description "Class-of-service shaping rate for excess low burst";
           }
           leaf guaranteed-rate {
             type uint64;
             description "Class-of-service guaranteed rate";
           }
           leaf guaranteed-rate-burst {
             type uint32;
             description "Class-of-service guaranteed rate burst, in bytes";
           }
           leaf delay-buffer-rate {
             type uint64;
             description "Class-of-service delay buffer rate";
           }
           leaf excess-rate {
             type uint32;
             description "Class-of-service excess rate";
           }
           leaf excess-rate-high {
             type uint32;
             description "Class-of-service excess rate for excess-high priority traffic";
           }
           leaf excess-rate-medium-high {
             type uint32;
             description "Class-of-service excess rate for excess-medium-high priority traffic";
           }
           leaf excess-rate-medium-low {
             type uint32;
             description "Class-of-service excess rate for excess-medium-low priority traffic";
           }
           leaf excess-rate-low {
             type uint32;
             description "Class-of-service excess rate for excess-low priority traffic";
           }
           leaf adjust-minimum {
             type uint64;
             description "Class-of-service adjustment minimum rate";
           }
           leaf overhead-bytes {
             type int32;
             description "Class-of-service Overhead bytes";
           }
           leaf frame-mode-bytes {
             type int32;
             description "Class-of-service overhead bytes when in frame-mode";
           }
           leaf cell-mode-bytes {
             type int32;
             description "Class-of-service overhead bytes when in cell-mode";
           }
           leaf overhead-accounting-mode {
             type string;
             description "Class-of-service Overhead Accounting Mode";
           }
           container traffic-control-profile-instance {
             description "Class-of-service traffic control profile instance";
             leaf traffic-control-profile-instance-name {
               type string;
               description "Class-of-service traffic control profile instance";
             }
             leaf traffic-control-profile-instance-index {
               type uint32;
               description "Index number for Class-of-service traffic control profile instance";
             }
             leaf instance-reference-count {
               type uint32;
               description "Instance reference count";
             }
           }
         }
       }
     }
   }
   rpc get-cos-fragmentation-map-information {
     description "Show mapping of forwarding classes to fragmentation options";
     input {
       leaf fragmentation-map-name {
         description "Name of fragmentation map";
         type string;
       }
     }
     output {
       container cos-fragmentation-map-information {
         container fragmentation-map {
           description "Class-of-service fragmentation map";
           leaf fragmentation-map-name {
             type string;
             description "Class-of-service fragmentation map name";
           }
           leaf fragmentation-map-index {
             type uint32;
             description "Index number for Class-of-service fragmentation map";
           }
           container fragment-map {
             container no-fragmentation {
               leaf fc-name {
                 type string;
                 description "Class-of-service forwarding class name";
               }
             }
             container fragmentation {
               leaf fc-name {
                 type string;
                 description "Class-of-service forwarding class name";
               }
               leaf fragment-threshold {
                 type string;
                 description "Fragmentation threshold";
               }
             }
             container multilink_class {
               leaf fc-name {
                 type string;
                 description "Class-of-service forwarding class name";
               }
               leaf fragment-threshold {
                 type string;
                 description "Fragmentation threshold";
               }
               leaf fragment-multilink-class {
                 type int32;
                 description "Identifier for multilink class";
               }
             }
           }
         }
       }
     }
   }
   rpc get-cos-interface-map-information {
     description "Show mapping of CoS objects to interfaces";
     input {
       leaf interface-name {
         description "Name of interface";
         type string;
       }
       leaf level {
         type enumeration {
           enum "comprehensive" {
             description "Show interface, filter, policer and CoS information comprehensively";
           }
           enum "detail" {
             description "Show interface information, filter, policer and CoS object names";
           }
         }
       }
     }
     output {
       container cos-interface-information {
         container interface-map {
           description "Class-of-service interface mappings";
           leaf interface-name {
             type string;
             description "Class-of-service interface name";
           }
           leaf interface-index {
             type uint32;
             description "Class-of-service interface index";
           }
           leaf interface-queues-supported {
             type uint32;
             description "Number of queues supported on this interface";
           }
           leaf interface-queues-in-use {
             type uint32;
             description "Number of queues in use on this interface";
           }
           leaf interface-total-egress-queues-created {
             type uint32;
             description "Total number of non-default egress queues in use on this interface";
           }
           leaf interface-total-ingress-queues-created {
             type uint32;
             description "Total number of non-default ingress queues in use on this interface";
           }
           leaf interface-shaping-rate {
             type string;
             description "Class-of-service interface shaping rate";
           }
           leaf scheduler-map-name {
             type string;
             description "Class-of-service scheduler map name";
           }
           leaf scheduler-map-index {
             type uint64;
             description "Class-of-service scheduler map index";
           }
           leaf interface-input-shaping-rate {
             type string;
             description "Class-of-service interface input shaping rate";
           }
           leaf input-scheduler-map-name {
             type string;
             description "Class-of-service input scheduler map name";
           }
           leaf input-scheduler-map-index {
             type uint32;
             description "Index number for Class-of-service input scheduler map";
           }
           leaf chassis-scheduler-map-name {
             type string;
             description "Class-of-service chassis scheduler map name";
           }
           leaf chassis-scheduler-map-index {
             type uint32;
             description "Index number for Class-of-service chassis scheduler map";
           }
           leaf input-traffic-control-profile-name {
             type string;
             description "Class-of-service input traffic control profile name";
           }
           leaf input-traffic-control-profile-index {
             type uint64;
             description "Index number for Class-of-service input traffic control profile";
           }
           leaf output-traffic-control-profile-name {
             type string;
             description "Class-of-service output traffic control profile name";
           }
           leaf output-traffic-control-profile-index {
             type uint64;
             description "Index number for Class-of-service output traffic control profile";
           }
           leaf forwarding-class-map-name {
             type string;
             description "Class-of-service forwarding class map name";
           }
           leaf forwarding-class-map-index {
             type uint32;
             description "Index number for Class-of-service forwarding class map";
           }
           leaf interface-congestion-notification-map {
             type string;
             description "Congestion notification enabled/disabled on interface";
           }
           leaf interface-congestion-notification-map-name {
             type string;
             description "Congestion notification Profile Name";
           }
           leaf interface-congestion-notification-map-index {
             type uint32;
             description "Congestion notification Profile Index";
           }
           leaf interface-rewrite-value {
             type string;
             description "Interface rewrite value input / output";
           }
           leaf code-point-type {
             type string;
             description "Class-of-service code point type";
           }
           leaf code-point-bits {
             type string;
             description "Class-of-service code point bit sequence";
           }
           leaf scheduler-map-forwarding-class-set-name {
             type string;
             description "Class-of-service scheduler map forwarding-class-set name";
           }
           leaf scheduler-map-forwarding-class-set-index {
             type uint32;
             description "Class-of-service scheduler map forwarding class set index";
           }
           container forwarding-class-set-attachment {
             description "Class-of-service forwarding class set interface attachment ";
             leaf forwarding-class-set-name {
               type string;
               description "Class-of-service forwarding class set name";
             }
             leaf table-index {
               type uint32;
               description "Table index";
             }
           }
           container cos-objects {
             description "Class-of-service object  mappings";
             leaf cos-object-type {
               type string;
               description "Class-of-service object type";
             }
             leaf cos-object-name {
               type string;
               description "Class-of-service object name";
             }
             leaf cos-object-subtype {
               type string;
               description "Class-of-service object subtype";
             }
             leaf cos-object-index {
               type uint64;
               description "Class-of-service object index";
             }
           }
           container i-logical-map {
             leaf i-logical-name {
               type string;
               description "Class-of-service logical interface name";
             }
             leaf i-logical-index {
               type uint32;
               description "Class-of-service logical interface index";
             }
             leaf interface-has-dedicated-queues {
               type string;
               description "Whether interface has dedicated queues";
             }
             leaf policer-bandwidth {
               type uint32;
               description "Class-of-service logical interface policer bandwidth";
             }
             leaf policer-burst {
               type uint32;
               description "Class-of-service logical interface policer burst";
             }
             leaf shaper-bandwidth {
               type uint32;
               description "Class-of-service logical interface shaper bandwidth";
             }
             leaf shaper-burst {
               type uint32;
               description "Class-of-service logical interface shaper burst";
             }
             leaf shaping-rate {
               type uint64;
               description "Class-of-service shaping rate";
             }
             leaf burst-size {
               type string;
               description "Class-of-service logical interface burst size";
             }
             leaf input-shaping-rate {
               type uint64;
               description "Class-of-service input shaping rate";
             }
             leaf input-burst-size {
               type string;
               description "Class-of-service logical interface input burst size";
             }
             leaf adjusting-application-name {
               type string;
               description "The name of the application performing the rate adjustment";
             }
             leaf adjustment-type {
               type string;
               description "Class-of-service rate adjustment type";
             }
             leaf configured-shaping-rate {
               type uint64;
               description "Class-of-service configured shaping rate";
             }
             leaf adjustment-value {
               type uint64;
               description "Class-of-service adjusted shaping rate value";
             }
             leaf adjustment-overhead-accounting-mode {
               type string;
               description "Class-of-service adjusted overhead-accounting mode";
             }
             leaf adjustment-overhead-bytes {
               type int32;
               description "Class-of-service adjusted overhead bytes";
             }
             leaf adjustment-target {
               type string;
               description "Class-of-service rate adjustment target";
             }
             leaf adjustment-priority {
               type uint32;
               description "Class-of-service rate adjustment priority";
             }
             container cos-objects {
               description "Class-of-service object  mappings";
               leaf cos-object-type {
                 type string;
                 description "Class-of-service object type";
               }
               leaf cos-object-name {
                 type string;
                 description "Class-of-service object name";
               }
               leaf cos-object-subtype {
                 type string;
                 description "Class-of-service object subtype";
               }
               leaf cos-object-index {
                 type uint64;
                 description "Class-of-service object index";
               }
             }
           }
         }
       }
     }
   }
   rpc get-cos-routing-instance-map-information {
     description "Show mapping of CoS objects to routing instance";
     input {
       leaf routing-instance-name {
         description "Name of routing instance";
         type string;
       }
     }
     output {
       container cos-routing-instance-information {
         container routing-instance-map {
           description "Mapping between class-of-service objects and routing instances";
           leaf routing-instance-name {
             type string;
             description "Name of class-of-service routing instance";
           }
           container i-logical-map {
             leaf i-logical-name {
               type string;
               description "Class-of-service logical interface name";
             }
             leaf i-logical-index {
               type uint32;
               description "Class-of-service logical interface index";
             }
             container cos-objects {
               description "Class-of-service object  mappings";
               leaf cos-object-type {
                 type string;
                 description "Class-of-service object type";
               }
               leaf cos-object-name {
                 type string;
                 description "Class-of-service object name";
               }
               leaf cos-object-subtype {
                 type string;
                 description "Class-of-service object subtype";
               }
               leaf cos-object-index {
                 type uint64;
                 description "Class-of-service object index";
               }
             }
           }
         }
       }
     }
   }
   rpc get-cos-table-information {
     description "Show forwarding table information";
     output {
       container cos-table-information {
         container cos-classifier-table-information {
           container classifier-table {
             leaf table-index {
               type uint32;
               description "Table index";
             }
             leaf number-of-entries {
               type uint32;
               description "Number of entries in an output list";
             }
             leaf table-type {
               type string;
               description "Table type";
             }
             container classifier-table-entry {
               leaf code-point {
                 type string;
                 description "Class-of-service code point alias name or bits";
               }
               leaf fc-queue-number {
                 type uint32;
                 description "Class-of-service forwarding class queue number";
               }
               leaf loss-priority {
                 type string;
                 description "Class-of-service loss priority";
               }
             }
           }
         }
         container cos-classifier-table-map-information {
           container classifier-table-map {
             leaf logical-interface {
               type string;
               description "Logical interface name";
             }
             leaf logical-interface-index {
               type uint32;
               description "Logical interface index";
             }
             leaf table-index {
               type uint32;
               description "Table index";
             }
             leaf table-type {
               type string;
               description "Table type";
             }
           }
         }
         container cos-loss-priority-map-table-information {
           container loss-priority-map-table {
             leaf table-index {
               type uint32;
               description "Table index";
             }
             leaf number-of-entries {
               type uint32;
               description "Number of entries in an output list";
             }
             leaf table-type {
               type string;
               description "Table type";
             }
             container loss-priority-map-item {
               leaf code-point {
                 type string;
                 description "Class-of-service code point alias name or bits";
               }
               leaf loss-priority {
                 type string;
                 description "Class-of-service loss priority";
               }
             }
             container loss-priority-map-table-entry {
               leaf table-index {
                 type uint32;
                 description "Table index";
               }
               leaf code-point {
                 type string;
                 description "Class-of-service code point alias name or bits";
               }
               leaf loss-priority {
                 type string;
                 description "Class-of-service loss priority";
               }
             }
           }
         }
         container cos-loss-priority-map-table-binding-information {
           container loss-priority-map-table-binding {
             leaf logical-interface {
               type string;
               description "Logical interface name";
             }
             leaf logical-interface-index {
               type uint32;
               description "Logical interface index";
             }
             leaf table-index {
               type uint32;
               description "Table index";
             }
             leaf table-type {
               type string;
               description "Table type";
             }
           }
         }
         container cos-scheduler-map-table-information {
           container policy {
             leaf interface {
               type string;
             }
             leaf interface-index {
               type uint32;
               description "Class-of-service interface index";
             }
             leaf policy-index {
               type uint32;
             }
             leaf policy-type {
               type string;
             }
             leaf policy-number-of-queues {
               type uint32;
               description "Number of queues in this policy";
             }
             leaf if-traffic-control-profile-name {
               type string;
               description "Class-of-service traffic control profile name";
             }
             leaf if-traffic-control-profile-index {
               type uint32;
               description "Index number for Class-of-service traffic control profile";
             }
             leaf if-traffic-control-profile-instance-index {
               type uint32;
               description "Index number for traffic control profile instance";
             }
             leaf policy-shaping-rate {
               type uint32;
               description "Shaping rate";
             }
             leaf policy-shaping-rate-percentage {
               type uint32;
               description "Shaping rate as percentage";
             }
             leaf policy-shaping-rate-burst {
               type uint32;
               description "Shaping rate burst";
             }
             leaf policy-guaranteed-rate {
               type uint32;
               description "Guaranteed rate";
             }
             leaf policy-guaranteed-rate-percent {
               type uint32;
               description "Guaranteed rate as percentage";
             }
             leaf policy-guaranteed-rate-burst {
               type uint32;
               description "Guaranteed rate burst";
             }
             leaf policy-delay-buffer-rate {
               type uint32;
               description "Delay buffer rate";
             }
             leaf policy-delay-buffer-time {
               type uint32;
               description "Delay buffer time";
             }
             leaf policy-excess-rate-proportion {
               type uint32;
               description "Excess rate";
             }
             leaf policy-excess-rate-percent {
               type uint32;
               description "Excess rate as percentage";
             }
             leaf policy-overhead-bytes {
               type uint32;
               description "Overhead bytes";
             }
             leaf policy-adjust-min-shaping-rate {
               type uint32;
               description "Adjust minimum shaping rate";
             }
             leaf policy-flags {
               type uint32;
               description "Traffic control profile flags";
             }
             leaf policy-level {
               type uint32;
               description "Traffic control profile level";
             }
             container policy-entry {
               leaf table-index {
                 type uint32;
                 description "Table index";
               }
               leaf policy-entry-identifier {
                 type uint32;
                 description "Policy entry ID number";
               }
               leaf fc-number {
                 type uint32;
                 description "Identifier for Class-of-service forwarding class";
               }
               leaf fc-queue-number {
                 type uint32;
                 description "Class-of-service forwarding class queue number";
               }
               leaf policy-transmit-rate {
                 type uint32;
                 description "Transmit rate";
               }
               leaf policy-transmit-rate-percentage {
                 type uint32;
                 description "Transmit rate percentage";
               }
               leaf policy-transmit-rate-remainder {
                 type uint32;
                 description "Transmit rate is remainder";
               }
               leaf policy-buffer-size-temporal {
                 type uint32;
                 description "Buffer size in units of time";
               }
               leaf policy-buffer-size-percentage {
                 type uint32;
                 description "Buffer size percentage";
               }
               leaf policy-buffer-size-remainder {
                 type string;
                 description "Buffer size is remainder";
               }
               leaf policy-buffer-multicast-share {
                 type uint32;
                 description "Buffer size share percent for multicaste";
               }
               leaf policy-buffer-size-multi-destination-buffers {
                 type uint32;
                 description "Buffer size in units of bits";
               }
               leaf policy-shared-buffer-maximum-percentage {
                 type uint32;
                 description "Shared Buffer maximum percentage";
               }
               leaf policy-shared-buffer-multicast-maximum-percentage {
                 type uint32;
                 description "Shared Buffer multicast maximum percentage";
               }
               leaf policy-entry-shaping-rate {
                 type uint32;
                 description "Shaping rate";
               }
               leaf policy-entry-shaping-rate-percentage {
                 type uint32;
                 description "Shaping rate as percentage";
               }
               leaf policy-excess-rate-proportional {
                 type uint32;
                 description "Excess rate as proportion";
               }
               leaf policy-excess-rate-percentage {
                 type uint32;
                 description "Excess rate as percentage";
               }
               leaf policy-excess-priority {
                 type uint32;
                 description "Excess priority";
               }
               leaf policy-scheduling-priority {
                 type uint32;
                 description "Scheduling priority";
               }
               leaf policy-exact {
                 type uint32;
                 description "Policy is exact Boolean";
               }
               container policy-packet-loss-profile {
                 leaf high-drop-profile-identifier {
                   type uint32;
                   description "PLP high drop profile ID";
                 }
                 leaf medium-drop-profile-identifier {
                   type uint32;
                   description "PLP medium drop profile ID";
                 }
                 leaf low-drop-profile-identifier {
                   type uint32;
                   description "PLP low drop profile ID";
                 }
                 leaf medium-high-drop-profile-identifier {
                   type uint32;
                   description "PLP medium-high drop profile ID";
                 }
                 leaf medium-low-drop-profile-identifier {
                   type uint32;
                   description "PLP medium-low drop profile ID";
                 }
                 leaf tcp-high-drop-profile-identifier {
                   type uint32;
                   description "TCP PLP high drop profile ID";
                 }
                 leaf tcp-low-drop-profile-identifier {
                   type uint32;
                   description "TCP PLP low drop profile ID";
                 }
               }
             }
           }
         }
         container cos-red-information {
           container red {
             leaf red-drop-profile-identifier {
               type uint32;
             }
             leaf number-of-entries {
               type uint32;
               description "Number of entries in an output list";
             }
             container red-entry {
               container m-t-mx-j-series-cosinfo-red-entry-format {
                 leaf red-entry-index {
                   type uint32;
                 }
                 leaf red-fullness {
                   type uint32;
                 }
                 leaf red-drop-probability {
                   type uint32;
                 }
               }
               container ex-series-cosinfo-red-entry-format {
                 leaf red-entry-index {
                   type uint32;
                 }
                 leaf red-fullness {
                   type uint32;
                 }
               }
             }
           }
         }
         container cos-rewrite-table-information {
           container rewrite-table {
             leaf table-index {
               type uint32;
               description "Table index";
             }
             leaf number-of-entries {
               type uint32;
               description "Number of entries in an output list";
             }
             leaf table-type {
               type string;
               description "Table type";
             }
             container rewrite-table-entry {
               container one-bit {
                 leaf fc-queue-number {
                   type uint32;
                   description "Class-of-service forwarding class queue number";
                 }
                 leaf rewrite-low-codepoint {
                   type string;
                   description "Low loss-priority code point";
                 }
                 leaf rewrite-low-enable-state {
                   type string;
                   description "Rewrite state for loss-priority low";
                 }
                 leaf rewrite-high-codepoint {
                   type string;
                   description "High loss-priority code point";
                 }
                 leaf rewrite-high-enable-state {
                   type string;
                   description "Rewrite state for loss-priority high";
                 }
               }
               container tri-color {
                 leaf fc-queue-number {
                   type uint32;
                   description "Class-of-service forwarding class queue number";
                 }
                 leaf rewrite-low-codepoint {
                   type string;
                   description "Low loss-priority code point";
                 }
                 leaf rewrite-low-enable-state {
                   type string;
                   description "Rewrite state for loss-priority low";
                 }
                 leaf rewrite-medium-codepoint {
                   type string;
                   description "Medium loss-priority code point";
                 }
                 leaf rewrite-medium-enable-state {
                   type string;
                   description "Rewrite state for loss-priority medium";
                 }
                 leaf rewrite-high-codepoint {
                   type string;
                   description "High loss-priority code point";
                 }
                 leaf rewrite-high-enable-state {
                   type string;
                   description "Rewrite state for loss-priority high";
                 }
               }
               container two-bit {
                 leaf fc-queue-number {
                   type uint32;
                   description "Class-of-service forwarding class queue number";
                 }
                 leaf rewrite-low-codepoint {
                   type string;
                   description "Low loss-priority code point";
                 }
                 leaf rewrite-low-enable-state {
                   type string;
                   description "Rewrite state for loss-priority low";
                 }
                 leaf rewrite-high-codepoint {
                   type string;
                   description "High loss-priority code point";
                 }
                 leaf rewrite-high-enable-state {
                   type string;
                   description "Rewrite state for loss-priority high";
                 }
                 leaf rewrite-medium-low-codepoint {
                   type string;
                   description "Medium-low loss-priority code point";
                 }
                 leaf rewrite-medium-low-enable-state {
                   type string;
                   description "Rewrite state for loss-priority medium-low";
                 }
                 leaf rewrite-medium-high-codepoint {
                   type string;
                   description "Medium-high loss-priority code point";
                 }
                 leaf rewrite-medium-high-enable-state {
                   type string;
                   description "Rewrite state for loss-priority medium-high";
                 }
               }
             }
           }
         }
         container cos-rewrite-table-map-information {
           container rewrite-table-map {
             leaf logical-interface {
               type string;
               description "Logical interface name";
             }
             leaf logical-interface-index {
               type uint32;
               description "Logical interface index";
             }
             leaf table-index {
               type uint32;
               description "Table index";
             }
             leaf table-type {
               type string;
               description "Table type";
             }
           }
         }
         container cos-loss-priority-rewrite-table-information {
           container loss-priority-rewrite-table {
             leaf table-index {
               type uint32;
               description "Table index";
             }
             leaf number-of-entries {
               type uint32;
               description "Number of entries in an output list";
             }
             leaf table-type {
               type string;
               description "Table type";
             }
             container loss-priority-rewrite-item {
               leaf loss-priority {
                 type string;
                 description "Class-of-service loss priority";
               }
               leaf code-point {
                 type string;
                 description "Class-of-service code point alias name or bits";
               }
             }
             container loss-priority-rewrite-table-entry {
               leaf table-index {
                 type uint32;
                 description "Table index";
               }
               leaf loss-priority {
                 type string;
                 description "Class-of-service loss priority";
               }
               leaf code-point {
                 type string;
                 description "Class-of-service code point alias name or bits";
               }
             }
           }
         }
         container cos-loss-priority-rewrite-table-binding-information {
           container loss-priority-rewrite-table-binding {
             leaf logical-interface {
               type string;
               description "Logical interface name";
             }
             leaf logical-interface-index {
               type uint32;
               description "Logical interface index";
             }
             leaf table-index {
               type uint32;
               description "Table index";
             }
             leaf table-type {
               type string;
               description "Table type";
             }
           }
         }
         container cos-policer-table-map-information {
           container policer-table-map {
             leaf p-interface {
               type string;
             }
             leaf p-interface-index {
               type uint32;
             }
             leaf policer-bandwidth {
               type uint32;
               description "Class-of-service logical interface policer bandwidth";
             }
             leaf policer-burst {
               type uint32;
               description "Class-of-service logical interface policer burst";
             }
           }
         }
         container cos-shaper-table-map-information {
           container shaper-table-map {
             leaf s-interface {
               type string;
             }
             leaf s-interface-index {
               type uint32;
             }
             leaf shaper-bandwidth {
               type uint32;
               description "Class-of-service logical interface shaper bandwidth";
             }
             leaf shaper-burst {
               type uint32;
               description "Class-of-service logical interface shaper burst";
             }
           }
         }
       }
     }
   }
   rpc get-cos-classifier-table-information {
     description "Show classifier information";
     output {
       container cos-classifier-table-information {
         container classifier-table {
           leaf table-index {
             type uint32;
             description "Table index";
           }
           leaf number-of-entries {
             type uint32;
             description "Number of entries in an output list";
           }
           leaf table-type {
             type string;
             description "Table type";
           }
           container classifier-table-entry {
             leaf code-point {
               type string;
               description "Class-of-service code point alias name or bits";
             }
             leaf fc-queue-number {
               type uint32;
               description "Class-of-service forwarding class queue number";
             }
             leaf loss-priority {
               type string;
               description "Class-of-service loss priority";
             }
           }
         }
       }
     }
   }
   rpc get-cos-classifier-table-map-information {
     description "Show mapping of interfaces to classifiers";
     output {
       container cos-classifier-table-map-information {
         container classifier-table-map {
           leaf logical-interface {
             type string;
             description "Logical interface name";
           }
           leaf logical-interface-index {
             type uint32;
             description "Logical interface index";
           }
           leaf table-index {
             type uint32;
             description "Table index";
           }
           leaf table-type {
             type string;
             description "Table type";
           }
         }
       }
     }
   }
   rpc get-cos-loss-priority-rewrite-table-information {
     description "Show loss priority rewrite table";
     output {
       container cos-loss-priority-rewrite-table-information {
         container loss-priority-rewrite-table {
           leaf table-index {
             type uint32;
             description "Table index";
           }
           leaf number-of-entries {
             type uint32;
             description "Number of entries in an output list";
           }
           leaf table-type {
             type string;
             description "Table type";
           }
           container loss-priority-rewrite-item {
             leaf loss-priority {
               type string;
               description "Class-of-service loss priority";
             }
             leaf code-point {
               type string;
               description "Class-of-service code point alias name or bits";
             }
           }
           container loss-priority-rewrite-table-entry {
             leaf table-index {
               type uint32;
               description "Table index";
             }
             leaf loss-priority {
               type string;
               description "Class-of-service loss priority";
             }
             leaf code-point {
               type string;
               description "Class-of-service code point alias name or bits";
             }
           }
         }
       }
     }
   }
   rpc get-cos-loss-priority-rewrite-table-binding-information {
     description "Show interface to loss priority rewrite binding";
     output {
       container cos-loss-priority-rewrite-table-binding-information {
         container loss-priority-rewrite-table-binding {
           leaf logical-interface {
             type string;
             description "Logical interface name";
           }
           leaf logical-interface-index {
             type uint32;
             description "Logical interface index";
           }
           leaf table-index {
             type uint32;
             description "Table index";
           }
           leaf table-type {
             type string;
             description "Table type";
           }
         }
       }
     }
   }
   rpc get-cos-scheduler-map-table-information {
     description "Show scheduler map";
     output {
       container cos-scheduler-map-table-information {
         container policy {
           leaf interface {
             type string;
           }
           leaf interface-index {
             type uint32;
             description "Class-of-service interface index";
           }
           leaf policy-index {
             type uint32;
           }
           leaf policy-type {
             type string;
           }
           leaf policy-number-of-queues {
             type uint32;
             description "Number of queues in this policy";
           }
           leaf if-traffic-control-profile-name {
             type string;
             description "Class-of-service traffic control profile name";
           }
           leaf if-traffic-control-profile-index {
             type uint32;
             description "Index number for Class-of-service traffic control profile";
           }
           leaf if-traffic-control-profile-instance-index {
             type uint32;
             description "Index number for traffic control profile instance";
           }
           leaf policy-shaping-rate {
             type uint32;
             description "Shaping rate";
           }
           leaf policy-shaping-rate-percentage {
             type uint32;
             description "Shaping rate as percentage";
           }
           leaf policy-shaping-rate-burst {
             type uint32;
             description "Shaping rate burst";
           }
           leaf policy-guaranteed-rate {
             type uint32;
             description "Guaranteed rate";
           }
           leaf policy-guaranteed-rate-percent {
             type uint32;
             description "Guaranteed rate as percentage";
           }
           leaf policy-guaranteed-rate-burst {
             type uint32;
             description "Guaranteed rate burst";
           }
           leaf policy-delay-buffer-rate {
             type uint32;
             description "Delay buffer rate";
           }
           leaf policy-delay-buffer-time {
             type uint32;
             description "Delay buffer time";
           }
           leaf policy-excess-rate-proportion {
             type uint32;
             description "Excess rate";
           }
           leaf policy-excess-rate-percent {
             type uint32;
             description "Excess rate as percentage";
           }
           leaf policy-overhead-bytes {
             type uint32;
             description "Overhead bytes";
           }
           leaf policy-adjust-min-shaping-rate {
             type uint32;
             description "Adjust minimum shaping rate";
           }
           leaf policy-flags {
             type uint32;
             description "Traffic control profile flags";
           }
           leaf policy-level {
             type uint32;
             description "Traffic control profile level";
           }
           container policy-entry {
             leaf table-index {
               type uint32;
               description "Table index";
             }
             leaf policy-entry-identifier {
               type uint32;
               description "Policy entry ID number";
             }
             leaf fc-number {
               type uint32;
               description "Identifier for Class-of-service forwarding class";
             }
             leaf fc-queue-number {
               type uint32;
               description "Class-of-service forwarding class queue number";
             }
             leaf policy-transmit-rate {
               type uint32;
               description "Transmit rate";
             }
             leaf policy-transmit-rate-percentage {
               type uint32;
               description "Transmit rate percentage";
             }
             leaf policy-transmit-rate-remainder {
               type uint32;
               description "Transmit rate is remainder";
             }
             leaf policy-buffer-size-temporal {
               type uint32;
               description "Buffer size in units of time";
             }
             leaf policy-buffer-size-percentage {
               type uint32;
               description "Buffer size percentage";
             }
             leaf policy-buffer-size-remainder {
               type string;
               description "Buffer size is remainder";
             }
             leaf policy-buffer-multicast-share {
               type uint32;
               description "Buffer size share percent for multicaste";
             }
             leaf policy-buffer-size-multi-destination-buffers {
               type uint32;
               description "Buffer size in units of bits";
             }
             leaf policy-shared-buffer-maximum-percentage {
               type uint32;
               description "Shared Buffer maximum percentage";
             }
             leaf policy-shared-buffer-multicast-maximum-percentage {
               type uint32;
               description "Shared Buffer multicast maximum percentage";
             }
             leaf policy-entry-shaping-rate {
               type uint32;
               description "Shaping rate";
             }
             leaf policy-entry-shaping-rate-percentage {
               type uint32;
               description "Shaping rate as percentage";
             }
             leaf policy-excess-rate-proportional {
               type uint32;
               description "Excess rate as proportion";
             }
             leaf policy-excess-rate-percentage {
               type uint32;
               description "Excess rate as percentage";
             }
             leaf policy-excess-priority {
               type uint32;
               description "Excess priority";
             }
             leaf policy-scheduling-priority {
               type uint32;
               description "Scheduling priority";
             }
             leaf policy-exact {
               type uint32;
               description "Policy is exact Boolean";
             }
             container policy-packet-loss-profile {
               leaf high-drop-profile-identifier {
                 type uint32;
                 description "PLP high drop profile ID";
               }
               leaf medium-drop-profile-identifier {
                 type uint32;
                 description "PLP medium drop profile ID";
               }
               leaf low-drop-profile-identifier {
                 type uint32;
                 description "PLP low drop profile ID";
               }
               leaf medium-high-drop-profile-identifier {
                 type uint32;
                 description "PLP medium-high drop profile ID";
               }
               leaf medium-low-drop-profile-identifier {
                 type uint32;
                 description "PLP medium-low drop profile ID";
               }
               leaf tcp-high-drop-profile-identifier {
                 type uint32;
                 description "TCP PLP high drop profile ID";
               }
               leaf tcp-low-drop-profile-identifier {
                 type uint32;
                 description "TCP PLP low drop profile ID";
               }
             }
           }
         }
       }
     }
   }
   rpc get-scheduler-map-table-map-information {
     description "Show mapping of scheduler-maps to interfaces";
   }
   rpc get-cos-policer-table-map-information {
     description "Show policer";
     output {
       container cos-policer-table-map-information {
         container policer-table-map {
           leaf p-interface {
             type string;
           }
           leaf p-interface-index {
             type uint32;
           }
           leaf policer-bandwidth {
             type uint32;
             description "Class-of-service logical interface policer bandwidth";
           }
           leaf policer-burst {
             type uint32;
             description "Class-of-service logical interface policer burst";
           }
         }
       }
     }
   }
   rpc get-cos-shaper-table-map-information {
     description "Show shaper";
     output {
       container cos-shaper-table-map-information {
         container shaper-table-map {
           leaf s-interface {
             type string;
           }
           leaf s-interface-index {
             type uint32;
           }
           leaf shaper-bandwidth {
             type uint32;
             description "Class-of-service logical interface shaper bandwidth";
           }
           leaf shaper-burst {
             type uint32;
             description "Class-of-service logical interface shaper burst";
           }
         }
       }
     }
   }
   rpc get-cos-red-information {
     description "Show random early detection drop profile";
     output {
       container cos-red-information {
         container red {
           leaf red-drop-profile-identifier {
             type uint32;
           }
           leaf number-of-entries {
             type uint32;
             description "Number of entries in an output list";
           }
           container red-entry {
             container m-t-mx-j-series-cosinfo-red-entry-format {
               leaf red-entry-index {
                 type uint32;
               }
               leaf red-fullness {
                 type uint32;
               }
               leaf red-drop-probability {
                 type uint32;
               }
             }
             container ex-series-cosinfo-red-entry-format {
               leaf red-entry-index {
                 type uint32;
               }
               leaf red-fullness {
                 type uint32;
               }
             }
           }
         }
       }
     }
   }
   rpc get-cos-rewrite-table-information {
     description "Show rewrite information";
     output {
       container cos-rewrite-table-information {
         container rewrite-table {
           leaf table-index {
             type uint32;
             description "Table index";
           }
           leaf number-of-entries {
             type uint32;
             description "Number of entries in an output list";
           }
           leaf table-type {
             type string;
             description "Table type";
           }
           container rewrite-table-entry {
             container one-bit {
               leaf fc-queue-number {
                 type uint32;
                 description "Class-of-service forwarding class queue number";
               }
               leaf rewrite-low-codepoint {
                 type string;
                 description "Low loss-priority code point";
               }
               leaf rewrite-low-enable-state {
                 type string;
                 description "Rewrite state for loss-priority low";
               }
               leaf rewrite-high-codepoint {
                 type string;
                 description "High loss-priority code point";
               }
               leaf rewrite-high-enable-state {
                 type string;
                 description "Rewrite state for loss-priority high";
               }
             }
             container tri-color {
               leaf fc-queue-number {
                 type uint32;
                 description "Class-of-service forwarding class queue number";
               }
               leaf rewrite-low-codepoint {
                 type string;
                 description "Low loss-priority code point";
               }
               leaf rewrite-low-enable-state {
                 type string;
                 description "Rewrite state for loss-priority low";
               }
               leaf rewrite-medium-codepoint {
                 type string;
                 description "Medium loss-priority code point";
               }
               leaf rewrite-medium-enable-state {
                 type string;
                 description "Rewrite state for loss-priority medium";
               }
               leaf rewrite-high-codepoint {
                 type string;
                 description "High loss-priority code point";
               }
               leaf rewrite-high-enable-state {
                 type string;
                 description "Rewrite state for loss-priority high";
               }
             }
             container two-bit {
               leaf fc-queue-number {
                 type uint32;
                 description "Class-of-service forwarding class queue number";
               }
               leaf rewrite-low-codepoint {
                 type string;
                 description "Low loss-priority code point";
               }
               leaf rewrite-low-enable-state {
                 type string;
                 description "Rewrite state for loss-priority low";
               }
               leaf rewrite-high-codepoint {
                 type string;
                 description "High loss-priority code point";
               }
               leaf rewrite-high-enable-state {
                 type string;
                 description "Rewrite state for loss-priority high";
               }
               leaf rewrite-medium-low-codepoint {
                 type string;
                 description "Medium-low loss-priority code point";
               }
               leaf rewrite-medium-low-enable-state {
                 type string;
                 description "Rewrite state for loss-priority medium-low";
               }
               leaf rewrite-medium-high-codepoint {
                 type string;
                 description "Medium-high loss-priority code point";
               }
               leaf rewrite-medium-high-enable-state {
                 type string;
                 description "Rewrite state for loss-priority medium-high";
               }
             }
           }
         }
       }
     }
   }
   rpc get-cos-rewrite-table-map-information {
     description "Show interface to rewrite rule mapping";
     output {
       container cos-rewrite-table-map-information {
         container rewrite-table-map {
           leaf logical-interface {
             type string;
             description "Logical interface name";
           }
           leaf logical-interface-index {
             type uint32;
             description "Logical interface index";
           }
           leaf table-index {
             type uint32;
             description "Table index";
           }
           leaf table-type {
             type string;
             description "Table type";
           }
         }
       }
     }
   }
   rpc get-cos-translation-table-information {
     description "Show translation table information";
     output {
       container cos-translation-table-information {
         container translation-table {
           description "Class-of-service code point translation table";
           leaf table-index {
             type uint32;
             description "Table index";
           }
           leaf number-of-entries {
             type uint32;
             description "Number of entries in an output list";
           }
           leaf translation-table-type {
             type string;
             description "Class-of-service translation table type";
           }
           container translation-table-map {
             container translation-table-map-item {
               leaf from-code-point {
                 type string;
                 description "Class-of-service code point alias name or bits";
               }
               leaf to-code-point {
                 type string;
                 description "Class-of-service code point alias name or bits";
               }
             }
           }
           container translation-table-entry {
             leaf table-index {
               type uint32;
               description "Table index";
             }
             leaf from-code-point {
               type string;
               description "Class-of-service code point alias name or bits";
             }
             leaf to-code-point {
               type string;
               description "Class-of-service code point alias name or bits";
             }
           }
         }
       }
     }
   }
   rpc get-cos-translation-table-mapping-information {
     description "Show mapping of interfaces to translation table";
     output {
       container cos-translation-table-mapping-information {
         container translation-table-mapping {
           leaf logical-interface {
             type string;
             description "Logical interface name";
           }
           leaf logical-interface-index {
             type uint32;
             description "Logical interface index";
           }
           leaf table-index {
             type uint32;
             description "Table index";
           }
           leaf translation-table-type {
             type string;
             description "Class-of-service translation table type";
           }
         }
       }
     }
   }
   rpc get-cos-translation-table-map-information {
     description "Show mapping of code point to code point";
     input {
       leaf translation-table-name {
         description "Name of translation table";
         type string;
       }
       leaf type {
         description "Type of translation table";
         type enumeration {
           enum "to-inet-precedence-from-inet-precedence" {
             description "INET PRECEDENCE to INET PRECEDENCE translation table";
           }
           enum "to-dscp-from-dscp" {
             description "DSCP to DSCP translation table";
           }
           enum "to-dscp-ipv6-from-dscp-ipv6" {
             description "DSCP IPV6 to DSCP IPV6 translation table";
           }
           enum "to-exp-from-exp" {
             description "EXP to EXP translation table";
           }
         }
       }
     }
     output {
       container cos-translation-table-map-information {
         container translation-table {
           description "Class-of-service code point translation table";
           leaf translation-table-name {
             type string;
             description "Class-of-service translation table name";
           }
           leaf translation-table-type {
             type string;
             description "Class-of-service translation table type";
           }
           leaf table-index {
             type uint32;
             description "Table index";
           }
           container translation-table-map {
             container translation-table-map-item {
               leaf from-code-point {
                 type string;
                 description "Class-of-service code point alias name or bits";
               }
               leaf to-code-point {
                 type string;
                 description "Class-of-service code point alias name or bits";
               }
             }
           }
           container translation-table-entry {
             leaf table-index {
               type uint32;
               description "Table index";
             }
             leaf from-code-point {
               type string;
               description "Class-of-service code point alias name or bits";
             }
             leaf to-code-point {
               type string;
               description "Class-of-service code point alias name or bits";
             }
           }
         }
       }
     }
   }
   rpc get-cos-congestion-notification-information {
     description "Show congestion-notification information";
     input {
       leaf cnp-name {
         description "Name of congestion notification profile";
         type string;
       }
     }
     output {
       container cos-congestion-notification-information {
         container cos-congestion-notification {
           leaf congestion-notification-name {
             type string;
             description "Class-of-service congestion-notification name";
           }
           leaf congestion-notification-id {
             type uint32;
             description "Class-of-service congestion-notification Index";
           }
           container congestion-notification-input {
             leaf congestion-notification-type {
               type string;
               description "Class-of-service congestion-notification type";
             }
             leaf pfc-cable-length {
               type uint32;
               description "Length of cable in meter";
             }
             container congestion-notification-map {
               container congestion-notification-map-item {
                 leaf pfc-priority {
                   type string;
                   description "PFC priority";
                 }
                 leaf pfc-enable-state {
                   type string;
                   description "PFC state for the priority";
                 }
                 leaf pfc-mru {
                   type uint32;
                   description "Maximum Rx Unit";
                 }
               }
             }
           }
           container congestion-notification-output {
             leaf congestion-notification-type {
               type string;
               description "Class-of-service congestion-notification type";
             }
             container congestion-notification-output-map {
               container congestion-notification-output-map-item {
                 leaf pfc-empty {
                   type empty;
                 }
                 leaf pfc-priority {
                   type string;
                   description "PFC priority";
                 }
                 container pfc-flow-control-queue-list {
                   leaf pfc-flow-control-queue {
                     type uint32;
                     description "Flow Control Queue";
                   }
                 }
               }
             }
           }
         }
       }
     }
   }
 }
