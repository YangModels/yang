/*
 * Copyright (c) 2017 Juniper Networks, Inc.
 * All rights reserved.
 */

 module show-l2-learning {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-l2-learning-interface-information {
     description "Show interface";
     output {
       container l2ald-iff-information {
         container l2ald-iff-entry {
           container brief {
             leaf l2iff-lr-name {
               type string;
               description "Logical router name";
             }
             leaf l2iff-rtt-name {
               type string;
               description "Routing Instance name";
             }
             leaf l2iff-ifl-name {
               type string;
               description "Logical interface name";
             }
             leaf l2iff-ifbd-name {
               type string;
               description "BD name in compressed form";
             }
             leaf l2iff-mac-limit {
               type uint32;
               description "Maximum number of MAC addresses that can be learned on this interface family";
             }
             leaf l2iff-ifbd-stp-state {
               type string;
               description "STP state for this IFBD";
             }
             leaf l2iff-flags {
               type string;
               description "Attributes associated with this interface family";
             }
             leaf l2iff-index {
               type uint32;
               description "Interface family index";
             }
             leaf l2iff-generation {
               type uint32;
               description "Layer 2 interface family creation time";
             }
             leaf l2iff-rt-index {
               type uint32;
               description "Routing instance to which the interface family belongs";
             }
             leaf l2iff-ifd-index {
               type uint32;
               description "Physical media to which the interface family belongs";
             }
             leaf l2iff-ifl-index {
               type uint32;
               description "Logical interface to which the interface family belongs";
             }
             leaf l2iff-af-value {
               type uint32;
               description "Address family to which the interface family belongs";
             }
             leaf l2iff-sequence-number {
               type uint32;
               description "Current interface family sequence number";
             }
             leaf l2iff-mac-sequence-number {
               type uint32;
               description "Current MAC address sequence number for this interface family";
             }
             leaf l2iff-macs-learned {
               type uint32;
               description "Number of configured static and dynamic MACs that are learned on this interface family";
             }
             leaf l2iff-config-smacs-learned {
               type uint32;
               description "Number of configured static MACs that are learned on this interface family";
             }
             leaf l2iff-non-config-smacs-learned {
               type uint32;
               description "Number of non configured static MACs that are learned on this interface family";
             }
             leaf l2iff-handle {
               type uint32;
               description "Handle associated with this interface family";
             }
             leaf l2iff-config-mac-limit {
               type uint32;
               description "Maximum number of MAC addresses that is configured on this interface family";
             }
             leaf l2iff-config-smac-count {
               type uint32;
               description "Number of static MAC addresses that is configured on this interface family";
             }
             leaf l2iff-config-smac-applied {
               type uint32;
               description "Number of static MAC addresses that is successfully applied to MAC DB on this interface family";
             }
             leaf l2iff-config-rtb-handle {
               type uint32;
               description "Handle for the routing instance for this IFL config";
             }
             leaf l2iff-config-state {
               type string;
               description "Configured state attributes associated with this interface family";
             }
             leaf l2iff-config-flags {
               type string;
               description "Configured attributes associated with this interface family";
             }
             leaf l2iff-config-previous-flags {
               type string;
               description "Previous configured attributes associated with this interface family";
             }
             leaf l2iff-config-smac-address {
               type mac-addr;
               description "Configured static media access control address associated with this interface family";
             }
             leaf l2iff-config-smac-vlan {
               type uint32;
               description "Configured VLAN ID for the static MAC associated with this interface family";
             }
             leaf l2iff-config-smac-flags {
               type string;
               description "Configured static MAC attributes associated with this interface family";
             }
             leaf l2iff-interface-type {
               type string;
               description "Type of interface (IFF/IFBD)";
             }
             leaf l2iff-rtsock-write-errors {
               type uint32;
               description "Number of times kernel write has failed.";
             }
             leaf l2iff-trunk-vlan {
               type uint32;
               description "Specify the incoming VLAN id which gets translated.";
             }
             leaf l2iff-rewrite-op {
               type string;
               description "Configured rewrite operation.";
             }
             leaf l2iff-vstp-index {
               type uint32;
               description "VSTP index";
             }
             leaf l2iff-ifbd-flags {
               type string;
               description "L2 learning level flags";
             }
             leaf l2iff-ifbd-mac-limit {
               type uint32;
               description "MAC limit for the IFBD";
             }
             leaf l2iff-rbeb-mac-address {
               type mac-addr;
               description "Media access control address of remote backbone edge bridge (BEB)";
             }
             leaf l2iff-time-before-expiry {
               type uint32;
               description "Time before object is deleted in seconds";
             }
           }
           container detail {
             leaf l2iff-ifl-name {
               type string;
               description "Logical interface name";
             }
             leaf l2iff-interface-type {
               type string;
               description "Type of interface (IFF/IFBD)";
             }
             leaf l2iff-handle {
               type uint32;
               description "Handle associated with this interface family";
             }
             leaf l2iff-index {
               type uint32;
               description "Interface family index";
             }
             leaf l2iff-generation {
               type uint32;
               description "Layer 2 interface family creation time";
             }
             leaf l2iff-trunk-vlan {
               type uint32;
               description "Specify the incoming VLAN id which gets translated.";
             }
             leaf l2iff-flags {
               type string;
               description "Attributes associated with this interface family";
             }
             leaf l2iff-sequence-number {
               type uint32;
               description "Current interface family sequence number";
             }
             leaf l2iff-mac-sequence-number {
               type uint32;
               description "Current MAC address sequence number for this interface family";
             }
             leaf l2iff-ifd-index {
               type uint32;
               description "Physical media to which the interface family belongs";
             }
             leaf l2iff-rt-index {
               type uint32;
               description "Routing instance to which the interface family belongs";
             }
             leaf l2iff-ifl-index {
               type uint32;
               description "Logical interface to which the interface family belongs";
             }
             leaf l2iff-af-value {
               type uint32;
               description "Address family to which the interface family belongs";
             }
             leaf l2iff-mac-limit {
               type uint32;
               description "Maximum number of MAC addresses that can be learned on this interface family";
             }
             leaf l2iff-macs-learned {
               type uint32;
               description "Number of configured static and dynamic MACs that are learned on this interface family";
             }
             leaf l2iff-config-smacs-learned {
               type uint32;
               description "Number of configured static MACs that are learned on this interface family";
             }
             leaf l2iff-non-config-smacs-learned {
               type uint32;
               description "Number of non configured static MACs that are learned on this interface family";
             }
             leaf l2iff-vstp-index {
               type uint32;
               description "VSTP index";
             }
             leaf l2iff-rewrite-op {
               type string;
               description "Configured rewrite operation.";
             }
             leaf l2iff-rbeb-mac-address {
               type mac-addr;
               description "Media access control address of remote backbone edge bridge (BEB)";
             }
             leaf l2iff-time-before-expiry {
               type uint32;
               description "Time before object is deleted in seconds";
             }
           }
           container extensive {
             leaf l2iff-config-mac-limit {
               type uint32;
               description "Maximum number of MAC addresses that is configured on this interface family";
             }
             leaf l2iff-config-smac-count {
               type uint32;
               description "Number of static MAC addresses that is configured on this interface family";
             }
             leaf l2iff-config-smac-applied {
               type uint32;
               description "Number of static MAC addresses that is successfully applied to MAC DB on this interface family";
             }
             leaf l2iff-config-rtb-handle {
               type uint32;
               description "Handle for the routing instance for this IFL config";
             }
             leaf l2iff-config-state {
               type string;
               description "Configured state attributes associated with this interface family";
             }
             leaf l2iff-config-flags {
               type string;
               description "Configured attributes associated with this interface family";
             }
             leaf l2iff-config-previous-flags {
               type string;
               description "Previous configured attributes associated with this interface family";
             }
             leaf l2iff-config-smac-address {
               type mac-addr;
               description "Configured static media access control address associated with this interface family";
             }
             leaf l2iff-config-smac-vlan {
               type uint32;
               description "Configured VLAN ID for the static MAC associated with this interface family";
             }
             leaf l2iff-config-smac-flags {
               type string;
               description "Configured static MAC attributes associated with this interface family";
             }
             leaf l2iff-rtsock-write-errors {
               type uint32;
               description "Number of times kernel write has failed.";
             }
           }
           container debuginfo {
             leaf l2iff-interface-type {
               type string;
               description "Type of interface (IFF/IFBD)";
             }
             leaf l2iff-ifl-name {
               type string;
               description "Logical interface name";
             }
             leaf l2iff-index {
               type uint32;
               description "Interface family index";
             }
             leaf l2iff-rt-index {
               type uint32;
               description "Routing instance to which the interface family belongs";
             }
             leaf l2iff-ifd-index {
               type uint32;
               description "Physical media to which the interface family belongs";
             }
             leaf l2iff-flags {
               type string;
               description "Attributes associated with this interface family";
             }
             leaf l2iff-mac-limit {
               type uint32;
               description "Maximum number of MAC addresses that can be learned on this interface family";
             }
           }
         }
       }
     }
   }
   rpc get-l2-learning-global-mac-count {
     description "Show layer-2 global mac address count";
     output {
       container l2ald-global-macdb-count {
         leaf global-mac-count {
           type uint64;
           description "Number of global media access control addresses";
         }
       }
     }
   }
   rpc get-l2-learning-global-information {
     description "Show process-related information";
     output {
       container l2ald-process-information {
         leaf l2ald-max-peers {
           type uint32;
           description "Maximum number of Layer 2 address learning service peers allowed";
         }
         leaf l2ald-rtm-retries {
           type uint32;
           description "Configured limit on retry attempts for asynchronous event processing";
         }
         leaf l2ald-rtm-mac-process {
           type uint32;
           description "Number of media access control entries processed in each batch";
         }
         leaf l2ald-move-threshold-count {
           type uint32;
           description "Number of moves that will be treated as threshold for rapid MAC address moves";
         }
         leaf l2ald-move-threshold-time {
           type uint32;
           description "Duration of time considered for monitoring the rapid MAC address move";
         }
         container l2ald-control-options {
           description "Control options configured for the media access control address learning process";
           leaf l2ald-control-flag {
             type uint32;
             description "Currently configured value of control flags";
           }
           leaf l2ald-fnh-module-status {
             type string;
             description "Status of flood next-hop module (enabled or disabled)";
           }
           leaf l2ald-mlrn-module-status {
             type string;
             description "Status of media access control address learning module (enabled or disabled)";
           }
           leaf l2ald-irb-module-status {
             type string;
             description "Status of integrated routing and bridging module (enabled or disabled)";
           }
           leaf l2ald-routing-table-owner-status {
             type string;
             description "Status of routing table manipulation by process (enabled or disabled)";
           }
           leaf l2ald-hardware-split-horizon-status {
             type string;
             description "Status of split-horizon in hardware (enabled or disabled)";
           }
           leaf l2ald-hardware-learning-status {
             type string;
             description "Status of hardware learning (enabled or disabled)";
           }
           leaf l2ald-fork-ui-status {
             type string;
             description "Status of forking for 'show' commands (enabled or disabled)";
           }
           leaf l2ald-lc-status {
             type string;
             description "Status of lc interfaces (enabled or disabled)";
           }
           leaf l2ald-stp-status {
             type string;
             description "Status of Spanning Tree Protocol (enabled or disabled)";
           }
         }
         container l2ald-global-configuration {
           description "Global configuration values for the the media access control address learning process";
           leaf l2ald-mac-aging-time {
             type uint32;
             description "Configured aging interval for media access control entries";
           }
           leaf l2ald-config-flag {
             type uint32;
             description "Show the global configuration flag value";
           }
           leaf l2ald-mac-learning-status {
             type string;
             description "Status of media access control address learning (enabled or disabled)";
           }
           leaf l2ald-hardware-mac-learning-status {
             type string;
             description "Status of media access control address learning in hardware (enabled or disabled)";
           }
           leaf l2ald-software-mac-learning-status {
             type string;
             description "Status of media access control address learning in software (enabled or disabled)";
           }
           leaf l2ald-statistics-status {
             type string;
             description "Status of statistics collection for media access control entries (enabled or disabled)";
           }
           leaf l2ald-interface-mac-limit-wm {
             type uint32;
             description "Watermark of Inteface MAC limit in percentage";
           }
           leaf l2ald-rtb-mac-limit-wm {
             type uint32;
             description "Watermark of Routing MAC limit in percentage";
           }
           leaf l2ald-mac-limit-wm {
             type uint32;
             description "Watermark of Global MAC limit in percentage";
           }
           leaf l2ald-interface-mac-limit-timeout {
             type uint32;
             description "Timeout value on Interface MAC limit in seconds";
           }
           leaf l2ald-rtb-mac-limit-timeout {
             type uint32;
             description "Timeout value on Routing instance MAC limit in seconds";
           }
           leaf l2ald-mac-limit-timeout {
             type uint32;
             description "Timeout value on Global MAC limit in seconds";
           }
           leaf l2ald-global-mac-limit {
             type string;
             description "Status of global mac limit (whether reached or not)";
           }
           leaf l2ald-sequence-number {
             type uint32;
             description "Count of global sequence number";
           }
           leaf l2ald-global-mbb-flag {
             type string;
             description "Status of make-before-break knob (enabled or disabled)";
           }
           leaf l2ald-global-packet-action-drop {
             type string;
             description "Status of packet action drop (enabled or disabled)";
           }
           leaf l2ald-global-mac-limit-count {
             type string;
             description "Count of number of MACs allowed globally in the system";
           }
           leaf l2ald-mac-learn-toggle-count {
             type uint32;
             description "Count of status changes for media access control address learning (between enabled and disabled)";
           }
           leaf l2ald-hardware-mac-learn-toggle-count {
             type uint32;
             description "Count of status changes for media access control address learning in hardware (between enabled and disabled)";
           }
           leaf l2ald-software-mac-learn-toggle-count {
             type uint32;
             description "Count of status changes for media access control address learning in software (between enabled and disabled)";
           }
           leaf l2ald-statistics-toggle-count {
             type uint32;
             description "Count of status changes for statistics collection on media access control entries (between enabled and disabled)";
           }
           leaf l2ald-config-smac-count {
             type uint32;
             description "Number of configured static MACs that are learned globally";
           }
           leaf l2ald-non-config-smac-count {
             type uint32;
             description "Number of non configured static MACs that are learned globally";
           }
           leaf l2ald-control-mac-aging-status {
             type string;
             description "Status of Control MAC aging (enabled or disabled)";
           }
           leaf l2ald-global-mp-discard-notification-interval {
             type uint32;
             description "Timer value for Mac Pinning discard notification interval";
           }
           container brief {
             description "Global configuration values for the the media access control address learning process";
             leaf l2ald-le-aging-time {
               type uint32;
               description "LE aging time";
             }
             leaf l2ald-le-bridge-domain-aging-time {
               type uint32;
               description "LE bridge-domain aging time";
             }
             leaf l2ald-gc-global-mode {
               type string;
               description "Global Mode";
             }
           }
           container detail {
             description "Global configuration values for the the media access control address learning process";
             leaf l2ald-mac-aging-time {
               type uint32;
               description "Configured aging interval for media access control entries";
             }
             leaf l2ald-config-flag {
               type uint32;
               description "Show the global configuration flag value";
             }
             leaf l2ald-mac-learning-status {
               type string;
               description "Status of media access control address learning (enabled or disabled)";
             }
             leaf l2ald-hardware-mac-learning-status {
               type string;
               description "Status of media access control address learning in hardware (enabled or disabled)";
             }
             leaf l2ald-software-mac-learning-status {
               type string;
               description "Status of media access control address learning in software (enabled or disabled)";
             }
             leaf l2ald-statistics-status {
               type string;
               description "Status of statistics collection for media access control entries (enabled or disabled)";
             }
             leaf l2ald-interface-mac-limit-wm {
               type uint32;
               description "Watermark of Inteface MAC limit in percentage";
             }
             leaf l2ald-rtb-mac-limit-wm {
               type uint32;
               description "Watermark of Routing MAC limit in percentage";
             }
             leaf l2ald-mac-limit-wm {
               type uint32;
               description "Watermark of Global MAC limit in percentage";
             }
             leaf l2ald-interface-mac-limit-timeout {
               type uint32;
               description "Timeout value on Interface MAC limit in seconds";
             }
             leaf l2ald-rtb-mac-limit-timeout {
               type uint32;
               description "Timeout value on Routing instance MAC limit in seconds";
             }
             leaf l2ald-mac-limit-timeout {
               type uint32;
               description "Timeout value on Global MAC limit in seconds";
             }
             leaf l2ald-global-mac-limit {
               type string;
               description "Status of global mac limit (whether reached or not)";
             }
             leaf l2ald-sequence-number {
               type uint32;
               description "Count of global sequence number";
             }
             leaf l2ald-global-mbb-flag {
               type string;
               description "Status of make-before-break knob (enabled or disabled)";
             }
             leaf l2ald-global-packet-action-drop {
               type string;
               description "Status of packet action drop (enabled or disabled)";
             }
             leaf l2ald-global-mac-limit-count {
               type string;
               description "Count of number of MACs allowed globally in the system";
             }
             leaf l2ald-mac-learn-toggle-count {
               type uint32;
               description "Count of status changes for media access control address learning (between enabled and disabled)";
             }
             leaf l2ald-hardware-mac-learn-toggle-count {
               type uint32;
               description "Count of status changes for media access control address learning in hardware (between enabled and disabled)";
             }
             leaf l2ald-software-mac-learn-toggle-count {
               type uint32;
               description "Count of status changes for media access control address learning in software (between enabled and disabled)";
             }
             leaf l2ald-statistics-toggle-count {
               type uint32;
               description "Count of status changes for statistics collection on media access control entries (between enabled and disabled)";
             }
             leaf l2ald-config-smac-count {
               type uint32;
               description "Number of configured static MACs that are learned globally";
             }
             leaf l2ald-non-config-smac-count {
               type uint32;
               description "Number of non configured static MACs that are learned globally";
             }
             leaf l2ald-control-mac-aging-status {
               type string;
               description "Status of Control MAC aging (enabled or disabled)";
             }
             leaf l2ald-global-mp-discard-notification-interval {
               type uint32;
               description "Timer value for Mac Pinning discard notification interval";
             }
           }
         }
       }
     }
   }
   rpc get-l2-learning-routing-instances {
     description "Show routing instances";
     input {
       leaf instance-name {
         description "Display information for a specified instance";
         default "all";
         type string;
       }
       leaf bridge-domain {
         description "Particular bridge-domain or 'all'";
         default "all";
         type string;
       }
       leaf ifbd {
         description "Display information for ifbds under bd";
         type enumeration {
           enum "all" {
             description "Display all IFBDs";
           }
         }
       }
     }
     output {
       container l2ald-routing-table-information {
         container l2ald-rtb-entry {
           container brief {
             leaf l2rtb-instance-type {
               type string;
               description "Type of instance (routing instance/bridge domain)";
             }
             leaf l2rtb-logical-system {
               type string;
               description "Logical system name";
             }
             leaf l2rtb-name {
               type string;
               description "Name of the routing instance";
             }
             leaf l2rtb-bridging-domain {
               type string;
               description "Name of the bridging domain";
             }
             leaf l2rtb-id {
               type uint32;
               description "Routing instance identifier";
             }
             leaf l2rtb-l2irb-ifl-index {
               type uint32;
             }
             leaf l2rtb-flags {
               type string;
               description "Attributes associated with this routing instance";
             }
             leaf l2bd-vlan-id {
               type string;
               description "Bridge domain VLAN";
             }
           }
           container extensive {
             leaf l2rtb-logical-system {
               type string;
               description "Logical system name";
             }
             leaf l2rtb-name {
               type string;
               description "Name of the routing instance";
             }
             leaf l2rtb-bridging-domain {
               type string;
               description "Name of the bridging domain";
             }
             leaf l2rtb-id {
               type uint32;
               description "Routing instance identifier";
             }
             leaf l2bd-id {
               type uint32;
               description "Bridge domain identifier";
             }
             leaf l2bd-generation {
               type uint32;
               description "Bridge domain generation identifier";
             }
             leaf l2rtb-mac-limit {
               type uint32;
               description "Maximum number of MAC addresses that can be learned on this routing instance";
             }
             leaf l2rtb-macs-learned {
               type uint32;
               description "Number of configured static and dynamic MACs that are learned on this routing instance";
             }
             leaf l2rtb-config-smacs-learned {
               type uint32;
               description "Number of configured static MACs that are learned on this routing instance";
             }
             leaf l2rtb-non-config-smacs-learned {
               type uint32;
               description "Number of non configured static MACs that are learned on this routing instance";
             }
             leaf l2rtb-irb-interface {
               type string;
               description "Name of the IRB interface associated with this routing instance";
             }
             leaf l2rtb-irb-interface-index {
               type uint32;
               description "IRB interface index associated with this routing instance";
             }
             leaf l2rtb-sequence-number {
               type uint32;
               description "Current routing instance sequence number";
             }
             leaf l2rtb-handle {
               type uint32;
               description "Handle associated with this routing instance";
             }
             leaf l2bd-vlan-id {
               type string;
               description "Bridge domain VLAN";
             }
             leaf l2rtb-flags {
               type string;
               description "Attributes associated with this routing instance";
             }
             leaf l2rtb-peer-pbbn-rtb-id {
               type uint32;
               description "Peer PBBN RTB index";
             }
             leaf l2rtb-configured-service-id {
               type uint32;
               description "Configured Service-id attributes associated with this routing instance";
             }
             leaf l2rtb-active-service-id {
               type uint32;
               description "Service-id attributes associated with this routing instance/bridge domain";
             }
             leaf l2rtb-config-bd-vlan {
               type string;
               description "Vlan configured for the givn bridge domain on routing instance";
             }
             leaf l2rtb-config-operation {
               type string;
               description "Configuration notify operation on bridge domain/routing instance";
             }
             leaf l2rtb-config-smac-count {
               type uint32;
               description "Configured Static MAC on the BD";
             }
             leaf l2rtb-config-params {
               type string;
               description "Configured attributes associated with this routing instance/bridge domain";
             }
             leaf l2rtb-config-flags {
               type string;
               description "Configured flags associated with this routing instance/bridge domain";
             }
             leaf l2rtb-configured-rg-id {
               type uint32;
               description "Config Redundancy Group ID";
             }
             leaf l2rtb-active-rg-id {
               type uint32;
               description "Active Redundancy Group ID";
             }
             leaf l2rtb-configured-bd-service-id {
               type uint32;
               description "Configured Service-id attributes associated with this bridge domain";
             }
             leaf l2rtb-active-bd-service-id {
               type uint32;
               description "Service-id attributes associated with this bridge domain";
             }
             leaf l2rtb-configured-bd-vnid {
               type uint32;
               description "Configured VXLAN identifier";
             }
             leaf l2rtb-active-bd-vnid {
               type uint32;
               description "Active VXLAN identifier";
             }
             leaf l2rtb-configured-bd-vxgrp {
               type string;
               description "Configured VXLAN multicast group IP address";
             }
             leaf l2rtb-active-bd-vxgrp {
               type string;
               description "Active VXLAN multicast group IP address";
             }
             leaf l2rtb-configured-decap-accept-inner-vlan {
               type uint32;
               description "Configured VXLAN Decap accept inner vlan";
             }
             leaf l2rtb-configured-encap-inner-vlan {
               type uint32;
               description "Configured VXLAN Encap inner vlan";
             }
             leaf l2rtb-configured-unreachable-rvtep-timer {
               type uint32;
               description "Configured VXLAN Unreachable rvtep timer";
             }
             leaf l2rtb-configured-ovsdb-enabled {
               type string;
               description "Configured VXLAN OVSDB Enabled";
             }
             leaf l2rtb-active-bd-l3rtt {
               type uint32;
               description "Active VXLAN Layer-3 routing instance index";
             }
             leaf l2rtb-active-bd-svtep-ip {
               type string;
               description "Active VXLAN source tunnel endpoint IP address";
             }
             leaf l2rtb-config-ownership-flags {
               type string;
               description "Configured ownership flags on attributes associated with this routing instance/bridge domain";
             }
             leaf l2rtb-ownership-flags {
               type string;
               description "Kernel ownership flags on attributes associated with this routing instance";
             }
             leaf l2rtb-config-mvrp-ref-count {
               type uint32;
               description " Number of join count on the bridge domain";
             }
             leaf l2rtb-rtsock-write-errors {
               type uint32;
               description "Number of times kernel write has failed.";
             }
           }
         }
       }
     }
   }
   rpc get-l2-learning-provider-instance {
     description "Show provider instance (I-component)";
     input {
       leaf instance {
         description "Display information for a specified instance";
         default "all";
         type string;
       }
       leaf bridge-domain {
         description "Display information for a specified bridge domain";
         status deprecated;
         default "all";
         type string;
       }
       leaf bridge-domain-name {
         description "Display information for a specified bridge domain";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf isid {
         description "Display Information for specified ISID or all ISID(s)";
         type string;
       }
     }
   }
   rpc get-l2-learning-backbone-instance {
     description "Show provider backbone instance (B-component)";
     input {
       leaf instance {
         description "Display information for a specified instance";
         default "all";
         type string;
       }
       leaf bridge-domain {
         description "Display information for a specified bridge domain";
         status deprecated;
         default "all";
         type string;
       }
       leaf bridge-domain-name {
         description "Display information for a specified bridge domain";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf isid {
         description "Display Information for specified ISID or all ISID(s)";
         type string;
       }
     }
     output {
       container l2ald-pbn {
         container l2ald-pbn-entry-common {
           container brief {
             leaf l2pbn-logical-system {
               type string;
               description "Logical system name";
             }
             leaf l2pbn-rtb {
               type string;
               description "Name of the routing instance(I-Component)";
             }
           }
           container detail {
             leaf l2pbn-logical-system {
               type string;
               description "Logical system name";
             }
           }
         }
         container l2ald-pbn-entry {
           container brief {
             leaf l2pbn-pbn-bd {
               type string;
               description "I-Component bridging domain";
             }
             leaf l2pbn-svlan {
               type string;
               description "Service Provider bridge vlan(S-VLAN)";
             }
             leaf l2pbn-isid {
               type uint32;
               description "Service Provider I-tag(ISID)";
             }
             leaf l2pbn-sbmac {
               type string;
               description "Source B-MAC address";
             }
             leaf l2pbn-pbbn-bd {
               type string;
               description "B-Component bridging domain";
             }
             leaf l2pbn-bvlan {
               type string;
               description "Backbone bridge vlan(B-VLAN)";
             }
             leaf l2pbn-flags {
               type string;
               description "Attributes of this Service Instance I-tag";
             }
             leaf l2pbn-logical-system {
               type string;
               description "Logical system name";
             }
             leaf l2pbn-bridging-domain {
               type string;
               description "I-Component bridging domain";
             }
           }
           container detail {
             leaf l2pbn-rtb {
               type string;
               description "Name of the routing instance(I-Component)";
             }
             leaf l2pbn-rtb-bb {
               type string;
               description "Name of the routing instance(B-Component)";
             }
             leaf l2pbn-pbn-bd {
               type string;
               description "I-Component bridging domain";
             }
             leaf l2pbn-pbbn-bd {
               type string;
               description "B-Component bridging domain";
             }
             leaf l2pbn-pbn-bd-index {
               type uint32;
               description "BD Index of I-Component bridging domain";
             }
             leaf l2pbn-pbbn-bd-index {
               type uint32;
               description "BD Index of B-Component bridging domain";
             }
             leaf l2pbn-svlan {
               type string;
               description "Service Provider bridge vlan(S-VLAN)";
             }
             leaf l2pbn-bvlan {
               type string;
               description "Backbone bridge vlan(B-VLAN)";
             }
             leaf l2pbn-generation {
               type uint32;
               description "Backbone connectivity establishment time";
             }
             leaf l2pbn-isid {
               type uint32;
               description "Service Provider I-tag(ISID)";
             }
             leaf l2pbn-sequence-number {
               type uint32;
               description "Backbone connectivity establishment sequence number";
             }
             leaf l2pbn-handle {
               type uint32;
               description "Handle associated with this PBN's connectivity to PBBN";
             }
             leaf l2pbn-flags {
               type string;
               description "Attributes of this Service Instance I-tag";
             }
             leaf l2pbn-mac-address {
               type string;
               description "Remote BEB Mac address";
             }
             leaf l2pbn-logical-system {
               type string;
               description "Logical system name";
             }
             leaf l2pbn-bridging-domain {
               type string;
               description "I-Component bridging domain";
             }
           }
         }
       }
     }
   }
   rpc get-l2-learning-remote-backbone-edge-bridges {
     description "Show remote backbone edge bridges in a PBBN network";
     input {
       leaf remote-beb-mac-address {
         description "Remote backbone edge bridge MAC address";
         default "all";
         type mac-addr;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
     }
     output {
       container l2ald-rbeb-information {
         container l2ald-rbeb-entry {
           container brief {
             leaf l2-rbeb-logical-system {
               type string;
               description "PBBN Logical system name where remote backbone edge bridges were identified";
             }
             leaf l2-rbeb-routing-instance {
               type string;
               description "PBBN Routing instance where remote backbone edge bridges were identified";
             }
             leaf l2-rbeb-mac-address {
               type mac-addr;
               description "Remote backbone edge bridge's media access control address";
             }
             leaf l2-rbeb-time-left-sec {
               type uint32;
               description "Time in seconds left before backbone edge bridge next-hop is deleted";
             }
             leaf l2-rbeb-time-left-msec {
               type uint32;
               description "Time in milli-seconds left before backbone edge bridge next-hop is deleted";
             }
             leaf l2-rbeb-flags {
               type string;
               description "Remote backbone edge bridge flags";
             }
             leaf l2-rbeb-reference-count {
               type uint32;
               description "Remote backbone edge bridge reference count";
             }
           }
           container detail {
             leaf l2-rbeb-logical-system {
               type string;
               description "PBBN Logical system name where remote backbone edge bridges were identified";
             }
             leaf l2-rbeb-routing-instance {
               type string;
               description "PBBN Routing instance where remote backbone edge bridges were identified";
             }
             leaf l2-rbeb-le-index {
               type uint32;
               description "Remote backbone edge bridge's system index";
             }
             leaf l2-rbeb-mac-address {
               type mac-addr;
               description "Remote backbone edge bridge's media access control address";
             }
             leaf l2-rbeb-time-left-sec {
               type uint32;
               description "Time in seconds left before backbone edge bridge next-hop is deleted";
             }
             leaf l2-rbeb-time-left-msec {
               type uint32;
               description "Time in milli-seconds left before backbone edge bridge next-hop is deleted";
             }
             leaf l2-rbeb-flags {
               type string;
               description "Remote backbone edge bridge flags";
             }
             leaf l2-rbeb-state-flags {
               type string;
               description "Remote backbone edge bridge state flags";
             }
             leaf l2-rbeb-reference-count {
               type uint32;
               description "Remote backbone edge bridge reference count";
             }
           }
         }
       }
     }
   }
   rpc get-l2-learning-redundancy-groups {
     description "Show redundancy-groups";
     input {
       leaf logical-system {
         description "Name of logical system";
         type string {
           junos:posix-pattern "^[a-zA-Z0-9_-]{1,63}$";
           junos:pattern-message "Logical-system name is a string consisting of up to 63 letters, numbers, dashes and underscores";
         }
       }
       leaf redundancy-group-id {
         description "Display information for a specified RG";
         default "0";
         type uint32 {
           range "0 .. 4294967294";
         }
       }
       leaf options {
         description "Display information for specified RG or all RG(s)";
         type enumeration {
           enum "remote-macs" {
             description "Display MAC for all RG(s)";
           }
           enum "arp-statistics" {
             description "Show MCAE ARP Synchronization statistics";
           }
           enum "nd-statistics" {
             description "Show MCAE ND synchronization statistics";
           }
           enum "remote-irb-ifas" {
             description "Show MCLAG Remote IRB IFAs";
           }
           enum "local-irb-ifas" {
             description "Show MCLAG Locally Syned IRB IFAs";
           }
         }
       }
     }
     output {
       container l2ald-mc-ae-rg-entry {
         container brief {
           leaf logical-system-name {
             type string;
             description "Logical System";
           }
           leaf l2ald-mc-ae-rg-id {
             type uint32;
             description "Redundancy Group ID";
           }
           leaf l2ald-mc-ae-rg-flags {
             type string;
             description "Redundancy Group Flags";
           }
         }
         container detail {
           leaf logical-system-name {
             type string;
             description "Logical System";
           }
           leaf l2ald-mc-ae-rg-id {
             type uint32;
             description "Redundancy Group ID";
           }
           leaf l2ald-mc-ae-rg-flags {
             type string;
             description "Redundancy Group Flags";
           }
           leaf l2ald-mc-ae-rg-ref-count {
             type uint32;
             description "Redundancy reference count";
           }
           leaf l2ald-mc-ae-rg-disconnect-count {
             type uint32;
             description "Redundancy group disconnect count";
           }
           leaf l2ald-mc-ae-rg-tx-count {
             type uint32;
             description "Redundancy MAC tx count";
           }
           leaf l2ald-mc-ae-rg-rx-count {
             type uint32;
             description "Redundancy MAC rx count";
           }
         }
       }
     }
   }
   rpc get-l2-learning-nh-learn-entries {
     description "Display information on all RNH_LE entries";
     output {
       container l2ald-nh-learn-entity {
         container evpn-format {
           leaf l2rtt-name {
             type string;
             description "Routing instance";
           }
           leaf l2-nh-learn-router-id {
             type uint32;
             description "Router ID (Indirect NH ID)";
           }
           leaf l2-nh-learn-index {
             type uint32;
             description "RNH LE nexthop index";
           }
           leaf l2-mh-ifl-name {
             type string;
             description "Multi-homed IFL name";
           }
           leaf interface-esi {
             type string;
             description "ESI";
           }
         }
       }
     }
   }
   rpc get-l2-learning-vxlan-svtep-info {
     description "Display source VXLAN tunnel endpoint configuration";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
     }
   }
   rpc get-l2-learning-vxlan-svtep-ip-information {
     description "Display VXLAN configuration for source ip address";
     input {
       leaf virtual-tunnel-end-point-source-ip {
         description "Display information for a source ip";
         type ipaddr;
         mandatory true;
       }
     }
   }
   rpc get-l2-learning-vxlan-rvtep-info {
     description "Display remote VXLAN tunnel endpoint information";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
     }
   }
   rpc get-l2-learning-vxlan-rvtep-mactable-information {
     description "Display remote VTEP MAC table";
   }
   rpc get-l2-learning-vxlan-remote-svtep-ip-information {
     description "Display remote VXLAN endpoints associated with source endpoint";
     input {
       leaf virtual-tunnel-end-point-source-ip {
         description "Display information for a source ip";
         type ipaddr;
         mandatory true;
       }
     }
   }
   rpc get-l2-learning-vxlan-rvtep-ip-information {
     description "Display remote VTEP MAC table for ip address";
     input {
       leaf virtual-tunnel-end-point-remote-ip {
         description "Display information for a remote end point";
         type ipaddr;
         mandatory true;
       }
     }
   }
   rpc get-l2-learning-vxlan-esi-info {
     description "Display VXLAN tunnel endpoint ESI information";
   }
   rpc get-evpn-arp-statistics {
     description "EVPN arp statistics for irb interfaces";
     input {
       leaf instance {
         description "Display information for a specified instance";
         default "all";
         type string;
       }
       leaf bridge-domain {
         description "Name of bridging domain, or 'all'";
         default "all";
         type string;
       }
     }
     output {
       container l2rtb-evpn-arp-statistics {
         container l2rtb-evpn-arp-statistics-entry {
           leaf interface-name {
             type string;
             description "Bridging media access control address interface";
           }
           leaf l2rtb-name {
             type string;
             description "Name of the routing instance";
           }
           leaf bd-name {
             type string;
             description "Bridging media access control address count for bridge-domain";
           }
           leaf arp-add-count {
             type uint32;
             description "Number of arp route adds received from local interfaces";
           }
           leaf arp-delete-count {
             type uint32;
             description "Number of arp route deletes received from local interfaces";
           }
           leaf arp-drop-count {
             type uint32;
             description "Number of arps dropped";
           }
           leaf arp-sent-count {
             type uint32;
             description "Number of arps sent to EVPN peer device";
           }
         }
       }
     }
   }
   rpc get-evpn-arp-statistics-interface {
     description "Display information for irb interfaces";
     input {
       container interface-choice {
         choice interface-choice_c {
           case interface-name {
             leaf interface-name {
               description "Name of the irb interface";
               type string;
             }
           }
           case all {
             leaf all {
               description "All irb interfaces";
               type empty;
             }
           }
         }
       }
     }
   }
   rpc get-evpn-nd-statistics {
     description "EVPN ND statistics for irb interfaces";
     input {
       leaf instance {
         description "Display information for a specified instance";
         default "all";
         type string;
       }
       leaf bridge-domain {
         description "Name of bridging domain, or 'all'";
         default "all";
         type string;
       }
     }
     output {
       container l2rtb-evpn-nd-statistics {
         container l2rtb-evpn-nd-statistics-entry {
           leaf interface-name {
             type string;
             description "Bridging media access control address interface";
           }
           leaf l2rtb-name {
             type string;
             description "Name of the routing instance";
           }
           leaf bd-name {
             type string;
             description "Bridging media access control address count for bridge-domain";
           }
           leaf nd-add-count {
             type uint32;
             description "Number of nd route adds received from local interfaces";
           }
           leaf nd-delete-count {
             type uint32;
             description "Number of nd route deletes received from local interfaces";
           }
           leaf nd-drop-count {
             type uint32;
             description "Number of nds dropped";
           }
           leaf nd-sent-count {
             type uint32;
             description "Number of nds sent to EVPN peer device";
           }
         }
       }
     }
   }
   rpc get-evpn-nd-statistics-interface {
     description "Display information for irb interfaces";
     input {
       container interface-choice {
         choice interface-choice_c {
           case interface-name {
             leaf interface-name {
               description "Name of the irb interface";
               type string;
             }
           }
           case all {
             leaf all {
               description "All irb interfaces";
               type empty;
             }
           }
         }
       }
     }
   }
 }
