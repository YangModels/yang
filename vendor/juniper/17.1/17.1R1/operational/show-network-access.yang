/*
 * Copyright (c) 2017 Juniper Networks, Inc.
 * All rights reserved.
 */

 module show-network-access {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-authentication-pending-table {
     description "Show pending authentication requests";
     input {
       container filter {
         choice filter_c {
           case detail {
             leaf get-authentication-pending-table-detailed {
               description "Show the detailed information";
               type empty;
             }
           }
           case index {
             leaf get-authentication-pending-table-specific {
               description "Show detail information for a specific request";
               type uint64 {
                 range "1 .. 18446744073709551615";
               }
             }
           }
         }
       }
     }
   }
   rpc get-authentication-statistics {
     description "Show authentication statistics";
     output {
       container auth-statistics {
         container total-statistics {
           leaf total-requests {
             type uint32;
             description "Number of authentication requests received";
           }
           leaf total-responses {
             type uint32;
             description "Number of authentication requests replied to";
           }
         }
         container radius-auth-statistics {
           leaf total-requests {
             type uint32;
             description "Number of authentication requests received";
           }
           leaf success-responses {
             type uint32;
             description "Number of succeeded authentication requests";
           }
           leaf failure-responses {
             type uint32;
             description "Number of failed authentication requests";
           }
         }
         container ldap-auth-statistics {
           leaf total-requests {
             type uint32;
             description "Number of authentication requests received";
           }
           leaf success-responses {
             type uint32;
             description "Number of succeeded authentication requests";
           }
           leaf failure-responses {
             type uint32;
             description "Number of failed authentication requests";
           }
         }
         container securid-auth-statistics {
           leaf total-requests {
             type uint32;
             description "Number of authentication requests received";
           }
           leaf success-responses {
             type uint32;
             description "Number of succeeded authentication requests";
           }
           leaf failure-responses {
             type uint32;
             description "Number of failed authentication requests";
           }
         }
         container local-auth-statistics {
           leaf total-requests {
             type uint32;
             description "Number of authentication requests received";
           }
           leaf success-responses {
             type uint32;
             description "Number of succeeded authentication requests";
           }
           leaf failure-responses {
             type uint32;
             description "Number of failed authentication requests";
           }
         }
       }
     }
   }
   rpc get-domain-map-statistics {
     description "Domain-map module statistics";
     output {
       container domain-map-statistics {
         leaf matched-domains {
           type uint32;
           description "The parsed domain name matched a configured domain";
         }
         leaf unmatched-domains {
           type uint32;
           description "The parsed domain name did not match any configured domains";
         }
         leaf missing-domains {
           type uint32;
           description "The username is missing the domain portion";
         }
         leaf stripped-username {
           type uint32;
           description "The domain portion was stripped from the username string";
         }
         leaf stripped-domain {
           type uint32;
           description "The user portion was stripped for authentication only";
         }
         leaf default-used {
           type uint32;
           description "Domain name of default was used for the mapping";
         }
       }
     }
   }
   rpc get-aaa-subscriber-table {
     description "List subscriber specific command options";
     input {
       leaf username {
         description "Show details for this subscriber's session entry";
         type string;
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
   }
   rpc get-aaa-subscriber-statistics {
     description "Statistics on subscriber events";
     input {
       leaf username {
         description "Show statistics for this subscriber's session entry";
         type string;
         mandatory true;
       }
     }
   }
   rpc get-aaa-module-statistics {
     description "(Re)authentication, authorization and accounting (AAA) module statistics";
     input {
       leaf statistics-type {
         type enumeration {
           enum "authentication" {
             description "Authentication statistics";
           }
           enum "accounting" {
             description "Accounting statistics";
           }
           enum "dynamic-requests" {
             description "Dynamic requests statistics";
           }
           enum "re-authentication" {
             description "Re-authentication statistics";
           }
           enum "preauthentication" {
             description "Preauthentication statistics";
           }
           enum "subscribers" {
             description "Subscriber statistics";
           }
           enum "radius" {
             description "RADIUS statistics";
           }
           enum "pending-accounting-stops" {
             description "Pending Accouting stop statistics";
           }
         }
         mandatory true;
       }
       leaf detail {
         description "Display detailed output";
         type empty;
       }
     }
     output {
       container aaa-module-statistics {
         leaf requests {
           type uint32;
           description "Number of requests received";
         }
         leaf multistack-requests {
           type uint32;
           description "Number of multistack requests received";
         }
         leaf accepts {
           type uint32;
           description "Number of authentication accepts";
         }
         leaf rejects {
           type uint32;
           description "Number of authentication rejects";
         }
         leaf radius-failures {
           type uint32;
           description "Number of RADIUS authentication failures";
         }
         leaf rejects-queue-request-deleted {
           type uint32;
           description "Number of authentication rejects due to queue request deleted";
         }
         leaf rejects-malformed-reply {
           type uint32;
           description "Number of authentication rejects due to malformed reply";
         }
         leaf rejects-no-server-configured {
           type uint32;
           description "Number of authentication rejects due to no servers configured";
         }
         leaf rejects-access-profile-config-unavailable {
           type uint32;
           description "Number of authentication rejects due to unavailable access profile configuration";
         }
         leaf rejects-no-client-record {
           type uint32;
           description "Number of authentication rejects due to failure to create client record";
         }
         leaf rejects-no-client-request {
           type uint32;
           description "Number of authentication rejects due to failure to create client request";
         }
         leaf rejects-no-build-auth-request {
           type uint32;
           description "Number of authentication rejects due to failure to build authentication request";
         }
         leaf rejects-no-server {
           type uint32;
           description "Number of authentication rejects due to failure to find server";
         }
         leaf rejects-no-create-handle {
           type uint32;
           description "Number of authentication rejects due to failure to create handle";
         }
         leaf rejects-no-queue-request {
           type uint32;
           description "Number of authentication rejects due to failure to queue request";
         }
         leaf rejects-invalid-credentials {
           type uint32;
           description "Number of authentication rejects due to invalid credentials";
         }
         leaf rejects-internal-failure {
           type uint32;
           description "Number of authentication rejects due to internal failure";
         }
         leaf rejects-malformed-request {
           type uint32;
           description "Number of authentication rejects due to malformed request";
         }
         leaf rejects-license-unavailable {
           type uint32;
           description "Number of authentication rejects due to license unavailable";
         }
         leaf rejects-redirect-requested {
           type uint32;
           description "Number of authentication rejects due to redirect requested";
         }
         leaf local-failures {
           type uint32;
           description "Number of local authentication failures";
         }
         leaf ldap-failures {
           type uint32;
           description "Number of LDAP lookup failures";
         }
         leaf accounting-request-failures {
           type uint32;
           description "Number of accounting requests failed to be sent out";
         }
         leaf accounting-request-success {
           type uint32;
           description "Number of accounting requests sent out sucessfully";
         }
         leaf timeouts {
           type uint32;
           description "Number of requests timed out";
         }
         leaf accounting-response-failures {
           type uint32;
           description "Number of accounting response failures";
         }
         leaf accounting-response-success {
           type uint32;
           description "Number of successful accounting responses";
         }
         leaf acct-unknown-responses {
           type uint32;
           description "Number of unknown accounting responses received";
         }
         leaf acct-requests-pending {
           type uint32;
           description "Number of pending account requests sent";
         }
         leaf acct-malformed-responses {
           type uint32;
           description "Number of malformed accounting responses received";
         }
         leaf acct-retransmissions {
           type uint32;
           description "Number of accounting retransmissions";
         }
         leaf acct-bad-authenticators {
           type uint32;
           description "Number of bad accounting authenticators";
         }
         leaf acct-packets-dropped {
           type uint32;
           description "Number of accounting packets dropped because not supported for config";
         }
         leaf acct-acct-on-requests {
           type uint32;
           description "Number of account on requests sent";
         }
         leaf acct-start-requests {
           type uint32;
           description "Number of accounting start requests sent";
         }
         leaf acct-interim-requests {
           type uint32;
           description "Number of accounting interim requests sent";
         }
         leaf acct-stop-requests {
           type uint32;
           description "Number of accounting stop requests sent";
         }
         leaf acct-rollover-requests {
           type uint32;
           description "Number of accounting requests that rollover to another server due to timeout/maxout";
         }
         leaf acct-acct-on-responses {
           type uint32;
           description "Number of accounting on responses received";
         }
         leaf acct-start-responses {
           type uint32;
           description "Number of accounting start responses received";
         }
         leaf acct-interim-responses {
           type uint32;
           description "Number of accounting interim responses received";
         }
         leaf acct-stop-responses {
           type uint32;
           description "Number of accounting stop responses received";
         }
         leaf multistack-suppressions {
           type uint32;
           description "Number of multistack requests suppressed";
         }
         leaf challenges {
           type uint32;
           description "Number of authentication challenges";
         }
         leaf processed-ok {
           type uint32;
           description "Number of requests successfully processed";
         }
         leaf processed-initial {
           type uint32;
           description "Number of requests initially processed successfully";
         }
         leaf processing-error {
           type uint32;
           description "Number of requests unsuccessfully processed";
         }
         leaf silent-drops {
           type uint32;
           description "Number of requests silently dropped";
         }
         leaf internal-errors {
           type uint32;
           description "Number of internal errors";
         }
         leaf aborts {
           type uint32;
           description "Number of abort requests";
         }
         leaf interim-updates-rcvd {
           type uint32;
           description "Number of interim updates received from libstats";
         }
         leaf interim-updates-sent {
           type uint32;
           description "Number of interim updates sent to radius";
         }
         leaf interim-updates-error-rcvd {
           type uint32;
           description "Number of interim error callbacks received";
         }
         leaf requested-final-stats {
           type uint32;
           description "Number of final stats requested from libstats";
         }
         leaf final-stats-retry-count {
           type uint32;
           description "Number of final stats retried";
         }
         leaf final-stats-rcvd {
           type uint32;
           description "Number of final stats updates received";
         }
         leaf final-stats-error-rcvd {
           type uint32;
           description "Number of final stats errors received";
         }
         leaf final-stats-sent {
           type uint32;
           description "Number of final stats sent to radius";
         }
         leaf time-only-info-sent {
           type uint32;
           description "Number of time info only stops sent";
         }
         leaf stats-timer-fired {
           type uint32;
           description "Number of times the accounting stats timer fired";
         }
         leaf libstats-interim-egress-subs {
           type uint32;
           description "Interim egress subs";
         }
         leaf libstats-interim-ingress-subs {
           type uint32;
           description "Interim ingress subs";
         }
         leaf libstats-interim-egress-general-error {
           type uint32;
           description "Interim egress general error";
         }
         leaf libstats-interim-ingress-general-error {
           type uint32;
           description "Interim ingress general error";
         }
         leaf libstats-interim-egress-kernel-error {
           type uint32;
           description "Interim egress kernel error";
         }
         leaf libstats-interim-ingress-kernel-error {
           type uint32;
           description "Interim ingress kernel error";
         }
         leaf libstats-interim-egress-memory-error {
           type uint32;
           description "Interim egress memory error";
         }
         leaf libstats-interim-ingress-memory-error {
           type uint32;
           description "Interim ingress memory error";
         }
         leaf libstats-interim-egress-ipc-error {
           type uint32;
           description "Interim egress IPC error";
         }
         leaf libstats-interim-ingress-ipc-error {
           type uint32;
           description "Interim ingress IPC error";
         }
         leaf libstats-interim-egress-validation-error {
           type uint32;
           description "Interim egress validation error";
         }
         leaf libstats-interim-ingress-validation-error {
           type uint32;
           description "Interim ingress validation error";
         }
         leaf libstats-interim-egress-db-lookup-error {
           type uint32;
           description "Interim egress db lookup error";
         }
         leaf libstats-interim-ingress-db-lookup-error {
           type uint32;
           description "Interim ingress db lookup error";
         }
         leaf libstats-final-egress-subs {
           type uint32;
           description "Final egress subs";
         }
         leaf libstats-final-ingress-subs {
           type uint32;
           description "Final ingress subs";
         }
         leaf libstats-final-egress-general-error {
           type uint32;
           description "Final egress general error";
         }
         leaf libstats-final-ingress-general-error {
           type uint32;
           description "Final ingress general error";
         }
         leaf libstats-final-egress-kernel-error {
           type uint32;
           description "Final egress kernel error";
         }
         leaf libstats-final-ingress-kernel-error {
           type uint32;
           description "Final ingress kernel error";
         }
         leaf libstats-final-egress-memory-error {
           type uint32;
           description "Final egress memory error";
         }
         leaf libstats-final-ingress-memory-error {
           type uint32;
           description "Final ingress memory error";
         }
         leaf libstats-final-egress-ipc-error {
           type uint32;
           description "Final egress IPC error";
         }
         leaf libstats-final-ingress-ipc-error {
           type uint32;
           description "Final ingress IPC error";
         }
         leaf libstats-final-egress-validation-error {
           type uint32;
           description "Final egress validation error";
         }
         leaf libstats-final-ingress-validation-error {
           type uint32;
           description "Final ingress validation error";
         }
         leaf libstats-final-egress-db-lookup-error {
           type uint32;
           description "Final egress DB lookup error";
         }
         leaf libstats-final-ingress-db-lookup-error {
           type uint32;
           description "Final ingress DB lookup error";
         }
         leaf libstats-all-egress-msg-types {
           type uint32;
           description "All egress message types";
         }
         leaf libstats-all-ingress-msg-types {
           type uint32;
           description "All ingress message types";
         }
         leaf libstats-all-egress-general-error {
           type uint32;
           description "All egress general error";
         }
         leaf libstats-all-ingress-general-error {
           type uint32;
           description "All ingress general error";
         }
         leaf libstats-all-egress-kernel-error {
           type uint32;
           description "All egress kernel error";
         }
         leaf libstats-all-ingress-kernel-error {
           type uint32;
           description "All ingress kernel error";
         }
         leaf libstats-all-egress-memory-error {
           type uint32;
           description "All egress memory error";
         }
         leaf libstats-all-ingress-memory-error {
           type uint32;
           description "All ingress memory error";
         }
         leaf libstats-all-egress-ipc-error {
           type uint32;
           description "All egress IPC error";
         }
         leaf libstats-all-ingress-ipc-error {
           type uint32;
           description "All ingress IPC error";
         }
         leaf libstats-all-egress-validation-error {
           type uint32;
           description "All egress validation error";
         }
         leaf libstats-all-ingress-validation-error {
           type uint32;
           description "All ingress validation error";
         }
         leaf libstats-all-egress-db-lookup-error {
           type uint32;
           description "All egress DB lookup error";
         }
         leaf libstats-all-ingress-db-lookup-error {
           type uint32;
           description "All ingress DB lookup error";
         }
         leaf pending-acct-stops {
           type uint32;
           description "Number of requests received";
         }
         leaf acct-backup-record-creation-requests {
           type uint32;
           description "Number of backup records creation requests sent to backup accounting module";
         }
         leaf acct-backup-radius-retransmissions {
           type uint32;
           description "Number of radius retries sent in backup context";
         }
         leaf acct-backup-request-timeouts {
           type uint32;
           description "Number of backup requests that timed out";
         }
         leaf acct-backup-request-failures {
           type uint32;
           description "Number of backup requests that encountered an error";
         }
         leaf acct-backup-request-success {
           type uint32;
           description "Number of backup requests that were success";
         }
         leaf acct-backup-request-replay-success {
           type uint32;
           description "Number of backup requests that were reconstructed successfully during replay";
         }
         leaf acct-backup-radius-pending-request {
           type uint32;
           description "Number of Backup requests sent to radius server but yet to receive response or error";
         }
         leaf acct-backup-in-flight-requests {
           type uint32;
           description "Number of Backup requests sent but yet to receive response or error";
         }
         leaf acct-backup-response-success {
           type uint32;
           description "Number of backup responses received and processed by backup module";
         }
         leaf acct-backup-malformed-responses {
           type uint32;
           description "Number of requests sent to backup accounting module";
         }
         leaf acct-backup-bad-authenticators {
           type uint32;
           description "Number of bad accounting authenticators in backup context";
         }
         leaf acct-backup-packets-dropped {
           type uint32;
           description "Number of backup responses dropped due to an issue not covered above";
         }
         leaf acct-backup-rollover-requests {
           type uint32;
           description "Number of backup requests that rollover to another server due to timeout/maxout";
         }
         leaf acct-backup-unknown-responses {
           type uint32;
           description "Number of backup requests that rollover to another server due to timeout/maxout";
         }
         leaf acct-backup-radius-requests {
           type uint32;
           description "Number of backup requests that rollover to another server due to timeout/maxout";
         }
         leaf acct-backup-radius-responses {
           type uint32;
           description "Number of backup requests that rollover to another server due to timeout/maxout";
         }
         leaf acct-backup-radius-timeouts {
           type uint32;
           description "Number of backup requests that rollover to another server due to timeout/maxout";
         }
         container aaa-module-authentication-statistics {
         }
         container aaa-module-pending-accounting-stop-statistics {
           leaf pending-acct-stops {
             type uint32;
             description "Number of requests received";
           }
         }
         container aaa-module-preauthentication-statistics {
           leaf requests {
             type uint32;
             description "Number of requests received";
           }
           leaf multistack-requests {
             type uint32;
             description "Number of multistack requests received";
           }
           leaf accepts {
             type uint32;
             description "Number of authentication accepts";
           }
           leaf rejects {
             type uint32;
             description "Number of authentication rejects";
           }
           leaf challenges {
             type uint32;
             description "Number of authentication challenges";
           }
           leaf timeouts {
             type uint32;
             description "Number of requests timed out";
           }
         }
         container aaa-module-accounting-statistics {
           leaf requests {
             type uint32;
             description "Number of requests received";
           }
           leaf accounting-request-failures {
             type uint32;
             description "Number of accounting requests failed to be sent out";
           }
           leaf accounting-request-success {
             type uint32;
             description "Number of accounting requests sent out sucessfully";
           }
           leaf timeouts {
             type uint32;
             description "Number of requests timed out";
           }
           leaf accounting-response-failures {
             type uint32;
             description "Number of accounting response failures";
           }
           leaf accounting-response-success {
             type uint32;
             description "Number of successful accounting responses";
           }
           leaf acct-rollover-requests {
             type uint32;
             description "Number of accounting requests that rollover to another server due to timeout/maxout";
           }
           leaf acct-unknown-responses {
             type uint32;
             description "Number of unknown accounting responses received";
           }
           leaf acct-requests-pending {
             type uint32;
             description "Number of pending account requests sent";
           }
           leaf acct-malformed-responses {
             type uint32;
             description "Number of malformed accounting responses received";
           }
           leaf acct-retransmissions {
             type uint32;
             description "Number of accounting retransmissions";
           }
           leaf acct-bad-authenticators {
             type uint32;
             description "Number of bad accounting authenticators";
           }
           leaf acct-packets-dropped {
             type uint32;
             description "Number of accounting packets dropped because not supported for config";
           }
           leaf acct-acct-on-requests {
             type uint32;
             description "Number of account on requests sent";
           }
           leaf acct-start-requests {
             type uint32;
             description "Number of accounting start requests sent";
           }
           leaf acct-interim-requests {
             type uint32;
             description "Number of accounting interim requests sent";
           }
           leaf acct-stop-requests {
             type uint32;
             description "Number of accounting stop requests sent";
           }
           leaf acct-acct-on-responses {
             type uint32;
             description "Number of accounting on responses received";
           }
           leaf acct-start-responses {
             type uint32;
             description "Number of accounting start responses received";
           }
           leaf acct-interim-responses {
             type uint32;
             description "Number of accounting interim responses received";
           }
           leaf acct-stop-responses {
             type uint32;
             description "Number of accounting stop responses received";
           }
           leaf acct-backup-record-creation-requests {
             type uint32;
             description "Number of backup records creation requests sent to backup accounting module";
           }
           leaf acct-backup-radius-retransmissions {
             type uint32;
             description "Number of radius retries sent in backup context";
           }
           leaf acct-backup-request-timeouts {
             type uint32;
             description "Number of backup requests that timed out";
           }
           leaf acct-backup-request-failures {
             type uint32;
             description "Number of backup requests that encountered an error";
           }
           leaf acct-backup-request-success {
             type uint32;
             description "Number of backup requests that were success";
           }
           leaf acct-backup-request-replay-success {
             type uint32;
             description "Number of backup requests that were reconstructed successfully during replay";
           }
           leaf acct-backup-radius-pending-request {
             type uint32;
             description "Number of Backup requests sent to radius server but yet to receive response or error";
           }
           leaf acct-backup-in-flight-requests {
             type uint32;
             description "Number of Backup requests sent but yet to receive response or error";
           }
           leaf acct-backup-response-success {
             type uint32;
             description "Number of backup responses received and processed by backup module";
           }
           leaf acct-backup-malformed-responses {
             type uint32;
             description "Number of requests sent to backup accounting module";
           }
           leaf acct-backup-bad-authenticators {
             type uint32;
             description "Number of bad accounting authenticators in backup context";
           }
           leaf acct-backup-packets-dropped {
             type uint32;
             description "Number of backup responses dropped due to an issue not covered above";
           }
           leaf acct-backup-rollover-requests {
             type uint32;
             description "Number of backup requests that rollover to another server due to timeout/maxout";
           }
           leaf acct-backup-unknown-responses {
             type uint32;
             description "Number of backup requests that rollover to another server due to timeout/maxout";
           }
           leaf acct-backup-radius-requests {
             type uint32;
             description "Number of backup requests that rollover to another server due to timeout/maxout";
           }
           leaf acct-backup-radius-responses {
             type uint32;
             description "Number of backup requests that rollover to another server due to timeout/maxout";
           }
           leaf acct-backup-radius-timeouts {
             type uint32;
             description "Number of backup requests that rollover to another server due to timeout/maxout";
           }
         }
         container aaa-module-dynamic-requests-statistics {
           leaf requests {
             type uint32;
             description "Number of requests received";
           }
           leaf processed-ok {
             type uint32;
             description "Number of requests successfully processed";
           }
           leaf processed-initial {
             type uint32;
             description "Number of requests initially processed successfully";
           }
           leaf processing-error {
             type uint32;
             description "Number of requests unsuccessfully processed";
           }
           leaf silent-drops {
             type uint32;
             description "Number of requests silently dropped";
           }
           container aaa-module-dynamic-requests-bulkcoa-statistics {
             leaf bulkcoa-received {
               type uint32;
               description "Number of bulk-CoA different transactions received";
             }
             leaf bulkcoa-success {
               type uint32;
               description "Number of bulk-CoA transactions successfully committed";
             }
             leaf bulkcoa-timeout {
               type uint32;
               description "Number of bulk-CoA transactions timedout";
             }
             leaf bulkcoa-transaction-mismatch {
               type uint32;
               description "Number of bulk-CoA transaction-id mismatch";
             }
             leaf bulkcoa-in-progress {
               type uint32;
               description "Number of bulk-CoA transactions with processing already in progress";
             }
             leaf bulkcoa-no-services {
               type uint32;
               description "Number of bulk-CoA transactions with no services in Bulk-CoA";
             }
             leaf bulkcoa-service-not-found {
               type uint32;
               description "Number of bulk-CoA transactions with service not found to deactivate";
             }
             leaf bulkcoa-service-active {
               type uint32;
               description "Number of bulk-CoA transactions with service already active";
             }
             leaf bulkcoa-execution-failure {
               type uint32;
               description "Number of bulk-CoA transactions with execution failure";
             }
             leaf bulkcoa-logout-in-progress {
               type uint32;
               description "Number of bulk-CoA transactions with logout in progress";
             }
             leaf bulkcoa-max-services {
               type uint32;
               description "Number of bulk-CoA transactions with max services exceeded";
             }
             leaf bulkcoa-max-requests {
               type uint32;
               description "Number of bulk-CoA transactions with max requests exceeded";
             }
             leaf bulkcoa-max-concurrent-coas {
               type uint32;
               description "Max Number of bulk-CoA transactions concurrently being processed";
             }
             leaf bulkcoa-extensible-services-errors {
               type uint32;
               description "Number of bulk-CoA transactions with extensible services errors";
             }
           }
         }
         container aaa-module-volume-accounting-statistics {
           leaf interim-updates-rcvd {
             type uint32;
             description "Number of interim updates received from libstats";
           }
           leaf interim-updates-sent {
             type uint32;
             description "Number of interim updates sent to radius";
           }
           leaf interim-updates-error-rcvd {
             type uint32;
             description "Number of interim error callbacks received";
           }
           leaf requested-final-stats {
             type uint32;
             description "Number of final stats requested from libstats";
           }
           leaf final-stats-retry-count {
             type uint32;
             description "Number of final stats retried";
           }
           leaf final-stats-rcvd {
             type uint32;
             description "Number of final stats updates received";
           }
           leaf final-stats-error-rcvd {
             type uint32;
             description "Number of final stats errors received";
           }
           leaf final-stats-sent {
             type uint32;
             description "Number of final stats sent to radius";
           }
           leaf time-only-info-sent {
             type uint32;
             description "Number of time info only stops sent";
           }
           leaf stats-timer-fired {
             type uint32;
             description "Number of times the accounting stats timer fired";
           }
           leaf libstats-interim-egress-subs {
             type uint32;
             description "Interim egress subs";
           }
           leaf libstats-interim-ingress-subs {
             type uint32;
             description "Interim ingress subs";
           }
           leaf libstats-interim-egress-general-error {
             type uint32;
             description "Interim egress general error";
           }
           leaf libstats-interim-ingress-general-error {
             type uint32;
             description "Interim ingress general error";
           }
           leaf libstats-interim-egress-kernel-error {
             type uint32;
             description "Interim egress kernel error";
           }
           leaf libstats-interim-ingress-kernel-error {
             type uint32;
             description "Interim ingress kernel error";
           }
           leaf libstats-interim-egress-memory-error {
             type uint32;
             description "Interim egress memory error";
           }
           leaf libstats-interim-ingress-memory-error {
             type uint32;
             description "Interim ingress memory error";
           }
           leaf libstats-interim-egress-ipc-error {
             type uint32;
             description "Interim egress IPC error";
           }
           leaf libstats-interim-ingress-ipc-error {
             type uint32;
             description "Interim ingress IPC error";
           }
           leaf libstats-interim-egress-validation-error {
             type uint32;
             description "Interim egress validation error";
           }
           leaf libstats-interim-ingress-validation-error {
             type uint32;
             description "Interim ingress validation error";
           }
           leaf libstats-interim-egress-db-lookup-error {
             type uint32;
             description "Interim egress db lookup error";
           }
           leaf libstats-interim-ingress-db-lookup-error {
             type uint32;
             description "Interim ingress db lookup error";
           }
           leaf libstats-final-egress-subs {
             type uint32;
             description "Final egress subs";
           }
           leaf libstats-final-ingress-subs {
             type uint32;
             description "Final ingress subs";
           }
           leaf libstats-final-egress-general-error {
             type uint32;
             description "Final egress general error";
           }
           leaf libstats-final-ingress-general-error {
             type uint32;
             description "Final ingress general error";
           }
           leaf libstats-final-egress-kernel-error {
             type uint32;
             description "Final egress kernel error";
           }
           leaf libstats-final-ingress-kernel-error {
             type uint32;
             description "Final ingress kernel error";
           }
           leaf libstats-final-egress-memory-error {
             type uint32;
             description "Final egress memory error";
           }
           leaf libstats-final-ingress-memory-error {
             type uint32;
             description "Final ingress memory error";
           }
           leaf libstats-final-egress-ipc-error {
             type uint32;
             description "Final egress IPC error";
           }
           leaf libstats-final-ingress-ipc-error {
             type uint32;
             description "Final ingress IPC error";
           }
           leaf libstats-final-egress-validation-error {
             type uint32;
             description "Final egress validation error";
           }
           leaf libstats-final-ingress-validation-error {
             type uint32;
             description "Final ingress validation error";
           }
           leaf libstats-final-egress-db-lookup-error {
             type uint32;
             description "Final egress DB lookup error";
           }
           leaf libstats-final-ingress-db-lookup-error {
             type uint32;
             description "Final ingress DB lookup error";
           }
           leaf libstats-all-egress-msg-types {
             type uint32;
             description "All egress message types";
           }
           leaf libstats-all-ingress-msg-types {
             type uint32;
             description "All ingress message types";
           }
           leaf libstats-all-egress-general-error {
             type uint32;
             description "All egress general error";
           }
           leaf libstats-all-ingress-general-error {
             type uint32;
             description "All ingress general error";
           }
           leaf libstats-all-egress-kernel-error {
             type uint32;
             description "All egress kernel error";
           }
           leaf libstats-all-ingress-kernel-error {
             type uint32;
             description "All ingress kernel error";
           }
           leaf libstats-all-egress-memory-error {
             type uint32;
             description "All egress memory error";
           }
           leaf libstats-all-ingress-memory-error {
             type uint32;
             description "All ingress memory error";
           }
           leaf libstats-all-egress-ipc-error {
             type uint32;
             description "All egress IPC error";
           }
           leaf libstats-all-ingress-ipc-error {
             type uint32;
             description "All ingress IPC error";
           }
           leaf libstats-all-egress-validation-error {
             type uint32;
             description "All egress validation error";
           }
           leaf libstats-all-ingress-validation-error {
             type uint32;
             description "All ingress validation error";
           }
           leaf libstats-all-egress-db-lookup-error {
             type uint32;
             description "All egress DB lookup error";
           }
           leaf libstats-all-ingress-db-lookup-error {
             type uint32;
             description "All ingress DB lookup error";
           }
         }
         container aaa-module-re-authentication-statistics {
           leaf requests {
             type uint32;
             description "Number of requests received";
           }
           leaf accepts {
             type uint32;
             description "Number of authentication accepts";
           }
           leaf aborts {
             type uint32;
             description "Number of abort requests";
           }
           leaf challenges {
             type uint32;
             description "Number of authentication challenges";
           }
           leaf internal-errors {
             type uint32;
             description "Number of internal errors";
           }
           leaf rejects {
             type uint32;
             description "Number of authentication rejects";
           }
           leaf timeouts {
             type uint32;
             description "Number of requests timed out";
           }
         }
         container aaa-module-address-assignment-pool-statistics {
           leaf pool-name {
             type string;
             description "Pool name";
           }
           leaf link-name {
             type string;
             description "Link name";
           }
           leaf out-of-memory {
             type uint64;
             description "Number of times we have hit an out of memory condition";
           }
           leaf out-of-addresses {
             type uint64;
             description "Number of times we have hit an out of address condition";
           }
           leaf total-addresses {
             type uint64;
             description "Number of addresses in pool";
           }
           leaf used-addresses {
             type uint64;
             description "Number of addresses in use";
           }
           leaf excluded-addresses {
             type uint64;
             description "Number of addresses excluded";
           }
           leaf pool-usage {
             type int32;
             description "Percentage of addesses in use";
           }
         }
         container aaa-module-address-assignment-client-statistics {
           leaf client-name {
             type string;
             description "Client name";
           }
           leaf out-of-memory {
             type uint64;
             description "Number of times we have hit an out of memory condition";
           }
           leaf no-matches {
             type int32;
             description "Number of times we have not had an address match";
           }
         }
         container aaa-module-subscriber-statistics {
           leaf total-number-of-subscribers {
             type int32;
             description "Total number of subscribers";
           }
         }
         container aaa-module-radius-statistics {
           leaf radius-statistics-error {
             type string;
             description "Error message to display related to RADIUS server statistics";
           }
           container radius-server {
             description "RADIUS servers";
             leaf server-address {
               type ipaddr;
               description "RADIUS server address";
             }
             leaf profile {
               type string;
               description "Profile that includes this RADIUS server";
             }
             leaf max-outstanding {
               type int32;
               description "Maximum number of outstanding RADIUS requests for this server";
             }
             leaf current-outstanding {
               type int32;
               description "Current number of outstanding RADIUS requests for this server";
             }
             leaf peak-outstanding {
               type int32;
               description "Highest number of outstanding RADIUS requests for this server";
             }
             leaf fail-outstanding {
               type int32;
               description "Number of max-outstanding-exceeded failures for this server";
             }
           }
         }
         container aaa-module-radius-queue-statistics {
           leaf profile {
             type string;
             description "Profile that includes this RADIUS server";
           }
           leaf current-size {
             type int32;
             description "Current number of entries on this RADIUS queue";
           }
           leaf peak {
             type int32;
             description "Peak entries on this RADIUS queue";
           }
           leaf max-size {
             type int32;
             description "Maximum number of entries on this RADIUS queue";
           }
         }
       }
     }
   }
   rpc get-address-assignment-pool-statistics {
     description "Show pool information based on pool name";
     input {
       leaf get-address-assignment-pool-table-specific {
         description "Show information for a specific pool";
         type string;
         mandatory true;
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container aaa-module-statistics {
         leaf requests {
           type uint32;
           description "Number of requests received";
         }
         leaf multistack-requests {
           type uint32;
           description "Number of multistack requests received";
         }
         leaf accepts {
           type uint32;
           description "Number of authentication accepts";
         }
         leaf rejects {
           type uint32;
           description "Number of authentication rejects";
         }
         leaf radius-failures {
           type uint32;
           description "Number of RADIUS authentication failures";
         }
         leaf rejects-queue-request-deleted {
           type uint32;
           description "Number of authentication rejects due to queue request deleted";
         }
         leaf rejects-malformed-reply {
           type uint32;
           description "Number of authentication rejects due to malformed reply";
         }
         leaf rejects-no-server-configured {
           type uint32;
           description "Number of authentication rejects due to no servers configured";
         }
         leaf rejects-access-profile-config-unavailable {
           type uint32;
           description "Number of authentication rejects due to unavailable access profile configuration";
         }
         leaf rejects-no-client-record {
           type uint32;
           description "Number of authentication rejects due to failure to create client record";
         }
         leaf rejects-no-client-request {
           type uint32;
           description "Number of authentication rejects due to failure to create client request";
         }
         leaf rejects-no-build-auth-request {
           type uint32;
           description "Number of authentication rejects due to failure to build authentication request";
         }
         leaf rejects-no-server {
           type uint32;
           description "Number of authentication rejects due to failure to find server";
         }
         leaf rejects-no-create-handle {
           type uint32;
           description "Number of authentication rejects due to failure to create handle";
         }
         leaf rejects-no-queue-request {
           type uint32;
           description "Number of authentication rejects due to failure to queue request";
         }
         leaf rejects-invalid-credentials {
           type uint32;
           description "Number of authentication rejects due to invalid credentials";
         }
         leaf rejects-internal-failure {
           type uint32;
           description "Number of authentication rejects due to internal failure";
         }
         leaf rejects-malformed-request {
           type uint32;
           description "Number of authentication rejects due to malformed request";
         }
         leaf rejects-license-unavailable {
           type uint32;
           description "Number of authentication rejects due to license unavailable";
         }
         leaf rejects-redirect-requested {
           type uint32;
           description "Number of authentication rejects due to redirect requested";
         }
         leaf local-failures {
           type uint32;
           description "Number of local authentication failures";
         }
         leaf ldap-failures {
           type uint32;
           description "Number of LDAP lookup failures";
         }
         leaf accounting-request-failures {
           type uint32;
           description "Number of accounting requests failed to be sent out";
         }
         leaf accounting-request-success {
           type uint32;
           description "Number of accounting requests sent out sucessfully";
         }
         leaf timeouts {
           type uint32;
           description "Number of requests timed out";
         }
         leaf accounting-response-failures {
           type uint32;
           description "Number of accounting response failures";
         }
         leaf accounting-response-success {
           type uint32;
           description "Number of successful accounting responses";
         }
         leaf acct-unknown-responses {
           type uint32;
           description "Number of unknown accounting responses received";
         }
         leaf acct-requests-pending {
           type uint32;
           description "Number of pending account requests sent";
         }
         leaf acct-malformed-responses {
           type uint32;
           description "Number of malformed accounting responses received";
         }
         leaf acct-retransmissions {
           type uint32;
           description "Number of accounting retransmissions";
         }
         leaf acct-bad-authenticators {
           type uint32;
           description "Number of bad accounting authenticators";
         }
         leaf acct-packets-dropped {
           type uint32;
           description "Number of accounting packets dropped because not supported for config";
         }
         leaf acct-acct-on-requests {
           type uint32;
           description "Number of account on requests sent";
         }
         leaf acct-start-requests {
           type uint32;
           description "Number of accounting start requests sent";
         }
         leaf acct-interim-requests {
           type uint32;
           description "Number of accounting interim requests sent";
         }
         leaf acct-stop-requests {
           type uint32;
           description "Number of accounting stop requests sent";
         }
         leaf acct-rollover-requests {
           type uint32;
           description "Number of accounting requests that rollover to another server due to timeout/maxout";
         }
         leaf acct-acct-on-responses {
           type uint32;
           description "Number of accounting on responses received";
         }
         leaf acct-start-responses {
           type uint32;
           description "Number of accounting start responses received";
         }
         leaf acct-interim-responses {
           type uint32;
           description "Number of accounting interim responses received";
         }
         leaf acct-stop-responses {
           type uint32;
           description "Number of accounting stop responses received";
         }
         leaf multistack-suppressions {
           type uint32;
           description "Number of multistack requests suppressed";
         }
         leaf challenges {
           type uint32;
           description "Number of authentication challenges";
         }
         leaf processed-ok {
           type uint32;
           description "Number of requests successfully processed";
         }
         leaf processed-initial {
           type uint32;
           description "Number of requests initially processed successfully";
         }
         leaf processing-error {
           type uint32;
           description "Number of requests unsuccessfully processed";
         }
         leaf silent-drops {
           type uint32;
           description "Number of requests silently dropped";
         }
         leaf internal-errors {
           type uint32;
           description "Number of internal errors";
         }
         leaf aborts {
           type uint32;
           description "Number of abort requests";
         }
         leaf interim-updates-rcvd {
           type uint32;
           description "Number of interim updates received from libstats";
         }
         leaf interim-updates-sent {
           type uint32;
           description "Number of interim updates sent to radius";
         }
         leaf interim-updates-error-rcvd {
           type uint32;
           description "Number of interim error callbacks received";
         }
         leaf requested-final-stats {
           type uint32;
           description "Number of final stats requested from libstats";
         }
         leaf final-stats-retry-count {
           type uint32;
           description "Number of final stats retried";
         }
         leaf final-stats-rcvd {
           type uint32;
           description "Number of final stats updates received";
         }
         leaf final-stats-error-rcvd {
           type uint32;
           description "Number of final stats errors received";
         }
         leaf final-stats-sent {
           type uint32;
           description "Number of final stats sent to radius";
         }
         leaf time-only-info-sent {
           type uint32;
           description "Number of time info only stops sent";
         }
         leaf stats-timer-fired {
           type uint32;
           description "Number of times the accounting stats timer fired";
         }
         leaf libstats-interim-egress-subs {
           type uint32;
           description "Interim egress subs";
         }
         leaf libstats-interim-ingress-subs {
           type uint32;
           description "Interim ingress subs";
         }
         leaf libstats-interim-egress-general-error {
           type uint32;
           description "Interim egress general error";
         }
         leaf libstats-interim-ingress-general-error {
           type uint32;
           description "Interim ingress general error";
         }
         leaf libstats-interim-egress-kernel-error {
           type uint32;
           description "Interim egress kernel error";
         }
         leaf libstats-interim-ingress-kernel-error {
           type uint32;
           description "Interim ingress kernel error";
         }
         leaf libstats-interim-egress-memory-error {
           type uint32;
           description "Interim egress memory error";
         }
         leaf libstats-interim-ingress-memory-error {
           type uint32;
           description "Interim ingress memory error";
         }
         leaf libstats-interim-egress-ipc-error {
           type uint32;
           description "Interim egress IPC error";
         }
         leaf libstats-interim-ingress-ipc-error {
           type uint32;
           description "Interim ingress IPC error";
         }
         leaf libstats-interim-egress-validation-error {
           type uint32;
           description "Interim egress validation error";
         }
         leaf libstats-interim-ingress-validation-error {
           type uint32;
           description "Interim ingress validation error";
         }
         leaf libstats-interim-egress-db-lookup-error {
           type uint32;
           description "Interim egress db lookup error";
         }
         leaf libstats-interim-ingress-db-lookup-error {
           type uint32;
           description "Interim ingress db lookup error";
         }
         leaf libstats-final-egress-subs {
           type uint32;
           description "Final egress subs";
         }
         leaf libstats-final-ingress-subs {
           type uint32;
           description "Final ingress subs";
         }
         leaf libstats-final-egress-general-error {
           type uint32;
           description "Final egress general error";
         }
         leaf libstats-final-ingress-general-error {
           type uint32;
           description "Final ingress general error";
         }
         leaf libstats-final-egress-kernel-error {
           type uint32;
           description "Final egress kernel error";
         }
         leaf libstats-final-ingress-kernel-error {
           type uint32;
           description "Final ingress kernel error";
         }
         leaf libstats-final-egress-memory-error {
           type uint32;
           description "Final egress memory error";
         }
         leaf libstats-final-ingress-memory-error {
           type uint32;
           description "Final ingress memory error";
         }
         leaf libstats-final-egress-ipc-error {
           type uint32;
           description "Final egress IPC error";
         }
         leaf libstats-final-ingress-ipc-error {
           type uint32;
           description "Final ingress IPC error";
         }
         leaf libstats-final-egress-validation-error {
           type uint32;
           description "Final egress validation error";
         }
         leaf libstats-final-ingress-validation-error {
           type uint32;
           description "Final ingress validation error";
         }
         leaf libstats-final-egress-db-lookup-error {
           type uint32;
           description "Final egress DB lookup error";
         }
         leaf libstats-final-ingress-db-lookup-error {
           type uint32;
           description "Final ingress DB lookup error";
         }
         leaf libstats-all-egress-msg-types {
           type uint32;
           description "All egress message types";
         }
         leaf libstats-all-ingress-msg-types {
           type uint32;
           description "All ingress message types";
         }
         leaf libstats-all-egress-general-error {
           type uint32;
           description "All egress general error";
         }
         leaf libstats-all-ingress-general-error {
           type uint32;
           description "All ingress general error";
         }
         leaf libstats-all-egress-kernel-error {
           type uint32;
           description "All egress kernel error";
         }
         leaf libstats-all-ingress-kernel-error {
           type uint32;
           description "All ingress kernel error";
         }
         leaf libstats-all-egress-memory-error {
           type uint32;
           description "All egress memory error";
         }
         leaf libstats-all-ingress-memory-error {
           type uint32;
           description "All ingress memory error";
         }
         leaf libstats-all-egress-ipc-error {
           type uint32;
           description "All egress IPC error";
         }
         leaf libstats-all-ingress-ipc-error {
           type uint32;
           description "All ingress IPC error";
         }
         leaf libstats-all-egress-validation-error {
           type uint32;
           description "All egress validation error";
         }
         leaf libstats-all-ingress-validation-error {
           type uint32;
           description "All ingress validation error";
         }
         leaf libstats-all-egress-db-lookup-error {
           type uint32;
           description "All egress DB lookup error";
         }
         leaf libstats-all-ingress-db-lookup-error {
           type uint32;
           description "All ingress DB lookup error";
         }
         leaf pending-acct-stops {
           type uint32;
           description "Number of requests received";
         }
         leaf acct-backup-record-creation-requests {
           type uint32;
           description "Number of backup records creation requests sent to backup accounting module";
         }
         leaf acct-backup-radius-retransmissions {
           type uint32;
           description "Number of radius retries sent in backup context";
         }
         leaf acct-backup-request-timeouts {
           type uint32;
           description "Number of backup requests that timed out";
         }
         leaf acct-backup-request-failures {
           type uint32;
           description "Number of backup requests that encountered an error";
         }
         leaf acct-backup-request-success {
           type uint32;
           description "Number of backup requests that were success";
         }
         leaf acct-backup-request-replay-success {
           type uint32;
           description "Number of backup requests that were reconstructed successfully during replay";
         }
         leaf acct-backup-radius-pending-request {
           type uint32;
           description "Number of Backup requests sent to radius server but yet to receive response or error";
         }
         leaf acct-backup-in-flight-requests {
           type uint32;
           description "Number of Backup requests sent but yet to receive response or error";
         }
         leaf acct-backup-response-success {
           type uint32;
           description "Number of backup responses received and processed by backup module";
         }
         leaf acct-backup-malformed-responses {
           type uint32;
           description "Number of requests sent to backup accounting module";
         }
         leaf acct-backup-bad-authenticators {
           type uint32;
           description "Number of bad accounting authenticators in backup context";
         }
         leaf acct-backup-packets-dropped {
           type uint32;
           description "Number of backup responses dropped due to an issue not covered above";
         }
         leaf acct-backup-rollover-requests {
           type uint32;
           description "Number of backup requests that rollover to another server due to timeout/maxout";
         }
         leaf acct-backup-unknown-responses {
           type uint32;
           description "Number of backup requests that rollover to another server due to timeout/maxout";
         }
         leaf acct-backup-radius-requests {
           type uint32;
           description "Number of backup requests that rollover to another server due to timeout/maxout";
         }
         leaf acct-backup-radius-responses {
           type uint32;
           description "Number of backup requests that rollover to another server due to timeout/maxout";
         }
         leaf acct-backup-radius-timeouts {
           type uint32;
           description "Number of backup requests that rollover to another server due to timeout/maxout";
         }
         container aaa-module-authentication-statistics {
         }
         container aaa-module-pending-accounting-stop-statistics {
           leaf pending-acct-stops {
             type uint32;
             description "Number of requests received";
           }
         }
         container aaa-module-preauthentication-statistics {
           leaf requests {
             type uint32;
             description "Number of requests received";
           }
           leaf multistack-requests {
             type uint32;
             description "Number of multistack requests received";
           }
           leaf accepts {
             type uint32;
             description "Number of authentication accepts";
           }
           leaf rejects {
             type uint32;
             description "Number of authentication rejects";
           }
           leaf challenges {
             type uint32;
             description "Number of authentication challenges";
           }
           leaf timeouts {
             type uint32;
             description "Number of requests timed out";
           }
         }
         container aaa-module-accounting-statistics {
           leaf requests {
             type uint32;
             description "Number of requests received";
           }
           leaf accounting-request-failures {
             type uint32;
             description "Number of accounting requests failed to be sent out";
           }
           leaf accounting-request-success {
             type uint32;
             description "Number of accounting requests sent out sucessfully";
           }
           leaf timeouts {
             type uint32;
             description "Number of requests timed out";
           }
           leaf accounting-response-failures {
             type uint32;
             description "Number of accounting response failures";
           }
           leaf accounting-response-success {
             type uint32;
             description "Number of successful accounting responses";
           }
           leaf acct-rollover-requests {
             type uint32;
             description "Number of accounting requests that rollover to another server due to timeout/maxout";
           }
           leaf acct-unknown-responses {
             type uint32;
             description "Number of unknown accounting responses received";
           }
           leaf acct-requests-pending {
             type uint32;
             description "Number of pending account requests sent";
           }
           leaf acct-malformed-responses {
             type uint32;
             description "Number of malformed accounting responses received";
           }
           leaf acct-retransmissions {
             type uint32;
             description "Number of accounting retransmissions";
           }
           leaf acct-bad-authenticators {
             type uint32;
             description "Number of bad accounting authenticators";
           }
           leaf acct-packets-dropped {
             type uint32;
             description "Number of accounting packets dropped because not supported for config";
           }
           leaf acct-acct-on-requests {
             type uint32;
             description "Number of account on requests sent";
           }
           leaf acct-start-requests {
             type uint32;
             description "Number of accounting start requests sent";
           }
           leaf acct-interim-requests {
             type uint32;
             description "Number of accounting interim requests sent";
           }
           leaf acct-stop-requests {
             type uint32;
             description "Number of accounting stop requests sent";
           }
           leaf acct-acct-on-responses {
             type uint32;
             description "Number of accounting on responses received";
           }
           leaf acct-start-responses {
             type uint32;
             description "Number of accounting start responses received";
           }
           leaf acct-interim-responses {
             type uint32;
             description "Number of accounting interim responses received";
           }
           leaf acct-stop-responses {
             type uint32;
             description "Number of accounting stop responses received";
           }
           leaf acct-backup-record-creation-requests {
             type uint32;
             description "Number of backup records creation requests sent to backup accounting module";
           }
           leaf acct-backup-radius-retransmissions {
             type uint32;
             description "Number of radius retries sent in backup context";
           }
           leaf acct-backup-request-timeouts {
             type uint32;
             description "Number of backup requests that timed out";
           }
           leaf acct-backup-request-failures {
             type uint32;
             description "Number of backup requests that encountered an error";
           }
           leaf acct-backup-request-success {
             type uint32;
             description "Number of backup requests that were success";
           }
           leaf acct-backup-request-replay-success {
             type uint32;
             description "Number of backup requests that were reconstructed successfully during replay";
           }
           leaf acct-backup-radius-pending-request {
             type uint32;
             description "Number of Backup requests sent to radius server but yet to receive response or error";
           }
           leaf acct-backup-in-flight-requests {
             type uint32;
             description "Number of Backup requests sent but yet to receive response or error";
           }
           leaf acct-backup-response-success {
             type uint32;
             description "Number of backup responses received and processed by backup module";
           }
           leaf acct-backup-malformed-responses {
             type uint32;
             description "Number of requests sent to backup accounting module";
           }
           leaf acct-backup-bad-authenticators {
             type uint32;
             description "Number of bad accounting authenticators in backup context";
           }
           leaf acct-backup-packets-dropped {
             type uint32;
             description "Number of backup responses dropped due to an issue not covered above";
           }
           leaf acct-backup-rollover-requests {
             type uint32;
             description "Number of backup requests that rollover to another server due to timeout/maxout";
           }
           leaf acct-backup-unknown-responses {
             type uint32;
             description "Number of backup requests that rollover to another server due to timeout/maxout";
           }
           leaf acct-backup-radius-requests {
             type uint32;
             description "Number of backup requests that rollover to another server due to timeout/maxout";
           }
           leaf acct-backup-radius-responses {
             type uint32;
             description "Number of backup requests that rollover to another server due to timeout/maxout";
           }
           leaf acct-backup-radius-timeouts {
             type uint32;
             description "Number of backup requests that rollover to another server due to timeout/maxout";
           }
         }
         container aaa-module-dynamic-requests-statistics {
           leaf requests {
             type uint32;
             description "Number of requests received";
           }
           leaf processed-ok {
             type uint32;
             description "Number of requests successfully processed";
           }
           leaf processed-initial {
             type uint32;
             description "Number of requests initially processed successfully";
           }
           leaf processing-error {
             type uint32;
             description "Number of requests unsuccessfully processed";
           }
           leaf silent-drops {
             type uint32;
             description "Number of requests silently dropped";
           }
           container aaa-module-dynamic-requests-bulkcoa-statistics {
             leaf bulkcoa-received {
               type uint32;
               description "Number of bulk-CoA different transactions received";
             }
             leaf bulkcoa-success {
               type uint32;
               description "Number of bulk-CoA transactions successfully committed";
             }
             leaf bulkcoa-timeout {
               type uint32;
               description "Number of bulk-CoA transactions timedout";
             }
             leaf bulkcoa-transaction-mismatch {
               type uint32;
               description "Number of bulk-CoA transaction-id mismatch";
             }
             leaf bulkcoa-in-progress {
               type uint32;
               description "Number of bulk-CoA transactions with processing already in progress";
             }
             leaf bulkcoa-no-services {
               type uint32;
               description "Number of bulk-CoA transactions with no services in Bulk-CoA";
             }
             leaf bulkcoa-service-not-found {
               type uint32;
               description "Number of bulk-CoA transactions with service not found to deactivate";
             }
             leaf bulkcoa-service-active {
               type uint32;
               description "Number of bulk-CoA transactions with service already active";
             }
             leaf bulkcoa-execution-failure {
               type uint32;
               description "Number of bulk-CoA transactions with execution failure";
             }
             leaf bulkcoa-logout-in-progress {
               type uint32;
               description "Number of bulk-CoA transactions with logout in progress";
             }
             leaf bulkcoa-max-services {
               type uint32;
               description "Number of bulk-CoA transactions with max services exceeded";
             }
             leaf bulkcoa-max-requests {
               type uint32;
               description "Number of bulk-CoA transactions with max requests exceeded";
             }
             leaf bulkcoa-max-concurrent-coas {
               type uint32;
               description "Max Number of bulk-CoA transactions concurrently being processed";
             }
             leaf bulkcoa-extensible-services-errors {
               type uint32;
               description "Number of bulk-CoA transactions with extensible services errors";
             }
           }
         }
         container aaa-module-volume-accounting-statistics {
           leaf interim-updates-rcvd {
             type uint32;
             description "Number of interim updates received from libstats";
           }
           leaf interim-updates-sent {
             type uint32;
             description "Number of interim updates sent to radius";
           }
           leaf interim-updates-error-rcvd {
             type uint32;
             description "Number of interim error callbacks received";
           }
           leaf requested-final-stats {
             type uint32;
             description "Number of final stats requested from libstats";
           }
           leaf final-stats-retry-count {
             type uint32;
             description "Number of final stats retried";
           }
           leaf final-stats-rcvd {
             type uint32;
             description "Number of final stats updates received";
           }
           leaf final-stats-error-rcvd {
             type uint32;
             description "Number of final stats errors received";
           }
           leaf final-stats-sent {
             type uint32;
             description "Number of final stats sent to radius";
           }
           leaf time-only-info-sent {
             type uint32;
             description "Number of time info only stops sent";
           }
           leaf stats-timer-fired {
             type uint32;
             description "Number of times the accounting stats timer fired";
           }
           leaf libstats-interim-egress-subs {
             type uint32;
             description "Interim egress subs";
           }
           leaf libstats-interim-ingress-subs {
             type uint32;
             description "Interim ingress subs";
           }
           leaf libstats-interim-egress-general-error {
             type uint32;
             description "Interim egress general error";
           }
           leaf libstats-interim-ingress-general-error {
             type uint32;
             description "Interim ingress general error";
           }
           leaf libstats-interim-egress-kernel-error {
             type uint32;
             description "Interim egress kernel error";
           }
           leaf libstats-interim-ingress-kernel-error {
             type uint32;
             description "Interim ingress kernel error";
           }
           leaf libstats-interim-egress-memory-error {
             type uint32;
             description "Interim egress memory error";
           }
           leaf libstats-interim-ingress-memory-error {
             type uint32;
             description "Interim ingress memory error";
           }
           leaf libstats-interim-egress-ipc-error {
             type uint32;
             description "Interim egress IPC error";
           }
           leaf libstats-interim-ingress-ipc-error {
             type uint32;
             description "Interim ingress IPC error";
           }
           leaf libstats-interim-egress-validation-error {
             type uint32;
             description "Interim egress validation error";
           }
           leaf libstats-interim-ingress-validation-error {
             type uint32;
             description "Interim ingress validation error";
           }
           leaf libstats-interim-egress-db-lookup-error {
             type uint32;
             description "Interim egress db lookup error";
           }
           leaf libstats-interim-ingress-db-lookup-error {
             type uint32;
             description "Interim ingress db lookup error";
           }
           leaf libstats-final-egress-subs {
             type uint32;
             description "Final egress subs";
           }
           leaf libstats-final-ingress-subs {
             type uint32;
             description "Final ingress subs";
           }
           leaf libstats-final-egress-general-error {
             type uint32;
             description "Final egress general error";
           }
           leaf libstats-final-ingress-general-error {
             type uint32;
             description "Final ingress general error";
           }
           leaf libstats-final-egress-kernel-error {
             type uint32;
             description "Final egress kernel error";
           }
           leaf libstats-final-ingress-kernel-error {
             type uint32;
             description "Final ingress kernel error";
           }
           leaf libstats-final-egress-memory-error {
             type uint32;
             description "Final egress memory error";
           }
           leaf libstats-final-ingress-memory-error {
             type uint32;
             description "Final ingress memory error";
           }
           leaf libstats-final-egress-ipc-error {
             type uint32;
             description "Final egress IPC error";
           }
           leaf libstats-final-ingress-ipc-error {
             type uint32;
             description "Final ingress IPC error";
           }
           leaf libstats-final-egress-validation-error {
             type uint32;
             description "Final egress validation error";
           }
           leaf libstats-final-ingress-validation-error {
             type uint32;
             description "Final ingress validation error";
           }
           leaf libstats-final-egress-db-lookup-error {
             type uint32;
             description "Final egress DB lookup error";
           }
           leaf libstats-final-ingress-db-lookup-error {
             type uint32;
             description "Final ingress DB lookup error";
           }
           leaf libstats-all-egress-msg-types {
             type uint32;
             description "All egress message types";
           }
           leaf libstats-all-ingress-msg-types {
             type uint32;
             description "All ingress message types";
           }
           leaf libstats-all-egress-general-error {
             type uint32;
             description "All egress general error";
           }
           leaf libstats-all-ingress-general-error {
             type uint32;
             description "All ingress general error";
           }
           leaf libstats-all-egress-kernel-error {
             type uint32;
             description "All egress kernel error";
           }
           leaf libstats-all-ingress-kernel-error {
             type uint32;
             description "All ingress kernel error";
           }
           leaf libstats-all-egress-memory-error {
             type uint32;
             description "All egress memory error";
           }
           leaf libstats-all-ingress-memory-error {
             type uint32;
             description "All ingress memory error";
           }
           leaf libstats-all-egress-ipc-error {
             type uint32;
             description "All egress IPC error";
           }
           leaf libstats-all-ingress-ipc-error {
             type uint32;
             description "All ingress IPC error";
           }
           leaf libstats-all-egress-validation-error {
             type uint32;
             description "All egress validation error";
           }
           leaf libstats-all-ingress-validation-error {
             type uint32;
             description "All ingress validation error";
           }
           leaf libstats-all-egress-db-lookup-error {
             type uint32;
             description "All egress DB lookup error";
           }
           leaf libstats-all-ingress-db-lookup-error {
             type uint32;
             description "All ingress DB lookup error";
           }
         }
         container aaa-module-re-authentication-statistics {
           leaf requests {
             type uint32;
             description "Number of requests received";
           }
           leaf accepts {
             type uint32;
             description "Number of authentication accepts";
           }
           leaf aborts {
             type uint32;
             description "Number of abort requests";
           }
           leaf challenges {
             type uint32;
             description "Number of authentication challenges";
           }
           leaf internal-errors {
             type uint32;
             description "Number of internal errors";
           }
           leaf rejects {
             type uint32;
             description "Number of authentication rejects";
           }
           leaf timeouts {
             type uint32;
             description "Number of requests timed out";
           }
         }
         container aaa-module-address-assignment-pool-statistics {
           leaf pool-name {
             type string;
             description "Pool name";
           }
           leaf link-name {
             type string;
             description "Link name";
           }
           leaf out-of-memory {
             type uint64;
             description "Number of times we have hit an out of memory condition";
           }
           leaf out-of-addresses {
             type uint64;
             description "Number of times we have hit an out of address condition";
           }
           leaf total-addresses {
             type uint64;
             description "Number of addresses in pool";
           }
           leaf used-addresses {
             type uint64;
             description "Number of addresses in use";
           }
           leaf excluded-addresses {
             type uint64;
             description "Number of addresses excluded";
           }
           leaf pool-usage {
             type int32;
             description "Percentage of addesses in use";
           }
         }
         container aaa-module-address-assignment-client-statistics {
           leaf client-name {
             type string;
             description "Client name";
           }
           leaf out-of-memory {
             type uint64;
             description "Number of times we have hit an out of memory condition";
           }
           leaf no-matches {
             type int32;
             description "Number of times we have not had an address match";
           }
         }
         container aaa-module-subscriber-statistics {
           leaf total-number-of-subscribers {
             type int32;
             description "Total number of subscribers";
           }
         }
         container aaa-module-radius-statistics {
           leaf radius-statistics-error {
             type string;
             description "Error message to display related to RADIUS server statistics";
           }
           container radius-server {
             description "RADIUS servers";
             leaf server-address {
               type ipaddr;
               description "RADIUS server address";
             }
             leaf profile {
               type string;
               description "Profile that includes this RADIUS server";
             }
             leaf max-outstanding {
               type int32;
               description "Maximum number of outstanding RADIUS requests for this server";
             }
             leaf current-outstanding {
               type int32;
               description "Current number of outstanding RADIUS requests for this server";
             }
             leaf peak-outstanding {
               type int32;
               description "Highest number of outstanding RADIUS requests for this server";
             }
             leaf fail-outstanding {
               type int32;
               description "Number of max-outstanding-exceeded failures for this server";
             }
           }
         }
         container aaa-module-radius-queue-statistics {
           leaf profile {
             type string;
             description "Profile that includes this RADIUS server";
           }
           leaf current-size {
             type int32;
             description "Current number of entries on this RADIUS queue";
           }
           leaf peak {
             type int32;
             description "Peak entries on this RADIUS queue";
           }
           leaf max-size {
             type int32;
             description "Maximum number of entries on this RADIUS queue";
           }
         }
       }
     }
   }
   rpc get-address-assignment-client-statistics {
     description "Show pool information based on client";
     input {
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       container aaa-module-statistics {
         leaf requests {
           type uint32;
           description "Number of requests received";
         }
         leaf multistack-requests {
           type uint32;
           description "Number of multistack requests received";
         }
         leaf accepts {
           type uint32;
           description "Number of authentication accepts";
         }
         leaf rejects {
           type uint32;
           description "Number of authentication rejects";
         }
         leaf radius-failures {
           type uint32;
           description "Number of RADIUS authentication failures";
         }
         leaf rejects-queue-request-deleted {
           type uint32;
           description "Number of authentication rejects due to queue request deleted";
         }
         leaf rejects-malformed-reply {
           type uint32;
           description "Number of authentication rejects due to malformed reply";
         }
         leaf rejects-no-server-configured {
           type uint32;
           description "Number of authentication rejects due to no servers configured";
         }
         leaf rejects-access-profile-config-unavailable {
           type uint32;
           description "Number of authentication rejects due to unavailable access profile configuration";
         }
         leaf rejects-no-client-record {
           type uint32;
           description "Number of authentication rejects due to failure to create client record";
         }
         leaf rejects-no-client-request {
           type uint32;
           description "Number of authentication rejects due to failure to create client request";
         }
         leaf rejects-no-build-auth-request {
           type uint32;
           description "Number of authentication rejects due to failure to build authentication request";
         }
         leaf rejects-no-server {
           type uint32;
           description "Number of authentication rejects due to failure to find server";
         }
         leaf rejects-no-create-handle {
           type uint32;
           description "Number of authentication rejects due to failure to create handle";
         }
         leaf rejects-no-queue-request {
           type uint32;
           description "Number of authentication rejects due to failure to queue request";
         }
         leaf rejects-invalid-credentials {
           type uint32;
           description "Number of authentication rejects due to invalid credentials";
         }
         leaf rejects-internal-failure {
           type uint32;
           description "Number of authentication rejects due to internal failure";
         }
         leaf rejects-malformed-request {
           type uint32;
           description "Number of authentication rejects due to malformed request";
         }
         leaf rejects-license-unavailable {
           type uint32;
           description "Number of authentication rejects due to license unavailable";
         }
         leaf rejects-redirect-requested {
           type uint32;
           description "Number of authentication rejects due to redirect requested";
         }
         leaf local-failures {
           type uint32;
           description "Number of local authentication failures";
         }
         leaf ldap-failures {
           type uint32;
           description "Number of LDAP lookup failures";
         }
         leaf accounting-request-failures {
           type uint32;
           description "Number of accounting requests failed to be sent out";
         }
         leaf accounting-request-success {
           type uint32;
           description "Number of accounting requests sent out sucessfully";
         }
         leaf timeouts {
           type uint32;
           description "Number of requests timed out";
         }
         leaf accounting-response-failures {
           type uint32;
           description "Number of accounting response failures";
         }
         leaf accounting-response-success {
           type uint32;
           description "Number of successful accounting responses";
         }
         leaf acct-unknown-responses {
           type uint32;
           description "Number of unknown accounting responses received";
         }
         leaf acct-requests-pending {
           type uint32;
           description "Number of pending account requests sent";
         }
         leaf acct-malformed-responses {
           type uint32;
           description "Number of malformed accounting responses received";
         }
         leaf acct-retransmissions {
           type uint32;
           description "Number of accounting retransmissions";
         }
         leaf acct-bad-authenticators {
           type uint32;
           description "Number of bad accounting authenticators";
         }
         leaf acct-packets-dropped {
           type uint32;
           description "Number of accounting packets dropped because not supported for config";
         }
         leaf acct-acct-on-requests {
           type uint32;
           description "Number of account on requests sent";
         }
         leaf acct-start-requests {
           type uint32;
           description "Number of accounting start requests sent";
         }
         leaf acct-interim-requests {
           type uint32;
           description "Number of accounting interim requests sent";
         }
         leaf acct-stop-requests {
           type uint32;
           description "Number of accounting stop requests sent";
         }
         leaf acct-rollover-requests {
           type uint32;
           description "Number of accounting requests that rollover to another server due to timeout/maxout";
         }
         leaf acct-acct-on-responses {
           type uint32;
           description "Number of accounting on responses received";
         }
         leaf acct-start-responses {
           type uint32;
           description "Number of accounting start responses received";
         }
         leaf acct-interim-responses {
           type uint32;
           description "Number of accounting interim responses received";
         }
         leaf acct-stop-responses {
           type uint32;
           description "Number of accounting stop responses received";
         }
         leaf multistack-suppressions {
           type uint32;
           description "Number of multistack requests suppressed";
         }
         leaf challenges {
           type uint32;
           description "Number of authentication challenges";
         }
         leaf processed-ok {
           type uint32;
           description "Number of requests successfully processed";
         }
         leaf processed-initial {
           type uint32;
           description "Number of requests initially processed successfully";
         }
         leaf processing-error {
           type uint32;
           description "Number of requests unsuccessfully processed";
         }
         leaf silent-drops {
           type uint32;
           description "Number of requests silently dropped";
         }
         leaf internal-errors {
           type uint32;
           description "Number of internal errors";
         }
         leaf aborts {
           type uint32;
           description "Number of abort requests";
         }
         leaf interim-updates-rcvd {
           type uint32;
           description "Number of interim updates received from libstats";
         }
         leaf interim-updates-sent {
           type uint32;
           description "Number of interim updates sent to radius";
         }
         leaf interim-updates-error-rcvd {
           type uint32;
           description "Number of interim error callbacks received";
         }
         leaf requested-final-stats {
           type uint32;
           description "Number of final stats requested from libstats";
         }
         leaf final-stats-retry-count {
           type uint32;
           description "Number of final stats retried";
         }
         leaf final-stats-rcvd {
           type uint32;
           description "Number of final stats updates received";
         }
         leaf final-stats-error-rcvd {
           type uint32;
           description "Number of final stats errors received";
         }
         leaf final-stats-sent {
           type uint32;
           description "Number of final stats sent to radius";
         }
         leaf time-only-info-sent {
           type uint32;
           description "Number of time info only stops sent";
         }
         leaf stats-timer-fired {
           type uint32;
           description "Number of times the accounting stats timer fired";
         }
         leaf libstats-interim-egress-subs {
           type uint32;
           description "Interim egress subs";
         }
         leaf libstats-interim-ingress-subs {
           type uint32;
           description "Interim ingress subs";
         }
         leaf libstats-interim-egress-general-error {
           type uint32;
           description "Interim egress general error";
         }
         leaf libstats-interim-ingress-general-error {
           type uint32;
           description "Interim ingress general error";
         }
         leaf libstats-interim-egress-kernel-error {
           type uint32;
           description "Interim egress kernel error";
         }
         leaf libstats-interim-ingress-kernel-error {
           type uint32;
           description "Interim ingress kernel error";
         }
         leaf libstats-interim-egress-memory-error {
           type uint32;
           description "Interim egress memory error";
         }
         leaf libstats-interim-ingress-memory-error {
           type uint32;
           description "Interim ingress memory error";
         }
         leaf libstats-interim-egress-ipc-error {
           type uint32;
           description "Interim egress IPC error";
         }
         leaf libstats-interim-ingress-ipc-error {
           type uint32;
           description "Interim ingress IPC error";
         }
         leaf libstats-interim-egress-validation-error {
           type uint32;
           description "Interim egress validation error";
         }
         leaf libstats-interim-ingress-validation-error {
           type uint32;
           description "Interim ingress validation error";
         }
         leaf libstats-interim-egress-db-lookup-error {
           type uint32;
           description "Interim egress db lookup error";
         }
         leaf libstats-interim-ingress-db-lookup-error {
           type uint32;
           description "Interim ingress db lookup error";
         }
         leaf libstats-final-egress-subs {
           type uint32;
           description "Final egress subs";
         }
         leaf libstats-final-ingress-subs {
           type uint32;
           description "Final ingress subs";
         }
         leaf libstats-final-egress-general-error {
           type uint32;
           description "Final egress general error";
         }
         leaf libstats-final-ingress-general-error {
           type uint32;
           description "Final ingress general error";
         }
         leaf libstats-final-egress-kernel-error {
           type uint32;
           description "Final egress kernel error";
         }
         leaf libstats-final-ingress-kernel-error {
           type uint32;
           description "Final ingress kernel error";
         }
         leaf libstats-final-egress-memory-error {
           type uint32;
           description "Final egress memory error";
         }
         leaf libstats-final-ingress-memory-error {
           type uint32;
           description "Final ingress memory error";
         }
         leaf libstats-final-egress-ipc-error {
           type uint32;
           description "Final egress IPC error";
         }
         leaf libstats-final-ingress-ipc-error {
           type uint32;
           description "Final ingress IPC error";
         }
         leaf libstats-final-egress-validation-error {
           type uint32;
           description "Final egress validation error";
         }
         leaf libstats-final-ingress-validation-error {
           type uint32;
           description "Final ingress validation error";
         }
         leaf libstats-final-egress-db-lookup-error {
           type uint32;
           description "Final egress DB lookup error";
         }
         leaf libstats-final-ingress-db-lookup-error {
           type uint32;
           description "Final ingress DB lookup error";
         }
         leaf libstats-all-egress-msg-types {
           type uint32;
           description "All egress message types";
         }
         leaf libstats-all-ingress-msg-types {
           type uint32;
           description "All ingress message types";
         }
         leaf libstats-all-egress-general-error {
           type uint32;
           description "All egress general error";
         }
         leaf libstats-all-ingress-general-error {
           type uint32;
           description "All ingress general error";
         }
         leaf libstats-all-egress-kernel-error {
           type uint32;
           description "All egress kernel error";
         }
         leaf libstats-all-ingress-kernel-error {
           type uint32;
           description "All ingress kernel error";
         }
         leaf libstats-all-egress-memory-error {
           type uint32;
           description "All egress memory error";
         }
         leaf libstats-all-ingress-memory-error {
           type uint32;
           description "All ingress memory error";
         }
         leaf libstats-all-egress-ipc-error {
           type uint32;
           description "All egress IPC error";
         }
         leaf libstats-all-ingress-ipc-error {
           type uint32;
           description "All ingress IPC error";
         }
         leaf libstats-all-egress-validation-error {
           type uint32;
           description "All egress validation error";
         }
         leaf libstats-all-ingress-validation-error {
           type uint32;
           description "All ingress validation error";
         }
         leaf libstats-all-egress-db-lookup-error {
           type uint32;
           description "All egress DB lookup error";
         }
         leaf libstats-all-ingress-db-lookup-error {
           type uint32;
           description "All ingress DB lookup error";
         }
         leaf pending-acct-stops {
           type uint32;
           description "Number of requests received";
         }
         leaf acct-backup-record-creation-requests {
           type uint32;
           description "Number of backup records creation requests sent to backup accounting module";
         }
         leaf acct-backup-radius-retransmissions {
           type uint32;
           description "Number of radius retries sent in backup context";
         }
         leaf acct-backup-request-timeouts {
           type uint32;
           description "Number of backup requests that timed out";
         }
         leaf acct-backup-request-failures {
           type uint32;
           description "Number of backup requests that encountered an error";
         }
         leaf acct-backup-request-success {
           type uint32;
           description "Number of backup requests that were success";
         }
         leaf acct-backup-request-replay-success {
           type uint32;
           description "Number of backup requests that were reconstructed successfully during replay";
         }
         leaf acct-backup-radius-pending-request {
           type uint32;
           description "Number of Backup requests sent to radius server but yet to receive response or error";
         }
         leaf acct-backup-in-flight-requests {
           type uint32;
           description "Number of Backup requests sent but yet to receive response or error";
         }
         leaf acct-backup-response-success {
           type uint32;
           description "Number of backup responses received and processed by backup module";
         }
         leaf acct-backup-malformed-responses {
           type uint32;
           description "Number of requests sent to backup accounting module";
         }
         leaf acct-backup-bad-authenticators {
           type uint32;
           description "Number of bad accounting authenticators in backup context";
         }
         leaf acct-backup-packets-dropped {
           type uint32;
           description "Number of backup responses dropped due to an issue not covered above";
         }
         leaf acct-backup-rollover-requests {
           type uint32;
           description "Number of backup requests that rollover to another server due to timeout/maxout";
         }
         leaf acct-backup-unknown-responses {
           type uint32;
           description "Number of backup requests that rollover to another server due to timeout/maxout";
         }
         leaf acct-backup-radius-requests {
           type uint32;
           description "Number of backup requests that rollover to another server due to timeout/maxout";
         }
         leaf acct-backup-radius-responses {
           type uint32;
           description "Number of backup requests that rollover to another server due to timeout/maxout";
         }
         leaf acct-backup-radius-timeouts {
           type uint32;
           description "Number of backup requests that rollover to another server due to timeout/maxout";
         }
         container aaa-module-authentication-statistics {
         }
         container aaa-module-pending-accounting-stop-statistics {
           leaf pending-acct-stops {
             type uint32;
             description "Number of requests received";
           }
         }
         container aaa-module-preauthentication-statistics {
           leaf requests {
             type uint32;
             description "Number of requests received";
           }
           leaf multistack-requests {
             type uint32;
             description "Number of multistack requests received";
           }
           leaf accepts {
             type uint32;
             description "Number of authentication accepts";
           }
           leaf rejects {
             type uint32;
             description "Number of authentication rejects";
           }
           leaf challenges {
             type uint32;
             description "Number of authentication challenges";
           }
           leaf timeouts {
             type uint32;
             description "Number of requests timed out";
           }
         }
         container aaa-module-accounting-statistics {
           leaf requests {
             type uint32;
             description "Number of requests received";
           }
           leaf accounting-request-failures {
             type uint32;
             description "Number of accounting requests failed to be sent out";
           }
           leaf accounting-request-success {
             type uint32;
             description "Number of accounting requests sent out sucessfully";
           }
           leaf timeouts {
             type uint32;
             description "Number of requests timed out";
           }
           leaf accounting-response-failures {
             type uint32;
             description "Number of accounting response failures";
           }
           leaf accounting-response-success {
             type uint32;
             description "Number of successful accounting responses";
           }
           leaf acct-rollover-requests {
             type uint32;
             description "Number of accounting requests that rollover to another server due to timeout/maxout";
           }
           leaf acct-unknown-responses {
             type uint32;
             description "Number of unknown accounting responses received";
           }
           leaf acct-requests-pending {
             type uint32;
             description "Number of pending account requests sent";
           }
           leaf acct-malformed-responses {
             type uint32;
             description "Number of malformed accounting responses received";
           }
           leaf acct-retransmissions {
             type uint32;
             description "Number of accounting retransmissions";
           }
           leaf acct-bad-authenticators {
             type uint32;
             description "Number of bad accounting authenticators";
           }
           leaf acct-packets-dropped {
             type uint32;
             description "Number of accounting packets dropped because not supported for config";
           }
           leaf acct-acct-on-requests {
             type uint32;
             description "Number of account on requests sent";
           }
           leaf acct-start-requests {
             type uint32;
             description "Number of accounting start requests sent";
           }
           leaf acct-interim-requests {
             type uint32;
             description "Number of accounting interim requests sent";
           }
           leaf acct-stop-requests {
             type uint32;
             description "Number of accounting stop requests sent";
           }
           leaf acct-acct-on-responses {
             type uint32;
             description "Number of accounting on responses received";
           }
           leaf acct-start-responses {
             type uint32;
             description "Number of accounting start responses received";
           }
           leaf acct-interim-responses {
             type uint32;
             description "Number of accounting interim responses received";
           }
           leaf acct-stop-responses {
             type uint32;
             description "Number of accounting stop responses received";
           }
           leaf acct-backup-record-creation-requests {
             type uint32;
             description "Number of backup records creation requests sent to backup accounting module";
           }
           leaf acct-backup-radius-retransmissions {
             type uint32;
             description "Number of radius retries sent in backup context";
           }
           leaf acct-backup-request-timeouts {
             type uint32;
             description "Number of backup requests that timed out";
           }
           leaf acct-backup-request-failures {
             type uint32;
             description "Number of backup requests that encountered an error";
           }
           leaf acct-backup-request-success {
             type uint32;
             description "Number of backup requests that were success";
           }
           leaf acct-backup-request-replay-success {
             type uint32;
             description "Number of backup requests that were reconstructed successfully during replay";
           }
           leaf acct-backup-radius-pending-request {
             type uint32;
             description "Number of Backup requests sent to radius server but yet to receive response or error";
           }
           leaf acct-backup-in-flight-requests {
             type uint32;
             description "Number of Backup requests sent but yet to receive response or error";
           }
           leaf acct-backup-response-success {
             type uint32;
             description "Number of backup responses received and processed by backup module";
           }
           leaf acct-backup-malformed-responses {
             type uint32;
             description "Number of requests sent to backup accounting module";
           }
           leaf acct-backup-bad-authenticators {
             type uint32;
             description "Number of bad accounting authenticators in backup context";
           }
           leaf acct-backup-packets-dropped {
             type uint32;
             description "Number of backup responses dropped due to an issue not covered above";
           }
           leaf acct-backup-rollover-requests {
             type uint32;
             description "Number of backup requests that rollover to another server due to timeout/maxout";
           }
           leaf acct-backup-unknown-responses {
             type uint32;
             description "Number of backup requests that rollover to another server due to timeout/maxout";
           }
           leaf acct-backup-radius-requests {
             type uint32;
             description "Number of backup requests that rollover to another server due to timeout/maxout";
           }
           leaf acct-backup-radius-responses {
             type uint32;
             description "Number of backup requests that rollover to another server due to timeout/maxout";
           }
           leaf acct-backup-radius-timeouts {
             type uint32;
             description "Number of backup requests that rollover to another server due to timeout/maxout";
           }
         }
         container aaa-module-dynamic-requests-statistics {
           leaf requests {
             type uint32;
             description "Number of requests received";
           }
           leaf processed-ok {
             type uint32;
             description "Number of requests successfully processed";
           }
           leaf processed-initial {
             type uint32;
             description "Number of requests initially processed successfully";
           }
           leaf processing-error {
             type uint32;
             description "Number of requests unsuccessfully processed";
           }
           leaf silent-drops {
             type uint32;
             description "Number of requests silently dropped";
           }
           container aaa-module-dynamic-requests-bulkcoa-statistics {
             leaf bulkcoa-received {
               type uint32;
               description "Number of bulk-CoA different transactions received";
             }
             leaf bulkcoa-success {
               type uint32;
               description "Number of bulk-CoA transactions successfully committed";
             }
             leaf bulkcoa-timeout {
               type uint32;
               description "Number of bulk-CoA transactions timedout";
             }
             leaf bulkcoa-transaction-mismatch {
               type uint32;
               description "Number of bulk-CoA transaction-id mismatch";
             }
             leaf bulkcoa-in-progress {
               type uint32;
               description "Number of bulk-CoA transactions with processing already in progress";
             }
             leaf bulkcoa-no-services {
               type uint32;
               description "Number of bulk-CoA transactions with no services in Bulk-CoA";
             }
             leaf bulkcoa-service-not-found {
               type uint32;
               description "Number of bulk-CoA transactions with service not found to deactivate";
             }
             leaf bulkcoa-service-active {
               type uint32;
               description "Number of bulk-CoA transactions with service already active";
             }
             leaf bulkcoa-execution-failure {
               type uint32;
               description "Number of bulk-CoA transactions with execution failure";
             }
             leaf bulkcoa-logout-in-progress {
               type uint32;
               description "Number of bulk-CoA transactions with logout in progress";
             }
             leaf bulkcoa-max-services {
               type uint32;
               description "Number of bulk-CoA transactions with max services exceeded";
             }
             leaf bulkcoa-max-requests {
               type uint32;
               description "Number of bulk-CoA transactions with max requests exceeded";
             }
             leaf bulkcoa-max-concurrent-coas {
               type uint32;
               description "Max Number of bulk-CoA transactions concurrently being processed";
             }
             leaf bulkcoa-extensible-services-errors {
               type uint32;
               description "Number of bulk-CoA transactions with extensible services errors";
             }
           }
         }
         container aaa-module-volume-accounting-statistics {
           leaf interim-updates-rcvd {
             type uint32;
             description "Number of interim updates received from libstats";
           }
           leaf interim-updates-sent {
             type uint32;
             description "Number of interim updates sent to radius";
           }
           leaf interim-updates-error-rcvd {
             type uint32;
             description "Number of interim error callbacks received";
           }
           leaf requested-final-stats {
             type uint32;
             description "Number of final stats requested from libstats";
           }
           leaf final-stats-retry-count {
             type uint32;
             description "Number of final stats retried";
           }
           leaf final-stats-rcvd {
             type uint32;
             description "Number of final stats updates received";
           }
           leaf final-stats-error-rcvd {
             type uint32;
             description "Number of final stats errors received";
           }
           leaf final-stats-sent {
             type uint32;
             description "Number of final stats sent to radius";
           }
           leaf time-only-info-sent {
             type uint32;
             description "Number of time info only stops sent";
           }
           leaf stats-timer-fired {
             type uint32;
             description "Number of times the accounting stats timer fired";
           }
           leaf libstats-interim-egress-subs {
             type uint32;
             description "Interim egress subs";
           }
           leaf libstats-interim-ingress-subs {
             type uint32;
             description "Interim ingress subs";
           }
           leaf libstats-interim-egress-general-error {
             type uint32;
             description "Interim egress general error";
           }
           leaf libstats-interim-ingress-general-error {
             type uint32;
             description "Interim ingress general error";
           }
           leaf libstats-interim-egress-kernel-error {
             type uint32;
             description "Interim egress kernel error";
           }
           leaf libstats-interim-ingress-kernel-error {
             type uint32;
             description "Interim ingress kernel error";
           }
           leaf libstats-interim-egress-memory-error {
             type uint32;
             description "Interim egress memory error";
           }
           leaf libstats-interim-ingress-memory-error {
             type uint32;
             description "Interim ingress memory error";
           }
           leaf libstats-interim-egress-ipc-error {
             type uint32;
             description "Interim egress IPC error";
           }
           leaf libstats-interim-ingress-ipc-error {
             type uint32;
             description "Interim ingress IPC error";
           }
           leaf libstats-interim-egress-validation-error {
             type uint32;
             description "Interim egress validation error";
           }
           leaf libstats-interim-ingress-validation-error {
             type uint32;
             description "Interim ingress validation error";
           }
           leaf libstats-interim-egress-db-lookup-error {
             type uint32;
             description "Interim egress db lookup error";
           }
           leaf libstats-interim-ingress-db-lookup-error {
             type uint32;
             description "Interim ingress db lookup error";
           }
           leaf libstats-final-egress-subs {
             type uint32;
             description "Final egress subs";
           }
           leaf libstats-final-ingress-subs {
             type uint32;
             description "Final ingress subs";
           }
           leaf libstats-final-egress-general-error {
             type uint32;
             description "Final egress general error";
           }
           leaf libstats-final-ingress-general-error {
             type uint32;
             description "Final ingress general error";
           }
           leaf libstats-final-egress-kernel-error {
             type uint32;
             description "Final egress kernel error";
           }
           leaf libstats-final-ingress-kernel-error {
             type uint32;
             description "Final ingress kernel error";
           }
           leaf libstats-final-egress-memory-error {
             type uint32;
             description "Final egress memory error";
           }
           leaf libstats-final-ingress-memory-error {
             type uint32;
             description "Final ingress memory error";
           }
           leaf libstats-final-egress-ipc-error {
             type uint32;
             description "Final egress IPC error";
           }
           leaf libstats-final-ingress-ipc-error {
             type uint32;
             description "Final ingress IPC error";
           }
           leaf libstats-final-egress-validation-error {
             type uint32;
             description "Final egress validation error";
           }
           leaf libstats-final-ingress-validation-error {
             type uint32;
             description "Final ingress validation error";
           }
           leaf libstats-final-egress-db-lookup-error {
             type uint32;
             description "Final egress DB lookup error";
           }
           leaf libstats-final-ingress-db-lookup-error {
             type uint32;
             description "Final ingress DB lookup error";
           }
           leaf libstats-all-egress-msg-types {
             type uint32;
             description "All egress message types";
           }
           leaf libstats-all-ingress-msg-types {
             type uint32;
             description "All ingress message types";
           }
           leaf libstats-all-egress-general-error {
             type uint32;
             description "All egress general error";
           }
           leaf libstats-all-ingress-general-error {
             type uint32;
             description "All ingress general error";
           }
           leaf libstats-all-egress-kernel-error {
             type uint32;
             description "All egress kernel error";
           }
           leaf libstats-all-ingress-kernel-error {
             type uint32;
             description "All ingress kernel error";
           }
           leaf libstats-all-egress-memory-error {
             type uint32;
             description "All egress memory error";
           }
           leaf libstats-all-ingress-memory-error {
             type uint32;
             description "All ingress memory error";
           }
           leaf libstats-all-egress-ipc-error {
             type uint32;
             description "All egress IPC error";
           }
           leaf libstats-all-ingress-ipc-error {
             type uint32;
             description "All ingress IPC error";
           }
           leaf libstats-all-egress-validation-error {
             type uint32;
             description "All egress validation error";
           }
           leaf libstats-all-ingress-validation-error {
             type uint32;
             description "All ingress validation error";
           }
           leaf libstats-all-egress-db-lookup-error {
             type uint32;
             description "All egress DB lookup error";
           }
           leaf libstats-all-ingress-db-lookup-error {
             type uint32;
             description "All ingress DB lookup error";
           }
         }
         container aaa-module-re-authentication-statistics {
           leaf requests {
             type uint32;
             description "Number of requests received";
           }
           leaf accepts {
             type uint32;
             description "Number of authentication accepts";
           }
           leaf aborts {
             type uint32;
             description "Number of abort requests";
           }
           leaf challenges {
             type uint32;
             description "Number of authentication challenges";
           }
           leaf internal-errors {
             type uint32;
             description "Number of internal errors";
           }
           leaf rejects {
             type uint32;
             description "Number of authentication rejects";
           }
           leaf timeouts {
             type uint32;
             description "Number of requests timed out";
           }
         }
         container aaa-module-address-assignment-pool-statistics {
           leaf pool-name {
             type string;
             description "Pool name";
           }
           leaf link-name {
             type string;
             description "Link name";
           }
           leaf out-of-memory {
             type uint64;
             description "Number of times we have hit an out of memory condition";
           }
           leaf out-of-addresses {
             type uint64;
             description "Number of times we have hit an out of address condition";
           }
           leaf total-addresses {
             type uint64;
             description "Number of addresses in pool";
           }
           leaf used-addresses {
             type uint64;
             description "Number of addresses in use";
           }
           leaf excluded-addresses {
             type uint64;
             description "Number of addresses excluded";
           }
           leaf pool-usage {
             type int32;
             description "Percentage of addesses in use";
           }
         }
         container aaa-module-address-assignment-client-statistics {
           leaf client-name {
             type string;
             description "Client name";
           }
           leaf out-of-memory {
             type uint64;
             description "Number of times we have hit an out of memory condition";
           }
           leaf no-matches {
             type int32;
             description "Number of times we have not had an address match";
           }
         }
         container aaa-module-subscriber-statistics {
           leaf total-number-of-subscribers {
             type int32;
             description "Total number of subscribers";
           }
         }
         container aaa-module-radius-statistics {
           leaf radius-statistics-error {
             type string;
             description "Error message to display related to RADIUS server statistics";
           }
           container radius-server {
             description "RADIUS servers";
             leaf server-address {
               type ipaddr;
               description "RADIUS server address";
             }
             leaf profile {
               type string;
               description "Profile that includes this RADIUS server";
             }
             leaf max-outstanding {
               type int32;
               description "Maximum number of outstanding RADIUS requests for this server";
             }
             leaf current-outstanding {
               type int32;
               description "Current number of outstanding RADIUS requests for this server";
             }
             leaf peak-outstanding {
               type int32;
               description "Highest number of outstanding RADIUS requests for this server";
             }
             leaf fail-outstanding {
               type int32;
               description "Number of max-outstanding-exceeded failures for this server";
             }
           }
         }
         container aaa-module-radius-queue-statistics {
           leaf profile {
             type string;
             description "Profile that includes this RADIUS server";
           }
           leaf current-size {
             type int32;
             description "Current number of entries on this RADIUS queue";
           }
           leaf peak {
             type int32;
             description "Peak entries on this RADIUS queue";
           }
           leaf max-size {
             type int32;
             description "Maximum number of entries on this RADIUS queue";
           }
         }
       }
     }
   }
   rpc get-aaa-terminate-code {
     description "Show terminate-code information";
     input {
       leaf verbosity_level {
         default "summary";
         type enumeration {
           enum "summary" {
             description "Display summary output(default)";
           }
           enum "brief" {
             description "Display brief output";
           }
           enum "detail" {
             description "Display detailed output";
           }
         }
       }
     }
   }
   rpc get-aaa-terminate-code-aaa {
     description "Limit display to AAA terminate codes";
     input {
       leaf verbosity_level {
         default "summary";
         type enumeration {
           enum "summary" {
             description "Display summary output(default)";
           }
           enum "brief" {
             description "Display brief output";
           }
           enum "detail" {
             description "Display detailed output";
           }
         }
       }
     }
   }
   rpc get-aaa-terminate-code-dhcp {
     description "Limit display to DHCP terminate codes";
     input {
       leaf verbosity_level {
         default "summary";
         type enumeration {
           enum "summary" {
             description "Display summary output(default)";
           }
           enum "brief" {
             description "Display brief output";
           }
           enum "detail" {
             description "Display detailed output";
           }
         }
       }
     }
   }
   rpc get-aaa-terminate-code-ppp {
     description "Limit display to PPP terminate codes";
     input {
       leaf verbosity_level {
         default "summary";
         type enumeration {
           enum "summary" {
             description "Display summary output(default)";
           }
           enum "brief" {
             description "Display brief output";
           }
           enum "detail" {
             description "Display detailed output";
           }
         }
       }
     }
   }
   rpc get-aaa-terminate-code-reverse {
     description "Show reverse terminate-code information";
     input {
       leaf verbosity_level {
         default "summary";
         type enumeration {
           enum "summary" {
             description "Display summary output(default)";
           }
           enum "brief" {
             description "Display brief output";
           }
           enum "detail" {
             description "Display detailed output";
           }
         }
       }
     }
   }
   rpc get-aaa-terminate-code-reverse-aaa {
     description "Limit display to AAA terminate codes";
     input {
       leaf verbosity_level {
         default "summary";
         type enumeration {
           enum "summary" {
             description "Display summary output(default)";
           }
           enum "brief" {
             description "Display brief output";
           }
           enum "detail" {
             description "Display detailed output";
           }
         }
       }
     }
   }
   rpc get-aaa-terminate-code-reverse-dhcp {
     description "Limit display to DHCP terminate codes";
     input {
       leaf verbosity_level {
         default "summary";
         type enumeration {
           enum "summary" {
             description "Display summary output(default)";
           }
           enum "brief" {
             description "Display brief output";
           }
           enum "detail" {
             description "Display detailed output";
           }
         }
       }
     }
   }
   rpc get-aaa-terminate-code-reverse-ppp {
     description "Limit display to PPP terminate codes";
     input {
       leaf verbosity_level {
         default "summary";
         type enumeration {
           enum "summary" {
             description "Display summary output(default)";
           }
           enum "brief" {
             description "Display brief output";
           }
           enum "detail" {
             description "Display detailed output";
           }
         }
       }
     }
   }
   rpc get-aaa-accounting-status {
     description "Statistics of RADIUS servers";
     output {
       container aaa-accounting-status {
         container aaa-accounting-status-list {
           leaf profile {
             type string;
             description "Profile that includes this RADIUS server";
           }
           leaf logical-system {
             type string;
             description "Logical system this RADIUS server is part of";
           }
           leaf routing-instance {
             type string;
             description "Routing instance this RADIUS server is part of";
           }
           leaf acct-on-response {
             type string;
             description "ACCT-ON Response from the RADIUS server";
           }
         }
       }
     }
   }
   rpc get-radius-servers-table {
     description "Show RADIUS servers information";
     input {
       leaf verbosity_level {
         default "brief";
         type enumeration {
           enum "brief" {
             description "Display brief output";
           }
           enum "detail" {
             description "Display detailed output";
           }
         }
       }
     }
     output {
       container aaa-module-radius-servers-information {
         container brief {
           container aaa-module-profile-radius-servers {
             leaf profile-name {
               type string;
               description "Profile-name using which the user is being authenticated";
             }
             leaf server-address {
               type ipaddr;
               description "RADIUS server address";
             }
             leaf authentication-port {
               type uint32;
               description "RADIUS authentication port";
             }
             leaf preauthentication-port {
               type uint32;
               description "RADIUS preauthentication port";
             }
             leaf accounting-port {
               type uint32;
               description "RADIUS accounting port";
             }
             leaf accounting-retry {
               type uint32;
               description "RADIUS accounting retry";
             }
             leaf accounting-timeout {
               type uint32;
               description "RADIUS accounting accounting timeout";
             }
             leaf available-status {
               type string;
               description "RADIUS server status";
             }
           }
           container aaa-module-radius-servers-statistics {
             leaf server-address {
               type ipaddr;
               description "RADIUS server address";
             }
             leaf last-rtt {
               type uint32;
               description "Last Round Trip Time";
             }
             leaf authentication-requests {
               type uint32;
               description "Authentication requests";
             }
             leaf authentication-rollover-requests {
               type uint32;
               description "Authentication rollover requests";
             }
             leaf authentication-retransmissions {
               type uint32;
               description "Authentication retransmissions";
             }
             leaf accepts {
               type uint32;
               description "Number of authentication accepts";
             }
             leaf rejects {
               type uint32;
               description "Number of authentication rejects";
             }
             leaf challenges {
               type uint32;
               description "Number of authentication challenges";
             }
             leaf authentication-malformed-responses {
               type uint32;
               description "Authentication malformed responses";
             }
             leaf authentication-bad-authenticators {
               type uint32;
               description "Authentication malformed responses";
             }
             leaf authentication-requests-pending {
               type uint32;
               description "Authentication requests pending";
             }
             leaf authentication-timeouts {
               type uint32;
               description "Authentication request timeouts";
             }
             leaf authentication-unknown-responses {
               type uint32;
               description "Authentication unknown responses";
             }
             leaf authentication-packets-dropped {
               type uint32;
               description "Authentication packets dropped";
             }
             leaf preauthentication-requests {
               type uint32;
               description "Preauthentication requests";
             }
             leaf preauthentication-rollover-requests {
               type uint32;
               description "Preauthentication rollover requests";
             }
             leaf preauthentication-retransmissions {
               type uint32;
               description "Preauthentication retransmissions";
             }
             leaf preauthentication-accepts {
               type uint32;
               description "Preauthentication accepts";
             }
             leaf preauthentication-rejects {
               type uint32;
               description "Preauthentication rejects";
             }
             leaf preauthentication-challenges {
               type uint32;
               description "Preauthentication challenges";
             }
             leaf preauthentication-malformed-responses {
               type uint32;
               description "Preauthentication malformed responses";
             }
             leaf preauthentication-bad-authenticators {
               type uint32;
               description "Preauthentication bad authenticators";
             }
             leaf preauthentication-requests-pending {
               type uint32;
               description "Preauthentication requests pending";
             }
             leaf preauthentication-timeouts {
               type uint32;
               description "Preauthentication request timeouts";
             }
             leaf preauthentication-unknown-responses {
               type uint32;
               description "Preauthentication unknown responses";
             }
             leaf preauthentication-packets-dropped {
               type uint32;
               description "Preauthentication packets dropped";
             }
             leaf accounting-start-requests {
               type uint32;
               description "Accounting start requests";
             }
             leaf accounting-interim-requests {
               type uint32;
               description "Accounting interim requests";
             }
             leaf accounting-stop-requests {
               type uint32;
               description "Accounting stop requests";
             }
             leaf accounting-reject-requests {
               type uint32;
               description "Accounting reject requests";
             }
             leaf accounting-rollover-requests {
               type uint32;
               description "Accounting rollover requests";
             }
             leaf accounting-retransmissions {
               type uint32;
               description "Accounting request retransmissions";
             }
             leaf accounting-start-response {
               type uint32;
               description "Accounting start responses";
             }
             leaf accounting-interim-response {
               type uint32;
               description "Accounting interim responses";
             }
             leaf accounting-stop-response {
               type uint32;
               description "Accounting stop responses";
             }
             leaf accounting-reject-response {
               type uint32;
               description "Accounting reject response";
             }
             leaf accounting-malformed-response {
               type uint32;
               description "Accounting malformed responses";
             }
             leaf accounting-bad-authenticators {
               type uint32;
               description "Accounting bad authenticators";
             }
             leaf accounting-requests-pending {
               type uint32;
               description "Accounting requests pending";
             }
             leaf accounting-timeouts {
               type uint32;
               description "Accounting request timeouts";
             }
             leaf accounting-unknown-responses {
               type uint32;
               description "Accounting unknown responses";
             }
             leaf accounting-packets-dropped {
               type uint32;
               description "Accounting packets dropped";
             }
           }
         }
         container detail {
           container aaa-module-profile-radius-servers {
             leaf profile-name {
               type string;
               description "Profile-name using which the user is being authenticated";
             }
             leaf server-address {
               type ipaddr;
               description "RADIUS server address";
             }
             leaf authentication-port {
               type uint32;
               description "RADIUS authentication port";
             }
             leaf preauthentication-port {
               type uint32;
               description "RADIUS preauthentication port";
             }
             leaf accounting-port {
               type uint32;
               description "RADIUS accounting port";
             }
             leaf accounting-retry {
               type uint32;
               description "RADIUS accounting retry";
             }
             leaf accounting-timeout {
               type uint32;
               description "RADIUS accounting accounting timeout";
             }
             leaf available-status {
               type string;
               description "RADIUS server status";
             }
             leaf last-rtt {
               type uint32;
               description "Last Round Trip Time";
             }
             leaf authentication-requests {
               type uint32;
               description "Authentication requests";
             }
             leaf authentication-rollover-requests {
               type uint32;
               description "Authentication rollover requests";
             }
             leaf authentication-retransmissions {
               type uint32;
               description "Authentication retransmissions";
             }
             leaf accepts {
               type uint32;
               description "Number of authentication accepts";
             }
             leaf rejects {
               type uint32;
               description "Number of authentication rejects";
             }
             leaf challenges {
               type uint32;
               description "Number of authentication challenges";
             }
             leaf authentication-malformed-responses {
               type uint32;
               description "Authentication malformed responses";
             }
             leaf authentication-bad-authenticators {
               type uint32;
               description "Authentication malformed responses";
             }
             leaf authentication-requests-pending {
               type uint32;
               description "Authentication requests pending";
             }
             leaf authentication-timeouts {
               type uint32;
               description "Authentication request timeouts";
             }
             leaf authentication-unknown-responses {
               type uint32;
               description "Authentication unknown responses";
             }
             leaf authentication-packets-dropped {
               type uint32;
               description "Authentication packets dropped";
             }
             leaf preauthentication-requests {
               type uint32;
               description "Preauthentication requests";
             }
             leaf preauthentication-rollover-requests {
               type uint32;
               description "Preauthentication rollover requests";
             }
             leaf preauthentication-retransmissions {
               type uint32;
               description "Preauthentication retransmissions";
             }
             leaf preauthentication-accepts {
               type uint32;
               description "Preauthentication accepts";
             }
             leaf preauthentication-rejects {
               type uint32;
               description "Preauthentication rejects";
             }
             leaf preauthentication-challenges {
               type uint32;
               description "Preauthentication challenges";
             }
             leaf preauthentication-malformed-responses {
               type uint32;
               description "Preauthentication malformed responses";
             }
             leaf preauthentication-bad-authenticators {
               type uint32;
               description "Preauthentication bad authenticators";
             }
             leaf preauthentication-requests-pending {
               type uint32;
               description "Preauthentication requests pending";
             }
             leaf preauthentication-timeouts {
               type uint32;
               description "Preauthentication request timeouts";
             }
             leaf preauthentication-unknown-responses {
               type uint32;
               description "Preauthentication unknown responses";
             }
             leaf preauthentication-packets-dropped {
               type uint32;
               description "Preauthentication packets dropped";
             }
             leaf accounting-start-requests {
               type uint32;
               description "Accounting start requests";
             }
             leaf accounting-interim-requests {
               type uint32;
               description "Accounting interim requests";
             }
             leaf accounting-stop-requests {
               type uint32;
               description "Accounting stop requests";
             }
             leaf accounting-reject-requests {
               type uint32;
               description "Accounting reject requests";
             }
             leaf accounting-rollover-requests {
               type uint32;
               description "Accounting rollover requests";
             }
             leaf accounting-retransmissions {
               type uint32;
               description "Accounting request retransmissions";
             }
             leaf accounting-start-response {
               type uint32;
               description "Accounting start responses";
             }
             leaf accounting-interim-response {
               type uint32;
               description "Accounting interim responses";
             }
             leaf accounting-stop-response {
               type uint32;
               description "Accounting stop responses";
             }
             leaf accounting-reject-response {
               type uint32;
               description "Accounting reject response";
             }
             leaf accounting-malformed-response {
               type uint32;
               description "Accounting malformed responses";
             }
             leaf accounting-bad-authenticators {
               type uint32;
               description "Accounting bad authenticators";
             }
             leaf accounting-requests-pending {
               type uint32;
               description "Accounting requests pending";
             }
             leaf accounting-timeouts {
               type uint32;
               description "Accounting request timeouts";
             }
             leaf accounting-unknown-responses {
               type uint32;
               description "Accounting unknown responses";
             }
             leaf accounting-packets-dropped {
               type uint32;
               description "Accounting packets dropped";
             }
           }
           container aaa-module-radius-servers-statistics {
             leaf server-address {
               type ipaddr;
               description "RADIUS server address";
             }
             leaf last-rtt {
               type uint32;
               description "Last Round Trip Time";
             }
             leaf authentication-requests {
               type uint32;
               description "Authentication requests";
             }
             leaf authentication-rollover-requests {
               type uint32;
               description "Authentication rollover requests";
             }
             leaf authentication-retransmissions {
               type uint32;
               description "Authentication retransmissions";
             }
             leaf accepts {
               type uint32;
               description "Number of authentication accepts";
             }
             leaf rejects {
               type uint32;
               description "Number of authentication rejects";
             }
             leaf challenges {
               type uint32;
               description "Number of authentication challenges";
             }
             leaf authentication-malformed-responses {
               type uint32;
               description "Authentication malformed responses";
             }
             leaf authentication-bad-authenticators {
               type uint32;
               description "Authentication malformed responses";
             }
             leaf authentication-requests-pending {
               type uint32;
               description "Authentication requests pending";
             }
             leaf authentication-timeouts {
               type uint32;
               description "Authentication request timeouts";
             }
             leaf authentication-unknown-responses {
               type uint32;
               description "Authentication unknown responses";
             }
             leaf authentication-packets-dropped {
               type uint32;
               description "Authentication packets dropped";
             }
             leaf preauthentication-requests {
               type uint32;
               description "Preauthentication requests";
             }
             leaf preauthentication-rollover-requests {
               type uint32;
               description "Preauthentication rollover requests";
             }
             leaf preauthentication-retransmissions {
               type uint32;
               description "Preauthentication retransmissions";
             }
             leaf preauthentication-accepts {
               type uint32;
               description "Preauthentication accepts";
             }
             leaf preauthentication-rejects {
               type uint32;
               description "Preauthentication rejects";
             }
             leaf preauthentication-challenges {
               type uint32;
               description "Preauthentication challenges";
             }
             leaf preauthentication-malformed-responses {
               type uint32;
               description "Preauthentication malformed responses";
             }
             leaf preauthentication-bad-authenticators {
               type uint32;
               description "Preauthentication bad authenticators";
             }
             leaf preauthentication-requests-pending {
               type uint32;
               description "Preauthentication requests pending";
             }
             leaf preauthentication-timeouts {
               type uint32;
               description "Preauthentication request timeouts";
             }
             leaf preauthentication-unknown-responses {
               type uint32;
               description "Preauthentication unknown responses";
             }
             leaf preauthentication-packets-dropped {
               type uint32;
               description "Preauthentication packets dropped";
             }
             leaf accounting-start-requests {
               type uint32;
               description "Accounting start requests";
             }
             leaf accounting-interim-requests {
               type uint32;
               description "Accounting interim requests";
             }
             leaf accounting-stop-requests {
               type uint32;
               description "Accounting stop requests";
             }
             leaf accounting-reject-requests {
               type uint32;
               description "Accounting reject requests";
             }
             leaf accounting-rollover-requests {
               type uint32;
               description "Accounting rollover requests";
             }
             leaf accounting-retransmissions {
               type uint32;
               description "Accounting request retransmissions";
             }
             leaf accounting-start-response {
               type uint32;
               description "Accounting start responses";
             }
             leaf accounting-interim-response {
               type uint32;
               description "Accounting interim responses";
             }
             leaf accounting-stop-response {
               type uint32;
               description "Accounting stop responses";
             }
             leaf accounting-reject-response {
               type uint32;
               description "Accounting reject response";
             }
             leaf accounting-malformed-response {
               type uint32;
               description "Accounting malformed responses";
             }
             leaf accounting-bad-authenticators {
               type uint32;
               description "Accounting bad authenticators";
             }
             leaf accounting-requests-pending {
               type uint32;
               description "Accounting requests pending";
             }
             leaf accounting-timeouts {
               type uint32;
               description "Accounting request timeouts";
             }
             leaf accounting-unknown-responses {
               type uint32;
               description "Accounting unknown responses";
             }
             leaf accounting-packets-dropped {
               type uint32;
               description "Accounting packets dropped";
             }
           }
         }
       }
     }
   }
   rpc get-address-assignment-pool-table {
     description "Show pool information";
     input {
       leaf get-address-assignment-pool-table-specific {
         description "Show information for a specific pool";
         type string;
         mandatory true;
       }
       leaf routing-instance {
         description "Name of routing instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
   }
   rpc get-address-assignment-preserved-table {
     description "Show preserved addresses";
   }
   rpc node-secret-file-table {
     description "Show SecurID server's node secret file path";
     output {
       container node-secret-file-table {
         container node-secret-file-table-entry {
           leaf server-name {
             type string;
             description "Name of the SecurID server associated with this node secret file";
           }
           leaf node-secret-file {
             type string;
             description "Path of the node secret file";
           }
         }
       }
     }
   }
   rpc get-gx-plus-state-information {
     description "Show gx-plus state information";
     output {
       container gx-plus-state-information {
         leaf gx-plus-engine-state {
           type string;
           description "Gx-plus engine state";
         }
         leaf gx-plus-config-state {
           type string;
           description "Gx-plus configuration state";
         }
         leaf gx-plus-active-config-state {
           type string;
           description "Gx-plus active configuration state";
         }
         leaf gx-plus-diameter-config-state {
           type string;
           description "Gx-plus diameter configuration state";
         }
         leaf gx-plus-total-prov-count {
           type uint32;
           description "Gx-plus number of entries, including pending, not including logouts";
         }
         leaf gx-plus-pending-prov-count {
           type uint32;
           description "Gx-plus number of pending entries";
         }
         leaf gx-plus-pending-logout-count {
           type uint32;
           description "Gx-plus number of pending logouts";
         }
       }
     }
   }
   rpc get-gx-plus-sync-state-information {
     description "Show gx-plus sync-state information";
     output {
       container gx-plus-sync-state-information {
         leaf gx-plus-sync-state-no-events {
           type string;
           description "No pending events";
         }
         container gx-plus-sync-state-data {
           description "Gx-plus sync state data";
           leaf gx-plus-sync-event-name {
             type string;
             description "Gx-plus sync-event name";
           }
           leaf gx-plus-sync-event-timeout {
             type uint32;
             description "Gx-plus sync-event time until next try timout (milliseconds)";
           }
         }
       }
     }
   }
   rpc get-gx-plus-statistics-information {
     description "Show gx-plus statistics information";
     input {
       leaf verbosity_level {
         default "brief";
         type enumeration {
           enum "brief" {
             description "Show brief output (deafault)";
           }
           enum "detail" {
             description "Show detailed output";
           }
           enum "extensive" {
             description "Show extensive output";
           }
         }
       }
     }
     output {
       container gx-plus-statistics-information {
         leaf gx-plus-statistics-no-counters {
           type string;
           description "No counters to display";
         }
         container gx-plus-statistics-table {
           description "Gx-plus statistics table";
           container gx-plus-statistics-data {
             description "Gx-plus statistics data";
           }
         }
         container gx-plus-sync-event-stats-table {
           description "Gx-plus sync-event stats table";
           container gx-plus-sync-event-stats-data {
             description "Gx-plus sync-event stats data";
           }
         }
         container gx-plus-sync-event-de-stats-table {
           description "Gx-plus syn-even diameter events stats table";
           container gx-plus-sync-event-de-stats-data {
             description "Gx-plus sync-event diameter event stats data";
           }
         }
         container gx-plus-upstream-stats-table {
           description "Gx-plus upstream stats table";
           container gx-plus-upstream-stats-data {
             description "Gx-plus upsteam stats data";
           }
         }
         container gx-plus-upstream-de-stats-table {
           description "Gx-plus upstream diameter events stats table";
           container gx-plus-upstream-de-stats-data {
             description "Gx-plus upsteam diameter event stats data";
           }
         }
         container gx-plus-downstream-stats-table {
           description "Gx-plus downstream stats-table";
           container gx-plus-downstream-stats-data {
             description "Gx-plus downsteam stats data";
           }
         }
       }
     }
   }
   rpc get-nasreq-counters {
     description "Nasreq module statistics";
   }
   rpc get-pcrf-state-information {
     description "Show pcrf state information";
     output {
       container pcrf-state-information {
         container pcrf-state-table {
           description "Pcrf state table";
           container pcrf-state-data {
             description "Pcrf state data";
           }
         }
       }
     }
   }
   rpc get-pcrf-statistics-information {
     description "Show pcrf statistics information";
     input {
       leaf verbosity_level {
         default "brief";
         type enumeration {
           enum "brief" {
             description "Show brief output (deafault)";
           }
           enum "detail" {
             description "Show detailed output";
           }
           enum "extensive" {
             description "Show extensive output";
           }
         }
       }
     }
     output {
       container pcrf-statistics-information {
         leaf pcrf-statistics-no-counters {
           type string;
           description "No counters to display";
         }
         container pcrf-statistics-table {
           description "Pcrf statistics table";
           container pcrf-statistics-data {
             description "Pcrf statistics data";
           }
         }
         container pcrf-diameter-event-table {
           description "Pcrf diameter event table";
           container pcrf-diameter-event-data {
             description "Pcrf diameter-event data";
           }
         }
         container pcrf-rule-install-table {
           description "Pcrf install table";
           container pcrf-rule-install-data {
             description "Pcrf rule install data";
           }
         }
         container pcrf-rule-remove-table {
           description "Pcrf remove table";
           container pcrf-rule-remove-data {
             description "Pcrf rule remove data";
           }
         }
       }
     }
   }
   rpc get-ocs-state-information {
     description "Show ocs state information";
     output {
       container ocs-state-information {
         container ocs-state-table {
           description "Ocs state table";
           container ocs-state-data {
             description "Ocs state data";
           }
         }
       }
     }
   }
   rpc get-ocs-statistics-information {
     description "Show ocs statistics information";
     input {
       leaf verbosity_level {
         default "brief";
         type enumeration {
           enum "brief" {
             description "Show brief output (deafault)";
           }
           enum "detail" {
             description "Show detailed output";
           }
           enum "extensive" {
             description "Show extensive output";
           }
         }
       }
     }
     output {
       container ocs-statistics-information {
         leaf ocs-statistics-no-counters {
           type string;
           description "No counters to display";
         }
         container ocs-statistics-table {
           description "Ocs statistics table";
           container ocs-statistics-data {
             description "Ocs statistics data";
           }
         }
         container ocs-diameter-event-table {
           description "Ocs diameter event table";
           container ocs-diameter-event-data {
             description "Ocs diameter-event data";
           }
         }
       }
     }
   }
 }
