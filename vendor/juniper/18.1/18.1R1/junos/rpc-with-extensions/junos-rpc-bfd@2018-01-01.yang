/*
 * Copyright (c) 2018 Juniper Networks, Inc.
 * All rights reserved.
 */
 module junos-rpc-bfd {
   namespace "http://yang.juniper.net/junos/rpc/bfd";

   prefix bfd;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for bfd command(s)";

   revision 2018-01-01 {
     description "Junos: 18.1R1.9";
   }

   rpc get-bfd-session-information {
     description "Show all BFD sessions";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml bfd-session-information;
         }
         case multichassis-tag {
           anyxml multi-routing-engine-results;
         }
       }
     }
   }
   rpc get-bfd-session-revert {
     description "Show BFD session on revert thread";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml bfd-thread-information;
         }
         case multichassis-tag {
           anyxml multi-routing-engine-results;
         }
       }
     }
   }
   rpc get-bfd-session-address {
     description "Show BFD session with specific neighbor address";
     input {
       leaf session_addr {
         description "Neighbor address of session";
         type jt:ipaddr;
         mandatory true;
       }
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml bfd-session-information;
         }
         case multichassis-tag {
           anyxml multi-routing-engine-results;
         }
       }
     }
   }
   rpc get-bfd-session-discriminator {
     description "Show BFD session with specific local discriminator";
     input {
       leaf discr_number {
         description "Local discriminator of session";
         type union {
           type uint32;
           type string {
             pattern "<.*>|$.*";
           }
         }
         mandatory true;
       }
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml bfd-session-information;
         }
         case multichassis-tag {
           anyxml multi-routing-engine-results;
         }
       }
     }
   }
   rpc get-bfd-session-client {
     description "Show all BFD sessions of a particular client";
     output {
       choice output_c {
         case output-tag {
           leaf output {
             type string;
           }
         }
         case actual-tag {
           anyxml bfd-session-client;
         }
         case multichassis-tag {
           anyxml multi-routing-engine-results;
         }
       }
     }
   }
   rpc get-bfd-session-client-rsvp {
     description "Show RSVP-OAM BFD sessions";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml bfd-session-information;
         }
         case multichassis-tag {
           anyxml multi-routing-engine-results;
         }
       }
     }
   }
   rpc get-bfd-session-client-vpls {
     description "Show VPLS-OAM BFD sessions";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml bfd-session-information;
         }
         case multichassis-tag {
           anyxml multi-routing-engine-results;
         }
       }
     }
   }
   rpc get-bfd-session-client-vpls-instance {
     description "Show vpls bfd sessions under the instance";
     input {
       leaf routing-instance {
         description "Name of routing instance";
         type string {
           junos:posix-pattern "!^((__.*__)|(all)|(.*[ ].*)|(\"\")|(.{129,}))$";
           junos:pattern-message "Must be a non-reserved string of 128 characters or less with no spaces.";
         }
         mandatory true;
       }
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml bfd-session-information;
         }
         case multichassis-tag {
           anyxml multi-routing-engine-results;
         }
       }
     }
   }
   rpc get-bfd-session-prefix {
     description "Show all BFD sessions for this LDP FEC";
     input {
       leaf prefix_addr {
         description "Prefix address of session";
         type jt:ipprefix;
         mandatory true;
       }
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml bfd-session-information;
         }
         case multichassis-tag {
           anyxml multi-routing-engine-results;
         }
       }
     }
   }
   rpc get-bfd-subscriber-session {
     description "Show subscriber session info";
     input {
       leaf verbosity {
         default "brief";
         type enumeration {
           enum "summary" {
             description "Display summary output";
           }
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml bfd-session-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
