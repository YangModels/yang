/*
 * Copyright (c) 2018 Juniper Networks, Inc.
 * All rights reserved.
 */
 module junos-rpc-test {
   namespace "http://yang.juniper.net/junos/rpc/test";

   prefix test;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for test command(s)";

   revision 2018-01-01 {
     description "Junos: 18.1R1.9";
   }

   rpc test-routing-policy {
     description "Import and export policy evaluation";
     input {
       leaf policy {
         description "Policy name";
         type string;
       }
       leaf prefix {
         description "Destination prefix";
         type string;
       }
     }
     output {
       choice output_c {
         case output-tag {
           leaf output {
             type string;
           }
         }
         case actual-tag {
           anyxml route-information;
         }
         case multichassis-tag {
           anyxml multi-routing-engine-results;
         }
       }
     }
   }
   rpc jdhcpd-code-coverage {
     description "Execute functions for code coverage";
     output {
       leaf output {
         type string;
       }
     }
   }
   rpc test-rfc2544-benchmarking {
     description "Rfc2544 test configuration";
     output {
       leaf output {
         type string;
       }
     }
   }
   rpc test-rfc2544-benchmarking-test {
     description "Start/stop a rfc2544 test";
     input {
       leaf test-name {
         description "Test name";
         type string;
       }
       leaf test-start-stop-clear {
         type enumeration {
           enum "start" {
             description "Start test";
           }
           enum "stop" {
             description "Stop test";
           }
           enum "clear-counters" {
             description "Clear test counters";
           }
         }
         mandatory true;
       }
       leaf routing-instance {
         description "Name of routing instance for rfc2544 test ";
         type string {
           junos:posix-pattern "!^((__.*__)|(all)|(.*[ ].*)|(\"\")|(.{129,}))$";
           junos:pattern-message "Must be a non-reserved string of 128 characters or less with no spaces.";
         }
       }
     }
     output {
       leaf output {
         type string;
       }
     }
   }
   rpc test-rfc2544-benchmarking-test-id {
     description "Stop a rfc2544 test";
     input {
       leaf test-id {
         description "Test id";
         type union {
           type uint32;
           type string {
             pattern "<.*>|$.*";
           }
         }
       }
       leaf test-stop {
         type enumeration {
           enum "stop" {
             description "Stop test";
           }
         }
       }
     }
     output {
       leaf output {
         type string;
       }
     }
   }
   rpc get-test-services-l2tp-tunnel-result {
     description "Check L2TP tunnel configuration for a subscriber";
     input {
       leaf user {
         description "Name of the subscriber";
         type string;
         mandatory true;
       }
       leaf password {
         description "Password for the subscriber";
         type string;
       }
       leaf tunnel-name {
         description "Name of the L2TP tunnel";
         type string;
       }
     }
     output {
       choice output_c {
         case output-tag {
           leaf output {
             type string;
           }
         }
         case actual-tag {
           anyxml test-services-l2tp-tunnel-result;
         }
         case multichassis-tag {
           anyxml multi-routing-engine-results;
         }
       }
     }
   }
   rpc test-services-traffic-load-balance-code-coverage {
     description "Execute Traffic load balance code-coverage";
     input {
       leaf database-id {
         description "Database identifier";
         type enumeration {
           enum "all" {
             description "All databases";
           }
           enum "probe" {
             description "Probe database";
           }
           enum "firewall" {
             description "Firewall";
           }
           enum "ip-db" {
             description "Ip database";
           }
           enum "clear-db" {
             description "Clear all databases";
           }
           enum "stats" {
             description "Stats";
           }
           enum "group-db" {
             description "Group database";
           }
           enum "heap" {
             description "Heap";
           }
           enum "virtual-svc-db" {
             description "Virtual srv database";
           }
           enum "instance-db" {
             description "Instance database";
           }
           enum "real-svc-db" {
             description "Real srv database";
           }
           enum "group-real-svc-db" {
             description "Group real srv database";
           }
           enum "validation-db" {
             description "Validation database";
           }
           enum "pconn-db" {
             description "Pconn database";
           }
           enum "gencfg-db" {
             description "Gencfg database";
           }
           enum "main" {
             description "Main functions";
           }
           enum "snmp" {
             description "SNMP functions";
           }
           enum "ui" {
             description "UI functions";
           }
           enum "config-parse" {
             description "Config parse functions";
           }
           enum "filter-config" {
             description "Filter database";
           }
           enum "ssd" {
             description "SSD functions";
           }
           enum "commit-checks" {
             description "Commit checks";
           }
         }
       }
     }
     output {
       leaf output {
         type string;
       }
     }
   }
   rpc test-services-traffic-load-balance-inject-error {
     description "Execute Traffic load balance error-injection";
     input {
       leaf error-id {
         description "Error identifier";
         type union {
           type uint32;
           type string {
             pattern "<.*>|$.*";
           }
         }
         mandatory true;
       }
       leaf always-fail {
         description "Fail always";
         type enumeration {
           enum "enable" {
             description "Enable failure";
           }
           enum "disable" {
             description "Disable failure";
           }
         }
         mandatory true;
       }
     }
     output {
       leaf output {
         type string;
       }
     }
   }
   rpc test-services-url-filter-inject-error {
     description "Execute URL Filtering error-injection";
     input {
       leaf error-id {
         description "Error identifier";
         type union {
           type uint32;
           type string {
             pattern "<.*>|$.*";
           }
         }
         mandatory true;
       }
       leaf always-fail {
         description "Fail always";
         type enumeration {
           enum "enable" {
             description "Enable failure";
           }
           enum "disable" {
             description "Disable failure";
           }
         }
         mandatory true;
       }
     }
     output {
       leaf output {
         type string;
       }
     }
   }
   rpc get-ppp-user-aaa-test-result {
     description "Test the aaa servers for a ppp user";
     input {
       leaf user {
         description "The username to test";
         type string;
         mandatory true;
       }
       leaf password {
         description "The password associated with username";
         type string;
       }
       leaf agent-remote-id {
         description "DSL forum agent remote id";
         type string {
           length "1 .. 63";
         }
       }
       leaf profile {
         description "Specify the access profile name which to use for user";
         type string;
       }
       leaf logical-system {
         description "Specify the logical-system in which to authenticate user";
         type string;
       }
       leaf routing-instance {
         description "Specify the routing-instance in which to authenticate user";
         type string;
       }
       leaf no-address-request {
         description "Request is for authentication without address-allocation";
         type empty;
       }
       leaf service-type {
         description "Service type ";
         type string;
       }
       choice terminate-code-choice {
         case terminate-code {
           leaf terminate-code {
             description "Specify PPP terminate-code";
             type enumeration {
               enum "admin-logout" {
                 description "Terminated-id with default mapping to 10";
               }
               enum "admin-reconnect-request" {
                 description "Terminated-id with default mapping to 10";
               }
               enum "authenticate-authenticator-timeout" {
                 description "Terminated-id with default mapping to 10";
               }
               enum "authenticate-challenge-timeout" {
                 description "Terminated-id with default mapping to 17";
               }
               enum "authenticate-chap-no-resources" {
                 description "Terminated-id with default mapping to 10";
               }
               enum "authenticate-chap-peer-authenticator-timeout" {
                 description "Terminated-id with default mapping to 17";
               }
               enum "authenticate-chap-peer-challenge-timeout" {
                 description "Terminated-id with default mapping to 17";
               }
               enum "authenticate-deny-by-peer" {
                 description "Terminated-id with default mapping to 4";
               }
               enum "authenticate-eap-challenge-larger-than-mtu" {
                 description "Terminated-id with default mapping to 10";
               }
               enum "authenticate-eap-peer-authenticator-timeout" {
                 description "Terminated-id with default mapping to 10";
               }
               enum "authenticate-eap-request-timeout" {
                 description "Terminated-id with default mapping to 10";
               }
               enum "authenticate-inactivity-timeout" {
                 description "Terminated-id with default mapping to 8";
               }
               enum "authenticate-max-requests" {
                 description "Terminated-id with default mapping to 10";
               }
               enum "authenticate-no-authenticator" {
                 description "Terminated-id with default mapping to 10";
               }
               enum "authenticate-no-resources" {
                 description "Terminated-id with default mapping to 10";
               }
               enum "authenticate-pap-peer-authenticator-timeout" {
                 description "Terminated-id with default mapping to 10";
               }
               enum "authenticate-pap-request-timeout" {
                 description "Terminated-id with default mapping to 5";
               }
               enum "authenticate-session-timeout" {
                 description "Terminated-id with default mapping to 10";
               }
               enum "authenticate-too-many-requests" {
                 description "Terminated-id with default mapping to 17";
               }
               enum "authenticate-tunnel-fail-immediate" {
                 description "Terminated-id with default mapping to 10";
               }
               enum "authenticate-tunnel-unsupported-tunnel-type" {
                 description "Terminated-id with default mapping to 10";
               }
               enum "bridging-admin-disable" {
                 description "Terminated-id with default mapping to 10";
               }
               enum "bridging-failed-to-activate-family-bridging" {
                 description "Terminated-id with default mapping to 10";
               }
               enum "bridging-inhibited-by-authentication" {
                 description "Terminated-id with default mapping to 10";
               }
               enum "bridging-link-down" {
                 description "Terminated-id with default mapping to 10";
               }
               enum "bridging-max-configure-exceeded" {
                 description "Terminated-id with default mapping to 10";
               }
               enum "bridging-max-passive-retries-exceeded" {
                 description "Terminated-id with default mapping to 10";
               }
               enum "bridging-max-sevice-disable" {
                 description "Terminated-id with default mapping to 10";
               }
               enum "bridging-no-local-ieee802-tagged-frame-format" {
                 description "Terminated-id with default mapping to 10";
               }
               enum "bridging-no-local-mac-frame-format" {
                 description "Terminated-id with default mapping to 2";
               }
               enum "bridging-no-peer-ieee802-tagged-frame-format" {
                 description "Terminated-id with default mapping to 10";
               }
               enum "bridging-no-peer-mac-fram-fromat" {
                 description "Terminated-id with default mapping to 8";
               }
               enum "bridging-no-service" {
                 description "Terminated-id with default mapping to 10";
               }
               enum "bridging-renegotiate-rx-conf-ack" {
                 description "Terminated-id with default mapping to 10";
               }
               enum "bridging-renegotiate-rx-conf-nak" {
                 description "Terminated-id with default mapping to 10";
               }
               enum "bridging-renegotiate-rx-conf-rej" {
                 description "Terminated-id with default mapping to 10";
               }
               enum "bridging-renegotiate-rx-conf-req" {
                 description "Terminated-id with default mapping to 10";
               }
               enum "bridging-stale-stacking" {
                 description "Terminated-id with default mapping to 10";
               }
               enum "bridging-terminate-code-rej" {
                 description "Terminated-id with default mapping to 10";
               }
               enum "bridging-terminate-term-ack" {
                 description "Terminated-id with default mapping to 10";
               }
               enum "bridging-terminate-term-req" {
                 description "Terminated-id with default mapping to 10";
               }
               enum "bundle-fail-activation" {
                 description "Terminated-id with default mapping to 10";
               }
               enum "bundle-fail-create" {
                 description "Terminated-id with default mapping to 10";
               }
               enum "bundle-fail-engine-add" {
                 description "Terminated-id with default mapping to 10";
               }
               enum "bundle-fail-fragment-size-mismatch" {
                 description "Terminated-id with default mapping to 10";
               }
               enum "bundle-fail-fragmentation-location" {
                 description "Terminated-id with default mapping to 10";
               }
               enum "bundle-fail-fragmentation-mismatch" {
                 description "Terminated-id with default mapping to 10";
               }
               enum "bundle-fail-hash-link-selection-mismatch" {
                 description "Terminated-id with default mapping to 10";
               }
               enum "bundle-fail-join" {
                 description "Terminated-id with default mapping to 10";
               }
               enum "bundle-fail-local-mped-not-set-yet" {
                 description "Terminated-id with default mapping to 10";
               }
               enum "bundle-fail-local-mrru-mismatch" {
                 description "Terminated-id with default mapping to 10";
               }
               enum "bundle-fail-local-mru-mismatch" {
                 description "Terminated-id with default mapping to 10";
               }
               enum "bundle-fail-peer-endpoint-discriminator-mismatch" {
                 description "Terminated-id with default mapping to 10";
               }
               enum "bundle-fail-peer-mrru-mismatch" {
                 description "Terminated-id with default mapping to 6";
               }
               enum "bundle-fail-profile-nak" {
                 description "Terminated-id with default mapping to 10";
               }
               enum "bundle-fail-reassembly-location" {
                 description "Terminated-id with default mapping to 10";
               }
               enum "bundle-fail-reassembly-mismatch" {
                 description "Terminated-id with default mapping to 10";
               }
               enum "bundle-fail-record-network" {
                 description "Terminated-id with default mapping to 10";
               }
               enum "bundle-fail-server-location-mismatch" {
                 description "Terminated-id with default mapping to 10";
               }
               enum "bundle-fail-static-link" {
                 description "Terminated-id with default mapping to 10";
               }
               enum "bundle-fail-unrecoverable-ifl" {
                 description "Terminated-id with default mapping to 10";
               }
               enum "dynamic-profile-instantiation-failed" {
                 description "Terminated-id with default mapping to 9";
               }
               enum "failover-during-authentication" {
                 description "Terminated-id with default mapping to 17";
               }
               enum "interface-admin-disable" {
                 description "Terminated-id with default mapping to 6";
               }
               enum "interface-no-hardware" {
                 description "Terminated-id with default mapping to 8";
               }
               enum "ip-admin-disable" {
                 description "Terminated-id with default mapping to 10";
               }
               enum "ip-failed-to-activate-family-inet" {
                 description "Terminated-id with default mapping to 10";
               }
               enum "ip-failed-to-activate-services" {
                 description "Terminated-id with default mapping to 10";
               }
               enum "ip-failed-to-add-access-internal-route" {
                 description "Terminated-id with default mapping to 10";
               }
               enum "ip-inhibited-by-authentication" {
                 description "Terminated-id with default mapping to 10";
               }
               enum "ip-link-down" {
                 description "Terminated-id with default mapping to 10";
               }
               enum "ip-max-configure-exceeded" {
                 description "Terminated-id with default mapping to 10";
               }
               enum "ip-max-passive-retries-exceeded" {
                 description "Terminated-id with default mapping to 10";
               }
               enum "ip-no-local-ip-address" {
                 description "Terminated-id with default mapping to 10";
               }
               enum "ip-no-local-ip-address-mask" {
                 description "Terminated-id with default mapping to 10";
               }
               enum "ip-no-local-primary-dns-address" {
                 description "Terminated-id with default mapping to 10";
               }
               enum "ip-no-local-primary-nbns-address" {
                 description "Terminated-id with default mapping to 10";
               }
               enum "ip-no-local-secondary-dns-address" {
                 description "Terminated-id with default mapping to 10";
               }
               enum "ip-no-local-secondary-nbns-address" {
                 description "Terminated-id with default mapping to 10";
               }
               enum "ip-no-peer-ip-address" {
                 description "Terminated-id with default mapping to 10";
               }
               enum "ip-no-peer-ip-address-mask" {
                 description "Terminated-id with default mapping to 10";
               }
               enum "ip-no-peer-primary-dns-address" {
                 description "Terminated-id with default mapping to 10";
               }
               enum "ip-no-peer-primary-nbns-address" {
                 description "Terminated-id with default mapping to 10";
               }
               enum "ip-no-peer-secondary-dns-address" {
                 description "Terminated-id with default mapping to 10";
               }
               enum "ip-no-peer-secondary-nbns-address" {
                 description "Terminated-id with default mapping to 10";
               }
               enum "ip-no-service" {
                 description "Terminated-id with default mapping to 10";
               }
               enum "ip-peer-renegotiate-rx-conf-ack" {
                 description "Terminated-id with default mapping to 10";
               }
               enum "ip-peer-renegotiate-rx-conf-nak" {
                 description "Terminated-id with default mapping to 10";
               }
               enum "ip-peer-renegotiate-rx-conf-rej" {
                 description "Terminated-id with default mapping to 10";
               }
               enum "ip-peer-renegotiate-rx-conf-req" {
                 description "Terminated-id with default mapping to 10";
               }
               enum "ip-peer-terminate-code-rej" {
                 description "Terminated-id with default mapping to 10";
               }
               enum "ip-peer-terminate-term-ack" {
                 description "Terminated-id with default mapping to 10";
               }
               enum "ip-peer-terminate-term-req" {
                 description "Terminated-id with default mapping to 10";
               }
               enum "ip-service-disable" {
                 description "Terminated-id with default mapping to 10";
               }
               enum "ip-stale-stacking" {
                 description "Terminated-id with default mapping to 10";
               }
               enum "ipv6-admin-disable" {
                 description "Terminated-id with default mapping to 10";
               }
               enum "ipv6-failed-to-activate-family-inet6" {
                 description "Terminated-id with default mapping to 10";
               }
               enum "ipv6-failed-to-activate-services" {
                 description "Terminated-id with default mapping to 10";
               }
               enum "ipv6-inhibited-by-authentication" {
                 description "Terminated-id with default mapping to 10";
               }
               enum "ipv6-link-down" {
                 description "Terminated-id with default mapping to 10";
               }
               enum "ipv6-local-and-peer-interface-ids-identical" {
                 description "Terminated-id with default mapping to 10";
               }
               enum "ipv6-max-configure-exceeded" {
                 description "Terminated-id with default mapping to 10";
               }
               enum "ipv6-max-passive-retries-exceeded" {
                 description "Terminated-id with default mapping to 10";
               }
               enum "ipv6-no-local-ipv6-interface-id" {
                 description "Terminated-id with default mapping to 10";
               }
               enum "ipv6-no-peer-ipv6-interface-id" {
                 description "Terminated-id with default mapping to 10";
               }
               enum "ipv6-no-service" {
                 description "Terminated-id with default mapping to 10";
               }
               enum "ipv6-peer-renegotiate-rx-conf-ack" {
                 description "Terminated-id with default mapping to 10";
               }
               enum "ipv6-peer-renegotiate-rx-conf-nak" {
                 description "Terminated-id with default mapping to 10";
               }
               enum "ipv6-peer-renegotiate-rx-conf-rej" {
                 description "Terminated-id with default mapping to 10";
               }
               enum "ipv6-peer-renegotiate-rx-conf-req" {
                 description "Terminated-id with default mapping to 10";
               }
               enum "ipv6-peer-terminate-code-rej" {
                 description "Terminated-id with default mapping to 10";
               }
               enum "ipv6-peer-terminate-term-ack" {
                 description "Terminated-id with default mapping to 10";
               }
               enum "ipv6-peer-terminate-term-req" {
                 description "Terminated-id with default mapping to 10";
               }
               enum "ipv6-service-disable" {
                 description "Terminated-id with default mapping to 10";
               }
               enum "ipv6-stale-stacking" {
                 description "Terminated-id with default mapping to 10";
               }
               enum "l2tp-session-apply-link-attribute-failed" {
                 description "Terminated-id with default mapping to 10";
               }
               enum "lcp-authenticate-terminate-hold" {
                 description "Terminated-id with default mapping to 10";
               }
               enum "lcp-configured-mrru-too-small" {
                 description "Terminated-id with default mapping to 10";
               }
               enum "lcp-configured-mru-invalid" {
                 description "Terminated-id with default mapping to 10";
               }
               enum "lcp-configured-mru-too-small" {
                 description "Terminated-id with default mapping to 10";
               }
               enum "lcp-dynamic-interface-hold" {
                 description "Terminated-id with default mapping to 10";
               }
               enum "lcp-failed-to-activate-services" {
                 description "Terminated-id with default mapping to 10";
               }
               enum "lcp-keepalive-failure" {
                 description "Terminated-id with default mapping to 10";
               }
               enum "lcp-loopback-rx-conf-req" {
                 description "Terminated-id with default mapping to 10";
               }
               enum "lcp-loopback-rx-echo-reply" {
                 description "Terminated-id with default mapping to 10";
               }
               enum "lcp-loopback-rx-echo-req" {
                 description "Terminated-id with default mapping to 10";
               }
               enum "lcp-max-configure-exceeded" {
                 description "Terminated-id with default mapping to 10";
               }
               enum "lcp-max-passive-retries-exceeded" {
                 description "Terminated-id with default mapping to 10";
               }
               enum "lcp-mru-changed" {
                 description "Terminated-id with default mapping to 8";
               }
               enum "lcp-negotiation-timeout" {
                 description "Terminated-id with default mapping to 10";
               }
               enum "lcp-no-local-accm" {
                 description "Terminated-id with default mapping to 10";
               }
               enum "lcp-no-local-acfc" {
                 description "Terminated-id with default mapping to 10";
               }
               enum "lcp-no-local-authentication" {
                 description "Terminated-id with default mapping to 10";
               }
               enum "lcp-no-local-endpoint-discriminator" {
                 description "Terminated-id with default mapping to 10";
               }
               enum "lcp-no-local-magic-number" {
                 description "Terminated-id with default mapping to 10";
               }
               enum "lcp-no-local-mrru" {
                 description "Terminated-id with default mapping to 10";
               }
               enum "lcp-no-local-mru" {
                 description "Terminated-id with default mapping to 10";
               }
               enum "lcp-no-local-pfc" {
                 description "Terminated-id with default mapping to 10";
               }
               enum "lcp-no-peer-accm" {
                 description "Terminated-id with default mapping to 10";
               }
               enum "lcp-no-peer-acfc" {
                 description "Terminated-id with default mapping to 10";
               }
               enum "lcp-no-peer-authentication" {
                 description "Terminated-id with default mapping to 10";
               }
               enum "lcp-no-peer-endpoint-discriminator" {
                 description "Terminated-id with default mapping to 10";
               }
               enum "lcp-no-peer-magic-number" {
                 description "Terminated-id with default mapping to 10";
               }
               enum "lcp-no-peer-mrru" {
                 description "Terminated-id with default mapping to 10";
               }
               enum "lcp-no-peer-mru" {
                 description "Terminated-id with default mapping to 10";
               }
               enum "lcp-no-peer-pfc" {
                 description "Terminated-id with default mapping to 10";
               }
               enum "lcp-peer-renegotiate-rx-conf-ack" {
                 description "Terminated-id with default mapping to 1";
               }
               enum "lcp-peer-renegotiate-rx-conf-nak" {
                 description "Terminated-id with default mapping to 1";
               }
               enum "lcp-peer-renegotiate-rx-conf-rej" {
                 description "Terminated-id with default mapping to 1";
               }
               enum "lcp-peer-renegotiate-rx-conf-req" {
                 description "Terminated-id with default mapping to 1";
               }
               enum "lcp-peer-terminate-code-rej" {
                 description "Terminated-id with default mapping to 1";
               }
               enum "lcp-peer-terminate-protocol-reject" {
                 description "Terminated-id with default mapping to 1";
               }
               enum "lcp-peer-terminate-term-ack" {
                 description "Terminated-id with default mapping to 1";
               }
               enum "lcp-peer-terminate-term-req" {
                 description "Terminated-id with default mapping to 1";
               }
               enum "lcp-tunnel-disconnected" {
                 description "Terminated-id with default mapping to 10";
               }
               enum "lcp-tunnel-failed" {
                 description "Terminated-id with default mapping to 10";
               }
               enum "license-limit-exceeded" {
                 description "Terminated-id with default mapping to 10";
               }
               enum "link-interface-no-hardware" {
                 description "Terminated-id with default mapping to 10";
               }
               enum "lower-interface-attach-failed" {
                 description "Terminated-id with default mapping to 2";
               }
               enum "lower-interface-down" {
                 description "Terminated-id with default mapping to 2";
               }
               enum "lower-interface-teardown" {
                 description "Terminated-id with default mapping to 17";
               }
               enum "mpls-admin-disable" {
                 description "Terminated-id with default mapping to 10";
               }
               enum "mpls-failed-to-activate-family-mpls" {
                 description "Terminated-id with default mapping to 10";
               }
               enum "mpls-link-down" {
                 description "Terminated-id with default mapping to 10";
               }
               enum "mpls-max-configure-exceeded" {
                 description "Terminated-id with default mapping to 10";
               }
               enum "mpls-max-passive-retries-exceeded" {
                 description "Terminated-id with default mapping to 10";
               }
               enum "mpls-no-service" {
                 description "Terminated-id with default mapping to 10";
               }
               enum "mpls-peer-renegotiate-rx-conf-ack" {
                 description "Terminated-id with default mapping to 10";
               }
               enum "mpls-peer-renegotiate-rx-conf-nak" {
                 description "Terminated-id with default mapping to 10";
               }
               enum "mpls-peer-renegotiate-rx-conf-rej" {
                 description "Terminated-id with default mapping to 10";
               }
               enum "mpls-peer-renegotiate-rx-conf-req" {
                 description "Terminated-id with default mapping to 10";
               }
               enum "mpls-peer-terminate-code-rej" {
                 description "Terminated-id with default mapping to 10";
               }
               enum "mpls-peer-terminate-term-ack" {
                 description "Terminated-id with default mapping to 10";
               }
               enum "mpls-peer-terminate-term-req" {
                 description "Terminated-id with default mapping to 10";
               }
               enum "mpls-service-disable" {
                 description "Terminated-id with default mapping to 10";
               }
               enum "mpls-stale-stacking" {
                 description "Terminated-id with default mapping to 10";
               }
               enum "network-interface-admin-disable" {
                 description "Terminated-id with default mapping to 10";
               }
               enum "no-bundle" {
                 description "Terminated-id with default mapping to 8";
               }
               enum "no-interface" {
                 description "Terminated-id with default mapping to 10";
               }
               enum "no-link-interface" {
                 description "Terminated-id with default mapping to 10";
               }
               enum "no-ncps-available" {
                 description "Terminated-id with default mapping to 10";
               }
               enum "no-network-interface" {
                 description "Terminated-id with default mapping to 6";
               }
               enum "no-upper-interface" {
                 description "Terminated-id with default mapping to 9";
               }
               enum "osi-admin-disable" {
                 description "Terminated-id with default mapping to 10";
               }
               enum "osi-failed-to-activate-family-osi" {
                 description "Terminated-id with default mapping to 10";
               }
               enum "osi-link-down" {
                 description "Terminated-id with default mapping to 10";
               }
               enum "osi-max-configure-exceeded" {
                 description "Terminated-id with default mapping to 10";
               }
               enum "osi-max-passive-retries-exceeded" {
                 description "Terminated-id with default mapping to 10";
               }
               enum "osi-no-local-align-npdu" {
                 description "Terminated-id with default mapping to 10";
               }
               enum "osi-no-peer-align-npdu" {
                 description "Terminated-id with default mapping to 10";
               }
               enum "osi-no-service" {
                 description "Terminated-id with default mapping to 10";
               }
               enum "osi-peer-renegotiate-rx-conf-ack" {
                 description "Terminated-id with default mapping to 10";
               }
               enum "osi-peer-renegotiate-rx-conf-nak" {
                 description "Terminated-id with default mapping to 10";
               }
               enum "osi-peer-renegotiate-rx-conf-rej" {
                 description "Terminated-id with default mapping to 10";
               }
               enum "osi-peer-renegotiate-rx-conf-req" {
                 description "Terminated-id with default mapping to 10";
               }
               enum "osi-peer-terminate-code-rej" {
                 description "Terminated-id with default mapping to 10";
               }
               enum "osi-peer-terminate-term-ack" {
                 description "Terminated-id with default mapping to 10";
               }
               enum "osi-peer-terminate-term-req" {
                 description "Terminated-id with default mapping to 10";
               }
               enum "osi-service-disable" {
                 description "Terminated-id with default mapping to 10";
               }
               enum "osi-stale-stacking" {
                 description "Terminated-id with default mapping to 10";
               }
               enum "recovery-active-state-cleanup" {
                 description "Terminated-id with default mapping to 9";
               }
               enum "recovery-configured-state-cleanup" {
                 description "Terminated-id with default mapping to 9";
               }
               enum "recovery-init-state-cleanup" {
                 description "Terminated-id with default mapping to 9";
               }
               enum "recovery-terminated-state-cleanup" {
                 description "Terminated-id with default mapping to 9";
               }
               enum "recovery-terminating-state-cleanup" {
                 description "Terminated-id with default mapping to 9";
               }
               enum "session-init-failed" {
                 description "Terminated-id with default mapping to 9";
               }
               enum "subscriber-mgr-activation-failed" {
                 description "Terminated-id with default mapping to 9";
               }
               enum "subscriber-mgr-get-credentials-failed" {
                 description "Terminated-id with default mapping to 9";
               }
               enum "subscriber-mgr-link-interface-not-found" {
                 description "Terminated-id with default mapping to 9";
               }
               enum "subscriber-mgr-set-state-active-failed" {
                 description "Terminated-id with default mapping to 9";
               }
             }
           }
         }
         case l2tp-terminate-code {
           leaf l2tp-terminate-code {
             description "Specify L2TP terminate-code";
             type enumeration {
               enum "issu-in-progress" {
                 description "Terminated-id with default mapping to 10";
               }
               enum "session-access-interface-down" {
                 description "Terminated-id with default mapping to 8";
               }
               enum "session-administrative-close" {
                 description "Terminated-id with default mapping to 6";
               }
               enum "session-administrative-drain" {
                 description "Terminated-id with default mapping to 6";
               }
               enum "session-call-down" {
                 description "Terminated-id with default mapping to 10";
               }
               enum "session-call-failed" {
                 description "Terminated-id with default mapping to 15";
               }
               enum "session-create-failed-icrq-to-initiator-tunnel" {
                 description "Terminated-id with default mapping to 9";
               }
               enum "session-create-failed-invalid-config" {
                 description "Terminated-id with default mapping to 10";
               }
               enum "session-create-failed-limit-reached" {
                 description "Terminated-id with default mapping to 9";
               }
               enum "session-create-failed-no-resources" {
                 description "Terminated-id with default mapping to 9";
               }
               enum "session-create-failed-single-shot-tunnel-already-fired" {
                 description "Terminated-id with default mapping to 9";
               }
               enum "session-create-failed-too-busy" {
                 description "Terminated-id with default mapping to 9";
               }
               enum "session-failover-protocol-resync-disconnect" {
                 description "Terminated-id with default mapping to 6";
               }
               enum "session-hardware-unavailable" {
                 description "Terminated-id with default mapping to 8";
               }
               enum "session-no-resources-server-port" {
                 description "Terminated-id with default mapping to 9";
               }
               enum "session-not-ready" {
                 description "Terminated-id with default mapping to 9";
               }
               enum "session-receive-cdn" {
                 description "Terminated-id with default mapping to 10";
               }
               enum "session-receive-cdn-avp-bad-hidden" {
                 description "Terminated-id with default mapping to 10";
               }
               enum "session-receive-cdn-avp-bad-value-assigned-session-id" {
                 description "Terminated-id with default mapping to 10";
               }
               enum "session-receive-cdn-avp-duplicate-value-assigned-session-id" {
                 description "Terminated-id with default mapping to 10";
               }
               enum "session-receive-cdn-avp-malformed-bad-length" {
                 description "Terminated-id with default mapping to 10";
               }
               enum "session-receive-cdn-avp-malformed-truncated" {
                 description "Terminated-id with default mapping to 10";
               }
               enum "session-receive-cdn-avp-missing-mandatory-assigned-session-id" {
                 description "Terminated-id with default mapping to 10";
               }
               enum "session-receive-cdn-avp-missing-mandatory-result-code" {
                 description "Terminated-id with default mapping to 10";
               }
               enum "session-receive-cdn-avp-missing-random-vector" {
                 description "Terminated-id with default mapping to 10";
               }
               enum "session-receive-cdn-avp-missing-secret" {
                 description "Terminated-id with default mapping to 10";
               }
               enum "session-receive-cdn-avp-unknown" {
                 description "Terminated-id with default mapping to 10";
               }
               enum "session-receive-cdn-no-resources" {
                 description "Terminated-id with default mapping to 10";
               }
               enum "session-receive-iccn-avp-bad-hidden" {
                 description "Terminated-id with default mapping to 10";
               }
               enum "session-receive-iccn-avp-bad-value-framing-type" {
                 description "Terminated-id with default mapping to 10";
               }
               enum "session-receive-iccn-avp-bad-value-proxy-authen-type" {
                 description "Terminated-id with default mapping to 10";
               }
               enum "session-receive-iccn-avp-bad-value-unsupported-proxy-authen-type" {
                 description "Terminated-id with default mapping to 10";
               }
               enum "session-receive-iccn-avp-malformed-bad-length" {
                 description "Terminated-id with default mapping to 10";
               }
               enum "session-receive-iccn-avp-malformed-truncated" {
                 description "Terminated-id with default mapping to 10";
               }
               enum "session-receive-iccn-avp-missing-mandatory-connect-speed" {
                 description "Terminated-id with default mapping to 10";
               }
               enum "session-receive-iccn-avp-missing-mandatory-framing-type" {
                 description "Terminated-id with default mapping to 10";
               }
               enum "session-receive-iccn-avp-missing-mandatory-proxy-authen-challenge" {
                 description "Terminated-id with default mapping to 10";
               }
               enum "session-receive-iccn-avp-missing-mandatory-proxy-authen-id" {
                 description "Terminated-id with default mapping to 10";
               }
               enum "session-receive-iccn-avp-missing-mandatory-proxy-authen-name" {
                 description "Terminated-id with default mapping to 10";
               }
               enum "session-receive-iccn-avp-missing-mandatory-proxy-authen-response" {
                 description "Terminated-id with default mapping to 10";
               }
               enum "session-receive-iccn-avp-missing-random-vector" {
                 description "Terminated-id with default mapping to 10";
               }
               enum "session-receive-iccn-avp-missing-secret" {
                 description "Terminated-id with default mapping to 10";
               }
               enum "session-receive-iccn-avp-unknown" {
                 description "Terminated-id with default mapping to 10";
               }
               enum "session-receive-iccn-no-resources" {
                 description "Terminated-id with default mapping to 10";
               }
               enum "session-receive-iccn-unexpected" {
                 description "Terminated-id with default mapping to 10";
               }
               enum "session-receive-icrp-avp-bad-hidden" {
                 description "Terminated-id with default mapping to 10";
               }
               enum "session-receive-icrp-avp-bad-value-assigned-session-id" {
                 description "Terminated-id with default mapping to 10";
               }
               enum "session-receive-icrp-avp-duplicate-value-assigned-session-id" {
                 description "Terminated-id with default mapping to 10";
               }
               enum "session-receive-icrp-avp-malformed-bad-length" {
                 description "Terminated-id with default mapping to 10";
               }
               enum "session-receive-icrp-avp-malformed-truncated" {
                 description "Terminated-id with default mapping to 10";
               }
               enum "session-receive-icrp-avp-missing-mandatory-assigned-session-id" {
                 description "Terminated-id with default mapping to 10";
               }
               enum "session-receive-icrp-avp-missing-random-vector" {
                 description "Terminated-id with default mapping to 10";
               }
               enum "session-receive-icrp-avp-missing-secret" {
                 description "Terminated-id with default mapping to 10";
               }
               enum "session-receive-icrp-avp-unknown" {
                 description "Terminated-id with default mapping to 10";
               }
               enum "session-receive-icrp-no-resources" {
                 description "Terminated-id with default mapping to 10";
               }
               enum "session-receive-icrp-unexpected" {
                 description "Terminated-id with default mapping to 10";
               }
               enum "session-receive-icrq-administrative-close" {
                 description "Terminated-id with default mapping to 6";
               }
               enum "session-receive-icrq-authenticate-failed-host" {
                 description "Terminated-id with default mapping to 10";
               }
               enum "session-receive-icrq-avp-bad-hidden" {
                 description "Terminated-id with default mapping to 10";
               }
               enum "session-receive-icrq-avp-bad-value-assigned-session-id" {
                 description "Terminated-id with default mapping to 10";
               }
               enum "session-receive-icrq-avp-bad-value-bearer-type" {
                 description "Terminated-id with default mapping to 10";
               }
               enum "session-receive-icrq-avp-bad-value-cisco-nas-port" {
                 description "Terminated-id with default mapping to 10";
               }
               enum "session-receive-icrq-avp-duplicate-value-assigned-session-id" {
                 description "Terminated-id with default mapping to 10";
               }
               enum "session-receive-icrq-avp-malformed-bad-length" {
                 description "Terminated-id with default mapping to 10";
               }
               enum "session-receive-icrq-avp-malformed-truncated" {
                 description "Terminated-id with default mapping to 10";
               }
               enum "session-receive-icrq-avp-missing-mandatory-assigned-session-id" {
                 description "Terminated-id with default mapping to 10";
               }
               enum "session-receive-icrq-avp-missing-mandatory-call-serial-number" {
                 description "Terminated-id with default mapping to 10";
               }
               enum "session-receive-icrq-avp-missing-random-vector" {
                 description "Terminated-id with default mapping to 10";
               }
               enum "session-receive-icrq-avp-missing-secret" {
                 description "Terminated-id with default mapping to 10";
               }
               enum "session-receive-icrq-avp-unknown" {
                 description "Terminated-id with default mapping to 10";
               }
               enum "session-receive-icrq-no-resources" {
                 description "Terminated-id with default mapping to 10";
               }
               enum "session-receive-icrq-unexpected" {
                 description "Terminated-id with default mapping to 10";
               }
               enum "session-receive-occn-avp-bad-hidden" {
                 description "Terminated-id with default mapping to 10";
               }
               enum "session-receive-occn-avp-bad-value-framing-type" {
                 description "Terminated-id with default mapping to 10";
               }
               enum "session-receive-occn-avp-malformed-bad-length" {
                 description "Terminated-id with default mapping to 10";
               }
               enum "session-receive-occn-avp-malformed-truncated" {
                 description "Terminated-id with default mapping to 10";
               }
               enum "session-receive-occn-avp-missing-mandatory-connect-speed" {
                 description "Terminated-id with default mapping to 10";
               }
               enum "session-receive-occn-avp-missing-mandatory-framing-type" {
                 description "Terminated-id with default mapping to 10";
               }
               enum "session-receive-occn-avp-missing-random-vector" {
                 description "Terminated-id with default mapping to 10";
               }
               enum "session-receive-occn-avp-missing-secret" {
                 description "Terminated-id with default mapping to 10";
               }
               enum "session-receive-occn-avp-unknown" {
                 description "Terminated-id with default mapping to 10";
               }
               enum "session-receive-occn-no-resources" {
                 description "Terminated-id with default mapping to 10";
               }
               enum "session-receive-occn-unexpected" {
                 description "Terminated-id with default mapping to 10";
               }
               enum "session-receive-ocrp-avp-bad-hidden" {
                 description "Terminated-id with default mapping to 10";
               }
               enum "session-receive-ocrp-avp-bad-value-assigned-session-id" {
                 description "Terminated-id with default mapping to 10";
               }
               enum "session-receive-ocrp-avp-duplicate-value-assigned-session-id" {
                 description "Terminated-id with default mapping to 10";
               }
               enum "session-receive-ocrp-avp-malformed-bad-length" {
                 description "Terminated-id with default mapping to 10";
               }
               enum "session-receive-ocrp-avp-malformed-truncated" {
                 description "Terminated-id with default mapping to 10";
               }
               enum "session-receive-ocrp-avp-missing-mandatory-assigned-session-id" {
                 description "Terminated-id with default mapping to 10";
               }
               enum "session-receive-ocrp-avp-missing-random-vector" {
                 description "Terminated-id with default mapping to 10";
               }
               enum "session-receive-ocrp-avp-missing-secret" {
                 description "Terminated-id with default mapping to 10";
               }
               enum "session-receive-ocrp-avp-unknown" {
                 description "Terminated-id with default mapping to 10";
               }
               enum "session-receive-ocrp-no-resources" {
                 description "Terminated-id with default mapping to 10";
               }
               enum "session-receive-ocrp-unexpected" {
                 description "Terminated-id with default mapping to 10";
               }
               enum "session-receive-ocrq-administrative-close" {
                 description "Terminated-id with default mapping to 6";
               }
               enum "session-receive-ocrq-authenticate-failed-host" {
                 description "Terminated-id with default mapping to 10";
               }
               enum "session-receive-ocrq-avp-bad-hidden" {
                 description "Terminated-id with default mapping to 10";
               }
               enum "session-receive-ocrq-avp-bad-value-assigned-session-id" {
                 description "Terminated-id with default mapping to 10";
               }
               enum "session-receive-ocrq-avp-bad-value-bearer-type" {
                 description "Terminated-id with default mapping to 10";
               }
               enum "session-receive-ocrq-avp-bad-value-framing-type" {
                 description "Terminated-id with default mapping to 10";
               }
               enum "session-receive-ocrq-avp-duplicate-value-assigned-session-id" {
                 description "Terminated-id with default mapping to 10";
               }
               enum "session-receive-ocrq-avp-malformed-bad-length" {
                 description "Terminated-id with default mapping to 10";
               }
               enum "session-receive-ocrq-avp-malformed-truncated" {
                 description "Terminated-id with default mapping to 10";
               }
               enum "session-receive-ocrq-avp-missing-mandatory-assigned-session-id" {
                 description "Terminated-id with default mapping to 10";
               }
               enum "session-receive-ocrq-avp-missing-mandatory-bearer-type" {
                 description "Terminated-id with default mapping to 10";
               }
               enum "session-receive-ocrq-avp-missing-mandatory-call-serial-number" {
                 description "Terminated-id with default mapping to 10";
               }
               enum "session-receive-ocrq-avp-missing-mandatory-called-number" {
                 description "Terminated-id with default mapping to 10";
               }
               enum "session-receive-ocrq-avp-missing-mandatory-framing-type" {
                 description "Terminated-id with default mapping to 10";
               }
               enum "session-receive-ocrq-avp-missing-mandatory-maximum-bps" {
                 description "Terminated-id with default mapping to 10";
               }
               enum "session-receive-ocrq-avp-missing-mandatory-minimum-bps" {
                 description "Terminated-id with default mapping to 10";
               }
               enum "session-receive-ocrq-avp-missing-random-vector" {
                 description "Terminated-id with default mapping to 10";
               }
               enum "session-receive-ocrq-avp-missing-secret" {
                 description "Terminated-id with default mapping to 10";
               }
               enum "session-receive-ocrq-avp-unknown" {
                 description "Terminated-id with default mapping to 10";
               }
               enum "session-receive-ocrq-no-resources" {
                 description "Terminated-id with default mapping to 10";
               }
               enum "session-receive-ocrq-unexpected" {
                 description "Terminated-id with default mapping to 10";
               }
               enum "session-receive-ocrq-unsupported" {
                 description "Terminated-id with default mapping to 9";
               }
               enum "session-receive-sli-avp-bad-hidden" {
                 description "Terminated-id with default mapping to 10";
               }
               enum "session-receive-sli-avp-bad-value-accm" {
                 description "Terminated-id with default mapping to 10";
               }
               enum "session-receive-sli-avp-malformed-bad-length" {
                 description "Terminated-id with default mapping to 10";
               }
               enum "session-receive-sli-avp-malformed-truncated" {
                 description "Terminated-id with default mapping to 10";
               }
               enum "session-receive-sli-avp-missing-mandatory-accm" {
                 description "Terminated-id with default mapping to 10";
               }
               enum "session-receive-sli-avp-missing-random-vector" {
                 description "Terminated-id with default mapping to 10";
               }
               enum "session-receive-sli-avp-missing-secret" {
                 description "Terminated-id with default mapping to 10";
               }
               enum "session-receive-sli-avp-unknown" {
                 description "Terminated-id with default mapping to 10";
               }
               enum "session-receive-sli-no-resources" {
                 description "Terminated-id with default mapping to 10";
               }
               enum "session-receive-unexpected-packet-lac-incoming" {
                 description "Terminated-id with default mapping to 10";
               }
               enum "session-receive-unexpected-packet-lac-outgoing" {
                 description "Terminated-id with default mapping to 10";
               }
               enum "session-receive-unexpected-packet-lns-incoming" {
                 description "Terminated-id with default mapping to 10";
               }
               enum "session-receive-unexpected-packet-lns-outgoing" {
                 description "Terminated-id with default mapping to 10";
               }
               enum "session-receive-unknown-session-id" {
                 description "Terminated-id with default mapping to 10";
               }
               enum "session-receive-wen-avp-bad-hidden" {
                 description "Terminated-id with default mapping to 10";
               }
               enum "session-receive-wen-avp-malformed-bad-length" {
                 description "Terminated-id with default mapping to 10";
               }
               enum "session-receive-wen-avp-malformed-truncated" {
                 description "Terminated-id with default mapping to 10";
               }
               enum "session-receive-wen-avp-missing-mandatory-call-errors" {
                 description "Terminated-id with default mapping to 10";
               }
               enum "session-receive-wen-avp-missing-random-vector" {
                 description "Terminated-id with default mapping to 10";
               }
               enum "session-receive-wen-avp-missing-secret" {
                 description "Terminated-id with default mapping to 10";
               }
               enum "session-receive-wen-avp-unknown" {
                 description "Terminated-id with default mapping to 10";
               }
               enum "session-receive-wen-no-resources" {
                 description "Terminated-id with default mapping to 10";
               }
               enum "session-timeout-connection" {
                 description "Terminated-id with default mapping to 10";
               }
               enum "session-timeout-inactivity" {
                 description "Terminated-id with default mapping to 4";
               }
               enum "session-timeout-session" {
                 description "Terminated-id with default mapping to 5";
               }
               enum "session-timeout-upper-create" {
                 description "Terminated-id with default mapping to 9";
               }
               enum "session-transmit-speed-unavailable" {
                 description "Terminated-id with default mapping to 9";
               }
               enum "session-tunnel-down" {
                 description "Terminated-id with default mapping to 15";
               }
               enum "session-tunnel-failed" {
                 description "Terminated-id with default mapping to 15";
               }
               enum "session-tunnel-switch-profile-deleted" {
                 description "Terminated-id with default mapping to 6";
               }
               enum "session-tunneled-interface-down" {
                 description "Terminated-id with default mapping to 8";
               }
               enum "session-unknown-cause" {
                 description "Terminated-id with default mapping to 9";
               }
               enum "session-upper-create-failed" {
                 description "Terminated-id with default mapping to 9";
               }
               enum "session-upper-removed" {
                 description "Terminated-id with default mapping to 15";
               }
               enum "session-warmstart-not-operational" {
                 description "Terminated-id with default mapping to 15";
               }
               enum "session-warmstart-recovery-error" {
                 description "Terminated-id with default mapping to 15";
               }
               enum "session-warmstart-uppper-not-restacked" {
                 description "Terminated-id with default mapping to 10";
               }
               enum "session-rx-icrq-issu-in-progress" {
                 description "Terminated-id with default mapping to 10";
               }
               enum "session-rx-ocrq-issu-in-progress" {
                 description "Terminated-id with default mapping to 10";
               }
               enum "tunnel-administrative-close" {
                 description "Terminated-id with default mapping to 6";
               }
               enum "tunnel-administrative-drain" {
                 description "Terminated-id with default mapping to 6";
               }
               enum "tunnel-control-channel-failed" {
                 description "Terminated-id with default mapping to 15";
               }
               enum "tunnel-created-no-sessions" {
                 description "Terminated-id with default mapping to 1";
               }
               enum "tunnel-destination-address-changed" {
                 description "Terminated-id with default mapping to 6";
               }
               enum "tunnel-destination-down" {
                 description "Terminated-id with default mapping to 10";
               }
               enum "tunnel-failover-protocol-no-resources-for-recovery-tunnel" {
                 description "Terminated-id with default mapping to 15";
               }
               enum "tunnel-failover-protocol-no-resources-for-session-resync" {
                 description "Terminated-id with default mapping to 15";
               }
               enum "tunnel-failover-protocol-not-supported" {
                 description "Terminated-id with default mapping to 15";
               }
               enum "tunnel-failover-protocol-not-supported-by-peer" {
                 description "Terminated-id with default mapping to 15";
               }
               enum "tunnel-failover-protocol-recovery-control-channel-failed" {
                 description "Terminated-id with default mapping to 15";
               }
               enum "tunnel-failover-protocol-recovery-tunnel-failed" {
                 description "Terminated-id with default mapping to 15";
               }
               enum "tunnel-failover-protocol-recovery-tunnel-finished" {
                 description "Terminated-id with default mapping to 1";
               }
               enum "tunnel-failover-protocol-recovery-tunnel-primary-down" {
                 description "Terminated-id with default mapping to 1";
               }
               enum "tunnel-failover-protocol-session-resync-failed" {
                 description "Terminated-id with default mapping to 15";
               }
               enum "tunnel-host-profile-changed" {
                 description "Terminated-id with default mapping to 6";
               }
               enum "tunnel-host-profile-deleted" {
                 description "Terminated-id with default mapping to 6";
               }
               enum "tunnel-receive-fsq-avp-bad-hidden" {
                 description "Terminated-id with default mapping to 15";
               }
               enum "tunnel-receive-fsq-avp-malformed-bad-length" {
                 description "Terminated-id with default mapping to 15";
               }
               enum "tunnel-receive-fsq-avp-malformed-truncated" {
                 description "Terminated-id with default mapping to 15";
               }
               enum "tunnel-receive-fsq-avp-missing-mandatory-failover-session-state" {
                 description "Terminated-id with default mapping to 15";
               }
               enum "tunnel-receive-fsq-avp-missing-random-vector" {
                 description "Terminated-id with default mapping to 15";
               }
               enum "tunnel-receive-fsq-avp-missing-secret" {
                 description "Terminated-id with default mapping to 15";
               }
               enum "tunnel-receive-fsq-avp-unknown" {
                 description "Terminated-id with default mapping to 15";
               }
               enum "tunnel-receive-fsq-no-resources" {
                 description "Terminated-id with default mapping to 15";
               }
               enum "tunnel-receive-fsq-session-id-not-null" {
                 description "Terminated-id with default mapping to 15";
               }
               enum "tunnel-receive-fsr-avp-bad-hidden" {
                 description "Terminated-id with default mapping to 15";
               }
               enum "tunnel-receive-fsr-avp-malformed-bad-length" {
                 description "Terminated-id with default mapping to 15";
               }
               enum "tunnel-receive-fsr-avp-malformed-truncated" {
                 description "Terminated-id with default mapping to 15";
               }
               enum "tunnel-receive-fsr-avp-missing-mandatory-failover-session-state" {
                 description "Terminated-id with default mapping to 15";
               }
               enum "tunnel-receive-fsr-avp-missing-random-vector" {
                 description "Terminated-id with default mapping to 15";
               }
               enum "tunnel-receive-fsr-avp-missing-secret" {
                 description "Terminated-id with default mapping to 15";
               }
               enum "tunnel-receive-fsr-avp-unknown" {
                 description "Terminated-id with default mapping to 15";
               }
               enum "tunnel-receive-fsr-no-resources" {
                 description "Terminated-id with default mapping to 15";
               }
               enum "tunnel-receive-fsr-session-id-not-null" {
                 description "Terminated-id with default mapping to 15";
               }
               enum "tunnel-receive-recovery-scccn-authenticate-failed-challenge" {
                 description "Terminated-id with default mapping to 17";
               }
               enum "tunnel-receive-recovery-scccn-avp-bad-hidden" {
                 description "Terminated-id with default mapping to 15";
               }
               enum "tunnel-receive-recovery-scccn-avp-bad-value-challenge-response" {
                 description "Terminated-id with default mapping to 15";
               }
               enum "tunnel-receive-recovery-scccn-avp-malformed-bad-length" {
                 description "Terminated-id with default mapping to 15";
               }
               enum "tunnel-receive-recovery-scccn-avp-malformed-truncated" {
                 description "Terminated-id with default mapping to 15";
               }
               enum "tunnel-receive-recovery-scccn-avp-missing-challenge-response" {
                 description "Terminated-id with default mapping to 17";
               }
               enum "tunnel-receive-recovery-scccn-avp-missing-random-vector" {
                 description "Terminated-id with default mapping to 15";
               }
               enum "tunnel-receive-recovery-scccn-avp-missing-secret" {
                 description "Terminated-id with default mapping to 15";
               }
               enum "tunnel-receive-recovery-scccn-avp-unexpected-challenge-response" {
                 description "Terminated-id with default mapping to 15";
               }
               enum "tunnel-receive-recovery-scccn-avp-unknown" {
                 description "Terminated-id with default mapping to 15";
               }
               enum "tunnel-receive-recovery-scccn-no-resources" {
                 description "Terminated-id with default mapping to 15";
               }
               enum "tunnel-receive-recovery-scccn-session-id-not-null" {
                 description "Terminated-id with default mapping to 15";
               }
               enum "tunnel-receive-recovery-scccp-avp-unexpected-challenge-response" {
                 description "Terminated-id with default mapping to 15";
               }
               enum "tunnel-receive-recovery-scccp-avp-bad-value-challenge-response" {
                 description "Terminated-id with default mapping to 15";
               }
               enum "tunnel-receive-recovery-scccp-avp-missing-challenge-response" {
                 description "Terminated-id with default mapping to 17";
               }
               enum "tunnel-receive-recovery-sccrp-authenticate-failed-challenge" {
                 description "Terminated-id with default mapping to 17";
               }
               enum "tunnel-receive-recovery-sccrp-avp-bad-hidden" {
                 description "Terminated-id with default mapping to 15";
               }
               enum "tunnel-receive-recovery-sccrp-avp-bad-value-assigned-tunnel-id" {
                 description "Terminated-id with default mapping to 15";
               }
               enum "tunnel-receive-recovery-sccrp-avp-bad-value-bearer-capabilities" {
                 description "Terminated-id with default mapping to 15";
               }
               enum "tunnel-receive-recovery-sccrp-avp-bad-value-challenge" {
                 description "Terminated-id with default mapping to 15";
               }
               enum "tunnel-receive-recovery-sccrp-avp-bad-value-framing-capabilities" {
                 description "Terminated-id with default mapping to 15";
               }
               enum "tunnel-receive-recovery-sccrp-avp-bad-value-protocol-version" {
                 description "Terminated-id with default mapping to 15";
               }
               enum "tunnel-receive-recovery-sccrp-avp-bad-value-receive-window-size" {
                 description "Terminated-id with default mapping to 15";
               }
               enum "tunnel-receive-recovery-sccrp-avp-bad-value-suggested-control-sequence" {
                 description "Terminated-id with default mapping to 15";
               }
               enum "tunnel-receive-recovery-sccrp-avp-duplicate-value-assigned-tunnel-id" {
                 description "Terminated-id with default mapping to 15";
               }
               enum "tunnel-receive-recovery-sccrp-avp-malformed-bad-length" {
                 description "Terminated-id with default mapping to 15";
               }
               enum "tunnel-receive-recovery-sccrp-avp-malformed-truncated" {
                 description "Terminated-id with default mapping to 15";
               }
               enum "tunnel-receive-recovery-sccrp-avp-mismatched-host-name" {
                 description "Terminated-id with default mapping to 15";
               }
               enum "tunnel-receive-recovery-sccrp-avp-mismatched-vendor-name" {
                 description "Terminated-id with default mapping to 15";
               }
               enum "tunnel-receive-recovery-sccrp-avp-missing-mandatory-assigned-tunnel-id" {
                 description "Terminated-id with default mapping to 15";
               }
               enum "tunnel-receive-recovery-sccrp-avp-missing-mandatory-framing-capabilities" {
                 description "Terminated-id with default mapping to 15";
               }
               enum "tunnel-receive-recovery-sccrp-avp-missing-mandatory-host-name" {
                 description "Terminated-id with default mapping to 15";
               }
               enum "tunnel-receive-recovery-sccrp-avp-missing-mandatory-protocol-version" {
                 description "Terminated-id with default mapping to 15";
               }
               enum "tunnel-receive-recovery-sccrp-avp-missing-random-vector" {
                 description "Terminated-id with default mapping to 15";
               }
               enum "tunnel-receive-recovery-sccrp-avp-missing-secret" {
                 description "Terminated-id with default mapping to 15";
               }
               enum "tunnel-receive-recovery-sccrp-avp-unexpected-challenge-without-secret" {
                 description "Terminated-id with default mapping to 15";
               }
               enum "tunnel-receive-recovery-sccrp-avp-unknown" {
                 description "Terminated-id with default mapping to 15";
               }
               enum "tunnel-receive-recovery-sccrp-no-resources" {
                 description "Terminated-id with default mapping to 15";
               }
               enum "tunnel-receive-recovery-sccrp-session-id-not-null" {
                 description "Terminated-id with default mapping to 15";
               }
               enum "tunnel-receive-recovery-sccrq-administrative-close" {
                 description "Terminated-id with default mapping to 6";
               }
               enum "tunnel-receive-recovery-sccrq-avp-bad-hidden" {
                 description "Terminated-id with default mapping to 15";
               }
               enum "tunnel-receive-recovery-sccrq-avp-bad-value-assigned-tunnel-id" {
                 description "Terminated-id with default mapping to 15";
               }
               enum "tunnel-receive-recovery-sccrq-avp-bad-value-bearer-capabilities" {
                 description "Terminated-id with default mapping to 15";
               }
               enum "tunnel-receive-recovery-sccrq-avp-bad-value-challenge" {
                 description "Terminated-id with default mapping to 15";
               }
               enum "tunnel-receive-recovery-sccrq-avp-bad-value-framing-capabilities" {
                 description "Terminated-id with default mapping to 15";
               }
               enum "tunnel-receive-recovery-sccrq-avp-bad-value-protocol-version" {
                 description "Terminated-id with default mapping to 15";
               }
               enum "tunnel-receive-recovery-sccrq-avp-bad-value-receive-window-size" {
                 description "Terminated-id with default mapping to 15";
               }
               enum "tunnel-receive-recovery-sccrq-avp-bad-value-tunnel-recovery" {
                 description "Terminated-id with default mapping to 15";
               }
               enum "tunnel-receive-recovery-sccrq-avp-duplicate-value-assigned-tunnel-id" {
                 description "Terminated-id with default mapping to 15";
               }
               enum "tunnel-receive-recovery-sccrq-avp-duplicate-value-tie-breaker" {
                 description "Terminated-id with default mapping to 15";
               }
               enum "tunnel-receive-recovery-sccrq-avp-malformed-bad-length" {
                 description "Terminated-id with default mapping to 15";
               }
               enum "tunnel-receive-recovery-sccrq-avp-malformed-truncated" {
                 description "Terminated-id with default mapping to 15";
               }
               enum "tunnel-receive-recovery-sccrq-avp-mismatched-host-name" {
                 description "Terminated-id with default mapping to 15";
               }
               enum "tunnel-receive-recovery-sccrq-avp-mismatched-vendor-name" {
                 description "Terminated-id with default mapping to 15";
               }
               enum "tunnel-receive-recovery-sccrq-avp-missing-mandatory-assigned-tunnel-id" {
                 description "Terminated-id with default mapping to 15";
               }
               enum "tunnel-receive-recovery-sccrq-avp-missing-mandatory-framing-capabilities" {
                 description "Terminated-id with default mapping to 15";
               }
               enum "tunnel-receive-recovery-sccrq-avp-missing-mandatory-host-name" {
                 description "Terminated-id with default mapping to 15";
               }
               enum "tunnel-receive-recovery-sccrq-avp-missing-mandatory-protocol-version" {
                 description "Terminated-id with default mapping to 15";
               }
               enum "tunnel-receive-recovery-sccrq-avp-missing-mandatory-tunnel-recovery" {
                 description "Terminated-id with default mapping to 15";
               }
               enum "tunnel-receive-recovery-sccrq-avp-missing-random-vector" {
                 description "Terminated-id with default mapping to 15";
               }
               enum "tunnel-receive-recovery-sccrq-avp-missing-secret" {
                 description "Terminated-id with default mapping to 15";
               }
               enum "tunnel-receive-recovery-sccrq-avp-missing-tie-breaker" {
                 description "Terminated-id with default mapping to 15";
               }
               enum "tunnel-receive-recovery-sccrq-avp-unexpected-challenge-without-secret" {
                 description "Terminated-id with default mapping to 15";
               }
               enum "tunnel-receive-recovery-sccrq-avp-unknown" {
                 description "Terminated-id with default mapping to 15";
               }
               enum "tunnel-receive-recovery-sccrq-no-resources-max-tunnels" {
                 description "Terminated-id with default mapping to 15";
               }
               enum "tunnel-receive-recovery-sccrq-session-id-not-null" {
                 description "Terminated-id with default mapping to 15";
               }
               enum "tunnel-receive-recovery-sccrq-tunnel-id-not-null" {
                 description "Terminated-id with default mapping to 15";
               }
               enum "tunnel-receive-recovery-stopccn-avp-bad-hidden" {
                 description "Terminated-id with default mapping to 15";
               }
               enum "tunnel-receive-recovery-stopccn-avp-bad-value-assigned-tunnel-id" {
                 description "Terminated-id with default mapping to 15";
               }
               enum "tunnel-receive-recovery-stopccn-avp-duplicate-value-assigned-tunnel-id" {
                 description "Terminated-id with default mapping to 15";
               }
               enum "tunnel-receive-recovery-stopccn-avp-malformed-bad-length" {
                 description "Terminated-id with default mapping to 15";
               }
               enum "tunnel-receive-recovery-stopccn-avp-malformed-truncated" {
                 description "Terminated-id with default mapping to 15";
               }
               enum "tunnel-receive-recovery-stopccn-avp-missing-mandatory-assigned-tunnel-id" {
                 description "Terminated-id with default mapping to 15";
               }
               enum "tunnel-receive-recovery-stopccn-avp-missing-mandatory-result-code" {
                 description "Terminated-id with default mapping to 15";
               }
               enum "tunnel-receive-recovery-stopccn-avp-missing-random-vector" {
                 description "Terminated-id with default mapping to 15";
               }
               enum "tunnel-receive-recovery-stopccn-avp-missing-secret" {
                 description "Terminated-id with default mapping to 15";
               }
               enum "tunnel-receive-recovery-stopccn-avp-unknown" {
                 description "Terminated-id with default mapping to 15";
               }
               enum "tunnel-receive-recovery-stopccn-no-resources" {
                 description "Terminated-id with default mapping to 15";
               }
               enum "tunnel-receive-recovery-stopccn-session-id-not-null" {
                 description "Terminated-id with default mapping to 15";
               }
               enum "tunnel-receive-recovery-unexpected-packet" {
                 description "Terminated-id with default mapping to 15";
               }
               enum "tunnel-receive-recovery-unknown-packet-message-type-indecipherable" {
                 description "Terminated-id with default mapping to 15";
               }
               enum "tunnel-receive-recovery-unknown-packet-message-type-unrecognized" {
                 description "Terminated-id with default mapping to 15";
               }
               enum "tunnel-receive-scccn-authenticate-failed-challenge" {
                 description "Terminated-id with default mapping to 17";
               }
               enum "tunnel-receive-scccn-avp-bad-hidden" {
                 description "Terminated-id with default mapping to 15";
               }
               enum "tunnel-receive-scccn-avp-bad-value-challenge-response" {
                 description "Terminated-id with default mapping to 15";
               }
               enum "tunnel-receive-scccn-avp-malformed-bad-length" {
                 description "Terminated-id with default mapping to 15";
               }
               enum "tunnel-receive-scccn-avp-malformed-truncated" {
                 description "Terminated-id with default mapping to 15";
               }
               enum "tunnel-receive-scccn-avp-missing-challenge-response" {
                 description "Terminated-id with default mapping to 17";
               }
               enum "tunnel-receive-scccn-avp-missing-random-vector" {
                 description "Terminated-id with default mapping to 15";
               }
               enum "tunnel-receive-scccn-avp-missing-secret" {
                 description "Terminated-id with default mapping to 15";
               }
               enum "tunnel-receive-scccn-avp-unexpected-challenge-response" {
                 description "Terminated-id with default mapping to 15";
               }
               enum "tunnel-receive-scccn-avp-unknown" {
                 description "Terminated-id with default mapping to 15";
               }
               enum "tunnel-receive-scccn-no-resources" {
                 description "Terminated-id with default mapping to 15";
               }
               enum "tunnel-receive-scccn-session-id-not-null" {
                 description "Terminated-id with default mapping to 15";
               }
               enum "tunnel-receive-scccn-unexpected" {
                 description "Terminated-id with default mapping to 15";
               }
               enum "tunnel-receive-sccrp-authenticate-failed-challenge" {
                 description "Terminated-id with default mapping to 17";
               }
               enum "tunnel-receive-sccrp-authenticate-failed-host" {
                 description "Terminated-id with default mapping to 17";
               }
               enum "tunnel-receive-sccrp-avp-bad-hidden" {
                 description "Terminated-id with default mapping to 15";
               }
               enum "tunnel-receive-sccrp-avp-bad-value-assigned-tunnel-id" {
                 description "Terminated-id with default mapping to 15";
               }
               enum "tunnel-receive-sccrp-avp-bad-value-bearer-capabilities" {
                 description "Terminated-id with default mapping to 15";
               }
               enum "tunnel-receive-sccrp-avp-bad-value-challenge" {
                 description "Terminated-id with default mapping to 15";
               }
               enum "tunnel-receive-sccrp-avp-bad-value-challenge-response" {
                 description "Terminated-id with default mapping to 15";
               }
               enum "tunnel-receive-sccrp-avp-bad-value-failover-capability" {
                 description "Terminated-id with default mapping to 15";
               }
               enum "tunnel-receive-sccrp-avp-bad-value-framing-capabilities" {
                 description "Terminated-id with default mapping to 15";
               }
               enum "tunnel-receive-sccrp-avp-bad-value-protocol-version" {
                 description "Terminated-id with default mapping to 15";
               }
               enum "tunnel-receive-sccrp-avp-bad-value-receive-window-size" {
                 description "Terminated-id with default mapping to 15";
               }
               enum "tunnel-receive-sccrp-avp-duplicate-value-assigned-tunnel-id" {
                 description "Terminated-id with default mapping to 15";
               }
               enum "tunnel-receive-sccrp-avp-malformed-bad-length" {
                 description "Terminated-id with default mapping to 15";
               }
               enum "tunnel-receive-sccrp-avp-malformed-truncated" {
                 description "Terminated-id with default mapping to 15";
               }
               enum "tunnel-receive-sccrp-avp-missing-challenge-response" {
                 description "Terminated-id with default mapping to 17";
               }
               enum "tunnel-receive-sccrp-avp-missing-mandatory-assigned-tunnel-id" {
                 description "Terminated-id with default mapping to 15";
               }
               enum "tunnel-receive-sccrp-avp-missing-mandatory-framing-capabilities" {
                 description "Terminated-id with default mapping to 15";
               }
               enum "tunnel-receive-sccrp-avp-missing-mandatory-host-name" {
                 description "Terminated-id with default mapping to 15";
               }
               enum "tunnel-receive-sccrp-avp-missing-mandatory-protocol-version" {
                 description "Terminated-id with default mapping to 15";
               }
               enum "tunnel-receive-sccrp-avp-missing-random-vector" {
                 description "Terminated-id with default mapping to 15";
               }
               enum "tunnel-receive-sccrp-avp-missing-secret" {
                 description "Terminated-id with default mapping to 15";
               }
               enum "tunnel-receive-sccrp-avp-unexpected-challenge-response" {
                 description "Terminated-id with default mapping to 15";
               }
               enum "tunnel-receive-sccrp-avp-unexpected-challenge-without-secret" {
                 description "Terminated-id with default mapping to 15";
               }
               enum "tunnel-receive-sccrp-avp-unknown" {
                 description "Terminated-id with default mapping to 15";
               }
               enum "tunnel-receive-sccrp-no-resources" {
                 description "Terminated-id with default mapping to 15";
               }
               enum "tunnel-receive-sccrp-session-id-not-null" {
                 description "Terminated-id with default mapping to 15";
               }
               enum "tunnel-receive-sccrp-unexpected" {
                 description "Terminated-id with default mapping to 15";
               }
               enum "tunnel-receive-sccrq-administrative-close" {
                 description "Terminated-id with default mapping to 6";
               }
               enum "tunnel-receive-sccrq-authenticate-failed-host" {
                 description "Terminated-id with default mapping to 17";
               }
               enum "tunnel-receive-sccrq-avp-bad-hidden" {
                 description "Terminated-id with default mapping to 15";
               }
               enum "tunnel-receive-sccrq-avp-bad-value-assigned-tunnel-id" {
                 description "Terminated-id with default mapping to 15";
               }
               enum "tunnel-receive-sccrq-avp-bad-value-bearer-capabilities" {
                 description "Terminated-id with default mapping to 15";
               }
               enum "tunnel-receive-sccrq-avp-bad-value-challenge" {
                 description "Terminated-id with default mapping to 15";
               }
               enum "tunnel-receive-sccrq-avp-bad-value-failover-capability" {
                 description "Terminated-id with default mapping to 15";
               }
               enum "tunnel-receive-sccrq-avp-bad-value-framing-capabilities" {
                 description "Terminated-id with default mapping to 15";
               }
               enum "tunnel-receive-sccrq-avp-bad-value-protocol-version" {
                 description "Terminated-id with default mapping to 15";
               }
               enum "tunnel-receive-sccrq-avp-bad-value-receive-window-size" {
                 description "Terminated-id with default mapping to 15";
               }
               enum "tunnel-receive-sccrq-avp-duplicate-value-assigned-tunnel-id" {
                 description "Terminated-id with default mapping to 15";
               }
               enum "tunnel-receive-sccrq-avp-malformed-bad-length" {
                 description "Terminated-id with default mapping to 15";
               }
               enum "tunnel-receive-sccrq-avp-malformed-truncated" {
                 description "Terminated-id with default mapping to 15";
               }
               enum "tunnel-receive-sccrq-avp-missing-mandatory-assigned-tunnel-id" {
                 description "Terminated-id with default mapping to 15";
               }
               enum "tunnel-receive-sccrq-avp-missing-mandatory-framing-capabilities" {
                 description "Terminated-id with default mapping to 15";
               }
               enum "tunnel-receive-sccrq-avp-missing-mandatory-host-name" {
                 description "Terminated-id with default mapping to 15";
               }
               enum "tunnel-receive-sccrq-avp-missing-mandatory-protocol-version" {
                 description "Terminated-id with default mapping to 15";
               }
               enum "tunnel-receive-sccrq-avp-missing-random-vector" {
                 description "Terminated-id with default mapping to 15";
               }
               enum "tunnel-receive-sccrq-avp-missing-secret" {
                 description "Terminated-id with default mapping to 15";
               }
               enum "tunnel-receive-sccrq-avp-unexpected-challenge-without-secret" {
                 description "Terminated-id with default mapping to 15";
               }
               enum "tunnel-receive-sccrq-avp-unknown" {
                 description "Terminated-id with default mapping to 15";
               }
               enum "tunnel-receive-sccrq-bad-address" {
                 description "Terminated-id with default mapping to 15";
               }
               enum "tunnel-receive-sccrq-invalid-ns" {
                 description "Terminated-id with default mapping to 10";
               }
               enum "tunnel-receive-sccrq-no-resources" {
                 description "Terminated-id with default mapping to 15";
               }
               enum "tunnel-receive-sccrq-no-resources-max-tunnels" {
                 description "Terminated-id with default mapping to 15";
               }
               enum "tunnel-receive-sccrq-session-id-not-null" {
                 description "Terminated-id with default mapping to 15";
               }
               enum "tunnel-receive-sccrq-unexpected" {
                 description "Terminated-id with default mapping to 15";
               }
               enum "tunnel-receive-session-packet-null-session-id-invalid" {
                 description "Terminated-id with default mapping to 15";
               }
               enum "tunnel-receive-session-packet-null-session-id-without-assigned-session-id" {
                 description "Terminated-id with default mapping to 15";
               }
               enum "tunnel-receive-stopccn" {
                 description "Terminated-id with default mapping to 1";
               }
               enum "tunnel-receive-stopccn-avp-bad-hidden" {
                 description "Terminated-id with default mapping to 15";
               }
               enum "tunnel-receive-stopccn-avp-bad-value-assigned-tunnel-id" {
                 description "Terminated-id with default mapping to 15";
               }
               enum "tunnel-receive-stopccn-avp-duplicate-value-assigned-tunnel-id" {
                 description "Terminated-id with default mapping to 15";
               }
               enum "tunnel-receive-stopccn-avp-malformed-bad-length" {
                 description "Terminated-id with default mapping to 15";
               }
               enum "tunnel-receive-stopccn-avp-malformed-truncated" {
                 description "Terminated-id with default mapping to 15";
               }
               enum "tunnel-receive-stopccn-avp-missing-mandatory-assigned-tunnel-id" {
                 description "Terminated-id with default mapping to 15";
               }
               enum "tunnel-receive-stopccn-avp-missing-mandatory-result-code" {
                 description "Terminated-id with default mapping to 15";
               }
               enum "tunnel-receive-stopccn-avp-missing-random-vector" {
                 description "Terminated-id with default mapping to 15";
               }
               enum "tunnel-receive-stopccn-avp-missing-secret" {
                 description "Terminated-id with default mapping to 15";
               }
               enum "tunnel-receive-stopccn-avp-unknown" {
                 description "Terminated-id with default mapping to 15";
               }
               enum "tunnel-receive-stopccn-no-resources" {
                 description "Terminated-id with default mapping to 15";
               }
               enum "tunnel-receive-stopccn-session-id-not-null" {
                 description "Terminated-id with default mapping to 15";
               }
               enum "tunnel-receive-unexpected-packet" {
                 description "Terminated-id with default mapping to 15";
               }
               enum "tunnel-receive-unexpected-packet-for-session" {
                 description "Terminated-id with default mapping to 15";
               }
               enum "tunnel-receive-unknown-packet-message-type-indecipherable" {
                 description "Terminated-id with default mapping to 15";
               }
               enum "tunnel-receive-unknown-packet-message-type-unrecognized" {
                 description "Terminated-id with default mapping to 15";
               }
               enum "tunnel-timeout-connection" {
                 description "Terminated-id with default mapping to 15";
               }
               enum "tunnel-timeout-connection-recovery-tunnel" {
                 description "Terminated-id with default mapping to 15";
               }
               enum "tunnel-timeout-idle" {
                 description "Terminated-id with default mapping to 1";
               }
               enum "tunnel-unknown-cause" {
                 description "Terminated-id with default mapping to 9";
               }
               enum "tunnel-warmstart-not-operational" {
                 description "Terminated-id with default mapping to 15";
               }
               enum "tunnel-warmstart-recovery-error" {
                 description "Terminated-id with default mapping to 15";
               }
             }
           }
         }
       }
     }
     output {
       choice output_c {
         case output-tag {
           leaf output {
             type string;
           }
         }
         case actual-tag {
           anyxml aaa-test-result;
         }
         case multichassis-tag {
           anyxml multi-routing-engine-results;
         }
       }
     }
   }
   rpc get-dhcp-user-aaa-test-result {
     description "Test the aaa servers for a dhcp user";
     input {
       leaf user {
         description "The username to test";
         type string;
         mandatory true;
       }
       leaf password {
         description "The password associated with username";
         type string;
       }
       leaf profile {
         description "Specify the access profile name which to use for user";
         type string;
       }
       leaf logical-system {
         description "Specify the logical-system in which to authenticate user";
         type string;
       }
       leaf routing-instance {
         description "Specify the routing-instance in which to authenticate user";
         type string;
       }
       leaf service-type {
         description "Service type ";
         type string;
       }
       leaf mac-address {
         description "Specify the Mac address of the DHCP client";
         type jt:mac-addr;
       }
       leaf option-82 {
         description "Specify the DHCP option 82";
         type string;
       }
       leaf agent-remote-id {
         description "DSL forum agent remote id ";
         type string {
           length "1 .. 63";
         }
       }
       leaf source-address {
         description "Use specified address as source address";
         type jt:ipv4addr;
       }
       leaf no-address-request {
         description "Request is for authentication without address-allocation";
         type empty;
       }
       leaf terminate-code {
         description "Specify DHCP terminate-code";
         type enumeration {
           enum "client-request" {
             description "Terminated-id with default mapping to 1";
           }
           enum "lost-carrier" {
             description "Terminated-id with default mapping to 2";
           }
           enum "nak" {
             description "Terminated-id with default mapping to 15";
           }
           enum "nas-logout" {
             description "Terminated-id with default mapping to 10";
           }
           enum "no-offers" {
             description "Terminated-id with default mapping to 4";
           }
         }
       }
     }
     output {
       choice output_c {
         case output-tag {
           leaf output {
             type string;
           }
         }
         case actual-tag {
           anyxml aaa-test-result;
         }
         case multichassis-tag {
           anyxml multi-routing-engine-results;
         }
       }
     }
   }
   rpc get-authdlite-user-aaa-test-result {
     description "Test the aaa servers for a authdlite user";
     input {
       leaf user {
         description "The username to test";
         type string;
         mandatory true;
       }
       leaf password {
         description "The password associated with username";
         type string;
       }
       leaf profile {
         description "Specify the access profile name which to use for user";
         type string;
       }
       leaf port {
         description "Specify NAS-port to be used for test";
         type string;
       }
       leaf zero-stats {
         description "Specify that acct stats should be set to zero";
         type empty;
       }
       leaf xauth {
         description "Emulate xauth client";
         type empty;
       }
     }
     output {
       choice output_c {
         case output-tag {
           leaf output {
             type string;
           }
         }
         case actual-tag {
           anyxml aaa-test-result;
         }
         case multichassis-tag {
           anyxml multi-routing-engine-results;
         }
       }
     }
   }
   rpc get-ocs-sftp-backup-test-result {
     description "Test aaa ocs sftp-backup";
     output {
       choice output_c {
         case output-tag {
           leaf output {
             type string;
           }
         }
         case actual-tag {
           anyxml ocs-sftp-backup-test-result;
         }
         case multichassis-tag {
           anyxml multi-routing-engine-results;
         }
       }
     }
   }
   rpc test-dot1x-sync-req {
     description "Send sync request to peer AD";
     input {
       leaf rg-id {
         description "Specify redundancy-group";
         type union {
           type uint32;
           type string {
             pattern "<.*>|$.*";
           }
         }
       }
     }
     output {
       choice output_c {
         case output-tag {
           leaf output {
             type string;
           }
         }
         case actual-tag {
           anyxml dot1x-sync-req;
         }
         case multichassis-tag {
           anyxml multi-routing-engine-results;
         }
       }
     }
   }
   rpc test-dot1x-sync-all {
     description "Send sync message containing all the authenticated entries";
     input {
       leaf rg-id {
         description "Specify redundancy-group";
         type union {
           type uint32;
           type string {
             pattern "<.*>|$.*";
           }
         }
       }
     }
     output {
       choice output_c {
         case output-tag {
           leaf output {
             type string;
           }
         }
         case actual-tag {
           anyxml dot1x-sync-all;
         }
         case multichassis-tag {
           anyxml multi-routing-engine-results;
         }
       }
     }
   }
   rpc test-dot1x-sync-mac {
     description "Simulate receiving sync message for particular session";
     input {
       leaf session {
         description "Session param ae-id, ifl-nm, mac, ch-id, user, filter-id, vlan, voip";
         type string;
       }
     }
     output {
       choice output_c {
         case output-tag {
           leaf output {
             type string;
           }
         }
         case actual-tag {
           anyxml dot1x-sync-mac;
         }
         case multichassis-tag {
           anyxml multi-routing-engine-results;
         }
       }
     }
   }
   rpc test-dot1x-del-sync-mac {
     input {
       leaf session {
         description "Session param ae-id, ifl-nm, mac";
         type string;
       }
     }
     output {
       choice output_c {
         case output-tag {
           leaf output {
             type string;
           }
         }
         case actual-tag {
           anyxml dot1x-del-sync-mac;
         }
         case multichassis-tag {
           anyxml multi-routing-engine-results;
         }
       }
     }
   }
   rpc none {
     description "Layer 2 forwarding commands";
     input {
       leaf in-memory-debug {
         description "Enable or disable in-memory tracing";
         type enumeration {
           enum "disable" {
             description "Disable in-memory tracing";
           }
           enum "enable" {
             description "Enable in-memory tracing";
           }
         }
       }
     }
     output {
       leaf output {
         type string;
       }
     }
   }
   rpc test-aaa-asm-ccr {
     description "Test commands to send CCR from diameter-asm";
     input {
       leaf msg-type {
         description "Specify CCR Message type";
         type enumeration {
           enum "ccri" {
             description "Trigger CCR-I message";
           }
           enum "ccru" {
             description "Trigger CCR-U message";
           }
           enum "ccrt" {
             description "Trigger CCR-T message";
           }
         }
         mandatory true;
       }
       leaf app-type {
         description "Specify Application type";
         type enumeration {
           enum "app-gx" {
             description "Trigger Gx message";
           }
           enum "app-gy" {
             description "Trigger Gy message";
           }
         }
         mandatory true;
       }
       leaf message-length {
         description "Specify message length";
         type enumeration {
           enum "short" {
             description "Short Gx message";
           }
           enum "long" {
             description "Long Gy message";
           }
         }
       }
       leaf te-id {
         description "TEID to be used in CCR";
         type union {
           type uint32;
           type string {
             pattern "<.*>|$.*";
           }
         }
         mandatory true;
       }
       leaf bearer-id {
         description "Bearer-id to be used in CCR";
         type union {
           type uint32;
           type string {
             pattern "<.*>|$.*";
           }
         }
         mandatory true;
       }
       leaf profile {
         description "Diameter application profile name";
         type string {
           length "1 .. 64";
         }
       }
       leaf count {
         description "Number of ccr messages, default is 1";
         type union {
           type uint32;
           type string {
             pattern "<.*>|$.*";
           }
         }
       }
       leaf rate {
         description "Number of ccr messages per 100msec, default is 100";
         type union {
           type uint32;
           type string {
             pattern "<.*>|$.*";
           }
         }
       }
     }
     output {
       leaf output {
         type string;
       }
     }
   }
   rpc get-radius-server-access-test-result {
     description "Test user access to a radius server";
     input {
       leaf address {
         description "RADIUS server address";
         type jt:ipv4addr;
         mandatory true;
       }
       leaf authentication-port {
         description "RADIUS server authentication port number";
         default "1812";
         type union {
           type string {
             pattern "<.*>|$.*";
           }
           type uint16 {
             range "1 .. 65535";
           }
         }
       }
       leaf secret {
         description "Shared secret with the RADIUS server";
         type string;
         mandatory true;
       }
       leaf user {
         description "User name to be authenticated to the RADIUS server";
         type string;
         mandatory true;
       }
       leaf password {
         description "Password for the user";
         type string;
         mandatory true;
       }
       leaf timeout {
         description "Request timeout period";
         default "3";
         units "seconds";
         type union {
           type string {
             pattern "<.*>|$.*";
           }
           type uint32 {
             range "1 .. 90";
           }
         }
       }
       leaf retry {
         description "Retry attempts";
         default "3";
         type union {
           type string {
             pattern "<.*>|$.*";
           }
           type uint32 {
             range "1 .. 10";
           }
         }
       }
       leaf source-address {
         description "Use specified address as source address";
         type jt:ipv4addr;
       }
     }
     output {
       choice output_c {
         case output-tag {
           leaf output {
             type string;
           }
         }
         case actual-tag {
           anyxml radius-access-server-test-result;
         }
         case multichassis-tag {
           anyxml multi-routing-engine-results;
         }
       }
     }
   }
   rpc get-radius-profile-access-test-result {
     description "Test user access to an access profile";
     input {
       leaf profile-name {
         description "Access profile name";
         type string;
         mandatory true;
       }
       leaf user {
         description "User name to be authenticated to the RADIUS server";
         type string;
         mandatory true;
       }
       leaf password {
         description "Password for the user";
         type string;
         mandatory true;
       }
       leaf get-radius-profile-access-test-detail-result {
         description "Show radius attributes returned by the server";
         type empty;
       }
     }
     output {
       choice output_c {
         case output-tag {
           leaf output {
             type string;
           }
         }
         case actual-tag {
           anyxml radius-profile-access-test-result;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
