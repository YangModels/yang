/*
 * Copyright (c) 2018 Juniper Networks, Inc.
 * All rights reserved.
 */
 module junos-nfx-conf-unified-edge {
   namespace "http://yang.juniper.net/junos-nfx/conf/unified-edge";

   prefix jc-unified-edge;

   import junos-common-ddl-extensions {
     prefix junos;
   }

   import junos-common-types {
     prefix jt;
   }

   import junos-nfx-conf-root {
     prefix jc;
   }

   organization "Juniper Networks, Inc.";

   contact "yang-support@juniper.net";

   description "Junos unified-edge configuration module";

   revision 2018-01-01 {
     description "Junos: 18.1R1.9";
   }

   augment /jc:configuration {
     uses unified-edge-group;
   }
   augment /jc:configuration/jc:groups {
     uses unified-edge-group;
   }
   grouping unified-edge-group {
   }
 }
