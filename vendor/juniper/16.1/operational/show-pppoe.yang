/*
 * Copyright (c) 2017 Juniper Networks, Inc.
 * All rights reserved.
 */

 module show-pppoe {
  namespace "http://yang.juniper.net/yang/1.1/jrpc";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc get-pppoe-interface-information {
     description "Show interface information";
     input {
       leaf level {
         type enumeration {
           enum "brief" {
             description "Show brief output";
           }
           enum "detail" {
             description "Show detailed output";
           }
           enum "extensive" {
             description "Show extensive output";
           }
         }
       }
       leaf interface-name {
         description "Name of PPPoE logical interface";
         type string;
       }
     }
     output {
       container pppoe-interface-information {
         container brief {
           container pppoe-interface {
             leaf interface-name {
               type string;
               description "Interface name";
             }
             leaf underlying-interface-name {
               type string;
               description "Underlying interface name";
             }
             leaf state {
               type string;
               description "State";
             }
             leaf session-id {
               type string;
               description "Session ID";
             }
             leaf remote-mac {
               type string;
               description "Remote MAC address";
             }
             leaf padg-credits {
               type int32;
               description "PADG transmit credits";
             }
           }
         }
         container detail {
           container pppoe-interface {
             leaf interface-name {
               type string;
               description "Interface name";
             }
             leaf interface-index {
               type string;
               description "Index";
             }
             leaf state {
               type string;
               description "State";
             }
             leaf session-id {
               type string;
               description "Session ID";
             }
             leaf ifl-type {
               type string;
               description "Type";
             }
             leaf service-name {
               type string;
               description "Service name";
             }
             leaf remote-mac {
               type string;
               description "Remote MAC address";
             }
             leaf ac-name-session {
               type string;
               description "Session AC name";
             }
             leaf ac-name-config {
               type string;
               description "Configured AC name";
             }
             leaf session-uptime {
               type string;
               description "Duration for which the session has been up";
             }
             leaf dynamic-profile {
               type string;
               description "Dynamic Profile name";
             }
             leaf auto-reconnect {
               type string;
               description "Autoreconnect timeout";
             }
             leaf idle-timeout {
               type string;
               description "Idle timeout";
             }
             leaf underlying-interface-name {
               type string;
               description "Underlying interface name";
             }
             leaf underlying-interface-index {
               type string;
               description "Underlying interface index";
             }
             leaf ignore-eol-tag {
               type string;
               description "Ignore End-of-List TAG";
             }
             leaf agent-circuit-id {
               type string;
               description "Agent Circuit ID";
             }
             leaf agent-remote-id {
               type string;
               description "Agent Remote ID";
             }
             leaf aci-iflset-name {
               type string;
               description "ACI Interface Set name";
             }
             leaf aci-iflset-index {
               type string;
               description "ACI Interface Set index";
             }
             leaf padm-motm {
               type string;
               description "PADM Message of the Moment tag";
             }
             leaf padm-hurl {
               type string;
               description "PADM HTTP URL tag";
             }
             leaf pppoe-credits {
               type string;
               description "Forwarding credit balances";
             }
             leaf pppoe-credit-scale-factor {
               type string;
               description "Scaling factor";
             }
             leaf dynamic-interface-bandwidth {
               type string;
               description "Dynamic interface bandwidth";
             }
             leaf padg-credits {
               type int32;
               description "PADG transmit credits";
             }
           }
         }
         container extensive {
           container pppoe-interface {
             leaf interface-name {
               type string;
               description "Interface name";
             }
             leaf interface-index {
               type string;
               description "Index";
             }
             leaf state {
               type string;
               description "State";
             }
             leaf session-id {
               type string;
               description "Session ID";
             }
             leaf ifl-type {
               type string;
               description "Type";
             }
             leaf service-name {
               type string;
               description "Service name";
             }
             leaf remote-mac {
               type string;
               description "Remote MAC address";
             }
             leaf ac-name-session {
               type string;
               description "Session AC name";
             }
             leaf ac-name-config {
               type string;
               description "Configured AC name";
             }
             leaf session-uptime {
               type string;
               description "Duration for which the session has been up";
             }
             leaf dynamic-profile {
               type string;
               description "Dynamic Profile name";
             }
             leaf auto-reconnect {
               type string;
               description "Autoreconnect timeout";
             }
             leaf idle-timeout {
               type string;
               description "Idle timeout";
             }
             leaf underlying-interface-name {
               type string;
               description "Underlying interface name";
             }
             leaf underlying-interface-index {
               type string;
               description "Underlying interface index";
             }
             leaf ignore-eol-tag {
               type string;
               description "Ignore End-of-List TAG";
             }
             leaf agent-circuit-id {
               type string;
               description "Agent Circuit ID";
             }
             leaf agent-remote-id {
               type string;
               description "Agent Remote ID";
             }
             leaf aci-iflset-name {
               type string;
               description "ACI Interface Set name";
             }
             leaf aci-iflset-index {
               type string;
               description "ACI Interface Set index";
             }
             leaf padm-motm {
               type string;
               description "PADM Message of the Moment tag";
             }
             leaf padm-hurl {
               type string;
               description "PADM HTTP URL tag";
             }
             leaf pppoe-credits {
               type string;
               description "Forwarding credit balances";
             }
             leaf pppoe-credit-scale-factor {
               type string;
               description "Scaling factor";
             }
             leaf dynamic-interface-bandwidth {
               type string;
               description "Dynamic interface bandwidth";
             }
             leaf padg-credits {
               type int32;
               description "PADG transmit credits";
             }
           }
         }
       }
     }
   }
   rpc get-pppoe-lockout-information {
     description "Show interface lockout information";
     input {
       leaf underlying-interface-name {
         description "Name of PPPoE underlying logical interface";
         type string;
       }
     }
   }
   rpc get-pppoe-lockout-vlan-information {
     description "VLAN Identifier of PPPoE underlying logical interface";
     input {
       leaf device-name {
         description "Name of physical port or AE bundle";
         type interface-device;
         mandatory true;
       }
       leaf svlan-id {
         description "SVLAN tag";
         type uint16 {
           range "1 .. 4094";
         }
       }
       leaf vlan-id {
         description "VLAN tag";
         type uint16 {
           range "1 .. 4094";
         }
       }
     }
   }
   rpc get-pppoe-lockout-atm-information {
     description "ATM Identifier of PPPoE underlying logical interface";
     input {
       leaf device-name {
         description "Name of physical port or AE bundle";
         type interface-device;
         mandatory true;
       }
       leaf vpi {
         description "ATM VPI";
         type uint16 {
           range "0 .. 255";
         }
         mandatory true;
       }
       leaf vci {
         description "ATM VCI";
         type uint16 {
           range "0 .. 65535";
         }
         mandatory true;
       }
     }
   }
   rpc get-pppoe-service-name-table-information {
     description "Show service name table information";
     input {
       leaf table-name {
         description "Name of PPPoE service name table";
         type string;
       }
     }
     output {
       container pppoe-service-name-table-information {
         leaf service-name-table {
           type string;
           description "Name of Service Name Table";
         }
         container pppoe-service-name {
           leaf service-name {
             type string;
             description "Service name";
           }
           leaf service-action {
             type string;
             description "Service action";
           }
           leaf dynamic-profile {
             type string;
             description "Dynamic Profile name";
           }
           leaf routing-instance {
             type string;
             description "Routing Instance name";
           }
           leaf max-sessions {
             type int32;
             description "Maximum number of PPPoE sessions";
           }
           leaf active-sessions {
             type int32;
             description "Number of active PPPoE sessions";
           }
           leaf max-sessions-exceeded-delay {
             type string;
             description "Max-sessions exceeded delay";
           }
           container pppoe-aci-ari-entry {
             leaf agent-circuit-id {
               type string;
               description "Agent Circuit ID";
             }
             leaf agent-remote-id {
               type string;
               description "Agent Remote ID";
             }
             leaf static-interface {
               type string;
               description "Static PPPoE Interface name";
             }
           }
         }
       }
     }
   }
   rpc get-pppoe-session-information {
     description "Show active PPPoE session information";
     input {
       leaf service {
         description "Name of PPPoE service";
         type string;
       }
       leaf aci {
         description "Agent Circuit ID";
         type string;
       }
       leaf ari {
         description "Agent Remote ID";
         type string;
       }
     }
   }
   rpc get-pppoe-statistics-information {
     description "Show PPPoE-related interface statistics";
     input {
       leaf underlying-interface-name {
         description "Name of PPPoE underlying logical interface";
         type string;
       }
     }
     output {
       container pppoe-statistics-information {
         container pppoe-statistics {
           leaf active-sessions {
             type int32;
             description "Number of active PPPoE sessions";
           }
           container pppoe-counters {
             leaf padi-sent {
               type int32;
               description "PADI sent counter";
             }
             leaf padi-received {
               type int32;
               description "PADI received counter";
             }
             leaf pado-sent {
               type int32;
               description "PADO sent counter";
             }
             leaf pado-received {
               type int32;
               description "PADO received counter";
             }
             leaf padr-sent {
               type int32;
               description "PADR sent counter";
             }
             leaf padr-received {
               type int32;
               description "PADR received counter";
             }
             leaf pads-sent {
               type int32;
               description "PADS sent counter";
             }
             leaf pads-received {
               type int32;
               description "PADS received counter";
             }
             leaf padt-sent {
               type int32;
               description "PADT sent counter";
             }
             leaf padt-received {
               type int32;
               description "PADT received counter";
             }
             leaf padm-sent {
               type int32;
               description "PADM sent counter";
             }
             leaf padm-received {
               type int32;
               description "PADM received counter";
             }
             leaf padn-sent {
               type int32;
               description "PADN sent counter";
             }
             leaf padn-received {
               type int32;
               description "PADN received counter";
             }
             leaf padg-sent {
               type int32;
               description "PADG sent counter";
             }
             leaf padg-received {
               type int32;
               description "PADG received counter";
             }
             leaf padc-sent {
               type int32;
               description "PADC sent counter";
             }
             leaf padc-received {
               type int32;
               description "PADC received counter";
             }
             leaf padq-sent {
               type int32;
               description "PADQ sent counter";
             }
             leaf padq-received {
               type int32;
               description "PADQ received counter";
             }
             leaf servname-err-sent {
               type int32;
               description "Service name error sent counter";
             }
             leaf servname-err-received {
               type int32;
               description "Service name error received counter";
             }
             leaf acsystem-err-sent {
               type int32;
               description "AC system error sent counter";
             }
             leaf acsystem-err-received {
               type int32;
               description "AC system error received counter";
             }
             leaf generic-err-sent {
               type int32;
               description "Generic error sent counter";
             }
             leaf generic-err-received {
               type int32;
               description "Generic error received counter";
             }
             leaf malformed-pkt-received {
               type int32;
               description "Malformed error received counter";
             }
             leaf unknown-pkt-received {
               type int32;
               description "Unknown packet received counter";
             }
             leaf padi-tmo {
               type int32;
               description "PADI timeout counter";
             }
             leaf pado-tmo {
               type int32;
               description "PADO timeout counter";
             }
             leaf padr-tmo {
               type int32;
               description "PADR timeout counter";
             }
             leaf padi-recv-err {
               type int32;
               description "PADI receive error counter";
             }
             leaf pado-recv-err {
               type int32;
               description "PADO receive error counter";
             }
             leaf padr-recv-err {
               type int32;
               description "PADR receive error counter";
             }
             leaf pads-recv-err {
               type int32;
               description "PADS receive error counter";
             }
           }
         }
       }
     }
   }
   rpc get-pppoe-interface-set-information {
     description "Show interface set information";
     input {
       leaf interface-set-name {
         description "Name of PPPoE interface set";
         type string;
       }
     }
     output {
       container pppoe-interface-set-information {
         container pppoe-interface-set {
           leaf interface-set-name {
             type string;
             description "Interface set name";
           }
           leaf interface-set-index {
             type string;
             description "Interface set index";
           }
           leaf state {
             type string;
             description "State";
           }
           leaf dynamic-profile {
             type string;
             description "Dynamic Profile name";
           }
           leaf max-sessions {
             type int32;
             description "Maximum number of PPPoE sessions";
           }
           leaf max-sessions-vsa-ignore {
             type string;
             description "Ignore max-sessions VSA";
           }
           leaf active-sessions {
             type int32;
             description "Number of active PPPoE sessions";
           }
           leaf agent-circuit-id {
             type string;
             description "Agent Circuit ID";
           }
           leaf agent-remote-id {
             type string;
             description "Agent Remote ID";
           }
         }
         container pppoe-interface-set-members {
           description "PPPoE interface-set member information";
           container pppoe-interface {
             leaf interface-name {
               type string;
               description "Interface name";
             }
             leaf interface-index {
               type string;
               description "Index";
             }
             leaf padg-credits {
               type int32;
               description "PADG transmit credits";
             }
           }
         }
       }
     }
   }
   rpc get-pppoe-underlying-interface-information {
     description "Show underlying interface information";
     input {
       leaf level {
         type enumeration {
           enum "brief" {
             description "Show brief output";
           }
           enum "detail" {
             description "Show detailed output";
           }
           enum "extensive" {
             description "Show extensive output";
           }
           enum "lockout" {
             description "Show lockout output";
           }
         }
       }
       leaf underlying-interface-name {
         description "Name of PPPoE underlying logical interface";
         type string;
       }
     }
     output {
       container pppoe-underlying-interface-information {
         container brief {
           container pppoe-underlying-interface {
             leaf underlying-interface-name {
               type string;
               description "Underlying interface name";
             }
             leaf service-name-table {
               type string;
               description "Name of Service Name Table";
             }
             leaf dynamic-profile {
               type string;
               description "Dynamic Profile name";
             }
           }
         }
         container detail {
           container pppoe-underlying-interface {
             leaf underlying-interface-name {
               type string;
               description "Underlying interface name";
             }
             leaf underlying-interface-index {
               type string;
               description "Underlying interface index";
             }
             leaf state {
               type string;
               description "State";
             }
             leaf dynamic-profile {
               type string;
               description "Dynamic Profile name";
             }
             leaf max-sessions {
               type int32;
               description "Maximum number of PPPoE sessions";
             }
             leaf max-sessions-vsa-ignore {
               type string;
               description "Ignore max-sessions VSA";
             }
             leaf active-sessions {
               type int32;
               description "Number of active PPPoE sessions";
             }
             leaf ac-name {
               type string;
               description "Access Concentrator name";
             }
             leaf duplicate-protection {
               type string;
               description "Duplicate protection mode";
             }
             leaf short-cycle-protection {
               type string;
               description "Short cycle protection mode";
             }
             leaf aci-autosensing {
               type string;
               description "ACI VLAN Autosensing mode";
             }
             leaf service-name-table {
               type string;
               description "Name of Service Name Table";
             }
             leaf direct-connect {
               type string;
               description "Direct connect mode";
             }
           }
         }
         container extensive {
           container pppoe-underlying-interface {
             leaf underlying-interface-name {
               type string;
               description "Underlying interface name";
             }
             leaf underlying-interface-index {
               type string;
               description "Underlying interface index";
             }
             leaf state {
               type string;
               description "State";
             }
             leaf dynamic-profile {
               type string;
               description "Dynamic Profile name";
             }
             leaf max-sessions {
               type int32;
               description "Maximum number of PPPoE sessions";
             }
             leaf max-sessions-vsa-ignore {
               type string;
               description "Ignore max-sessions VSA";
             }
             leaf active-sessions {
               type int32;
               description "Number of active PPPoE sessions";
             }
             leaf ac-name {
               type string;
               description "Access Concentrator name";
             }
             leaf duplicate-protection {
               type string;
               description "Duplicate protection mode";
             }
             leaf short-cycle-protection {
               type string;
               description "Short cycle protection mode";
             }
             leaf aci-autosensing {
               type string;
               description "ACI VLAN Autosensing mode";
             }
             leaf service-name-table {
               type string;
               description "Name of Service Name Table";
             }
             leaf direct-connect {
               type string;
               description "Direct connect mode";
             }
           }
         }
         container lockout {
           container pppoe-underlying-interface {
             leaf underlying-interface-name {
               type string;
               description "Underlying interface name";
             }
             leaf underlying-interface-index {
               type string;
               description "Underlying interface index";
             }
             leaf encapsulation-type-identifier {
               type string;
               description "Encapsulation type identifier";
             }
             leaf short-cycle-protection {
               type string;
               description "Short cycle protection mode";
             }
           }
         }
       }
     }
   }
   rpc get-pppoe-version {
     description "Show version";
     output {
       container pppoe-version {
         leaf max-sessions {
           type int32;
           description "Maximum number of PPPoE sessions";
         }
         leaf padi-resend-tmo {
           type int32;
           description "PADI resend timeout";
         }
         leaf padr-resend-tmo {
           type int32;
           description "PADR resend timeout";
         }
         leaf max-resend-tmo {
           type int32;
           description "Maximum resend timeout";
         }
         leaf max-ac-tmo {
           type int32;
           description "Maximum configured AC timeout";
         }
       }
     }
   }
 }
